-- vim: ft=mib comments=\f\:\",\b\:\-\-,\:\-\-,\f\b\:- fo+=tcqlornw tw=72 nocin nosi sts=4 sw=4
-- =============================================================================
-- 
-- @(#) $RCSfile: OPENSS7-M2UA-ASP-MIB.mib,v $ $Name:  $($Revision: 0.9.2.8 $) $Date: 2009-01-10 17:22:26 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-10 17:22:26 $ by $Author: brian $
--
-- -----------------------------------------------------------------------------
--
-- $Log: OPENSS7-M2UA-ASP-MIB.mib,v $
-- Revision 0.9.2.8  2009-01-10 17:22:26  brian
-- - updated mibs
--
-- Revision 0.9.2.7  2008-12-27 10:01:50  brian
-- - updated mibs and stubs
--
-- Revision 0.9.2.6  2008-10-11 04:34:38  brian
-- - cleanup MIBs
--
-- Revision 0.9.2.5  2008-04-29 01:52:24  brian
-- - updated headers for release
--
-- Revision 0.9.2.4  2008-01-24 17:40:54  brian
-- - updated mibs
--
-- Revision 0.9.2.3  2007/12/15 20:19:11  brian
-- - updates
--
-- Revision 0.9.2.2  2007/10/15 01:14:26  brian
-- - updated MIBs
--
-- Revision 0.9.2.1  2007/09/29 14:31:32  brian
-- - added new mib files
--
-- =============================================================================

OPENSS7-M2UA-ASP-MIB DEFINITIONS ::= BEGIN

IMPORTS
    AdministrativeState, AvailabilityStatus, OperationalState, 
    ProceduralStatus, SimpleNameType, StandbyStatus, UsageState
	FROM OPENSS7-SMI-MIB
    SigtranOptions, RegistrationPolicy, AspIdPolicy, 
    AssociationPolicy, AspState, AsState, TrafficMode
	FROM OPENSS7-SIGTRAN-TC
    CommonLanguageName
	FROM OPENSS7-TC
    openss7Modules
	FROM OPENSS7-SMI
    OBJECT-GROUP, NOTIFICATION-GROUP, MODULE-COMPLIANCE
	FROM SNMPv2-CONF
    MODULE-IDENTITY, OBJECT-TYPE, Unsigned32
	FROM SNMPv2-SMI
    TEXTUAL-CONVENTION, RowStatus
	FROM SNMPv2-TC;

m2uaAspMIB MODULE-IDENTITY
    LAST-UPDATED
	"200709250000Z"
    ORGANIZATION
	"OpenSS7 Corporation"
    CONTACT-INFO
	"Brian Bidulock
	 OpenSS7 Corporation
	 1469 Jefferys Crescent
	 Edmonton, Alberta T6L 6T1
	 CANADA
	 Tel: +1 780 490 1141
	 Fax: +1 780 490 1241
	 Mob: +1 780 953 0557
	 E-Mail: bidulock@openss7.org"
    DESCRIPTION
	"MIB Module for SIGTRAN M2UA ASP management.
	 
	 Containment:
	 
	 Each Asp contains a number of Sg.  An Sg may be contained by 
	 zero or more Asps.  An Sg contained by an Asp is a signalling 
	 gateway that provides service to the As for that Asp.
	 
	 Each Sg contains a number of As.  The As contained by the Sg 
	 are application servers that are served by the Sg.
	 
	 Each As served by an Sg contains a number of If.  The If 
	 contained by the As are the interfaces associated with the As.
	 
	 Each Asp contains a number of Sg.  The Sg contained by the Asp 
	 are the Sgs that provide service to the Asp."
    REVISION "200709250000Z"
    DESCRIPTION
	"First release of this module."
    REVISION "200810100532Z"
    DESCRIPTION
	"Corrections to work with OpenSS7 MIB Browser."
    ::= { openss7Modules 221 }

-- Top-level structure of the MIB

m2uaAspNotifications	OBJECT IDENTIFIER ::= { m2uaAspMIB		 0 }
m2uaAspObjects		OBJECT IDENTIFIER ::= { m2uaAspMIB		 1 }
m2uaAspConformance	OBJECT IDENTIFIER ::= { m2uaAspMIB		 2 }

--
-- From STD 58: [To] achieve compatiblity with SNMPv1 traps, both when 
-- converting SMIv1 information modules to an dfrom this SMI, and in the 
-- procedures employed by multi-lingual systems and proxy forwarding 
-- applications, the next to last subidentifier must have the value 
-- zero.
--

m2uaAspTables		OBJECT IDENTIFIER ::= { m2uaAspObjects		 1 }
m2uaAspScalars		OBJECT IDENTIFIER ::= { m2uaAspObjects		 2 }
m2uaAspNotifs		OBJECT IDENTIFIER ::= { m2uaAspObjects		 3 }
m2uaAspOids		OBJECT IDENTIFIER ::= { m2uaAspObjects		 4 }

m2uaAspCompliances	OBJECT IDENTIFIER ::= { m2uaAspConformance	 1 }
m2uaAspGroups		OBJECT IDENTIFIER ::= { m2uaAspConformance	 2 }

m2uaAspAsp		OBJECT IDENTIFIER ::= { m2uaAspTables		 1 }
m2uaAspSg		OBJECT IDENTIFIER ::= { m2uaAspTables		 2 }
m2uaAspAspSg		OBJECT IDENTIFIER ::= { m2uaAspTables		 3 }
m2uaAspAs		OBJECT IDENTIFIER ::= { m2uaAspTables		 4 }
m2uaAspIf		OBJECT IDENTIFIER ::= { m2uaAspTables		 5 }
m2uaAspAsIf		OBJECT IDENTIFIER ::= { m2uaAspTables		 6 }
m2uaAspSgAs		OBJECT IDENTIFIER ::= { m2uaAspTables		 7 }
m2uaAspAspAs		OBJECT IDENTIFIER ::= { m2uaAspTables		 8 }
m2uaAspAspSgAs		OBJECT IDENTIFIER ::= { m2uaAspTables		 9 }

-- ====================================================================
--
-- 1.3.6.1.4.1.25951.1.221 m2uaAspMIB
-- |__(0) m2uaAspNotifications
-- |__(1) m2uaAspObjects
-- |  |__(1) m2uaAspTables
-- |  |  |__( 1) m2uaAspAsp
-- |  |  |  |__( 1) m2uaAspTable
-- |  |  |     |__( 1) m2uaAspEntry
-- |  |  |        |__( 1) m2uaAspId
-- |  |  |        |__( 2) m2uaAspAdministrativeState
-- |  |  |        |__( 3) m2uaAspOperationalState
-- |  |  |        |__( 4) m2uaAspProceduralStatus
-- |  |  |        |__( 5) m2uaAspUsageState
-- |  |  |        |__( 6) m2uaAspAspState
-- |  |  |        |__( 7) m2uaAspCapablities
-- |  |  |        |__( 8) m2uaAspRegistrationPolicy
-- |  |  |        |__( 9) m2uaAspName
-- |  |  |        |__(10) m2uaAspRowStatus
-- |  |  |
-- |  |  |__( 2) m2uaAspSg
-- |  |  |  |__( 1) m2uaSgTable
-- |  |  |     |__( 1) m2uaSgEntry
-- |  |  |        |__( 1) m2uaSgId
-- |  |  |        |__( 2) m2uaSgName
-- |  |  |        |__( 3) m2uaSgAdministrativeState
-- |  |  |        |__( 4) m2uaSgOperationalState
-- |  |  |        |__( 5) m2uaSgProceduralStatus
-- |  |  |        |__( 6) m2uaSgStandbyStatus
-- |  |  |        |__( 7) m2uaSgPrimarySg
-- |  |  |        |__( 8) m2uaSgAspState
-- |  |  |        |__( 9) m2uaSgUsageState
-- |  |  |        |__(10) m2uaSgVersion
-- |  |  |        |__(11) m2uaSgOptions
-- |  |  |        |__(12) m2uaSgRegistrationPolicy
-- |  |  |        |__(13) m2uaSgProtocolPayloadId
-- |  |  |        |__(14) m2uaSgIpPort
-- |  |  |        |__(15) m2uaSgPrimaryIpAddress
-- |  |  |        |__(16) m2uaSgMinOstreams
-- |  |  |        |__(17) m2uaSgMaxIstreams
-- |  |  |        |__(18) m2uaSgRowStatus
-- |  |  |
-- |  |  |__( 3) m2uaAspAspSg
-- |  |  |  |__( 1) m2uaAspSgTable
-- |  |  |     |__( 1) m2uaAspSgEntry
-- |  |  |        |__( 1) m2uaAspSgAdministrativeState
-- |  |  |        |__( 2) m2uaAspSgOperationalState
-- |  |  |        |__( 3) m2uaAspSgProceduralStatus
-- |  |  |        |__( 4) m2uaAspSgUsageState
-- |  |  |        |__( 5) m2uaAspSgOperationalState
-- |  |  |        |__( 6) m2uaAspSgAvailabilityStatus
-- |  |  |        |__( 7) m2uaAspSgAspState
-- |  |  |        |__( 8) m2uaAspSgAspIdPolicy
-- |  |  |        |__( 9) m2uaAspSgAspId
-- |  |  |        |__(10) m2uaAspSgAssociationPolicy
-- |  |  |        |__(11) m2uaAspSgIpPort
-- |  |  |        |__(12) m2uaAspSgPrimaryIpAddress
-- |  |  |        |__(13) m2uaAspSgRowStatus
-- |  |  |
-- |  |  |__( 4) m2uaAspAs
-- |  |  |  |__( 1) m2uaAsTable
-- |  |  |     |__( 1) m2uaAsEntry
-- |  |  |        |__( 1) m2uaAsId
-- |  |  |        |__( 2) m2uaAsName
-- |  |  |        |__( 3) m2uaAsTrafficMode
-- |  |  |        |__( 4) m2uaAsAdministrativeState
-- |  |  |        |__( 5) m2uaAsOperationalState
-- |  |  |        |__( 6) m2uaAsProceduralStatus
-- |  |  |        |__( 7) m2uaAsUsageState
-- |  |  |        |__( 8) m2uaAsAsState
-- |  |  |        |__( 9) m2uaAsRowStatus
-- |  |  |
-- |  |  |__( 5) m2uaAspIf
-- |  |  |  |__( 1) m2uaIfTable
-- |  |  |     |__( 1) m2uaIfEntry
-- |  |  |        |__( 1) m2uaIfId
-- |  |  |        |__( 2) m2uaIfAsIndex
-- |  |  |        |__( 3) m2uaIfIdentifier
-- |  |  |        |__( 4) m2uaIfName
-- |  |  |        |__( 5) m2uaIfRowStatus
-- |  |  |
-- |  |  |__( 6) m2uaAspAsIf
-- |  |  |  |__( 1) m2uaAsIfTable
-- |  |  |     |__( 1) m2uaAsIfEntry
-- |  |  |        |__( 1) 
-- |  |  |
-- |  |  |__( 7) m2uaAspSgAs
-- |  |  |  |__( 1) m2uaSgAsTable
-- |  |  |     |__( 1) m2uaSgAsEntry
-- |  |  |        |__( 1) m2uaSgAsOrdering
-- |  |  |        |__( 2) m2uaSgAsAdministrativeState
-- |  |  |        |__( 3) m2uaSgAsOperationalState
-- |  |  |        |__( 4) m2uaSgAsProceduralStatus
-- |  |  |        |__( 5) m2uaSgAsUsageState
-- |  |  |        |__( 6) m2uaSgAsOperationalState
-- |  |  |        |__( 7) m2uaSgAsAvailabilityStatus
-- |  |  |        |__( 8) m2uaSgAsStandbyStatus
-- |  |  |        |__( 9) m2uaSgAsPrimarySg
-- |  |  |        |__(10) m2uaSgAsAsState
-- |  |  |        |__(11) m2uaSgAsRowStatus
-- |  |  |
-- |  |  |__( 8) m2uaAspAspAs
-- |  |  |  |__( 1) m2uaAspAsTable
-- |  |  |     |__( 1) m2uaAspAsEntry
-- |  |  |        |__( 1) m2uaAspAsAdministrativeState
-- |  |  |        |__( 2) m2uaAspAsOperationalState
-- |  |  |        |__( 3) m2uaAspAsProceduralStatus
-- |  |  |        |__( 4) m2uaAspAsUsageState
-- |  |  |        |__( 5) m2uaAspAsAsState
-- |  |  |        |__( 6) m2uaAspAsRowStatus
-- |  |  |
-- |  |  |__( 9) m2uaAspAspSgAs
-- |  |     |__( 1) m2uaAspSgAsTable
-- |  |        |__( 1) m2uaAspSgAsEntry
-- |  |           |__( 1) m2uaAspSgAsAdministrativeState
-- |  |           |__( 2) m2uaAspSgAsOperationalState
-- |  |           |__( 3) m2uaAspSgAsProceduralStatus
-- |  |           |__( 4) m2uaAspSgAsUsageState
-- |  |           |__( 5) m2uaAspSgAsStandbyStatus
-- |  |           |__( 6) m2uaAspSgAsRowStatus
-- |  |
-- |  |__(2) m2uaAspScalars
-- |  |__(3) m2uaAspNotifs
-- |  |__(4) m2uaAspOids
-- |
-- |__(2) m2uaAspConformance
--    |__(1) m2uaAspCompliances
--    |__(2) m2uaAspGroups


-- ====================================================================

m2uaAspTable OBJECT-TYPE
    SYNTAX	SEQUENCE OF M2uaAspEntry
    MAX-ACCESS	not-accessible
    STATUS	current
    DESCRIPTION
	"m2uaAspAsp  The M2UA ASP table.
	 
	 Provides the ASP table.  The ASP table is a list of all of the 
	 ASPs known to this host.
	 
	 The ASP table provides a list of all of the ASPs known to this 
	 host."
    ::= { m2uaAspAsp 1 }

m2uaAspEntry OBJECT-TYPE
    SYNTAX	M2uaAspEntry
    MAX-ACCESS	not-accessible
    STATUS	current
    DESCRIPTION
	"This is an entry in the ASP table.  The index is provided by 
	 this table."
    INDEX	{
		    m2uaAspId
		}
    ::= { m2uaAspTable 1 }

M2uaAspEntry ::=
    SEQUENCE {
	m2uaAspId				SimpleNameType,
	m2uaAspAdministrativeState		AdministrativeState,
	m2uaAspOperationalState			OperationalState,
	m2uaAspProceduralStatus			ProceduralStatus,
	m2uaAspUsageState			UsageState,
	m2uaAspAspState				AspState,
	m2uaAspCapablities			SigtranOptions,
	m2uaAspRegistrationPolicy		RegistrationPolicy,
	m2uaAspName				CommonLanguageName,
	m2uaAspRowStatus			RowStatus
    }

m2uaAspId OBJECT-TYPE
    SYNTAX	SimpleNameType
    MAX-ACCESS	not-accessible
    STATUS	current
    DESCRIPTION
	"This is the index of the M2UA ASP table.  This is a shared 
	 index."
    ::= { m2uaAspEntry 1 }

m2uaAspAdministrativeState OBJECT-TYPE
    SYNTAX	AdministrativeState
    MAX-ACCESS	read-create
    STATUS	current
    DESCRIPTION
	"This is the overall administrative state of the ASP.  When 
	 locked(0) the ASP is disabled and no local AS will be served 
	 and no association to any SG is in place.  When unlocked(1), 
	 local AS will be able to use the ASP and it will form 
	 associations to remote SG.
	 
	  - locked(0): The resource is administratively prohibited from 
	    performing services for its users.
	 
	  - unlocked(1): The resource is administratively permitted to 
	    perform services for its users.  This is independent of its 
	    inherent operability.
	 
	  - shuttingDown(2): Use of the resource is administratively 
	    permitted to existing instances of use only.  While the 
	    system remains in the shutting down state, the manager may 
	    at any time cause the managed object to revert to the 
	    unlocked state.
	 
	 This is a convenience as the value could be determined by 
	 examining the administrative state of each of the ASP-SG 
	 relations; however, the agent must maintain this information 
	 for proper generation of alarms."
    REFERENCE
	"ITU-T Rec. X.721 (1992) | ISO/IEC 10165-2 : 1992, administrativeState.
	 ITU-T Rec. X.731 (1992) | ISO/IEC 10164-2 : 1993, Section 8.1.1.3."
    ::= { m2uaAspEntry 2 }

m2uaAspOperationalState OBJECT-TYPE
    SYNTAX	OperationalState
    MAX-ACCESS	read-only
    STATUS	current
    DESCRIPTION
	""
    REFERENCE
	""
    ::= { m2uaAspEntry 3 }

m2uaAspProceduralStatus OBJECT-TYPE
    SYNTAX	ProceduralStatus
    MAX-ACCESS	read-only
    STATUS	current
    DESCRIPTION
	"This is the overall procedural status of the ASP following the 
	 ProceduralStatus textual convention of the OPENSS7-TMN-TC 
	 module.  Procedural status is a set valued state and this is 
	 simply the intersection (logical OR) of the procedural status 
	 of the ASP for each SG that supports it.
	 
	  - intializationRequired(0): The resource requires 
	    initialization to be invoked by the manager before it can 
	    perform its normal functions, and this procedure has not 
	    been initiated.  The manager may be able to invoke such 
	    initialization through an action.  The terminating condition 
	    may also be present.  The operational state is disabled.
	 
	  - notInitialized(1): The resource requires initialization 
	    before it can perform its normal functions, and this 
	    procedure has not been initiated.  The resource initializes 
	    itself autonomously, but the operational state may be either 
	    disabled or enabled, depending upon the managed object class 
	    definition.
	 
	  - initializing(2): The resource requires initialization before 
	    it can perform its normal functions, and this procedure has 
	    been initiated but is not yet complete.  When this condition 
	    is present, the intitialization required condition is 
	    absent, since initialization has already begun.  The 
	    operational state may be disabled or enabled, depending upon 
	    the managed object class defintion.
	 
	  - reporting(3): not used.
	 
	  - terminating(4): The resource is in a termination phase.  If 
	    the resource does not reinitialize itself autonomously, the 
	    initialization required condition is also present and the 
	    operational state is disabled; otherwise, the operational 
	    state may be either disabled or enabled, depending upon the 
	    managed object class definition.
	 
	 This is a convenience as the value could be determined by 
	 examining the procedural status of each of the ASP-SG 
	 associations; however, the agent must maintain this information 
	 for proper generation of alarms.."
    REFERENCE
	"ITU-T Rec. X.721 (1992) | ISO/IEC 10165-2 : 1992, proceduralStatus.
	 ITU-T Rec. X.731 (1992) | ISO/IEC 10164-2 : 1993, Section 8.1.2.2."
    ::= { m2uaAspEntry 4 }

m2uaAspUsageState OBJECT-TYPE
    SYNTAX	UsageState
    MAX-ACCESS	read-only
    STATUS	current
    DESCRIPTION
	"This is the overall usage state of the ASP following the 
	 UsageState textual convention of the OPENSS7-TMN-TC module.  
	 When idle(0) none of the ASP-SG associations are active or busy 
	 (including the case where no ASP-SG associations have been 
	 provisioned).  When active(1), at least one of the ASP-SG 
	 relations are active and none are busy.  WHen busy(2), at least 
	 one of the ASP-SG relations are busy.
	 
	  - idle(0): The resource is not currently in use.
	 
	  - active(1): The resource is in used, and has sufficient spare 
	    operating capcity to provide for additional users 
	    simultaneously.
	 
	  - busy(2): The resource is in use, but it has no spare 
	    operating capacity to provide for additional users at this 
	    instant.
	 
	 This is a convenience in that the value could be determined by 
	 examining the usage state for each of the ASP-SG relations; 
	 however, the overall state is necessary to determine the 
	 severity of alarms."
    REFERENCE
	"ITU-T Rec. X.721 (1992) | ISO/IEC 10165-2 : 1992, usageState.
	 ITU-T Rec. X.731 (1992) | ISO/IEC 10164-2 : 1993, Section 8.1.1.2."
    ::= { m2uaAspEntry 5 }

m2uaAspAspState OBJECT-TYPE
    SYNTAX	AspState
    MAX-ACCESS	read-create
    STATUS	current
    DESCRIPTION
	"This is the overal ASP state of the ASP following the AspState 
	 textual convention of the OPENSS7-SIGTRAN-TC module.  The 
	 overall state is the most active state of the ASP-SG 
	 associations for this ASP.  If an ASP-SG relation is in the up 
	 state, then this state is up.  Otherwise, if there is an ASP-SG 
	 relation in the terminating state, then this state is 
	 terminating.  Otherwise, if there is an ASP-SG relation in the 
	 initializing state, then this state is initializing.  
	 Otherwise, this state is down.
	 
	 This is a convenience in that the value could be determined by 
	 examining the ASP state for each of the ASP-SG relations; 
	 however, the overall state is necessary to determin the 
	 severity of alarms."
    ::= { m2uaAspEntry 6 }

m2uaAspCapablities OBJECT-TYPE
    SYNTAX	SigtranOptions
    MAX-ACCESS	read-create
    STATUS	current
    DESCRIPTION
	"This provides the capabilities of the ASP using the 
	 SigtranOptions textual convention of the OPENSS7-SIGTRAN-TC 
	 module."
    ::= { m2uaAspEntry 7 }

m2uaAspRegistrationPolicy OBJECT-TYPE
    SYNTAX	RegistrationPolicy
    MAX-ACCESS	read-create
    STATUS	current
    DESCRIPTION
	"This provides the registration policy for the ASP and is 
	 intended on reflecting the registration policy of the ASP 
	 towards the local AS that it serves.  It is tempered by the 
	 registration policy of the particular SG that serves an ASP."
    DEFVAL	{ 0 } -- unknown(0)
    ::= { m2uaAspEntry 8 }

m2uaAspName OBJECT-TYPE
    SYNTAX	CommonLanguageName
    MAX-ACCESS	read-create
    STATUS	current
    DESCRIPTION
	"Provides an additional name for the ASP following the COMMON 
	 LANGUAGE procedures and the CommonLanguageName textual 
	 convention from the OPENSS7-TC module.  When unused (the 
	 default) this column contains a null string."
    ::= { m2uaAspEntry 9 }

m2uaAspRowStatus OBJECT-TYPE
    SYNTAX	RowStatus
    MAX-ACCESS	read-create
    STATUS	current
    DESCRIPTION
	"This is the mechnism by which management stations can add, 
	 modify and delete rows from this table."
    ::= { m2uaAspEntry 10 }


-- ====================================================================

m2uaSgTable OBJECT-TYPE
    SYNTAX	SEQUENCE OF M2uaSgEntry
    MAX-ACCESS	not-accessible
    STATUS	current
    DESCRIPTION
	"m2uaAspSg  The M2UA SG Table.
	 
	 Provides the SG table.  The SG table is a list of all the SGs 
	 known to this host.
	 
	 The SG table provides a list of all the SGs known to this host.  
	 The purpose of this table is to identify all of the remote SG 
	 that this host can contact and the information for contacting 
	 the SG.  It also contains the general options associated with 
	 the SG."
    ::= { m2uaAspSg 1 }

m2uaSgEntry OBJECT-TYPE
    SYNTAX	M2uaSgEntry
    MAX-ACCESS	not-accessible
    STATUS	current
    DESCRIPTION
	"This is an entry in the SG table.  The entry consists of known 
	 characteristics about the remote SG.  The index is provided by 
	 this table."
    INDEX	{
		    m2uaSgId
		}
    ::= { m2uaSgTable 1 }

M2uaSgEntry ::=
    SEQUENCE {
	m2uaSgId				SimpleNameType,
	m2uaSgName				CommonLanguageName,
	m2uaSgAdministrativeState		AdministrativeState,
	m2uaSgAdministrativeState		OperationalState,
	m2uaSgProceduralStatus			ProceduralStatus,
	m2uaSgStandbyStatus			StandbyStatus,
	m2uaSgPrimarySg				Unsigned32,
	m2uaSgAspState				AspState,
	m2uaSgUsageState			UsageState,
	m2uaSgVersion				INTEGER,
	m2uaSgOptions				SigtranOptions,
	m2uaSgRegistrationPolicy		RegistrationPolicy,
	m2uaSgProtocolPayloadId			INTEGER,
	m2uaSgIpPort				INTEGER,
	m2uaSgPrimaryIpAddress			IpAddress,
	m2uaSgMinOstreams			INTEGER,
	m2uaSgMaxIstreams			INTEGER,
	m2uaSgRowStatus				RowStatus
    }

m2uaSgId OBJECT-TYPE
    SYNTAX	SimpleNameType
    MAX-ACCESS	not-accessible
    STATUS	current
    DESCRIPTION
	"This is the index of an entry in the SG table.  It is shared 
	 with other tables.  This is a shared index."
    ::= { m2uaSgEntry 1 }

m2uaSgName OBJECT-TYPE
    SYNTAX	CommonLanguageName
    MAX-ACCESS	read-create
    STATUS	current
    DESCRIPTION
	"This is the name of the signalling gateway following COMMON 
	 LANGUAGE procedures and the CommonLanguageName text 
	 convention."
    ::= { m2uaSgEntry 2 }

m2uaSgAdministrativeState OBJECT-TYPE
    SYNTAX	AdministrativeState
    MAX-ACCESS	read-create
    STATUS	current
    DESCRIPTION
	"This is the adminstrative state of the SG following the 
	 AdministrativeState textual convention of the OPENSS7-TMN-TC 
	 module.  The administrative state can be locked(0) or 
	 unlocked(1).  When locked(0) no association exists between the 
	 local host and the remote SG.  When unlocked(1), associations 
	 can be formed to this SG.  When set to locked(0), associations 
	 that exist between this host and the remote SG will be 
	 dropped.
	 
	  - locked(0): The resource is administratively prohibited from 
	    performing services for its users.
	 
	  - unlocked(1): The resource is administratively permitted to 
	    perform services for its users.  This is independent of its 
	    inherent operability.
	 
	  - shuttingDown(2): Use of the resource is administratively 
	    permitted to existing instances of use only.  While the 
	    system remains in the shutting down state, the manager may 
	    at any time cause the managed object to revert to the 
	    unlocked state."
    REFERENCE
	"ITU-T Rec. X.721 (1992) | ISO/IEC 10165-2 : 1992, administrativeState.
	 ITU-T Rec. X.731 (1992) | ISO/IEC 10164-2 : 1993, Section 8.1.1.3."
    DEFVAL	{ 0 } -- locked(0)
    ::= { m2uaSgEntry 3 }

m2uaSgOperationalState OBJECT-TYPE
    SYNTAX	OperationalState
    MAX-ACCESS	read-only
    STATUS	current
    DESCRIPTION
	""
    REFERENCE
	""
    ::= { m2uaSgEntry 4 }

m2uaSgProceduralStatus OBJECT-TYPE
    SYNTAX	ProceduralStatus
    MAX-ACCESS	read-only
    STATUS	current
    DESCRIPTION
	"This is the procedural state of the SG following the 
	 ProceduralStatus textual convention of the OPENSS7-TMN-TC 
	 module.  The procedural state is set valued and represents the 
	 intersection (logical OR) of the procedural status of the 
	 ASP-SG relationships or associations to this SG.
	 
	  - intializationRequired(0): The resource requires 
	    initialization to be invoked by the manager before it can 
	    perform its normal functions, and this procedure has not 
	    been initiated.  The manager may be able to invoke such 
	    initialization through an action.  The terminating condition 
	    may also be present.  The operational state is disabled.
	 
	  - notInitialized(1): The resource requires initialization 
	    before it can perform its normal functions, and this 
	    procedure has not been initiated.  The resource initializes 
	    itself autonomously, but the operational state may be either 
	    disabled or enabled, depending upon the managed object class 
	    definition.
	 
	  - initializing(2): The resource requires initialization before 
	    it can perform its normal functions, and this procedure has 
	    been initiated but is not yet complete.  When this condition 
	    is present, the intitialization required condition is 
	    absent, since initialization has already begun.  The 
	    operational state may be disabled or enabled, depending upon 
	    the managed object class defintion.
	 
	  - reporting(3): not used.
	 
	  - terminating(4): The resource is in a termination phase.  If 
	    the resource does not reinitialize itself autonomously, the 
	    initialization required condition is also present and the 
	    operational state is disabled; otherwise, the operational 
	    state may be either disabled or enabled, depending upon the 
	    managed object class definition.
	
	 This is a convenience as this procedural state could be 
	 determined by examining the procedural states of the individual 
	 ASP-SG relations."
    REFERENCE
	"ITU-T Rec. X.721 (1992) | ISO/IEC 10165-2 : 1992, proceduralStatus.
	 ITU-T Rec. X.731 (1992) | ISO/IEC 10164-2 : 1993, Section 8.1.2.2."
    DEFVAL	{ 0 }
    ::= { m2uaSgEntry 5 }

m2uaSgStandbyStatus OBJECT-TYPE
    SYNTAX	StandbyStatus
    MAX-ACCESS	read-only
    STATUS	current
    DESCRIPTION
	""
    REFERENCE
	""
    ::= { m2uaSgEntry 6 }

m2uaSgPrimarySg OBJECT-TYPE
    SYNTAX	Unsigned32
    MAX-ACCESS	read-only
    STATUS	current
    DESCRIPTION
	""
    REFERENCE
	""
    ::= { m2uaSgEntry 7 }

m2uaSgAspState OBJECT-TYPE
    SYNTAX	AspState
    MAX-ACCESS	read-create
    STATUS	current
    DESCRIPTION
	"This provides the overall state of all ASPs for this SG using 
	 the AspState textual convention.  It represents the most active 
	 state of all of the ASPs.  When at least one ASP is in the up 
	 state, the state is up.  When no ASPs are in the up state but 
	 at least one ASP is in the terminating state, the state is 
	 terminating.  When no ASP is in those states, but at least one 
	 ASP is in the initializing state, the state is initializing, 
	 when no ASP is in any state other than down, the state is down.
	 
	 When set to the down state, all ASPs will execute the ASP Down 
	 procedure if they are not in the terminating or down state 
	 already.  When set to the up state, all ASPs will execute the 
	 ASP Up procedure if they are not in the intiializing or up 
	 state already.  Note that this does not affect the long term 
	 state of the ASPs, use the AdministrativeState textual 
	 convention for that purpose"
    DEFVAL	{ 0 } -- down(0)
    ::= { m2uaSgEntry 8 }

m2uaSgUsageState OBJECT-TYPE
    SYNTAX	UsageState
    MAX-ACCESS	read-only
    STATUS	current
    DESCRIPTION
	"This it the overall usage state of the SG following the 
	 UsageState textual convention of the OPENSS7-TMN-TC module.  
	 The usage state may be idle(0), active(1) or busy(2).  When 
	 idle(0), no ASP-SG relation is in the active(1) or busy(2) 
	 operational state.  When active(1), a least one ASP-SG relation 
	 is in the active(1) operational state and no ASP-SG relation is 
	 in the busy(2) operational state.  When busy(2), at least one 
	 ASP-SG relation is in the busy(2) operational state.
	 
	  - idle(0): The resource is not currently in use.
	 
	  - active(1): The resource is in used, and has sufficient spare 
	    operating capcity to provide for additional users 
	    simultaneously.
	 
	  - busy(2): The resource is in use, but it has no spare 
	    operating capacity to provide for additional users at this 
	    instant.
	 
	 This is a convenience as this operational state could be 
	 determined by examining the operational state of the individual 
	 ASP-SG relations."
    REFERENCE
	"ITU-T Rec. X.721 (1992) | ISO/IEC 10165-2 : 1992, usageState.
	 ITU-T Rec. X.731 (1992) | ISO/IEC 10164-2 : 1993, Section 8.1.1.2."
    DEFVAL	{ 0 } -- idle(0)
    ::= { m2uaSgEntry 9 }

m2uaSgVersion OBJECT-TYPE
    SYNTAX	INTEGER {
			    interoperable(0),
			    rfc3331(1),
			    ts102141(2)
		    }
    MAX-ACCESS	read-create
    STATUS	current
    DESCRIPTION
	"This provides the protocol version associated with the remote 
	 signalling gateway.  The version is either rfc3331(1) for RFC 
	 3331 standard behaviour, or ts102141(2) for ETSI TS 102 141 
	 behaviour, or interoperable(0) for interoperable behaviour that 
	 can accomodate both."
    REFERENCE
	"RFC 3331, ETSI TS 102 141"
    DEFVAL	{ 1 } -- rfc3331(1)
    ::= { m2uaSgEntry 10 }

m2uaSgOptions OBJECT-TYPE
    SYNTAX	SigtranOptions
    MAX-ACCESS	read-create
    STATUS	current
    DESCRIPTION
	"This represents the overall options associated with the remote 
	 SG and follows the SigtranOptions textual convention.  Options 
	 that are not pertinent to M2UA may be ignored.  If the SG 
	 supports ASPEXT, the agent will be able to update these options 
	 after an ASP Up procedure has been established with the SG."
    ::= { m2uaSgEntry 11 }

m2uaSgRegistrationPolicy OBJECT-TYPE
    SYNTAX	RegistrationPolicy
    MAX-ACCESS	read-create
    STATUS	current
    DESCRIPTION
	"The provide the registration policy of the SG following the 
	 RegistrationPolicy textual convention."
    DEFVAL	{ 0 } -- unknown(0)
    ::= { m2uaSgEntry 12 }

m2uaSgProtocolPayloadId OBJECT-TYPE
    SYNTAX	INTEGER (0|2)
    MAX-ACCESS	read-create
    STATUS	current
    DESCRIPTION
	"This column provides the SCTP Protocol Payload Identifier that 
	 will be used in packet sent on associations to this SG.  The 
	 default is the PID assigned to M2UA.  In accordance with RFC 
	 3331, the value must either be 0 or 2.  The default value is 2 
	 to assist with protocol analysis."
    DEFVAL	{ 2 }
    ::= { m2uaSgEntry 13 }

m2uaSgIpPort OBJECT-TYPE
    SYNTAX	INTEGER(1..65535)
    MAX-ACCESS	read-create
    STATUS	current
    DESCRIPTION
	"This column provides the IP port number at which to contact the 
	 SG.   The default is the well known port number for M2UA."
    DEFVAL	{ 2904 }
    ::= { m2uaSgEntry 14 }

m2uaSgPrimaryIpAddress OBJECT-TYPE
    SYNTAX	IpAddress
    MAX-ACCESS	read-create
    STATUS	current
    DESCRIPTION
	"This is the primary Ip address at which the SG may be 
	 contacted.  Secondary addresses may also be added in a side 
	 table."
    ::= { m2uaSgEntry 15 }

m2uaSgMinOstreams OBJECT-TYPE
    SYNTAX	INTEGER (2..16384)
    MAX-ACCESS	read-create
    STATUS	current
    DESCRIPTION
	"This is the minimum number of outbound streams that must be 
	 supported by the connection to the SG.  The minimum value is 2 
	 per RFC 3331.  A reasonable default is 32."
    DEFVAL	{ 32 }
    ::= { m2uaSgEntry 16 }

m2uaSgMaxIstreams OBJECT-TYPE
    SYNTAX	INTEGER (2..16384)
    MAX-ACCESS	read-create
    STATUS	current
    DESCRIPTION
	"This provides the maximum number of inbound streams that will 
	 be reported when forming a connection to the SG.  The minimum 
	 value to support RFC 3331 is 2.  The value of 32 is a more 
	 reasonable default."
    DEFVAL	{ 32 }
    ::= { m2uaSgEntry 17 }

-- TODO: other primary SCTP protocol parameters for the association 
-- needd to be included here.

m2uaSgRowStatus OBJECT-TYPE
    SYNTAX	RowStatus
    MAX-ACCESS	read-create
    STATUS	current
    DESCRIPTION
	"This provides the ability for a management station to add, 
	 delete and otherwise control the contianing row in the SG 
	 table.  read-create columns, with the exception of 
	 AdministrativeState cannot be changed while the row is in the 
	 active state.  RowStatus cannot be changed while the row is in 
	 the unlocked(1) administrative state."
    REFERENCE
	"STD 58"
    ::= { m2uaSgEntry 18 }


-- ====================================================================

m2uaAspSgTable OBJECT-TYPE
    SYNTAX	SEQUENCE OF M2uaAspSgEntry
    MAX-ACCESS	not-accessible
    STATUS	current
    DESCRIPTION
	"m2uaAspSg  The ASP-SG relation table.
	 
	 This provides the ASP-SG table.  Each entry in this table is a 
	 possible SCTP association between an ASP and the SG.
	 
	 The ASP-SG relation table lists all of the allowable 
	 connections between ASPs and SG and provides the ASP 
	 characeteristic of the association."
    ::= { m2uaAspAspSg 1 }

m2uaAspSgEntry OBJECT-TYPE
    SYNTAX	M2uaAspSgEntry
    MAX-ACCESS	not-accessible
    STATUS	current
    DESCRIPTION
	"This provides an entry in the ASP-SG table.  When combined with 
	 the informatoin in the ASP and SG tables, it provides all of 
	 the information necessary to form an association between the 
	 ASP and the SG.  The m2uaAspId and m2uaSgId indices are shared.  
	 The indices represent the relationship between the indexed ASP 
	 and SG."
    INDEX	{
		    m2uaAspId,
		    m2uaSgId
		}
    ::= { m2uaAspSgTable 1 }

M2uaAspSgEntry ::=
    SEQUENCE {
	m2uaAspSgAdministrativeState		AdministrativeState,
	m2uaAspSgOperationalState		OperationalState,
	m2uaAspSgProceduralStatus		ProceduralStatus,
	m2uaAspSgUsageState			UsageState,
	m2uaAspSgOperationalState		OperationalState,
	m2uaAspSgAvailabilityStatus		AvailabilityStatus,
	m2uaAspSgAspState			AspState,
	m2uaAspSgAspIdPolicy			AspIdPolicy,
	m2uaAspSgAspId				Unsigned32,
	m2uaAspSgAssociationPolicy		AssociationPolicy,
	m2uaAspSgIpPort				INTEGER,
	m2uaAspSgPrimaryIpAddress		IpAddress,
	m2uaAspSgRowStatus			RowStatus
    }

m2uaAspSgAdminstrativeState OBJECT-TYPE
    SYNTAX	AdministrativeState
    MAX-ACCESS	read-create
    STATUS	current
    DESCRIPTION
	"This provides the administrative state of the ASP-SG 
	 association, following the AdministrativeState textual 
	 convention.  The administrative state may be locked(0) or 
	 unlocked(1).  When locked(0) no association will exist between 
	 the ASP and the SG.  When unlocked(1), an association may be 
	 formed between the ASP and the SG.  When set to locked(0) from 
	 unlocked(1), any SCTP associoation that exists from this ASP to 
	 the SG will be dropped.
	 
	  - locked(0): The resource is administratively prohibited from 
	    performing services for its users.
	 
	  - unlocked(1): The resource is administratively permitted to 
	    perform services for its users.  This is independent of its 
	    inherent operability.
	 
	  - shuttingDown(2): Use of the resource is administratively 
	    permitted to existing instances of use only.  While the 
	    system remains in the shutting down state, the manager may 
	    at any time cause the managed object to revert to the 
	    unlocked state."
    REFERENCE
	"ITU-T Rec. X.721 (1992) | ISO/IEC 10165-2 : 1992, administrativeState.
	 ITU-T Rec. X.731 (1992) | ISO/IEC 10164-2 : 1993, Section 8.1.1.3."
    ::= { m2uaAspSgEntry 1 }

m2uaAspSgOperationalState OBJECT-TYPE
    SYNTAX	OperationalState
    MAX-ACCESS	read-only
    STATUS	current
    DESCRIPTION
	""
    REFERENCE
	""
    ::= { m2uaAspSgEntry 2 }

m2uaAspSgProceduralStatus OBJECT-TYPE
    SYNTAX	ProceduralStatus
    MAX-ACCESS	read-only
    STATUS	current
    DESCRIPTION
	"This provides the procedural status of the ASP-SG association, 
	 following the ProceduralStatus textual convention.  The 
	 procedural status is set valued and may contain 
	 initializationRequired(0), notInitialized(1), initializing(2), 
	 reporting(3), terminating(4).  When initializationRequired(0) 
	 is set, no bound local association instance (e.g. socket 
	 descriptor) exists for the SCTP association.  When 
	 notInitialized(1) is set, a bound descriptor exists for the 
	 SCTP association, but no connection attempt has been made on 
	 the descriptor.  When initializing(3) is set, the SCTP 
	 association is connecting.  When terminating(4) is set, the 
	 SCTP association is shutting down.  When no bits are set, the 
	 SCTP association is connected.
	 
	  - intializationRequired(0): The resource requires 
	    initialization to be invoked by the manager before it can 
	    perform its normal functions, and this procedure has not 
	    been initiated.  The manager may be able to invoke such 
	    initialization through an action.  The terminating condition 
	    may also be present.  The operational state is disabled.
	 
	  - notInitialized(1): The resource requires initialization 
	    before it can perform its normal functions, and this 
	    procedure has not been initiated.  The resource initializes 
	    itself autonomously, but the operational state may be either 
	    disabled or enabled, depending upon the managed object class 
	    definition.
	 
	  - initializing(2): The resource requires initialization before 
	    it can perform its normal functions, and this procedure has 
	    been initiated but is not yet complete.  When this condition 
	    is present, the intitialization required condition is 
	    absent, since initialization has already begun.  The 
	    operational state may be disabled or enabled, depending upon 
	    the managed object class defintion.
	 
	  - reporting(3): not used.
	 
	  - terminating(4): The resource is in a termination phase.  If 
	    the resource does not reinitialize itself autonomously, the 
	    initialization required condition is also present and the 
	    operational state is disabled; otherwise, the operational 
	    state may be either disabled or enabled, depending upon the 
	    managed object class definition."
    REFERENCE
	"ITU-T Rec. X.721 (1992) | ISO/IEC 10165-2 : 1992, proceduralStatus.
	 ITU-T Rec. X.731 (1992) | ISO/IEC 10164-2 : 1993, Section 8.1.2.2."
    ::= { m2uaAspSgEntry 3 }

m2uaAspSgUsageState OBJECT-TYPE
    SYNTAX	UsageState
    MAX-ACCESS	read-only
    STATUS	current
    DESCRIPTION
	"This provides the usage state of the ASP-SG association, 
	 following the UsageState textual convention.  The usage state 
	 is on of idle(0), active(1) or busy(2).  When idle(0), the SCTP 
	 association is unable to carry user traffic, when active(1) it 
	 is able to carry user traffic, when busy(2) it is congested 
	 with user traffic.
	 
	  - idle(0): The resource is not currently in use.
	 
	  - active(1): The resource is in used, and has sufficient spare 
	    operating capcity to provide for additional users 
	    simultaneously.
	 
	  - busy(2): The resource is in use, but it has no spare 
	    operating capacity to provide for additional users at this 
	    instant."
    REFERENCE
	"ITU-T Rec. X.721 (1992) | ISO/IEC 10165-2 : 1992, usageState.
	 ITU-T Rec. X.731 (1992) | ISO/IEC 10164-2 : 1993, Section 8.1.1.2."
    ::= { m2uaAspSgEntry 4 }

m2uaAspSgOperationalState OBJECT-TYPE
    SYNTAX	OperationalState
    MAX-ACCESS	read-only
    STATUS	current
    DESCRIPTION
	"
	  - disabled(0), the resource is totally inoperable and unable 
	    to provide service to the user(s);
	 
	  - enabled(1), the resource is partially or fully operable and 
	    available for use.
	"
    REFERENCE
	"ITU-T Rec. X.721 (1992) | ISO/IEC 10165-2 : 1992, operationalState.
	 ITU-T Rec. X.731 (1992) | ISO/IEC 10164-2 : 1993, Section 8.1.1.1."
    ::= { m2uaAspSgEntry 5 }

m2uaAspSgAvailabilityStatus OBJECT-TYPE
    SYNTAX	AvailabilityStatus
    MAX-ACCESS	read-only
    STATUS	current
    DESCRIPTION
	"Provides the availability status of the ASP-SG relation 
	 following the availability status textual convention of the 
	 OPENSS7-SMI-MIB in accordance with X.721 (1992) | ISO/IEC 
	 10165-2.  This is a set-valued object that may contain zero or 
	 more of the following values:
	 
	  - inTest(0), The resource is undergoing a test procedure.  If 
	    the administrative state is locked or shutting down then 
	    normal users are precluded from using the resource and the 
	    control status attribute has the value reserved for test.  
	    Tests that do not exclude additional users can be present in 
	    any operational or administrative state but the reserved for 
	    test condition should not be present.
	 
	  - failed(1), The resource has an internal fault that prevents 
	    it from operating.  The operational state is disabled.
	 
	  - powerOff(2), The resource requires power to be applied and 
	    is not powered on.  For example, a fuse or other protection 
	    device is known to have removed power or a low voltage 
	    condition has been detected.  The operational state is 
	    disabled.
	 
	  - offLine(3), The resource requires a routing operation to be 
	    performed to place it online and make it available for use.  
	    The operation may be manual or automatic, or both.  The 
	    operational state is disabled.
	 
	  - offDuty(4), The resource has been made inactive by an 
	    internal control process in accordance with a predetermined 
	    time schedule.  Under normal conditions the control process 
	    can be expected to reactivate the resource at some scheduled 
	    time, and it is therefore considered to be optional.  The 
	    operational state is enabled or disabled.
	 
	  - dependency(5), The resource cannot operate because some 
	    other resource on which it depends is (i.e, a resource not 
	    represented by the same managed object) unavailable.  For 
	    example, a device is not accessible because its controller 
	    is powered off.  The operational state is disabled.
	 
	  - degraded(6), The service available from the resource is 
	    degraded in some respect, such as in speed or operating 
	    capacity.  Failure of a test or an unacceptable performance 
	    measurement has established that some or all services are 
	    not functional or are degraded due to presence of a defect.  
	    However, the resource remains available for service, either 
	    because some services are satisfactory or because degraded 
	    service is preferable to no service at all.  Object specific 
	    attributes may be deinfed to represent further information 
	    indicating, for example, which serivces are not functional 
	    and the nature of the degradation.  The operational state is 
	    enabled.
	 
	  - notInstalled(7), The resource represented by the managed 
	    object is not present, or is incomplete.  For example, a 
	    plug-in module is missing, a cable is disconnected or a 
	    software module is not loaded.  The operational state is 
	    disabled.
	 
	  - logFull(8), This indicates a log full condition the 
	    semantics of which are defined in ITU-T Rec. X.735.
	"
    REFERENCE
	"ITU-T Rec. X.721 (1992) | ISO/IEC 10165-2 : 1992, availabilityStatus
	 ITU-T Rec. X.731 (1992) | ISO/IEC 10164-2 : 1993, Section 8.1.2.3."
    ::= { m2uaAspSgEntry 6 }


m2uaAspSgAspState OBJECT-TYPE
    SYNTAX	AspState
    MAX-ACCESS	read-create
    STATUS	current
    DESCRIPTION
	"This provides the ASP state for the ASP for the ASP-SG 
	 asscociation following the AspState textual convention.  When 
	 down, the ASP is in the ASP-DOWN state for the association or 
	 the association does not exist.  When initializing, the ASP is 
	 performing the ASP Up procedure.  When terminating, the ASP is 
	 performing the ASP Down procedure.  When up, the ASP is in the 
	 ASP-UP state.
	 
	 When the management station sets this column to down from the 
	 up state, the ASP will execute the ASP Down procedure (but the 
	 association will not be dropped).  When set to up from the 
	 downs state, the ASP will execute the ASP Up procedure.  Be 
	 forewarned that the ASP will attempt to return itself to the 
	 previous state.  For a stable administrative control, use the 
	 AdministrativeState column."
    REFERENCE
	"RFC 3331"
    ::= { m2uaAspSgEntry 7 }


m2uaAspSgAspIdPolicy OBJECT-TYPE
    SYNTAX	AspIdPolicy
    MAX-ACCESS	read-create
    STATUS	current
    DESCRIPTION
	"This column provides an ASP Identifier policy to use with the 
	 SG when connecting from this ASP according to the AspIdPolicy 
	 textual convention.  The value can be permitted(0), 
	 forbidden(1) or required(2)."
    REFERENCE
	"RFC 3331 3.3.2.1"
    ::= { m2uaAspSgEntry 8 }

m2uaAspSgAspId OBJECT-TYPE
    SYNTAX	Unsigned32
    MAX-ACCESS	read-create
    STATUS	current
    DESCRIPTION
	"This provides the ASP Identifier to be provided to the SG on 
	 the ASP Up which identifies this ASP to the SG, depending on 
	 the value of m2uaAspSgAspIdPolicy."
    REFERENCE
	"RFC 3331 3.3.2.1"
    DEFVAL	{ 0 }
    ::= { m2uaAspSgEntry 9 }

m2uaAspSgAssociationPolicy OBJECT-TYPE
    SYNTAX	AssociationPolicy
    MAX-ACCESS	read-create
    STATUS	current
    DESCRIPTION
	"This provides the assocation policy for this SCTP association 
	 using the AssociationPolicy textual convention.  The policy can 
	 be unknown, in which case the formation and cessation of SCTP 
	 associations is left to the implementation; always, the SCTP 
	 associations are formed and released under management control; 
	 ondemand(2), associations are formed when local AS require 
	 service and are released when there is no local AS requiring 
	 service; and other(3) some other implementation defined 
	 mechanism."
    DEFVAL	{ 0 } -- unknown(0)
    ::= { m2uaAspSgEntry 10 }

m2uaAspSgIpPort OBJECT-TYPE
    SYNTAX	INTEGER(1..65535)
    MAX-ACCESS	read-create
    STATUS	current
    DESCRIPTION
	"This provides the port number from which the ASP will connect 
	 to the SG.  This is for when the SG requires that the ASP 
	 identify itself will full transport endpoint address.  When set 
	 to the reserved value of zero(0), it indicates that the ASP may 
	 use any port number to connect to the SG."
    REFERENCE
	"RFC 3331 3.3.2.1"
    DEFVAL	{ 0 }
    ::= { m2uaAspSgEntry 11 }

m2uaAspSgPrimaryIpAddress OBJECT-TYPE
    SYNTAX	IpAddress
    MAX-ACCESS	read-create
    STATUS	current
    DESCRIPTION
	"This provides the primary IP address from which the ASP will 
	 connect.  This is for the case where the host is multihomed and 
	 yet must connect from a specific IP address for the SG to 
	 identify it.  The default value is the zero address indicating 
	 that any Ip address may be used to connect."
    ::= { m2uaAspSgEntry 12 }

m2uaAspSgRowStatus OBJECT-TYPE
    SYNTAX	RowStatus
    MAX-ACCESS	read-create
    STATUS	current
    DESCRIPTION
	"This is the status used by management stations to create, 
	 modify or delete a row.  Altering ASPId, IpPort and IpAddress 
	 on a row in the active state will have no effect upon an 
	 existing association."
    ::= { m2uaAspSgEntry 13 }


-- ====================================================================

m2uaAsTable OBJECT-TYPE
    SYNTAX	SEQUENCE OF M2uaAsEntry
    MAX-ACCESS	not-accessible
    STATUS	current
    DESCRIPTION
	"m2uaAs  The AS table.
	 
	 This provides the AS table.  The AS table is a list of all of 
	 the application servers known to this host.
	 
	 The AS table provides a list of all application servers know to 
	 this host."
    ::= { m2uaAspAs 1 }

m2uaAsEntry OBJECT-TYPE
    SYNTAX	M2uaAsEntry
    MAX-ACCESS	not-accessible
    STATUS	current
    DESCRIPTION
	"This is an entry in the AS table.  The index is provided by 
	 this table."
    INDEX	{
		    m2uaAsId
		}
    ::= { m2uaAsTable 1 }

M2uaAsEntry ::=
    SEQUENCE {
	m2uaAsId				SimpleNameType,
	m2uaAsName				CommonLanguageName,
	m2uaAsTrafficMode			TrafficMode,
	m2uaAsAdministrativeState		AdministrativeState,
	m2uaAsOperationalState			OperationalState,
	m2uaAsProceduralStatus			ProceduralStatus,
	m2uaAsUsageState			UsageState,
	m2uaAsAsState				AsState,
	m2uaAsRowStatus				RowStatus
    }

m2uaAsId OBJECT-TYPE
    SYNTAX	SimpleNameType
    MAX-ACCESS	not-accessible
    STATUS	current
    DESCRIPTION
	"This is the index of the AS table.  This index may also be used 
	 as a local application server identifier.  This is a shared 
	 index."
    ::= { m2uaAsEntry 1 }

m2uaAsName OBJECT-TYPE
    SYNTAX	CommonLanguageName
    MAX-ACCESS	read-create
    STATUS	current
    DESCRIPTION
	"This is the name of the application server following COMMON 
	 LANGUAGE procedures and the CommongLanguageName textual 
	 convention.  Names should be derived from the COMMON LANGUAGE 
	 location identifier identifying the location of the service or 
	 facility rather than a local identifier.  Note that this is not 
	 necessarily the SG CLLI as the AS could be served by multiple 
	 SGs at different locations."
    ::= { m2uaAsEntry 2 }

m2uaAsTrafficMode OBJECT-TYPE
    SYNTAX	TrafficMode
    MAX-ACCESS	read-create
    STATUS	current
    DESCRIPTION
	"This is the traffic mode for the application server in all SG 
	 that serve the AS, following the TrafficMode textual 
	 convention."
    ::= { m2uaAsEntry 3 }

m2uaAsAdministrativeState OBJECT-TYPE
    SYNTAX	AdministrativeState
    MAX-ACCESS	read-create
    STATUS	current
    DESCRIPTION
	"This is the administrative state of the AS following 
	 AdministrativeState textual convention.  The state can be 
	 locked(0) or unlocked(1).  When locked(0), the AS will be in 
	 the AS Down state in all ASPs.  When unlocked(1), the AS may be 
	 activated for an ASP.  When set to the locked(0) state from the 
	 unlocked(1) state by a management station, the agent will move 
	 the AS to the down AS state for all SGs that serve the AS.
	 
	  - locked(0): The resource is administratively prohibited from 
	    performing services for its users.
	 
	  - unlocked(1): The resource is administratively permitted to 
	    perform services for its users.  This is independent of its 
	    inherent operability.
	 
	  - shuttingDown(2): Use of the resource is administratively 
	    permitted to existing instances of use only.  While the 
	    system remains in the shutting down state, the manager may 
	    at any time cause the managed object to revert to the 
	    unlocked state."
    REFERENCE
	"ITU-T Rec. X.721 (1992) | ISO/IEC 10165-2 : 1992, administrativeState.
	 ITU-T Rec. X.731 (1992) | ISO/IEC 10164-2 : 1993, Section 8.1.1.3."
    ::= { m2uaAsEntry 4 }

m2uaAsOperationalState OBJECT-TYPE
    SYNTAX	OperationalState
    MAX-ACCESS	read-only
    STATUS	current
    DESCRIPTION
	""
    REFERENCE
	""
    ::= { m2uaAsEntry 5 }

m2uaAsProceduralStatus OBJECT-TYPE
    SYNTAX	ProceduralStatus
    MAX-ACCESS	read-create
    STATUS	current
    DESCRIPTION
	"This is the procedural status of the AS following the 
	 ProceduralStatus textual conventions.  The procedural status is 
	 a set value which may contain initializationReqired(0), 
	 notInitialized(1), initializing(2), reporting(3), 
	 terminating(4).  This value represents the intersection 
	 (logical OR) of the procedural status of the AS for each SG in 
	 which it is served.
	 
	  - intializationRequired(0): The resource requires 
	    initialization to be invoked by the manager before it can 
	    perform its normal functions, and this procedure has not 
	    been initiated.  The manager may be able to invoke such 
	    initialization through an action.  The terminating condition 
	    may also be present.  The operational state is disabled.
	 
	  - notInitialized(1): The resource requires initialization 
	    before it can perform its normal functions, and this 
	    procedure has not been initiated.  The resource initializes 
	    itself autonomously, but the operational state may be either 
	    disabled or enabled, depending upon the managed object class 
	    definition.
	 
	  - initializing(2): The resource requires initialization before 
	    it can perform its normal functions, and this procedure has 
	    been initiated but is not yet complete.  When this condition 
	    is present, the intitialization required condition is 
	    absent, since initialization has already begun.  The 
	    operational state may be disabled or enabled, depending upon 
	    the managed object class defintion.
	 
	  - reporting(3): not used.
	 
	  - terminating(4): The resource is in a termination phase.  If 
	    the resource does not reinitialize itself autonomously, the 
	    initialization required condition is also present and the 
	    operational state is disabled; otherwise, the operational 
	    state may be either disabled or enabled, depending upon the 
	    managed object class definition.
	 
	 This is a convenience as the value could be determined by 
	 examining the procedural status of the AS for each SG which 
	 serves it."
    REFERENCE
	"ITU-T Rec. X.721 (1992) | ISO/IEC 10165-2 : 1992, proceduralStatus.
	 ITU-T Rec. X.731 (1992) | ISO/IEC 10164-2 : 1993, Section 8.1.2.2."
    ::= { m2uaAsEntry 6 }

m2uaAsUsageState OBJECT-TYPE
    SYNTAX	UsageState
    MAX-ACCESS	read-create
    STATUS	current
    DESCRIPTION
	"This is the usage state of the AS following the UsageState 
	 textual convention.  The usage state may be idle(0), active(1) 
	 or busy(2).  When idle(0), the AS is in the idle state in all 
	 SG serving it.  When active(1), it is in the active state for 
	 at least one of the SG serving it, and not in the busy state 
	 for any SG serving it.  When busy(2), it is in the busy state 
	 for at least one SG serving it.
	 
	  - idle(0): The resource is not currently in use.
	 
	  - active(1): The resource is in used, and has sufficient spare 
	    operating capcity to provide for additional users 
	    simultaneously.
	 
	  - busy(2): The resource is in use, but it has no spare 
	    operating capacity to provide for additional users at this 
	    instant."
    REFERENCE
	"ITU-T Rec. X.721 (1992) | ISO/IEC 10165-2 : 1992, usageState.
	 ITU-T Rec. X.731 (1992) | ISO/IEC 10164-2 : 1993, Section 8.1.1.2."
    ::= { m2uaAsEntry 7 }

m2uaAsAsState OBJECT-TYPE
    SYNTAX	AsState
    MAX-ACCESS	read-create
    STATUS	current
    DESCRIPTION
	"This is the overall AS state of this AS for all SG that serve 
	 it. This state is the most active state of the states of the 
	 individual SG supporting the AS.  If there is one ore more SG 
	 for which the AS is active(4) then the state is active, 
	 otherwise if there is one ore more SG in the deactivating(3) 
	 state, the state is deactivating, otherwise, if there is one or 
	 more in the activating(2) state, the state is activating, 
	 otherwise, one or more inactive(1), inactive, else down(0).
	 
	 This is a convenience because the value could be determined by 
	 examining the individual AS states for each SG; however, the 
	 value is required by the agent to determine alarm severity."
    ::= { m2uaAsEntry 8 }

m2uaAsRowStatus OBJECT-TYPE
    SYNTAX	RowStatus
    MAX-ACCESS	read-create
    STATUS	current
    DESCRIPTION
	"This object is used to create, modify and delete rows according 
	 to the RowStatus textual convention."
    ::= { m2uaAsEntry 9 }


-- ====================================================================

m2uaIfTable OBJECT-TYPE
    SYNTAX	SEQUENCE OF M2uaIfEntry
    MAX-ACCESS	not-accessible
    STATUS	current
    DESCRIPTION
	"m2uaIf The IF Table.
	 
	 This is the IF table.  It provides a list of all interfaces 
	 known to the host.
	 
	 The IF table provides a list of all interfaces known to this 
	 host."
    ::= { m2uaAspIf 1 }

m2uaIfEntry OBJECT-TYPE
    SYNTAX	M2uaIfEntry
    MAX-ACCESS	not-accessible
    STATUS	current
    DESCRIPTION
	"This is an entry in the IF table.  The index is provided by 
	 this table."
    INDEX	{
		    m2uaIfId
		}
    ::= { m2uaIfTable 1 }

M2uaIfEntry ::=
    SEQUENCE {
	m2uaIfId				SimpleNameType,
	m2uaIfAsIndex				Unsigned32,
	m2uaIfIdentifier			Unsigned32,
	m2uaIfName				CommonLanguageName,
	m2uaIfRowStatus				RowStatus
    }

m2uaIfId OBJECT-TYPE
    SYNTAX	SimpleNameType
    MAX-ACCESS	not-accessible
    STATUS	current
    DESCRIPTION
	"This is an index into the IF table.  This is a shared index."
    ::= { m2uaIfEntry 1 }

m2uaIfAsIndex OBJECT-TYPE
    SYNTAX	Unsigned32
    MAX-ACCESS	read-create
    STATUS	current
    DESCRIPTION
	"This provides an index into the AS table which identifies the 
	 application server to which this interface belongs."
    ::= { m2uaIfEntry 2 }

m2uaIfIdentifier OBJECT-TYPE
    SYNTAX	OCTET STRING (SIZE(1..16))
    MAX-ACCESS	read-create
    STATUS	current
    DESCRIPTION
	"This provides a local physical point of attachment identifiers 
	 that identifies the interface for the purposes of local 
	 binding."
    ::= { m2uaIfEntry 3 }

m2uaIfName OBJECT-TYPE
    SYNTAX	CommonLanguageName
    MAX-ACCESS	read-create
    STATUS	current
    DESCRIPTION
	"This provides a COMMON LANGUAGE name for the interface folowing 
	 the CommonLanguageName textual convention that provides a local 
	 name of the interface for the purposes of local binding."
    ::= { m2uaIfEntry 4 }

m2uaIfRowStatus OBJECT-TYPE
    SYNTAX	RowStatus
    MAX-ACCESS	read-create
    STATUS	current
    DESCRIPTION
	"This provides a mechanism for management stations to add, 
	 modify and delete rows in this table according to the RowStatus 
	 textual convention."
    ::= { m2uaIfEntry 5 }


-- ====================================================================

m2uaAsIfTable OBJECT-TYPE
    SYNTAX	SEQUENCE OF M2uaAsIfEntry
    MAX-ACCESS	not-accessible
    STATUS	current
    DESCRIPTION
	"m2uaAsIf  The AS-IF table.
	 
	 This is the AS-IF table that maps interfaces to application 
	 servers.
	 
	 This table provides the containment relationship between 
	 application servers and interfaces.  It is a convenience table 
	 because interfaces are assigned to application server when the 
	 interface is created."
    ::= { m2uaAspAsIf 1 }

m2uaAsIfEntry OBJECT-TYPE
    SYNTAX	M2uaAsEntry
    MAX-ACCESS	not-accessible
    STATUS	current
    DESCRIPTION
	"This is an entry in the AS-IF table.  The m2uaASId and m2uaIfId 
	 indices are shared.  The indices represent that this entry is a 
	 relationship between the indexed AS and interface."
    INDEX	{
		    m2uaAsId,   -- shared index
		    m2uaIfId    -- shared index
		}
    ::= { m2uaAsIfTable 1 }

M2uaAsIfEntry ::=
    SEQUENCE {
    }


-- ====================================================================

m2uaSgAsTable OBJECT-TYPE
    SYNTAX	SEQUENCE OF M2uaSgAsEntry
    MAX-ACCESS	not-accessible
    STATUS	current
    DESCRIPTION
	"m2uaSgAs  The SG-AS table.
	 
	 This is the SG-AS table that maps AS onto the SG that serve 
	 them.  Note that an AS can be served by more than one SG.
	 
	 This table provides a mapping of AS onto the SG that serve the 
	 AS.  Note that an AS can be served by more than one SG."
    ::= { m2uaAspSgAs 1 }

m2uaSgAsEntry OBJECT-TYPE
    SYNTAX	M2uaSgAsEntry
    MAX-ACCESS	not-accessible
    STATUS	current
    DESCRIPTION
	"This is an entry in the SG-AS table that represents an AS 
	 served by an SG.  The m2uaSgId and m2uaASId indices are shared.  
	 The indices represent that this entry is a relationship between 
	 the indexed SG and AS."
    INDEX	{
		    m2uaSgId,
		    m2uaAsId
		}
    ::= { m2uaSgAsTable 1 }

M2uaSgAsEntry ::=
    SEQUENCE {
	m2uaSgAsOrdering			Unsigned32,
	m2uaSgAsAdministrativeState		AdministrativeState,
	m2uaSgAsOperationalState		OperationalState,
	m2uaSgAsProceduralStatus		ProceduralStatus,
	m2uaSgAsUsageState			UsageState,
	m2uaSgAsOperationalState		OperationalState,
	m2uaSgAsAvailabilityStatus		AvailabilityStatus,
	m2uaSgAsStandbyStatus			StandbyStatus,
	m2uaSgAsPrimarySg			Unsigned32,
	m2uaSgAsAsState				AsState,
	m2uaSgAsRowStatus			RowStatus
    }

m2uaSgAsOrdering OBJECT-TYPE
    SYNTAX	Unsigned32
    MAX-ACCESS	read-create
    STATUS	current
    DESCRIPTION
	"This provides the ordering of the SG serving the AS.  When AS 
	 are served by multiple SG, they can only serve the AS in an 
	 primary-backup fashion.  This ordering provides the order in 
	 which the SG will be used by the ASP, with low values being the 
	 first used and then the next higher ordinal.  The ASP will only 
	 register and activate for one SG at a time.  If the activation 
	 procedure fails with one SG due to a permanent cause (e.g.  
	 failure to establish an SCTP association), the next oridinal SG 
	 in the list will be attempted.  Once activated with a given SG, 
	 no attempt will be made to activate with another SG until the 
	 current SG fails or the AS has been deactivated using the  
	 AsState or AdministrativeState columns."
    ::= { m2uaSgAsEntry 1 }

m2uaSgAsAdministrativeState OBJECT-TYPE
    SYNTAX	AdministrativeState
    MAX-ACCESS	read-create
    STATUS	current
    DESCRIPTION
	"This is the administrative state of the AS for the SG, 
	 following the AdministrativeState textual convention.  When 
	 locked(0), the AS will be inactive for the SG and any link keys 
	 for contained interfaces will be unregistered.  When 
	 unlocked(1), an ASP may resister a link key for an interface 
	 contained by the AS and may activate the AS.
	 
	  - locked(0): The resource is administratively prohibited from 
	    performing services for its users.
	 
	  - unlocked(1): The resource is administratively permitted to 
	    perform services for its users.  This is independent of its 
	    inherent operability.
	 
	  - shuttingDown(2): Use of the resource is administratively 
	    permitted to existing instances of use only.  While the 
	    system remains in the shutting down state, the manager may 
	    at any time cause the managed object to revert to the 
	    unlocked state."
    REFERENCE
	"ITU-T Rec. X.721 (1992) | ISO/IEC 10165-2 : 1992, administrativeState.
	 ITU-T Rec. X.731 (1992) | ISO/IEC 10164-2 : 1993, Section 8.1.1.3."
    ::= { m2uaSgAsEntry 2 }

m2uaSgAsOperationalState OBJECT-TYPE
    SYNTAX	OperationalState
    MAX-ACCESS	read-only
    STATUS	current
    DESCRIPTION
	""
    REFERENCE
	""
    ::= { m2uaSgAsEntry 3 }

m2uaSgAsProceduralStatus OBJECT-TYPE
    SYNTAX	ProceduralStatus
    MAX-ACCESS	read-only
    STATUS	current
    DESCRIPTION
	"This is the procedural status of the AS for the SG following 
	 the ProceduralStatus textual convention.  This is a set value 
	 which contains the intersection (logical OR) of the AS for this 
	 SG in each ASP using the AS.
	 
	  - intializationRequired(0): The resource requires 
	    initialization to be invoked by the manager before it can 
	    perform its normal functions, and this procedure has not 
	    been initiated.  The manager may be able to invoke such 
	    initialization through an action.  The terminating condition 
	    may also be present.  The operational state is disabled.
	 
	  - notInitialized(1): The resource requires initialization 
	    before it can perform its normal functions, and this 
	    procedure has not been initiated.  The resource initializes 
	    itself autonomously, but the operational state may be either 
	    disabled or enabled, depending upon the managed object class 
	    definition.
	 
	  - initializing(2): The resource requires initialization before 
	    it can perform its normal functions, and this procedure has 
	    been initiated but is not yet complete.  When this condition 
	    is present, the intitialization required condition is 
	    absent, since initialization has already begun.  The 
	    operational state may be disabled or enabled, depending upon 
	    the managed object class defintion.
	 
	  - reporting(3): not used.
	 
	  - terminating(4): The resource is in a termination phase.  If 
	    the resource does not reinitialize itself autonomously, the 
	    initialization required condition is also present and the 
	    operational state is disabled; otherwise, the operational 
	    state may be either disabled or enabled, depending upon the 
	    managed object class definition.
	 
	 This is a convenience as the value could be determined by 
	 examining the procedural status of the AS for this SG in each 
	 of the ASPs using the AS."
    REFERENCE
	"ITU-T Rec. X.721 (1992) | ISO/IEC 10165-2 : 1992, proceduralStatus.
	 ITU-T Rec. X.731 (1992) | ISO/IEC 10164-2 : 1993, Section 8.1.2.2."
    ::= { m2uaSgAsEntry 4 }

m2uaSgAsUsageState OBJECT-TYPE
    SYNTAX	UsageState
    MAX-ACCESS	read-only
    STATUS	current
    DESCRIPTION
	"This is the usage state of the AS for the SG following the 
	 UsageState textual convention.  When idle(0) the AS has a usage 
	 state of idle(0) for all ASPs using this AS at this SG.  When 
	 active(1), the AS is active for at least one ASP-SG relation, 
	 but is not busy in any ASP-SG relation.  When busy(2), the AS 
	 is busy for at least one ASP-SG relation.
	 
	  - idle(0): The resource is not currently in use.
	 
	  - active(1): The resource is in used, and has sufficient spare 
	    operating capcity to provide for additional users 
	    simultaneously.
	 
	  - busy(2): The resource is in use, but it has no spare 
	    operating capacity to provide for additional users at this 
	    instant."
    REFERENCE
	"ITU-T Rec. X.721 (1992) | ISO/IEC 10165-2 : 1992, usageState.
	 ITU-T Rec. X.731 (1992) | ISO/IEC 10164-2 : 1993, Section 8.1.1.2."
    DEFVAL	{ 0 } -- idle(0)
    ::= { m2uaSgAsEntry 5 }

m2uaSgAsOperationalState OBJECT-TYPE
    SYNTAX	OperationalState
    MAX-ACCESS	read-only
    STATUS	current
    DESCRIPTION
	"
	  - disabled(0), the resource is totally inoperable and unable 
	    to provide service to the user(s);
	 
	  - enabled(1), the resource is partially or fully operable and 
	    available for use.
	"
    REFERENCE
	"ITU-T Rec. X.721 (1992) | ISO/IEC 10165-2 : 1992, operationalState.
	 ITU-T Rec. X.731 (1992) | ISO/IEC 10164-2 : 1993, Section 8.1.1.1."
    ::= { m2uaSgAsEntry 6 }

m2uaSgAsAvailabilityStatus OBJECT-TYPE
    SYNTAX	AvailabilityStatus
    MAX-ACCESS	read-only
    STATUS	current
    DESCRIPTION
	""
    REFERENCE
	"ITU-T Rec. X.721 (1992) | ISO/IEC 10165-2 : 1992, availabilityStatus
	 ITU-T Rec. X.731 (1992) | ISO/IEC 10164-2 : 1993, Section 8.1.2.3."
    ::= { m2uaSgAsEntry 7 }

m2uaSgAsStandbyStatus OBJECT-TYPE
    SYNTAX	StandbyStatus
    MAX-ACCESS	read-only
    STATUS	current
    DESCRIPTION
	"When mutliple SG are used to serve an AS, this object provides 
	 the standby status of the SG with respect the AS.
	 
	  - hotStandby(0): The resource is not providing service, but is 
	    operating in synchronism with another resource that is to be 
	    backed-up (e.g, a computer shadowing another computer).  A 
	    resource with a hot standby status will be immediately able 
	    to take over the role of the resource to be backed-up, 
	    without the need for intialization activity, and will 
	    contain the same information as the resource being backed 
	    up.  The hot standby condition is mutually exclusive with 
	    the cold standby and providing service conditions.  The 
	    operational state is enabled.  The administrative state is 
	    unlocked.  The availability status is offline.
	 
	  - coldStandby(1): The resource is to back-up another resource, 
	    but is not syncrhonized with that resource.  A resource with 
	    a cold standby status will not be immediately able to take 
	    over the role of a resource to be backed up, and will 
	    require some initialization activity.  The cold standby 
	    condition is mutually exclusive with the hot standby and 
	    providing service condition.  The operational state is 
	    enabled or disabled.  The administrative state is locked or 
	    unlocked.  The procedural status contains not initialized or 
	    initialization required.  The availability status is 
	    offline.
	 
	  - providingService(2): The back-up resource is providing 
	    service and is backing up another resource.  The providing 
	    service condition is mutually exclusive with the hot stanbdy 
	    and cold standby conditions.  The operational state is 
	    enabled.  The administrative state is unlocked.  The 
	    availability status is online.
	"
    REFERENCE
	"ITU-T Rec. X.721 (1992) | ISO/IEC 10165-2 : 1992, standbyStatus.
	 ITU-T Rec. X.731 (1992) | ISO/IEC 10164-2 : 1993, Section 8.1.2.5."
    ::= { m2uaSgAsEntry 8 }

m2uaSgAsPrimarySg OBJECT-TYPE
    SYNTAX	Unsigned32
    MAX-ACCESS	read-only
    STATUS	current
    DESCRIPTION
	"Provides an index in to the SG table that corresponds to the 
	 primary SG for which this SG is a backup for the specified AS."
    ::= { m2uaSgAsEntry 9 }

m2uaSgAsAsState OBJECT-TYPE
    SYNTAX	AsState
    MAX-ACCESS	read-only
    STATUS	current
    DESCRIPTION
	"This is the overall AS state for the SG, following the AsState 
	 textual convention.  It is the most active states of the 
	 individual states for the ASP-SG associations for this SG.  If 
	 at least one ASP-SG association is in the active state for the 
	 AS, the state is active; one deactivating, deactivating; one 
	 activating, activating; one, inactive, inactive; else down.
	 
	 This is a convenience in that the value could be determined by 
	 a management station by examining the individual states of the 
	 AS in each ASP-SG relation, however, the value is necessary for 
	 the agent to determine the correct severity level for alarms."
    DEFVAL	{ 0 } -- down(0)
    ::= { m2uaSgAsEntry 10 }


m2uaSgAsRowStatus OBJECT-TYPE
    SYNTAX	RowStatus
    MAX-ACCESS	read-create
    STATUS	current
    DESCRIPTION
	"This provide a mechanism for management stations to add, modify 
	 and delete rows from this table.  To add rows, the associated 
	 index values must exist in their primary tables.  To delete a 
	 row, the entry must be in the locked(0) administrative state."
    ::= { m2uaSgAsEntry 11 }


-- ====================================================================

m2uaAspAsTable OBJECT-TYPE
    SYNTAX	SEQUENCE OF M2uaAspAsEntry
    MAX-ACCESS	not-accessible
    STATUS	current
    DESCRIPTION
	"m2uaAspAs  The ASP AS table.
	 
	 This provides the ASP AS table that provides the state of the 
	 AS at each ASP to which it is served.
	 
	 This table provides a mapping of which AS are served to 
	 which ASPs."
    ::= { m2uaAspAspAs 1 }

m2uaAspAsEntry OBJECT-TYPE
    SYNTAX	M2uaAspAsEntry
    MAX-ACCESS	not-accessible
    STATUS	current
    DESCRIPTION
	"This is an entry in the ASP AS table.  The m2uaAspId and 
	 m2uaASId are shared indices.  These indices represent that this 
	 entry is a relationship between the indexed ASP and AS."
    INDEX	{
		    m2uaAspId,
		    m2uaAsId
		}
    ::= { m2uaAspAsTable 1 }

M2uaAspAsEntry ::=
    SEQUENCE {
	m2uaAspAsAdministrativeState		AdministrativeState,
	m2uaAspAsOperationalState		OperationalState,
	m2uaAspAsProceduralStatus		ProceduralStatus,
	m2uaAspAsUsageState			UsageState,
	m2uaAspAsAsState			AsState,
	m2uaAspAsRowStatus			RowStatus
    }

m2uaAspAsAdministrativeState OBJECT-TYPE
    SYNTAX	AdministrativeState
    MAX-ACCESS	read-create
    STATUS	current
    DESCRIPTION
	"
	 
	  - locked(0): The resource is administratively prohibited from 
	    performing services for its users.
	 
	  - unlocked(1): The resource is administratively permitted to 
	    perform services for its users.  This is independent of its 
	    inherent operability.
	 
	  - shuttingDown(2): Use of the resource is administratively 
	    permitted to existing instances of use only.  While the 
	    system remains in the shutting down state, the manager may 
	    at any time cause the managed object to revert to the 
	    unlocked state."
    REFERENCE
	"ITU-T Rec. X.721 (1992) | ISO/IEC 10165-2 : 1992, administrativeState.
	 ITU-T Rec. X.731 (1992) | ISO/IEC 10164-2 : 1993, Section 8.1.1.3."
    DEFVAL	{ 0 } -- locked(0)
    ::= { m2uaAspAsEntry 1 }

m2uaAspAsOperationalState OBJECT-TYPE
    SYNTAX	OperationalState
    MAX-ACCESS	read-only
    STATUS	current
    DESCRIPTION
	""
    REFERENCE
	""
    ::= { m2uaAspAsEntry 2 }

m2uaAspAsProceduralStatus OBJECT-TYPE
    SYNTAX	ProceduralStatus
    MAX-ACCESS	read-only
    STATUS	current
    DESCRIPTION
	"
	 
	  - intializationRequired(0): The resource requires 
	    initialization to be invoked by the manager before it can 
	    perform its normal functions, and this procedure has not 
	    been initiated.  The manager may be able to invoke such 
	    initialization through an action.  The terminating condition 
	    may also be present.  The operational state is disabled.
	 
	  - notInitialized(1): The resource requires initialization 
	    before it can perform its normal functions, and this 
	    procedure has not been initiated.  The resource initializes 
	    itself autonomously, but the operational state may be either 
	    disabled or enabled, depending upon the managed object class 
	    definition.
	 
	  - initializing(2): The resource requires initialization before 
	    it can perform its normal functions, and this procedure has 
	    been initiated but is not yet complete.  When this condition 
	    is present, the intitialization required condition is 
	    absent, since initialization has already begun.  The 
	    operational state may be disabled or enabled, depending upon 
	    the managed object class defintion.
	 
	  - reporting(3): not used.
	 
	  - terminating(4): The resource is in a termination phase.  If 
	    the resource does not reinitialize itself autonomously, the 
	    initialization required condition is also present and the 
	    operational state is disabled; otherwise, the operational 
	    state may be either disabled or enabled, depending upon the 
	    managed object class definition."
    REFERENCE
	"ITU-T Rec. X.721 (1992) | ISO/IEC 10165-2 : 1992, proceduralStatus.
	 ITU-T Rec. X.731 (1992) | ISO/IEC 10164-2 : 1993, Section 8.1.2.2."
    ::= { m2uaAspAsEntry 3 }

m2uaAspAsUsageState OBJECT-TYPE
    SYNTAX	UsageState
    MAX-ACCESS	read-only
    STATUS	current
    DESCRIPTION
	"
	 
	  - idle(0): The resource is not currently in use.
	 
	  - active(1): The resource is in used, and has sufficient spare 
	    operating capcity to provide for additional users 
	    simultaneously.
	 
	  - busy(2): The resource is in use, but it has no spare 
	    operating capacity to provide for additional users at this 
	    instant."
    REFERENCE
	"ITU-T Rec. X.721 (1992) | ISO/IEC 10165-2 : 1992, usageState.
	 ITU-T Rec. X.731 (1992) | ISO/IEC 10164-2 : 1993, Section 8.1.1.2."
    DEFVAL	{ 0 } -- idle((0)
    ::= { m2uaAspAsEntry 4 }

m2uaAspAsAsState OBJECT-TYPE
    SYNTAX	RowStatus
    MAX-ACCESS	read-create
    STATUS	current
    DESCRIPTION
	"This is the overall AS state for the AS as used by this ASP.  
	 This is the reverse direction of view from most of the AS 
	 states: it is the state of the local AS within the host as 
	 viewed from the ASP instead of the state within the SG as 
	 viewed from the ASP.
	 
	 When down(0), there is no local AS bound to the interfaces, 
	 when inactive, there is a local AS bound to the interace, when 
	 activating, there is a local AS activating for the interface, 
	 when deactivating, the local AS is deactivating the interface, 
	 and when active, there is a local AS active for the interface.
	 
	 When a management station sets this state to down(0) from other 
	 than the down state, the local AS is hung up.  When a 
	 management station sets the state to inactive from the active 
	 state, the local AS is deactivated an informed.  Note that 
	 these are not long term measures: see the AdministrativeState 
	 textual convention in this row for lasting effects."
    ::= { m2uaAspAsEntry 5 }

m2uaAspAsRowStatus OBJECT-TYPE
    SYNTAX	RowStatus
    MAX-ACCESS	read-create
    STATUS	current
    DESCRIPTION
	""
    ::= { m2uaAspAsEntry 6 }


-- ====================================================================

m2uaAspSgAsTable OBJECT-TYPE
    SYNTAX	SEQUENCE OF M2uaAspSgAsEntry
    MAX-ACCESS	not-accessible
    STATUS	current
    DESCRIPTION
	"m2uaAspSgAs  The ASP-SG-AS table.
	 
	 This provides the ASP-SG-AS table that provides the state of 
	 each AS for each ASP-SG association.
	 
	 This table provides the state of each AS for each ASP-SG 
	 association."
    ::= { m2uaAspAspSgAs 1 }

m2uaAspSgAsEntry OBJECT-TYPE
    SYNTAX	M2uaAspSgAsEntry
    MAX-ACCESS	not-accessible
    STATUS	current
    DESCRIPTION
	"This provides an entry in the ASP-SG AS table.  The indices are 
	 shared.  The indices represent that this entry is a 
	 relationship between the indexed ASP, SG and AS."
    INDEX	{
		    m2uaAspId,
		    m2uaSgId,
		    m2uaAsId
		}
    ::= { m2uaAspSgAsTable 1 }

M2uaAspSgAsEntry ::=
    SEQUENCE {
	m2uaAspSgAsAdministrativeState		AdministrativeState,
	m2uaAspSgAsOperationalState		OperationalState,
	m2uaAspSgAsProceduralStatus		ProceduralStatus,
	m2uaAspSgAsUsageState			UsageState,
	m2uaAspSgAsStandbyStatus		StandbyStatus,
	m2uaAspSgAsRowStatus			AsState
    }

m2uaAspSgAsAdministrativeState OBJECT-TYPE
    SYNTAX	AdministrativeState
    MAX-ACCESS	read-write
    STATUS	current
    DESCRIPTION
	"Provides the administrative state of the AS for the ASP-SG 
	 association following the AdministrativeState textual 
	 convention from the OPENSS7-TMN-TC module.  When locked(0), the 
	 ASP will deactivate the AS and deregister any link keys 
	 registered for the contained interfaces.  When unlocked(1), the 
	 ASP will be permitted to register link keys for the contained 
	 interfaces and activate the AS.
	 
	  - locked(0): The resource is administratively prohibited from 
	    performing services for its users.
	 
	  - unlocked(1): The resource is administratively permitted to 
	    perform services for its users.  This is independent of its 
	    inherent operability.
	 
	  - shuttingDown(2): Use of the resource is administratively 
	    permitted to existing instances of use only.  While the 
	    system remains in the shutting down state, the manager may 
	    at any time cause the managed object to revert to the 
	    unlocked state."
    REFERENCE
	"ITU-T Rec. X.721 (1992) | ISO/IEC 10165-2 : 1992, administrativeState.
	 ITU-T Rec. X.731 (1992) | ISO/IEC 10164-2 : 1993, Section 8.1.1.3."
    ::= { m2uaAspSgAsEntry 1 }

m2uaAspSgAsOperationalState OBJECT-TYPE
    SYNTAX	OperationalState
    MAX-ACCESS	read-only
    STATUS	current
    DESCRIPTION
	""
    REFERENCE
	""
    ::= { m2uaAspSgAsEntry 2 }

m2uaAspSgAsProceduralStatus OBJECT-TYPE
    SYNTAX	ProceduralStatus
    MAX-ACCESS	read-only
    STATUS	current
    DESCRIPTION
	"Provides the procedural status of the AS for the ASP-SG 
	 association following the ProceduralStatus textual convention 
	 of the OPENSS7-TMN-TC module.  When the procedural status 
	 contains initializationRequired, the AS has not yet had link 
	 keys for its contained interfaces registered and registration 
	 is required.  When it contains notInitialized, the AS is 
	 inactive.  When it contains initializting, the ASP Active 
	 procedure is being performed for the AS.  When it contains 
	 terminating, the ASP Inactive procedure is being performed for 
	 the AS.
	 
	  - intializationRequired(0): The resource requires 
	    initialization to be invoked by the manager before it can 
	    perform its normal functions, and this procedure has not 
	    been initiated.  The manager may be able to invoke such 
	    initialization through an action.  The terminating condition 
	    may also be present.  The operational state is disabled.
	 
	  - notInitialized(1): The resource requires initialization 
	    before it can perform its normal functions, and this 
	    procedure has not been initiated.  The resource initializes 
	    itself autonomously, but the operational state may be either 
	    disabled or enabled, depending upon the managed object class 
	    definition.
	 
	  - initializing(2): The resource requires initialization before 
	    it can perform its normal functions, and this procedure has 
	    been initiated but is not yet complete.  When this condition 
	    is present, the intitialization required condition is 
	    absent, since initialization has already begun.  The 
	    operational state may be disabled or enabled, depending upon 
	    the managed object class defintion.
	 
	  - reporting(3): not used.
	 
	  - terminating(4): The resource is in a termination phase.  If 
	    the resource does not reinitialize itself autonomously, the 
	    initialization required condition is also present and the 
	    operational state is disabled; otherwise, the operational 
	    state may be either disabled or enabled, depending upon the 
	    managed object class definition."
    REFERENCE
	"ITU-T Rec. X.721 (1992) | ISO/IEC 10165-2 : 1992, proceduralStatus.
	 ITU-T Rec. X.731 (1992) | ISO/IEC 10164-2 : 1993, Section 8.1.2.2."
    ::= { m2uaAspSgAsEntry 3 }

m2uaAspSgAsUsageState OBJECT-TYPE
    SYNTAX	UsageState
    MAX-ACCESS	read-only
    STATUS	current
    DESCRIPTION
	"This provides the usage state of the AS for the ASP-SG 
	 association following the UsageState textual convention of the 
	 OPENSS7-TMN-TC module.  When idle(0), the AS is down or 
	 inactive for the ASP-SG association.  When active(1), the AS is 
	 active for the ASP-SG association.  When busy(2), the AS is 
	 active an experiencing congestion for the ASP-SG association.
	 
	  - idle(0): The resource is not currently in use.
	 
	  - active(1): The resource is in used, and has sufficient spare 
	    operating capcity to provide for additional users 
	    simultaneously.
	 
	  - busy(2): The resource is in use, but it has no spare 
	    operating capacity to provide for additional users at this 
	    instant."
    REFERENCE
	"ITU-T Rec. X.721 (1992) | ISO/IEC 10165-2 : 1992, usageState.
	 ITU-T Rec. X.731 (1992) | ISO/IEC 10164-2 : 1993, Section 8.1.1.2."
    ::= { m2uaAspSgAsEntry 4 }

m2uaAspSgAsStandbyStatus OBJECT-TYPE
    SYNTAX	StandbyStatus
    MAX-ACCESS	read-only
    STATUS	current
    DESCRIPTION
	"Provides the standby status of the ASP-SG association for the 
	 AS.  Only one ASP-SG association can effectively be used to 
	 provide M2UA access to the interface served by the application 
	 server.  When multiple ASP-SG associations are used to serve the 
	 application server, only one of these ASP-SG associations are 
	 in a providingService(2) state."
    REFERENCE
	"ITU-T Rec. X.721 (1992) | ISO/IEC 10165-2 : 1992, standbyStatus.
	 ITU-T Rec. X.731 (1992) | ISO/IEC 10164-2 : 1993, Section 8.1.2.5."
    ::= { m2uaAspSgAsEntry 5 }

m2uaAspSgAsRowStatus OBJECT-TYPE
    SYNTAX	AsState
    MAX-ACCESS	read-write
    STATUS	current
    DESCRIPTION
	"This provides the AS state for the ASP-SG association following 
	 the AsState textual convention of the OPENSS7-TMN-TC module.  
	 The AS statis is down(0) when the ASP has not completed an ASP 
	 Up procedure or has completed an ASP Down procedure.  Also, the 
	 ASP may be up but the AS has not completed registering its 
	 contained interfaces and regisration is required.  When 
	 inactive, the AS is inactive.  When activating, the ASP is 
	 performing the ASP Active procedure for the AS.  WHen 
	 deactivating, the ASP is performing the ASP Inactive procedure 
	 for the AS.  When active, the AS is active for the ASP-SG 
	 association.
	 
	 When a management station sets this column to down(0) from any 
	 other state, the ASP will deactivate and deregister the AS.  
	 When a management station sets this column to inactive(1) from 
	 any other state, the ASP will deactivate or register the AS.  
	 When set to active, the ASP will regiseter and activate the AS 
	 as required."
    REFERENCE
	"RFC 3331"
    ::= { m2uaAspSgAsEntry 6 }


END -- end module OPENSS7-M2UA-ASP-MIB


-- vim: ft=mib comments=\f\:\",\b\:\-\-,\:\-\-,\f\b\:- fo+=tcqlornw tw=72 nocin nosi sts=4 sw=4
