-- vim: ft=mib comments=\f\:\",\b\:\-\-,\:\-\-,\f\b\:- fo+=tcqlornw tw=72 nocin nosi sts=4 sw=4
-- =============================================================================
-- 
-- @(#) $RCSfile: OPENSS7-SIGTRAN-TC.mib,v $ $Name:  $($Revision: 0.9.2.7 $) $Date: 2009-01-25 07:23:05 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-25 07:23:05 $ by $Author: brian $
--
-- -----------------------------------------------------------------------------
--
-- $Log: OPENSS7-SIGTRAN-TC.mib,v $
-- Revision 0.9.2.7  2009-01-25 07:23:05  brian
-- - correct numbering
--
-- Revision 0.9.2.6  2009-01-10 17:22:26  brian
-- - updated mibs
--
-- Revision 0.9.2.5  2008-10-11 04:34:38  brian
-- - cleanup MIBs
--
-- Revision 0.9.2.4  2008-04-29 01:52:24  brian
-- - updated headers for release
--
-- Revision 0.9.2.3  2007/12/15 20:19:12  brian
-- - updates
--
-- Revision 0.9.2.2  2007/10/15 01:14:26  brian
-- - updated MIBs
--
-- =============================================================================

OPENSS7-SIGTRAN-TC DEFINITIONS ::= BEGIN

IMPORTS
	MODULE-IDENTITY
		FROM SNMPv2-SMI
	TEXTUAL-CONVENTION
		FROM SNMPv2-TC
	openss7Modules
		FROM OPENSS7-SMI;

sigtranTC MODULE-IDENTITY
	LAST-UPDATED
		"200709300514Z"
	ORGANIZATION
		"The OpenSS7 Project"
	CONTACT-INFO
		"Brian Bidulock
		 OpenSS7 Corporation
		 1469 Jefferys Crescent
		 Edmonton, Alberta
		 Canada  T6L 6T1
		 Tel: +1 780 490 1141
		 Fax: +1 780 490 1241
		 Mob: +1 780 953 0667
		 E-Mail: bidulock@openss7.org"
	DESCRIPTION
		"Provides textual conventions for common SIGTRAN 
		 subtypes."
	::= { openss7Modules 10 }

sigtranTrafficMode		OBJECT IDENTIFIER ::= { sigtranTC	 1 }
sigtranProtocolVersion		OBJECT IDENTIFIER ::= { sigtranTC	 2 }

ProtocolVersion ::= TEXTUAL-CONVENTION
	STATUS		current
	DESCRIPTION
		"This is a tetual convention that provides a prtoocol 
		 version for a SIGTRAN implementation of an adaptation 
		 layer.  It can take on the values of interoperable, or 
		 a value based on a protocol standard for the UA."
	SYNTAX		OBJECT IDENTIFIER

interoperableVersion OBJECT-IDENTITY
	STATUS		current
	DESCRIPTION
		"This is the interoperable version of the SIGTRAN UA and 
		 can be used to refer to a universally interoperable 
		 version of any of the the SIGTRAN UAs."
	::= { sigtranProtocolVersion 1 }

rfc3332Version OBJECT-IDENTITY
	STATUS		current
	DESCRIPTION
		"This is a version which supports M3UA as specified in 
		 RFC 3332."
	REFERENCE
		"RFC 3332"
	::= { sigtranProtocolVersion 2 }

ts102142Version OBJECT-IDENTITY
	STATUS		current
	DESCRIPTION
		"This is a version which supports M3UA as specified in 
		 RFC 3332 and ETSI ETS 102 142."
	REFERENCE
		"RFC 3332, ETSI TS 102 142"
	::= { sigtranProtocolVersion 3 }

rfc4666Version OBJECT-IDENTITY
	STATUS		current
	DESCRIPTION
		"This is a version which supports M3UA as specified in 
		 RFC 4666."
	REFERENCE
		"RFC 4666"
	::= { sigtranProtocolVersion 4 }

rfc3331Version OBJECT-IDENTITY
	STATUS		current
	DESCRIPTION
		"This is a version which supports M2UA as specified in 
		 RFC 3331."
	REFERENCE
		"RFC 3331"
	::= { sigtranProtocolVersion 5 }

ts102141Version OBJECT-IDENTITY
	STATUS		current
	DESCRIPTION
		"This is a version which supports M2UA as specified in 
		 RFC 3331 and ETSI TS 102 141."
	REFERENCE
		"RFC 3331, ETSI TS 102 141"
	::= { sigtranProtocolVersion 6 }

TrafficMode ::= TEXTUAL-CONVENTION
	STATUS		current
	DESCRIPTION
		"This is a textual convention that provides a traffic 
		 mode for a SIGTRAN user adaptation layer.  It can take 
		 on values of activeStandby, loadShare or broadCast, or 
		 an implementation defined type."
	SYNTAX		OBJECT IDENTIFIER

activeStandby OBJECT-IDENTITY
	STATUS		current
	DESCRIPTION
		"This is the SIGTRAN UA defined active-standby traffic 
		 mode type."
	::= { sigtranTrafficMode 1 }

loadShare OBJECT-IDENTITY
	STATUS		current
	DESCRIPTION
		"This is the SIGTRAN UA defined load-share traffic mode 
		 type."
	::= { sigtranTrafficMode 2 }

broadCast OBJECT-IDENTITY
	STATUS		current
	DESCRIPTION
		"This is the SIGTRAN UA defined broadcast traffic mode 
		 type."
	::= { sigtranTrafficMode 3 }

RegistrationPolicy ::= TEXTUAL-CONVENTION
	STATUS		current
	DESCRIPTION
		"This is a  textual convention that provides a 
		 registration policy for SIGTRAN user adaptation layers.  
		 It can take on values of forbidden, permitted or 
		 required.
		
		 When forbidden, at an SG, the SG will not permit an ASP 
		 to dynamically register a link or routing key 
		 associated with an AS; at an ASP, the ASP will not 
		 attempt to dynamically register a link or routing key 
		 associated with an AS.
		
		 When permitted, at an SG, the SG will permit, but not 
		 require, an ASP to register a link or routing key 
		 before activating the associated AS using its IID or 
		 RC; at an ASP, the ASP will only attempt to dynamically 
		 register a link or routing key when it has not been 
		 provisioned with an IID or RC value for the AS.
		
		 When required, at an SG, the SG will require an ASP to 
		 register a link or routing key before activating the 
		 asscoiated AS using its IID or RC; at an ASP, the ASP 
		 will dynamically register a link or routing key even 
		 when it knows the IID or RC value from configuration 
		 data."
	SYNTAX	INTEGER {
			unknown(1),
			forbidden(2),
			permitted(3),
			required(4)
		}

AspState ::= TEXTUAL-CONVENTION
	STATUS		current
	DESCRIPTION
		"This is a textual convention that provides ASP state at 
		 an SG or ASP.  When down, the ASP has not initiated an 
		 ASP Up procedure or has completed an ASP Down 
		 procedure; when initializing, the ASP is executing the 
		 ASP Up procedure; when terminating, the ASP is 
		 executing the ASP Down procedure, and when up, the ASP 
		 has completed the ASP Up procedure."
	SYNTAX	INTEGER {
			down(1),
			initializing(2),
			terminating(3),
			up(4)
		}

AsState ::= TEXTUAL-CONVENTION
	STATUS		current
	DESCRIPTION
		"This is a textual convention that provides AS state at 
		 an SG or ASP.  When down, the ASP has not completed an 
		 ASP Up procedure or has completed an ASP Down 
		 procedure.  When inactive an ASP has completed an ASP 
		 Up procedure or has completed an ASP Inactive 
		 procedure.  When activating, an ASP is performing an 
		 ASP Active procedure.  When deactivating, and ASP is 
		 performing an ASP Inactive procedure.  When active and 
		 ASP has completed an ASP Active procedure."
	SYNTAX	INTEGER {
			down(1),
			initializing(2),
			terminating(3),
			inactive(4),
			activating(5),
			deactivating(6),
			active(7)
		}

InterfaceIdentifier ::= TEXTUAL-CONVENTION
	STATUS		current
	DESCRIPTION
		"This is the integer interface identifier (IID) used by 
		 IUA, V5UA and M2UA.  This identifier uniquely 
		 identifies an interface (D-channel, V5.2 control 
		 channel, signalling link) at an SG.  This value should 
		 never be zero for practical reasons."
	SYNTAX		INTEGER (1..4294967295)

InterfaceIdentifierText ::= TEXTUAL-CONVENTION
	STATUS		current
	DESCRIPTION
		"This is the text-based interface identifier (Text-IID) 
		 use IUA, V5UA and M2UA.  This identifier uniquely 
		 identifies an interface (D-channel, V5.2 control 
		 channel, signalling link) at an SG.  This value must 
		 not be a NULL string, for practical reasons.  The 
		 alphabet is ANSI X3.4-1986 (ASCII).  For practical 
		 reasons, the string should not contain control 
		 characters, nor leading not trailing whitespace."
	SYNTAX		OCTET STRING (1..255)

SigtranOptions ::= TEXTUAL-CONVENTION
	STATUS		current
	DESCRIPTION
		"This text convention provides options associated with 
		 Application Server Processes or Signalling Gateways.  

		 When the aspext(0) bit is set, the ASP/SG supports 
		 draft-bidulock-sigtran-aspext.

		 When sginfo(1) is set, the ASP/SG supports 
		 draft-bidulock-sigtran-sginfo.  

		 When the loadsel(2) bit is set, the ASP/SG supports 
		 draft-bidulock-sigtran-loadsel.

		 When the loadgrp(3) bit is set, the ASP/SG supports 
		 draft-bidulock-sigtran-loadgrp.

		 When the corid(4) bit is set, the ASP/SG supports 
		 draft-bidulock-sigtran-corid.
		 
		 When the regext(5) bit is set, the ASP/SG supports 
		 draft-bidulock-sigtran-regext.
		 
		 When the sessid(6) bit is set, the ASP/SG supports 
		 draft-bidulock-sigtran-sessid.
		 
		 When the dynamic(7) bit is set, the ASP/SG supports 
		 dynamic registration.
		 
		 When the aspcong(8) bit is set, the ASP/SG supports 
		 draft-bidulock-sigtran-aspcong.
		 
		 When the textiid(9) bit is set, the ASP/SG supports 
		 text based interface identifiers."
	SYNTAX	BITS {
			aspext(0),
			sginfo(1),
			loadsel(2),
			loadgrp(3),
			corid(4),
			regext(5),
			sessid(6),
			dynamic(7),
			aspcong(8),
			textiid(9)
		}

AspIdPolicy ::= TEXTUAL-CONVENTION
	STATUS		current
	DESCRIPTION
		"This textual convention provides a policy for the ASP 
		 Identifier option for SIGTRAN UAs.
		 
		 When permitted(2), the ASP will provide an ASP 
		 identifier when the SGP indicates that one is required 
		 but will first attempt ASP Up procedures without one.  
		 The SGP will accept an ASP Identifier but will not 
		 require one.

		 When required(3), the ASP will always provide an ASP 
		 Identifier and the SGP will always require one.
		 
		 When forbidden(4), the ASP will not provide an ASP 
		 Identifier and the SGP will ignore any provided ASP 
		 Identifier."
	SYNTAX	INTEGER {
			unknown(1),
			permitted(2),
			required(3),
			forbidden(4),
		}

AssociationPolicy ::= TEXTUAL-CONVENTION
	STATUS		current
	DESCRIPTION
		"This textual convention determines the policy with 
		 regard to forming and dropping SCTP associations.  
		 There are three policies described here:

		 unknown(1) means that the decision as to when to form 
		 and release SCTP assocations is left to the 
		 implemenation.

		 always(2) means that SCTP associations are formed 
		 whenever they are able to be formed.  SCTP association 
		 stay connected until they are explicitly disabled.

		 ondemand(3) means that SCTP associations are formed 
		 only when they are needed, that is, whenever there is a 
		 local AS that attempts to activate and is served by an 
		 SG.  When there is no longer any local AS for the 
		 association, the SCTP asslocation is shut down.

		 other(3) is intended to handle some other 
		 implementation specific method."
	SYNTAX	INTEGER {
			unknown(1),
			always(2),
			ondemand(3),
			other(4)
		}

RestorationPolicy ::= TEXTUAL-CONVENTION
	STATUS		current
	DESCRIPTION
		"Restoration of SCTP associations and execution of the 
		 ASP Up procedures can be peformed manually (via a 
		 management station), or automatically (by the XUA 
		 implementation).  To prevent associations and the ASP 
		 Up procedure from oscillating rapidly between the 
		 ESTABLISHED or ASP Up and ASP Down or CLOSED states, an 
		 SCTP association oscillation filtering procedure shall 
		 be provided.  The procedure is applicable in all cases 
		 where automatic restoration and removal of SCTP 
		 associations to and from service is used.  The 
		 procedure is not invoked if restoration to or remove 
		 from service is intiated manually.  Association 
		 osciallation filtering is a local procedure.  Five 
		 procedures are optionally provided:

		 manual(1), provides manual association restoration to 
		 and removal from service only (management action is 
		 required and no automatic restoration is attempted);

		 simple(2), provides association oscillation filtering 
		 based on ITU-T Q.704 link oscillation filtering 
		 procedures and uses two timers, T17;

		 procedureA(3), provides association oscillation 
		 filtering based on ANSI T1.111.4 link osciallation 
		 procedure A and uses one timer, T32A;

		 procedureB(4), provides association oscillation 
		 filtering based on ANSI T1.111.4 link oscilation 
		 procedure B and uses two timers, T33A and T34A; and,

		 other(5), provides an implementation dependent link 
		 oscillation procedure based on implementation defined 
		 parameters.

		 Note that one timer, T19A, is applicable to all 
		 automatic restoration procedures, simple(2), 
		 procedureA(3), procedureB(4) and other(5)."
	REFERENCE
		"ITU-T Rec. Q.704 (1996), ANSI T1.111.4/2000"
	SYNTAX	INTEGER {
			manual(1),
			simple(2),
			procedureA(3),
			procedureB(4),
			other(5)
		}
		

END

-- vim: ft=mib comments=\f\:\",\b\:\-\-,\:\-\-,\f\b\:- fo+=tcqlornw tw=72 nocin nosi sts=8
