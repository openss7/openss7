-- vim: ft=mib comments=\f\:\",\b\:\-\-,\:\-\-,\f\b\:- fo+=tcqlornw tw=72 nocin nosi sts=4 sw=4
-- =============================================================================
-- 
-- @(#) $RCSfile: OPENSS7-TCAP-OM-MIB.mib,v $ $Name:  $($Revision: 0.9.2.5 $) $Date: 2009-03-02 05:14:55 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-03-02 05:14:55 $ by $Author: brian $
--
-- -----------------------------------------------------------------------------
--
-- $Log: OPENSS7-TCAP-OM-MIB.mib,v $
-- Revision 0.9.2.5  2009-03-02 05:14:55  brian
-- - updates
--
-- Revision 0.9.2.4  2009-01-10 17:09:27  brian
-- - updated agents
--
-- Revision 0.9.2.3  2008-12-31 16:04:49  brian
-- - updated mibs
--
-- Revision 0.9.2.2  2008-12-14 12:55:57  brian
-- - working up mibs
--
-- Revision 0.9.2.1  2008-12-12 06:18:55  brian
-- - add SS7 measurement mibs
--
-- =============================================================================

OPENSS7-TCAP-OM-MIB DEFINITIONS ::= BEGIN

IMPORTS
    MODULE-IDENTITY, OBJECT-TYPE, enterprises
	FROM SNMPv2-SMI
    MODULE-COMPLIANCE, InstancePointer, Integer32, Unsigned32, 
    TimeStamp, Counter
	FROM SNMPv2-TC
    PerfCurrentCount, PerfIntervalCount, PerfTotalCount
	FROM PerfHist-TC-MIB
    HCPerfValidIntervals, HCPerfInvalidIntervals, HCPerfTimeElapsed,
    HCPerfIntervalThreshold, HCPerfCurrentCount, HCPerfIntervalCount,
    HCPerfTotalCount
	FROM HC-PerfHist-TC-MIB
    sccpNetworkEntityId
	FROM OPENSS7-SCCP-MIB
    tcapTcUserId, tcapApplicationEntityId, tcapApplicationSubsystemId
	FROM OPENSS7-TCAP-MIB
    openss7, openss7Q, openss7Q752
	FROM OPENSS7-SMI;

tcapOmMIB MODULE-IDENTITY
    LAST-UPDATED
	"200812092229Z"
    ORGANIZATION
	"The OpenSS7 Project"
    CONTACT-INFO
	"Brian Bidulock
	 OpenSS7 Corporation
	 1469 Jefferys Crescent
	 Edmonton, Alberta  T6L 6T1
	 CANADA
	 Tel: +1 780 490 1141
	 Fax: +1 780 490 1241
	 Mob: +1 780 953 0557
	 mailto:bidulock@openss7.org"
    DESCRIPTION
	"The purpose of this MIB is to proivde SNMP support for the TCAP 
	 operational measurements provided in ITU-T Q.752 and ANSI 
	 T1.116.  There exists a draft GDMO specification for ANSI 
	 T1.116.1 from which this MIB is based.  Strangely enough, no 
	 GDMO is standardized for SS7 operational measurements.

	 The objective of this MIB is to support both the reporting of 
	 statistics obtained from Operational Measurements as well as 
	 providing a mechanism to activate and report the results of OM 
	 studies."
    REVISION
	"200812092229Z"
    DESCRIPTION
	"This is the initial revision of this MIB."
    ::= { openss7Q752 4 }

 -- top level organization of the MIB

tcapOmNotifications	OBJECT IDENTIFIER ::= { tcapOmMIB	 0 }
tcapOmObjects		OBJECT IDENTIFIER ::= { tcapOmMIB	 1 }
tcapOmConformance	OBJECT IDENTIFIER ::= { tcapOmMIB	 2 }

tcapOmTables		OBJECT IDENTIFIER ::= { tcapOmObjects	 1 }
tcapOmScalars		OBJECT IDENTIFIER ::= { tcapOmObjects	 2 }
tcapOmNotifs		OBJECT IDENTIFIER ::= { tcapOmObjects	 3 }
tcapOmOids		OBJECT IDENTIFIER ::= { tcapOmObjects	 4 }

tcapOmCompliance	OBJECT IDENTIFIER ::= { tcapOmConformance 1 }
tcapOmGroups		OBJECT IDENTIFIER ::= { tcapOmConformance 2 }
tcapOmCapabilities	OBJECT IDENTIFIER ::= { tcapOmConformance 3 }

tcapOmNodeMeasurements	OBJECT IDENTIFIER ::= { tcapOmTables	 1 }
tcapOmMsgMeasurements	OBJECT IDENTIFIER ::= { tcapOmTables	 2 }
tcapOmAEMeasurements	OBJECT IDENTIFIER ::= { tcapOmTables	 3 }
tcapOmOperMeasurements	OBJECT IDENTIFIER ::= { tcapOmTables	 4 }
tcapOmDevelMeasurements	OBJECT IDENTIFIER ::= { tcapOmTables	 5 }

-- (1.3.6.1.4.1.29591.17.752.4) openss7Q.752.4 (tcapOmMIB)
-- |__(0) tcapOmNotifications
-- |
-- |__(1) tcapOmObjects
-- |  |__(1) tcapOmTables
-- |  |  |__( 1) tcapOmNodeMeasurements
-- |  |  |  |__( 1) tcapOmNodeTable
-- |  |  |  |  |__( 1) tcapOmNodeEntry
-- |  |  |  |     |__( 1) tcapOmNodeMessagesSent
-- |  |  |  |     |__( 2) tcapOmNodeMessagesRecv
-- |  |  |  |     |__( 3) tcapOmNodeComponentsSent
-- |  |  |  |     |__( 4) tcapOmNodeComponentsRecv
-- |  |  |  |     |__( 5) tcapOmNode5minValidIntervals
-- |  |  |  |     |__( 6) tcapOmNode15minValidIntervals
-- |  |  |  |
-- |  |  |  |__( 2) tcapOmNodeCurrentTable
-- |  |  |  |  |__( 1) tcapOmNodeCurrentEntry
-- |  |  |  |     |__( 1) tcapOmNodeCurrentMessagesSent
-- |  |  |  |     |__( 2) tcapOmNodeCurrentMessagesRecv
-- |  |  |  |     |__( 3) tcapOmNodeCurrentComponentsSent
-- |  |  |  |     |__( 4) tcapOmNodeCurrentComponentsRecv
-- |  |  |  |
-- |  |  |  |__( 3) tcapOmNode5minIntTable
-- |  |  |  |  |__( 1) tcapOmNode5minIntEntry
-- |  |  |  |     |__( 1) tcapOmNode5minIntMessagesSent
-- |  |  |  |     |__( 2) tcapOmNode5minIntMessagesRecv
-- |  |  |  |     |__( 3) tcapOmNode5minIntComponentsSent
-- |  |  |  |     |__( 4) tcapOmNode5minIntComponentsRecv
-- |  |  |  |
-- |  |  |  |__( 4) tcapOmNode15minIntTable
-- |  |  |     |__( 1) tcapOmNode15minIntEntry
-- |  |  |        |__( 1) tcapOmNode15minIntMessagesSent
-- |  |  |        |__( 2) tcapOmNode15minIntMessagesRecv
-- |  |  |        |__( 3) tcapOmNode15minIntComponentsSent
-- |  |  |        |__( 4) tcapOmNode15minIntComponentsRecv
-- |  |  |
-- |  |  |__( 2) tcapOmMsgMeasurements
-- |  |  |  |__( 1) tcapOmMsgsTable
-- |  |  |  |  |__( 1) tcapOmMsgsEntry
-- |  |  |  |     |__( 1) tcapOmMsgsMessagesSent
-- |  |  |  |     |__( 2) tcapOmMsgsMessagesRecv
-- |  |  |  |     |__( 3) tcapOmMsgs5minValidIntervals
-- |  |  |  |     |__( 4) tcapOmMsgs15minValidIntervals
-- |  |  |  |
-- |  |  |  |__( 2) tcapOmMsgsCurrentTable
-- |  |  |  |  |__( 1) tcapOmMsgsCurrentEntry
-- |  |  |  |     |__( 1) tcapOmMsgsCurrentMessagesSent
-- |  |  |  |     |__( 2) tcapOmMsgsCurrentMessagesRecv
-- |  |  |  |
-- |  |  |  |__( 3) tcapOmMsgs5minIntTable
-- |  |  |  |  |__( 1) tcapOmMsgs5minIntEntry
-- |  |  |  |     |__( 1) tcapOmMsgs5minIntMessagesSent
-- |  |  |  |     |__( 2) tcapOmMsgs5minIntMessagesRecv
-- |  |  |  |
-- |  |  |  |__( 4) tcapOmMsgs15minIntTable
-- |  |  |     |__( 1) tcapOmMsgs15minIntEntry
-- |  |  |        |__( 1) tcapOmMsgs15minIntMessagesSent
-- |  |  |        |__( 2) tcapOmMsgs15minIntMessagesRecv
-- |  |  |
-- |  |  |__( 3) tcapOmAEMeasurements
-- |  |  |  |__( 1) tcapOmAETable
-- |  |  |  |  |__( 1) tcapOmAEEntry
-- |  |  |  |     |__( 1) tcapOmAEMeasurementDeleted
-- |  |  |  |     |__( 2) tcapOmAENewTransactions
-- |  |  |  |     |__( 3) tcapOmAEMeanOpenTransactions
-- |  |  |  |     |__( 4) tcapOmAENotUsed
-- |  |  |  |     |__( 5) tcapOmAECummulativeMeanDuration
-- |  |  |  |     |__( 6) tcapOmAEMaximumOpenTranactions
-- |  |  |  |     |__( 7) tcapOmAEThresholdExceeded
-- |  |  |  |     |__( 8) tcapOmAE5minValidIntervals
-- |  |  |  |     |__( 9) tcapOmAE15minValidIntervals
-- |  |  |  |
-- |  |  |  |__( 2) tcapOmAECurrentTable
-- |  |  |  |  |__( 1) tcapOmAECurrentEntry
-- |  |  |  |     |__( 1) tcapOmAECurrentMeasurementDeleted
-- |  |  |  |     |__( 2) tcapOmAECurrentNewTransactions
-- |  |  |  |     |__( 3) tcapOmAECurrentMeanOpenTransactions
-- |  |  |  |     |__( 4) tcapOmAECurrentNotUsed
-- |  |  |  |     |__( 5) tcapOmAECurrentCummulativeMeanDuration
-- |  |  |  |     |__( 6) tcapOmAECurrentMaximumOpenTranactions
-- |  |  |  |     |__( 7) tcapOmAECurrentThresholdExceeded
-- |  |  |  |
-- |  |  |  |__( 3) tcapOmAE5minIntTable
-- |  |  |  |  |__( 1) tcapOmAE5minIntEntry
-- |  |  |  |     |__( 1) tcapOmAE5minIntMeasurementDeleted
-- |  |  |  |     |__( 2) tcapOmAE5minIntNewTransactions
-- |  |  |  |     |__( 3) tcapOmAE5minIntMeanOpenTransactions
-- |  |  |  |     |__( 4) tcapOmAE5minIntNotUsed
-- |  |  |  |     |__( 5) tcapOmAE5minIntCummulativeMeanDuration
-- |  |  |  |     |__( 6) tcapOmAE5minIntMaximumOpenTranactions
-- |  |  |  |     |__( 7) tcapOmAE5minIntThresholdExceeded
-- |  |  |  |
-- |  |  |  |__( 4) tcapOmAE15minIntTable
-- |  |  |     |__( 1) tcapOmAE15minIntEntry
-- |  |  |        |__( 1) tcapOmAE15minIntMeasurementDeleted
-- |  |  |        |__( 2) tcapOmAE15minIntNewTransactions
-- |  |  |        |__( 3) tcapOmAE15minIntMeanOpenTransactions
-- |  |  |        |__( 4) tcapOmAE15minIntNotUsed
-- |  |  |        |__( 5) tcapOmAE15minIntCummulativeMeanDuration
-- |  |  |        |__( 6) tcapOmAE15minIntMaximumOpenTranactions
-- |  |  |        |__( 7) tcapOmAE15minIntThresholdExceeded
-- |  |  |
-- |  |  |__( 4) tcapOmOperMeasurements
-- |  |  |  |__( 1) tcapOmTcTable
-- |  |  |  |  |__( 1) tcapOmTcEntry
-- |  |  |  |     |__( 1) tcapOmTcPabortRecvUnrecTid
-- |  |  |  |     |__( 2) tcapOmTcPabortRecvResourceLim
-- |  |  |  |     |__( 3) tcapOmTcRejectRecvResourceLim
-- |  |  |  |     |__( 4) tcapOmTcPabortSentUnrecTid
-- |  |  |  |     |__( 5) tcapOmTcPabortSentResourceLim
-- |  |  |  |     |__( 6) tcapOmTcRejectSentResourceLim
-- |  |  |  |     |__( 7) tcapOmTcTcUserCancel
-- |  |  |  |     |__( 8) tcapOmTcMessagesDiscarded
-- |  |  |  |     |__( 9) tcapOmTcNotUsed
-- |  |  |  |     |__(10) tcapOmTcPabortsReceived
-- |  |  |  |     |__(11) tcapOmTcTcUserRejectsReceived
-- |  |  |  |     |__(12) tcapOmTcTpErrors
-- |  |  |  |     |__(13) tcapOmTc5minValidIntervals
-- |  |  |  |     |__(14) tcapOmTc15minValidIntervals
-- |  |  |  |
-- |  |  |  |__( 2) tcapOmTcCurrentTable
-- |  |  |  |  |__( 1) tcapOmTcCurrentEntry
-- |  |  |  |     |__( 1) tcapOmTcCurrentPabortRecvUnrecTid
-- |  |  |  |     |__( 2) tcapOmTcCurrentPabortRecvResourceLim
-- |  |  |  |     |__( 3) tcapOmTcCurrentRejectRecvResourceLim
-- |  |  |  |     |__( 4) tcapOmTcCurrentPabortSentUnrecTid
-- |  |  |  |     |__( 5) tcapOmTcCurrentPabortSentResourceLim
-- |  |  |  |     |__( 6) tcapOmTcCurrentRejectSentResourceLim
-- |  |  |  |     |__( 7) tcapOmTcCurrentTcUserCancel
-- |  |  |  |     |__( 8) tcapOmTcCurrentMessagesDiscarded
-- |  |  |  |     |__( 9) tcapOmTcCurrentNotUsed
-- |  |  |  |     |__(10) tcapOmTcCurrentPabortsReceived
-- |  |  |  |     |__(11) tcapOmTcCurrentTcUserRejectsReceived
-- |  |  |  |     |__(12) tcapOmTcCurrentTpErrors
-- |  |  |  |
-- |  |  |  |__( 3) tcapOmTc5minIntTable
-- |  |  |  |  |__( 1) tcapOmTc5minIntEntry
-- |  |  |  |     |__( 1) tcapOmTc5minIntPabortRecvUnrecTid
-- |  |  |  |     |__( 2) tcapOmTc5minIntPabortRecvResourceLim
-- |  |  |  |     |__( 3) tcapOmTc5minIntRejectRecvResourceLim
-- |  |  |  |     |__( 4) tcapOmTc5minIntPabortSentUnrecTid
-- |  |  |  |     |__( 5) tcapOmTc5minIntPabortSentResourceLim
-- |  |  |  |     |__( 6) tcapOmTc5minIntRejectSentResourceLim
-- |  |  |  |     |__( 7) tcapOmTc5minIntTcUserCancel
-- |  |  |  |     |__( 8) tcapOmTc5minIntMessagesDiscarded
-- |  |  |  |     |__( 9) tcapOmTc5minIntNotUsed
-- |  |  |  |     |__(10) tcapOmTc5minIntPabortsReceived
-- |  |  |  |     |__(11) tcapOmTc5minIntTcUserRejectsReceived
-- |  |  |  |     |__(12) tcapOmTc5minIntTpErrors
-- |  |  |  |
-- |  |  |  |__( 4) tcapOmTc15minIntTable
-- |  |  |     |__( 1) tcapOmTc15minIntEntry
-- |  |  |        |__( 1) tcapOmTc15minIntPabortRecvUnrecTid
-- |  |  |        |__( 2) tcapOmTc15minIntPabortRecvResourceLim
-- |  |  |        |__( 3) tcapOmTc15minIntRejectRecvResourceLim
-- |  |  |        |__( 4) tcapOmTc15minIntPabortSentUnrecTid
-- |  |  |        |__( 5) tcapOmTc15minIntPabortSentResourceLim
-- |  |  |        |__( 6) tcapOmTc15minIntRejectSentResourceLim
-- |  |  |        |__( 7) tcapOmTc15minIntTcUserCancel
-- |  |  |        |__( 8) tcapOmTc15minIntMessagesDiscarded
-- |  |  |        |__( 9) tcapOmTc15minIntNotUsed
-- |  |  |        |__(10) tcapOmTc15minIntPabortsReceived
-- |  |  |        |__(11) tcapOmTc15minIntTcUserRejectsReceived
-- |  |  |        |__(12) tcapOmTc15minIntTpErrors
-- |  |  |
-- |  |  |__( 5) tcapOmDevelMeasurements
-- |  |     |__( 1) tcapOmDevelRecvTable
-- |  |     |  |__( 1) tcapOmDevelRecvEntry
-- |  |     |     |__( 1) tcapOmDevelRecvPabortMessageType
-- |  |     |     |__( 2) tcapOmDevelRecvPabortIncorrectTp
-- |  |     |     |__( 3) tcapOmDevelRecvPabortBadTp
-- |  |     |     |__( 4) tcapOmDevelRecvRejectUnrecComp
-- |  |     |     |__( 5) tcapOmDevelRecvRejectMistypeComp
-- |  |     |     |__( 6) tcapOmDevelRecvRejectBadCompStruct
-- |  |     |     |__( 7) tcapOmDevelRecvRejectUnrecLinkId
-- |  |     |     |__( 8) tcapOmDevelRecvRejectUnrecIdRetRes
-- |  |     |     |__( 9) tcapOmDevelRecvRejectUnexpRetRes
-- |  |     |     |__(10) tcapOmDevelRecvRejectUnrecIdRetErr
-- |  |     |     |__(11) tcapOmDevelRecvRejectUnexpRetErr
-- |  |     |     |__(12) tcapOmDevelRecvUsrRejDupInvokeId
-- |  |     |     |__(13) tcapOmDevelRecvUsrRejUnrecOper
-- |  |     |     |__(14) tcapOmDevelRecvUsrRejParmInvoke
-- |  |     |     |__(15) tcapOmDevelRecvUsrRejReleasing
-- |  |     |     |__(16) tcapOmDevelRecvUsrRejUnexpLinkResp
-- |  |     |     |__(17) tcapOmDevelRecvUsrRejUnexpLinkOper
-- |  |     |     |__(18) tcapOmDevelRecvUsrRejUnrecError
-- |  |     |     |__(19) tcapOmDevelRecvUsrRejUnexpError
-- |  |     |     |__(20) tcapOmDevelRecvUsrRejParmRetResult
-- |  |     |     |__(21) tcapOmDevelRecvUsrRejParmRetError
-- |  |     |     |__(22) tcapOmDevelRecv5minValidIntervals
-- |  |     |     |__(23) tcapOmDevelRecv15minValidIntervals
-- |  |     |
-- |  |     |__( 2) tcapOmDevelRecvCurrentTable
-- |  |     |  |__( 1) tcapOmDevelRecvCurrentEntry
-- |  |     |     |__( 1) tcapOmDevelRecvCurrentPabortMessageType
-- |  |     |     |__( 2) tcapOmDevelRecvCurrentPabortIncorrectTp
-- |  |     |     |__( 3) tcapOmDevelRecvCurrentPabortBadTp
-- |  |     |     |__( 4) tcapOmDevelRecvCurrentRejectUnrecComp
-- |  |     |     |__( 5) tcapOmDevelRecvCurrentRejectMistypeComp
-- |  |     |     |__( 6) tcapOmDevelRecvCurrentRejectBadCompStruct
-- |  |     |     |__( 7) tcapOmDevelRecvCurrentRejectUnrecLinkId
-- |  |     |     |__( 8) tcapOmDevelRecvCurrentRejectUnrecIdRetRes
-- |  |     |     |__( 9) tcapOmDevelRecvCurrentRejectUnexpRetRes
-- |  |     |     |__(10) tcapOmDevelRecvCurrentRejectUnrecIdRetErr
-- |  |     |     |__(11) tcapOmDevelRecvCurrentRejectUnexpRetErr
-- |  |     |     |__(12) tcapOmDevelRecvCurrentUsrRejDupInvokeId
-- |  |     |     |__(13) tcapOmDevelRecvCurrentUsrRejUnrecOper
-- |  |     |     |__(14) tcapOmDevelRecvCurrentUsrRejParmInvoke
-- |  |     |     |__(15) tcapOmDevelRecvCurrentUsrRejReleasing
-- |  |     |     |__(16) tcapOmDevelRecvCurrentUsrRejUnexpLinkResp
-- |  |     |     |__(17) tcapOmDevelRecvCurrentUsrRejUnexpLinkOper
-- |  |     |     |__(18) tcapOmDevelRecvCurrentUsrRejUnrecError
-- |  |     |     |__(19) tcapOmDevelRecvCurrentUsrRejUnexpError
-- |  |     |     |__(20) tcapOmDevelRecvCurrentUsrRejParmRetResult
-- |  |     |     |__(21) tcapOmDevelRecvCurrentUsrRejParmRetError
-- |  |     |
-- |  |     |__( 3) tcapOmDevelRecv5minIntTable
-- |  |     |  |__( 1) tcapOmDevelRecv5minIntEntry
-- |  |     |     |__( 1) tcapOmDevelRecv5minIntPabortMessageType
-- |  |     |     |__( 2) tcapOmDevelRecv5minIntPabortIncorrectTp
-- |  |     |     |__( 3) tcapOmDevelRecv5minIntPabortBadTp
-- |  |     |     |__( 4) tcapOmDevelRecv5minIntRejectUnrecComp
-- |  |     |     |__( 5) tcapOmDevelRecv5minIntRejectMistypeComp
-- |  |     |     |__( 6) tcapOmDevelRecv5minIntRejectBadCompStruct
-- |  |     |     |__( 7) tcapOmDevelRecv5minIntRejectUnrecLinkId
-- |  |     |     |__( 8) tcapOmDevelRecv5minIntRejectUnrecIdRetRes
-- |  |     |     |__( 9) tcapOmDevelRecv5minIntRejectUnexpRetRes
-- |  |     |     |__(10) tcapOmDevelRecv5minIntRejectUnrecIdRetErr
-- |  |     |     |__(11) tcapOmDevelRecv5minIntRejectUnexpRetErr
-- |  |     |     |__(12) tcapOmDevelRecv5minIntUsrRejDupInvokeId
-- |  |     |     |__(13) tcapOmDevelRecv5minIntUsrRejUnrecOper
-- |  |     |     |__(14) tcapOmDevelRecv5minIntUsrRejParmInvoke
-- |  |     |     |__(15) tcapOmDevelRecv5minIntUsrRejReleasing
-- |  |     |     |__(16) tcapOmDevelRecv5minIntUsrRejUnexpLinkResp
-- |  |     |     |__(17) tcapOmDevelRecv5minIntUsrRejUnexpLinkOper
-- |  |     |     |__(18) tcapOmDevelRecv5minIntUsrRejUnrecError
-- |  |     |     |__(19) tcapOmDevelRecv5minIntUsrRejUnexpError
-- |  |     |     |__(20) tcapOmDevelRecv5minIntUsrRejParmRetResult
-- |  |     |     |__(21) tcapOmDevelRecv5minIntUsrRejParmRetError
-- |  |     |
-- |  |     |__( 4) tcapOmDevelRecv15minIntTable
-- |  |     |  |__( 1) tcapOmDevelRecv15minIntEntry
-- |  |     |     |__( 1) tcapOmDevelRecv15minIntPabortMessageType
-- |  |     |     |__( 2) tcapOmDevelRecv15minIntPabortIncorrectTp
-- |  |     |     |__( 3) tcapOmDevelRecv15minIntPabortBadTp
-- |  |     |     |__( 4) tcapOmDevelRecv15minIntRejectUnrecComp
-- |  |     |     |__( 5) tcapOmDevelRecv15minIntRejectMistypeComp
-- |  |     |     |__( 6) tcapOmDevelRecv15minIntRejectBadCompStruct
-- |  |     |     |__( 7) tcapOmDevelRecv15minIntRejectUnrecLinkId
-- |  |     |     |__( 8) tcapOmDevelRecv15minIntRejectUnrecIdRetRes
-- |  |     |     |__( 9) tcapOmDevelRecv15minIntRejectUnexpRetRes
-- |  |     |     |__(10) tcapOmDevelRecv15minIntRejectUnrecIdRetErr
-- |  |     |     |__(11) tcapOmDevelRecv15minIntRejectUnexpRetErr
-- |  |     |     |__(12) tcapOmDevelRecv15minIntUsrRejDupInvokeId
-- |  |     |     |__(13) tcapOmDevelRecv15minIntUsrRejUnrecOper
-- |  |     |     |__(14) tcapOmDevelRecv15minIntUsrRejParmInvoke
-- |  |     |     |__(15) tcapOmDevelRecv15minIntUsrRejReleasing
-- |  |     |     |__(16) tcapOmDevelRecv15minIntUsrRejUnexpLinkResp
-- |  |     |     |__(17) tcapOmDevelRecv15minIntUsrRejUnexpLinkOper
-- |  |     |     |__(18) tcapOmDevelRecv15minIntUsrRejUnrecError
-- |  |     |     |__(19) tcapOmDevelRecv15minIntUsrRejUnexpError
-- |  |     |     |__(20) tcapOmDevelRecv15minIntUsrRejParmRetResult
-- |  |     |     |__(21) tcapOmDevelRecv15minIntUsrRejParmRetError
-- |  |     |
-- |  |     |__( 5) tcapOmDevelSentTable
-- |  |     |  |__( 1) tcapOmDevelSentEntry
-- |  |     |     |__( 1) tcapOmDevelSentPabortMessageType
-- |  |     |     |__( 2) tcapOmDevelSentPabortIncorrectTp
-- |  |     |     |__( 3) tcapOmDevelSentPabortBadTp
-- |  |     |     |__( 4) tcapOmDevelSentRejectUnrecComp
-- |  |     |     |__( 5) tcapOmDevelSentRejectMistypeComp
-- |  |     |     |__( 6) tcapOmDevelSentRejectBadCompStruct
-- |  |     |     |__( 7) tcapOmDevelSentRejectUnrecLinkId
-- |  |     |     |__( 8) tcapOmDevelSentRejectUnrecIdRetRes
-- |  |     |     |__( 9) tcapOmDevelSentRejectUnexpRetRes
-- |  |     |     |__(10) tcapOmDevelSentRejectUnrecIdRetErr
-- |  |     |     |__(11) tcapOmDevelSentRejectUnexpRetErr
-- |  |     |     |__(12) tcapOmDevelSentUsrRejDupInvokeId
-- |  |     |     |__(13) tcapOmDevelSentUsrRejUnrecOper
-- |  |     |     |__(14) tcapOmDevelSentUsrRejParmInvoke
-- |  |     |     |__(15) tcapOmDevelSentUsrRejReleasing
-- |  |     |     |__(16) tcapOmDevelSentUsrRejUnexpLinkResp
-- |  |     |     |__(17) tcapOmDevelSentUsrRejUnexpLinkOper
-- |  |     |     |__(18) tcapOmDevelSentUsrRejUnrecError
-- |  |     |     |__(19) tcapOmDevelSentUsrRejUnexpError
-- |  |     |     |__(20) tcapOmDevelSentUsrRejParmRetResult
-- |  |     |     |__(21) tcapOmDevelSentUsrRejParmRetError
-- |  |     |     |__(22) tcapOmDevelSent5minValidIntervals
-- |  |     |     |__(23) tcapOmDevelSent15minValidIntervals
-- |  |     |
-- |  |     |__( 6) tcapOmDevelSentCurrentTable
-- |  |     |  |__( 1) tcapOmDevelSentCurrentEntry
-- |  |     |     |__( 1) tcapOmDevelSentCurrentPabortMessageType
-- |  |     |     |__( 2) tcapOmDevelSentCurrentPabortIncorrectTp
-- |  |     |     |__( 3) tcapOmDevelSentCurrentPabortBadTp
-- |  |     |     |__( 4) tcapOmDevelSentCurrentRejectUnrecComp
-- |  |     |     |__( 5) tcapOmDevelSentCurrentRejectMistypeComp
-- |  |     |     |__( 6) tcapOmDevelSentCurrentRejectBadCompStruct
-- |  |     |     |__( 7) tcapOmDevelSentCurrentRejectUnrecLinkId
-- |  |     |     |__( 8) tcapOmDevelSentCurrentRejectUnrecIdRetRes
-- |  |     |     |__( 9) tcapOmDevelSentCurrentRejectUnexpRetRes
-- |  |     |     |__(10) tcapOmDevelSentCurrentRejectUnrecIdRetErr
-- |  |     |     |__(11) tcapOmDevelSentCurrentRejectUnexpRetErr
-- |  |     |     |__(12) tcapOmDevelSentCurrentUsrRejDupInvokeId
-- |  |     |     |__(13) tcapOmDevelSentCurrentUsrRejUnrecOper
-- |  |     |     |__(14) tcapOmDevelSentCurrentUsrRejParmInvoke
-- |  |     |     |__(15) tcapOmDevelSentCurrentUsrRejReleasing
-- |  |     |     |__(16) tcapOmDevelSentCurrentUsrRejUnexpLinkResp
-- |  |     |     |__(17) tcapOmDevelSentCurrentUsrRejUnexpLinkOper
-- |  |     |     |__(18) tcapOmDevelSentCurrentUsrRejUnrecError
-- |  |     |     |__(19) tcapOmDevelSentCurrentUsrRejUnexpError
-- |  |     |     |__(20) tcapOmDevelSentCurrentUsrRejParmRetResult
-- |  |     |     |__(21) tcapOmDevelSentCurrentUsrRejParmRetError
-- |  |     |
-- |  |     |__( 7) tcapOmDevelSent5minIntTable
-- |  |     |  |__( 1) tcapOmDevelSent5minIntEntry
-- |  |     |     |__( 1) tcapOmDevelSent5minIntPabortMessageType
-- |  |     |     |__( 2) tcapOmDevelSent5minIntPabortIncorrectTp
-- |  |     |     |__( 3) tcapOmDevelSent5minIntPabortBadTp
-- |  |     |     |__( 4) tcapOmDevelSent5minIntRejectUnrecComp
-- |  |     |     |__( 5) tcapOmDevelSent5minIntRejectMistypeComp
-- |  |     |     |__( 6) tcapOmDevelSent5minIntRejectBadCompStruct
-- |  |     |     |__( 7) tcapOmDevelSent5minIntRejectUnrecLinkId
-- |  |     |     |__( 8) tcapOmDevelSent5minIntRejectUnrecIdRetRes
-- |  |     |     |__( 9) tcapOmDevelSent5minIntRejectUnexpRetRes
-- |  |     |     |__(10) tcapOmDevelSent5minIntRejectUnrecIdRetErr
-- |  |     |     |__(11) tcapOmDevelSent5minIntRejectUnexpRetErr
-- |  |     |     |__(12) tcapOmDevelSent5minIntUsrRejDupInvokeId
-- |  |     |     |__(13) tcapOmDevelSent5minIntUsrRejUnrecOper
-- |  |     |     |__(14) tcapOmDevelSent5minIntUsrRejParmInvoke
-- |  |     |     |__(15) tcapOmDevelSent5minIntUsrRejReleasing
-- |  |     |     |__(16) tcapOmDevelSent5minIntUsrRejUnexpLinkResp
-- |  |     |     |__(17) tcapOmDevelSent5minIntUsrRejUnexpLinkOper
-- |  |     |     |__(18) tcapOmDevelSent5minIntUsrRejUnrecError
-- |  |     |     |__(19) tcapOmDevelSent5minIntUsrRejUnexpError
-- |  |     |     |__(20) tcapOmDevelSent5minIntUsrRejParmRetResult
-- |  |     |     |__(21) tcapOmDevelSent5minIntUsrRejParmRetError
-- |  |     |
-- |  |     |__( 8) tcapOmDevelSent15minIntTable
-- |  |        |__( 1) tcapOmDevelSent15minIntEntry
-- |  |           |__( 1) tcapOmDevelSent15minIntPabortMessageType
-- |  |           |__( 2) tcapOmDevelSent15minIntPabortIncorrectTp
-- |  |           |__( 3) tcapOmDevelSent15minIntPabortBadTp
-- |  |           |__( 4) tcapOmDevelSent15minIntRejectUnrecComp
-- |  |           |__( 5) tcapOmDevelSent15minIntRejectMistypeComp
-- |  |           |__( 6) tcapOmDevelSent15minIntRejectBadCompStruct
-- |  |           |__( 7) tcapOmDevelSent15minIntRejectUnrecLinkId
-- |  |           |__( 8) tcapOmDevelSent15minIntRejectUnrecIdRetRes
-- |  |           |__( 9) tcapOmDevelSent15minIntRejectUnexpRetRes
-- |  |           |__(10) tcapOmDevelSent15minIntRejectUnrecIdRetErr
-- |  |           |__(11) tcapOmDevelSent15minIntRejectUnexpRetErr
-- |  |           |__(12) tcapOmDevelSent15minIntUsrRejDupInvokeId
-- |  |           |__(13) tcapOmDevelSent15minIntUsrRejUnrecOper
-- |  |           |__(14) tcapOmDevelSent15minIntUsrRejParmInvoke
-- |  |           |__(15) tcapOmDevelSent15minIntUsrRejReleasing
-- |  |           |__(16) tcapOmDevelSent15minIntUsrRejUnexpLinkResp
-- |  |           |__(17) tcapOmDevelSent15minIntUsrRejUnexpLinkOper
-- |  |           |__(18) tcapOmDevelSent15minIntUsrRejUnrecError
-- |  |           |__(19) tcapOmDevelSent15minIntUsrRejUnexpError
-- |  |           |__(20) tcapOmDevelSent15minIntUsrRejParmRetResult
-- |  |           |__(21) tcapOmDevelSent15minIntUsrRejParmRetError
-- |  |
-- |  |__(2) tcapOmScalars
-- |  |  |__( 1) tcapOm1stAndIntervalActivate
-- |  |  |__( 2) tcapOm1stAndIntervalDeactivate
-- |  |  |__( 3) tcapOm5MinActivate
-- |  |  |__( 4) tcapOm5MinDeaActivate
-- |  |  |__( 5) tcapOm15MinActivate
-- |  |  |__( 6) tcapOm15MinDeaActivate
-- |  |  |__( 7) tcapOmInterval
-- |  |  |__( 8) tcapOmDiscontinuityTime
-- |  |  |__( 9) tcapOmTimeStamp
-- |  |  |__(10) tcapOm5MinMaxIntervals
-- |  |  |__(11) tcapOm15MinMaxIntervals
-- |  |
-- |  |__(3) tcapOmNotifs
-- |  |  |__( 1) tcapOmMessageType
-- |  |
-- |  |__(4) tcapOmOids
-- |
-- |__(2) tcapOmConformance
--    |__(1) tcapOmCompliance
--    |__(2) tcapOmGroups
--    |__(3) tcapOmCapabilities


-- 5 TC monitoring and measurements
-- 5.1 General
--
-- Table 13 describes the TC utilization measurements.
-- Table 14 describes the TC error performance and stability 
-- measurements.
--
-- 5.2 Table 13
-- TC utilization measurements are listed in Table 13.
--
-- 5.2.1 Item 13.7 is a count of all new transactions in the interval, 
-- including those closed immediately by an ABORT after the opening 
-- BEGIN.
--
-- Item 13.8 is a measurement of the mean number of open transactions in 
-- the interval.  An open transaction is one to which a transaction 
-- identity has been allocated, and this identity is not yet frozen.
--
-- Measurement 13.10 (the cummulative mean duration of transactions) is 
-- the mean duration for all transactions that began between the start 
-- of measurements and the end of the measurement interval.  It includes 
-- the time from opening the transaction to the end of the interval, for 
-- those transactions that did not close during the interval.  Here, the 
-- trasnaction duration ia defined as the time from allocation of the 
-- transaction identity to freezing it.
--
-- See clause 5.2.2 for more information.
--
-- 5.2.2  An example of collection of measurements
-- A model to describe the collection of Items 13.8 and 13.10, used to 
-- explain possible measurement techniques by which is not intended to 
-- specify implementation, is as follows:
--
-- Suppose a system collects measurements in a number 's' of 
-- 'measurement centres'.  A measurement centre can be defeind as a 
-- point in the system that launches, or observes directly the launching 
-- of, a TC transaction, and it also either finishes the transaction, or 
-- observes directly its passing.  This point is assumed also to be able 
-- to count the number of free, frozen and thawing transaction 
-- identities with which it is concerned.  Thus in a multiprocessor 
-- system, there might be one (or more) measurement centre(s) per 
-- processor per Application Entity definition, which is responsible for 
-- launching all the transactions (instances) of that Application 
-- Entity.  For mesaurements collected by all the centers to refer to 
-- the same interval, it is assumed that each centre has a clock which 
-- 'ticks' at a rate sufficiently high to be able to measure with the 
-- required precision.  The clocks are also assumed to be syncrhonized 
-- to within one clock tick (if they are not, further calculations would 
-- be needed to determin the overall precision).  If necessary, each 
-- centre would have an 'active' set of measurements, and another set 
-- taken in the previous measurement interval, which might be awaiting 
-- collection.
--
-- Measurement 13.8 is the mean number of open transactions, estimated 
-- over a measurement interval, observations are taken at each new 
-- transaction during the interval.
-- 
-- The measurements can be over the whole Application Entity, or at 
-- teach centre, and then accumulated for the whole Application Entity.
--
-- Define a cummulative total 'Ac' of open transactions (this is set to 
-- 0 at the start of each measurement interval), and define 'a' as the 
-- number of open transactions at any time.  'a' is set to 0 at system 
-- initialisation, it is incremented at each transaction arrival, and 
-- decremented when each transaction leaves.  Define 'n' as the number 
-- of new transactions arriving during the measurement interval (which 
-- is set to '0' at the start of each interval).
--
-- When a transaction arrives, set:
--
--	Ac = Ac + a; a = a + 1; n = n + 1;
--
-- When a transction finishes, set:
--
--	a = a - 1;
--
-- When the reporting event occurs at the end of the measurement 
-- interval, report 'Ac', 'n' and 'a'.  Then initialize 'Ac' and 'n' to 
-- 0.
--
-- The mean number of open transactions during the interval for this 
-- measurement center is 'Ac/n', for several centers use the expression 
-- SUM(Ac)/SUM(n).
--
-- Item 13.10, the cummulative mean duration of transactions, requires 
-- that those transactions that were open at the start of measurements 
-- (but not those open at the start of the interval), be excluded from 
-- the measurements.  (It would be possible to include those open at the 
-- start of measurements, if some estimate of their age could be made, 
-- but for simplicity this is not considered here.)  To do this, the 
-- transaction record itself needs an indicator equal to an overall 
-- (measurement center) value set when measurements start, and unset 
-- when measurements finish, to exclude transactions that started before 
-- measurements did.
--
-- For this measurement, the following variables are kept at each 
-- measurement centre:
--
--  - A running cummulative transaction length time 'Tc'.  This is set to 
--    0 at the start of measurements, but is kept running during the 
--    successive measurement intervals.
--
--  - A cummulative transaction arrival counter 'Rc'.  This is 
--    initialized at the start of measurements, and is kept running 
--    during the successive measurement intervals.
--
--  - A counter 'time' which is set to 0 at the start of measurements, 
--    and is incremented by 1 for each clock tick.
--
-- The measurement is performed as follows:
--
--  1. when a transaction arrives, set 'Tc = Tc - time; Rc = Rc + 1;'
--
--  2. when a transaction finishes, if it started at or after the start 
--     of measurements, set 'Tc = Tc + time;'
--
--  3. at the end of the measurement interval, report 'Tc', 'Rc' and use 
--     'a' from item 13.8 (but with 'a' initialized at the start of 
--     measurements).  The mean duration of transactions measured in 
--     this interval is (Tc + a.time)/Rc for the centre, with 
--     appropriate extensions for the overall mean.
--
-- A possible alternative measurement could be the mean duration of new 
-- transaction occuring in the interval (providing those transaction 
-- open at the start of the interval, and long transactions, where 
-- catered-for separately).  If this were required, then some form of 
-- 'phase' indication would be required to be kept in each transaction 
-- record, sot that the finished of a 'new' transaction could be 
-- distinguished from the finish of a transaction that was open at teh 
-- start of the interval.  Then 'Tc', 'Rc', 'time' and 'a' would be kept 
-- relative to the interval, with them all set to 0 at its start.
--
-- 5.3  Table 14
-- TC error performance and stability measurements are listed in Table 
-- 14.  Measurements with detailed reasons can be found in Annex A, 
-- these are more appropriate during development of a service, rather 
-- than for operational use.
--
-- 5.3.1  Measurements 14.4 e) (resource limitation) can indicate a 
-- local TC resource problem, and requires the maintenance staff to be 
-- notified.
--
-- Measurement 14.4 d) (unrecognized transaction identity) might 
-- indicate problems of an operational nature.  Possible examples are:
--
-- - because of SCCP routing problems, the local TC has received a 
--   message for a transcation that never existed;
--
-- - messages arriving for transactions that have timed-out and been 
--   closed by the application.
--
-- To allow the source of the error to be traced, the originating 
-- address of the received message should be logged to for later 
-- retrieval.
--
-- At the first report, sufficient information should be provided to 
-- establish the fault's location.
--
-- 6.5  Transaction Capabilities (TCs)
-- 6.5.1 TC fault management measurements
-- Problem isolation during development may be assisted by measurements 
-- that indicate the reason for protocol error being reported.
--
-- Measurements (those of which are not of resource limitation are in 
-- Annex A)
--
-- - protocol error detected in transaction portion (Items 14.1 a) to e) 
--   and 14.4 a) to e));
-- - protocol error detected in component portion (Iterms 14.2 a) to h) 
--   and 14.5 a) to h));
-- - TC user generated problems (Items 14.3 a) to k) and 14.6 a) to k));
--
-- During operation, resource limtation measurements 14.1 e), 14.3 d), 
-- 14.4 e) and 14.6 d) are pertinent.  Also, items 14.7 through 14.11 
-- are counts for protocol errors, and provide a summary for these items 
-- in Annex A.
--
-- The purpose of these measurements is to monitor abnormal events of an 
-- operational nature, or peaks in errors that affect the quality of 
-- service offered to the TC users.  They also provide the means to 
-- collect additional information that allows the source of the errors 
-- to be traced.  To this end, a log of notifications which is 
-- retrievable on command (e.g. from an Operations System) could be 
-- kept.
--
-- Measurements 14.3 d) and 14.6 d) (resource limitations) indicate TC 
-- user resource problems when processing an invoked operation.  They 
-- are included in the TC measurements as they might be applciable to a 
-- number of different TC users.
--
-- 6.5.2  TC performance
-- The loading of TC resources may be indicated through the volume of 
-- messages and components handled.  They dynamic loading of TC 
-- resources can be observed by counting the number of new transactions 
-- during an interval, the mean number of open transactions during an 
-- interval indicates the static loading of TC.  The cummulative mean 
-- duration of transactions can be used for dimensioning TC an TC user 
-- resources, and to indicate operational problems.
--
-- Measurements
-- - total number of TC messages sent by the node (by message type) 
--   (item 13.1);
-- - total number of TC message received by the node (by message type) 
--   (item 13.2);
-- - total number of components sent by the node (item 13.3);
-- - total number of components received by the node (item 13.4);
-- - number of new transactions during an interval (item 13.6);
-- - mean number of open transactions during an interval (item 13.7);
-- - cummulative mean duration of transactions (item 13.9);
-- - maximum number of open transcation during an interval (item 13.10).
--
-- Also, an Operations System can use a measurement to activate this set 
-- of measurements:
-- - a report when the number of open transactions is greater than a 
--   pre-defined threshold (iterm 13.11).
--
-- Items 13.10 and 13.11 are equivalent to the X.738 minMaxScanner and 
-- Q.822 gaugeThreshold respectively, but they utilize an internal 
-- counter per Application Entity that is not itself reported, and hence 
-- is not given as a measurement (this is the current number of open 
-- transaction identities for which a 'snapshot' of open transactions at 
-- the measurement time is not necessarily representative of the 
-- performance of Application Entity's transactions throughout the 
-- measurement interval).  For an example of a possible method of 
-- implementing these measurements, see 5.2.1.


-- =============================================================================

tcapOmNodeTable OBJECT-TYPE
    SYNTAX	SEQUENCE OF TcapOmNodeEntry
    MAX-ACCESS	not-accessible
    STATUS	current
    DESCRIPTION
	""
    REFERENCE
	""
    ::= { tcapOmNodeMeasurements 1 }

tcapOmNodeEntry OBJECT-TYPE
    SYNTAX	TcapOmNodeEntry
    MAX-ACCESS	not-accessible
    STATUS	current
    DESCRIPTION
	""
    REFERENCE
	""
    INDEX	{
	sccpNetworkEntityId -- shared index
    }
    ::= { tcapOmNodeTable 1 }

TcapOmNodeEntry ::= SEQUENCE {
    tcapOmNodeMessagesSent			Counter,
    tcapOmNodeMessagesRecv			Counter,
    tcapOmNodeComponentsSent			Counter,
    tcapOmNodeComponentsRecv			Counter,
    tcapOmNode5minValidIntervals		HCPerfValidIntervals,
    tcapOmNode15minValidIntervals		HCPerfValidIntervals
}

tcapOmNodeMessagesSent OBJECT-TYPE
    SYNTAX	Counter
    UNITS	"Messages"
    MAX-ACCESS	read-only
    STATUS	current
    DESCRIPTION
	"The total number of TC messages sent by the node, irrespective 
	 of message type.  This is an obligatory measurement that is 
	 taken on a 5 and 15 minute interval basis."
    REFERENCE
	"ITU-T Rec. Q.752 (06/97) Table 13, Item 13.1 bis"
    ::= { tcapOmNodeEntry 1 }

tcapOmNodeMessagesRecv OBJECT-TYPE
    SYNTAX	Counter
    UNITS	"Messages"
    MAX-ACCESS	read-only
    STATUS	current
    DESCRIPTION
	"The total number of TC messages received by the node, 
	 irrespective of message type.  This is an obligatory 
	 measurement that is taken on a 5 and 15 minute interval basis."
    REFERENCE
	"ITU-T Rec. Q.752 (06/97) Table 13, Item 13.2 bis"
    ::= { tcapOmNodeEntry 2 }

tcapOmNodeComponentsSent OBJECT-TYPE
    SYNTAX	Counter
    UNITS	"Components"
    MAX-ACCESS	read-only
    STATUS	current
    DESCRIPTION
	"The total number of components sent by the node.  This is a 
	 non-obligatory measurement taken on a 5 and 15 minute interval 
	 basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.3.
	 ITU-T Rec. Q.772 Clause 3.1."
    ::= { tcapOmNodeEntry 3 }

tcapOmNodeComponentsRecv OBJECT-TYPE
    SYNTAX	Counter
    UNITS	"Components"
    MAX-ACCESS	read-only
    STATUS	current
    DESCRIPTION
	"The total number of components received by the node.  This is a 
	 non-obligatory measurement taken on a 5 and 15 minute interval 
	 basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.4.
	 ITU-T Rec. Q.772 Clause 3.1."
    ::= { tcapOmNodeEntry 4 }

tcapOmNode5minValidIntervals OBJECT-TYPE
    SYNTAX	HCPerfValidIntervals
    MAX-ACCESS	read-only
    STATUS	current
    DESCRIPTION
	"Indicates the number of valid 5-minute intervals of historical 
	 data that is collected int the corresonding history data table."
    ::= { tcapOmNodeEntry 5 }

tcapOmNode15minValidIntervals OBJECT-TYPE
    SYNTAX	HCPerfValidIntervals
    MAX-ACCESS	read-only
    STATUS	current
    DESCRIPTION
	"Indicates the number of valid 15-minute intervals of historical 
	 data that is collected in the corresponding history data 
	 table."
    ::= { tcapOmNodeEntry 6 }

-- =============================================================================

tcapOmNodeCurrentTable OBJECT-TYPE
    SYNTAX	SEQUENCE OF TcapOmNodeCurrentEntry
    MAX-ACCESS	not-accessible
    STATUS	current
    DESCRIPTION
	""
    REFERENCE
	""
    ::= { tcapOmNodeMeasurements 2 }

tcapOmNodeCurrentEntry OBJECT-TYPE
    SYNTAX	TcapOmNodeCurrentEntry
    MAX-ACCESS	not-accessible
    STATUS	current
    DESCRIPTION
	""
    REFERENCE
	""
    INDEX	{
	sccpNetworkEntityId -- shared index
    }
    ::= { tcapOmNodeCurrentTable 1 }

TcapOmNodeCurrentEntry ::= SEQUENCE {
    tcapOmNodeCurrentMessagesSent		PerfCurrentCount,
    tcapOmNodeCurrentMessagesRecv		PerfCurrentCount,
    tcapOmNodeCurrentComponentsSent		PerfCurrentCount,
    tcapOmNodeCurrentComponentsRecv		PerfCurrentCount
}

tcapOmNodeCurrentMessagesSent OBJECT-TYPE
    SYNTAX	PerfCurrentCount
    UNITS	"Messages"
    MAX-ACCESS	read-only
    STATUS	current
    DESCRIPTION
	"The total number of TC messages sent by the node, irrespective 
	 of message type.  This is an obligatory measurement that is 
	 taken on a 5 and 15 minute interval basis."
    REFERENCE
	"ITU-T Rec. Q.752 (06/97) Table 13, Item 13.1 bis"
    ::= { tcapOmNodeCurrentEntry 1 }

tcapOmNodeCurrentMessagesRecv OBJECT-TYPE
    SYNTAX	PerfCurrentCount
    UNITS	"Messages"
    MAX-ACCESS	read-only
    STATUS	current
    DESCRIPTION
	"The total number of TC messages received by the node, 
	 irrespective of message type.  This is an obligatory 
	 measurement that is taken on a 5 and 15 minute interval basis."
    REFERENCE
	"ITU-T Rec. Q.752 (06/97) Table 13, Item 13.2 bis"
    ::= { tcapOmNodeCurrentEntry 2 }

tcapOmNodeCurrentComponentsSent OBJECT-TYPE
    SYNTAX	PerfCurrentCount
    UNITS	"Components"
    MAX-ACCESS	read-only
    STATUS	current
    DESCRIPTION
	"The total number of components sent by the node.  This is a 
	 non-obligatory measurement taken on a 5 and 15 minute interval 
	 basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.3.
	 ITU-T Rec. Q.772 Clause 3.1."
    ::= { tcapOmNodeCurrentEntry 3 }

tcapOmNodeCurrentComponentsRecv OBJECT-TYPE
    SYNTAX	PerfCurrentCount
    UNITS	"Components"
    MAX-ACCESS	read-only
    STATUS	current
    DESCRIPTION
	"The total number of components received by the node.  This is a 
	 non-obligatory measurement taken on a 5 and 15 minute interval 
	 basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.4.
	 ITU-T Rec. Q.772 Clause 3.1."
    ::= { tcapOmNodeCurrentEntry 4 }

-- =============================================================================

tcapOmNode5minIntTable OBJECT-TYPE
    SYNTAX	SEQUENCE OF TcapOmNode5minIntEntry
    MAX-ACCESS	not-accessible
    STATUS	current
    DESCRIPTION
	""
    REFERENCE
	""
    ::= { tcapOmNodeMeasurements 3 }

tcapOmNode5minIntEntry OBJECT-TYPE
    SYNTAX	TcapOmNode5minIntEntry
    MAX-ACCESS	not-accessible
    STATUS	current
    DESCRIPTION
	""
    REFERENCE
	""
    INDEX	{
	sccpNetworkEntityId,	-- shared index
	tcapOmInterval		-- shared index
    }
    ::= { tcapOmNode5minIntTable 1 }

TcapOmNode5minIntEntry ::= SEQUENCE {
    tcapOmNode5minIntMessagesSent		PerfIntervalCount,
    tcapOmNode5minIntMessagesRecv		PerfIntervalCount,
    tcapOmNode5minIntComponentsSent		PerfIntervalCount,
    tcapOmNode5minIntComponentsRecv		PerfIntervalCount
}

tcapOmNode5minIntMessagesSent OBJECT-TYPE
    SYNTAX	PerfIntervalCount
    UNITS	"Messages"
    MAX-ACCESS	read-only
    STATUS	current
    DESCRIPTION
	"The total number of TC messages sent by the node, irrespective 
	 of message type.  This is an obligatory measurement that is 
	 taken on a 5 and 15 minute interval basis."
    REFERENCE
	"ITU-T Rec. Q.752 (06/97) Table 13, Item 13.1 bis"
    ::= { tcapOmNode5minIntEntry 1 }

tcapOmNode5minIntMessagesRecv OBJECT-TYPE
    SYNTAX	PerfIntervalCount
    UNITS	"Messages"
    MAX-ACCESS	read-only
    STATUS	current
    DESCRIPTION
	"The total number of TC messages received by the node, 
	 irrespective of message type.  This is an obligatory 
	 measurement that is taken on a 5 and 15 minute interval basis."
    REFERENCE
	"ITU-T Rec. Q.752 (06/97) Table 13, Item 13.2 bis"
    ::= { tcapOmNode5minIntEntry 2 }

tcapOmNode5minIntComponentsSent OBJECT-TYPE
    SYNTAX	PerfIntervalCount
    UNITS	"Components"
    MAX-ACCESS	read-only
    STATUS	current
    DESCRIPTION
	"The total number of components sent by the node.  This is a 
	 non-obligatory measurement taken on a 5 and 15 minute interval 
	 basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.3.
	 ITU-T Rec. Q.772 Clause 3.1."
    ::= { tcapOmNode5minIntEntry 3 }

tcapOmNode5minIntComponentsRecv OBJECT-TYPE
    SYNTAX	PerfIntervalCount
    UNITS	"Components"
    MAX-ACCESS	read-only
    STATUS	current
    DESCRIPTION
	"The total number of components received by the node.  This is a 
	 non-obligatory measurement taken on a 5 and 15 minute interval 
	 basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.4.
	 ITU-T Rec. Q.772 Clause 3.1."
    ::= { tcapOmNode5minIntEntry 4 }


-- =============================================================================

tcapOmNode15minIntTable OBJECT-TYPE
    SYNTAX	SEQUENCE OF TcapOmNode15minIntEntry
    MAX-ACCESS	not-accessible
    STATUS	current
    DESCRIPTION
	""
    REFERENCE
	""
    ::= { tcapOmNodeMeasurements 4 }

tcapOmNode15minIntEntry OBJECT-TYPE
    SYNTAX	TcapOmNode15minIntEntry
    MAX-ACCESS	not-accessible
    STATUS	current
    DESCRIPTION
	""
    REFERENCE
	""
    INDEX	{
	sccpNetworkEntityId,	-- shared index
	tcapOmInterval		-- shared index
    }
    ::= { tcapOmNode15minIntTable 1 }

TcapOmNode15minIntEntry ::= SEQUENCE {
    tcapOmNode15minIntMessagesSent		PerfIntervalCount,
    tcapOmNode15minIntMessagesRecv		PerfIntervalCount,
    tcapOmNode15minIntComponentsSent		PerfIntervalCount,
    tcapOmNode15minIntComponentsRecv		PerfIntervalCount
}

tcapOmNode15minIntMessagesSent OBJECT-TYPE
    SYNTAX	PerfIntervalCount
    UNITS	"Messages"
    MAX-ACCESS	read-only
    STATUS	current
    DESCRIPTION
	"The total number of TC messages sent by the node, irrespective 
	 of message type.  This is an obligatory measurement that is 
	 taken on a 5 and 15 minute interval basis."
    REFERENCE
	"ITU-T Rec. Q.752 (06/97) Table 13, Item 13.1 bis"
    ::= { tcapOmNode15minIntEntry 1 }

tcapOmNode15minIntMessagesRecv OBJECT-TYPE
    SYNTAX	PerfIntervalCount
    UNITS	"Messages"
    MAX-ACCESS	read-only
    STATUS	current
    DESCRIPTION
	"The total number of TC messages received by the node, 
	 irrespective of message type.  This is an obligatory 
	 measurement that is taken on a 5 and 15 minute interval basis."
    REFERENCE
	"ITU-T Rec. Q.752 (06/97) Table 13, Item 13.2 bis"
    ::= { tcapOmNode15minIntEntry 2 }

tcapOmNode15minIntComponentsSent OBJECT-TYPE
    SYNTAX	PerfIntervalCount
    UNITS	"Components"
    MAX-ACCESS	read-only
    STATUS	current
    DESCRIPTION
	"The total number of components sent by the node.  This is a 
	 non-obligatory measurement taken on a 5 and 15 minute interval 
	 basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.3.
	 ITU-T Rec. Q.772 Clause 3.1."
    ::= { tcapOmNode15minIntEntry 3 }

tcapOmNode15minIntComponentsRecv OBJECT-TYPE
    SYNTAX	PerfIntervalCount
    UNITS	"Components"
    MAX-ACCESS	read-only
    STATUS	current
    DESCRIPTION
	"The total number of components received by the node.  This is a 
	 non-obligatory measurement taken on a 5 and 15 minute interval 
	 basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.4.
	 ITU-T Rec. Q.772 Clause 3.1."
    ::= { tcapOmNode15minIntEntry 4 }


-- =============================================================================

tcapOmMsgsTable OBJECT-TYPE
    SYNTAX	SEQUENCE OF TcapOmMsgsEntry
    MAX-ACCESS	not-accessible
    STATUS	current
    DESCRIPTION
	""
    REFERENCE
	""
    ::= { tcapOmMsgMeasurements 1 }

tcapOmMsgsEntry OBJECT-TYPE
    SYNTAX	TcapOmMsgsEntry
    MAX-ACCESS	not-accessible
    STATUS	current
    DESCRIPTION
	""
    REFERENCE
	""
    INDEX	{
	sccpNetworkEntityId,	-- shared index
	tcapOmMessageType	-- shared index
    }
    ::= { tcapOmMsgsTable 1 }

TcapOmMsgsEntry ::= SEQUENCE {
    tcapOmMsgsMessagesSent			Counter,
    tcapOmMsgsMessagesRecv			Counter,
    tcapOmMsgs5minValidIntervals		HCPerfValidIntervals,
    tcapOmMsgs15minValidIntervals		HCPerfValidIntervals
}

tcapOmMsgsMessagesSent OBJECT-TYPE
    SYNTAX	Counter
    UNITS	"Messages per Message Type"
    MAX-ACCESS	read-only
    STATUS	current
    DESCRIPTION
	"The total number of TC messages sent by the node, by message 
	 type.  This is a non-obligatory measurement taken on a 5 and 15 
	 minute interval basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.1"
    ::= { tcapOmMsgsEntry 1 }

tcapOmMsgsMessagesRecv OBJECT-TYPE
    SYNTAX	Counter
    UNITS	"Messages per Message Type"
    MAX-ACCESS	read-only
    STATUS	current
    DESCRIPTION
	"The total number of TC messages received by the node, by 
	 message type.  This is a non-obligatory measurement taken on a 
	 5 and 15 minute interval basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.2"
    ::= { tcapOmMsgsEntry 2 }

tcapOmMsgs5minValidIntervals OBJECT-TYPE
    SYNTAX	HCPerfValidIntervals
    MAX-ACCESS	read-only
    STATUS	current
    DESCRIPTION
	"Indicates the number of valid 5-minute intervals of historical 
	 data that is collected int the corresonding history data table."
    ::= { tcapOmMsgsEntry 3 }

tcapOmMsgs15minValidIntervals OBJECT-TYPE
    SYNTAX	HCPerfValidIntervals
    MAX-ACCESS	read-only
    STATUS	current
    DESCRIPTION
	"Indicates the number of valid 15-minute intervals of historical 
	 data that is collected in the corresponding history data 
	 table."
    ::= { tcapOmMsgsEntry 4 }

-- =============================================================================

tcapOmMsgsCurrentTable OBJECT-TYPE
    SYNTAX	SEQUENCE OF TcapOmMsgsCurrentEntry
    MAX-ACCESS	not-accessible
    STATUS	current
    DESCRIPTION
	""
    REFERENCE
	""
    ::= { tcapOmMsgMeasurements 2 }

tcapOmMsgsCurrentEntry OBJECT-TYPE
    SYNTAX	TcapOmMsgsCurrentEntry
    MAX-ACCESS	not-accessible
    STATUS	current
    DESCRIPTION
	""
    REFERENCE
	""
    INDEX	{
	sccpNetworkEntityId,	-- shared index
	tcapOmMessageType	-- shared index
    }
    ::= { tcapOmMsgsCurrentTable 1 }

TcapOmMsgsCurrentEntry ::= SEQUENCE {
    tcapOmMsgsCurrentMessagesSent		PerfCurrentCount,
    tcapOmMsgsCurrentMessagesRecv		PerfCurrentCount
}

tcapOmMsgsCurrentMessagesSent OBJECT-TYPE
    SYNTAX	PerfCurrentCount
    UNITS	"Messages per Message Type"
    MAX-ACCESS	read-only
    STATUS	current
    DESCRIPTION
	"The total number of TC messages sent by the node, by message 
	 type.  This is a non-obligatory measurement taken on a 5 and 15 
	 minute interval basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.1"
    ::= { tcapOmMsgsCurrentEntry 1 }

tcapOmMsgsCurrentMessagesRecv OBJECT-TYPE
    SYNTAX	PerfCurrentCount
    UNITS	"Messages per Message Type"
    MAX-ACCESS	read-only
    STATUS	current
    DESCRIPTION
	"The total number of TC messages received by the node, by 
	 message type.  This is a non-obligatory measurement taken on a 
	 5 and 15 minute interval basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.2"
    ::= { tcapOmMsgsCurrentEntry 2 }

-- =============================================================================

tcapOmMsgs5minIntTable OBJECT-TYPE
    SYNTAX	SEQUENCE OF TcapOmMsgs5minIntEntry
    MAX-ACCESS	not-accessible
    STATUS	current
    DESCRIPTION
	""
    REFERENCE
	""
    ::= { tcapOmMsgMeasurements 3 }

tcapOmMsgs5minIntEntry OBJECT-TYPE
    SYNTAX	TcapOmMsgs5minIntEntry
    MAX-ACCESS	not-accessible
    STATUS	current
    DESCRIPTION
	""
    REFERENCE
	""
    INDEX	{
	sccpNetworkEntityId,	-- shared index
	tcapOmMessageType,	-- shared index
	tcapOmInterval		-- shared index
    }
    ::= { tcapOmMsgs5minIntTable 1 }

TcapOmMsgs5minIntEntry ::= SEQUENCE {
    tcapOmMsgs5minIntMessagesSent		PerfIntervalCount,
    tcapOmMsgs5minIntMessagesRecv		PerfIntervalCount
}

tcapOmMsgs5minIntMessagesSent OBJECT-TYPE
    SYNTAX	PerfIntervalCount
    UNITS	"Messages per Message Type"
    MAX-ACCESS	read-only
    STATUS	current
    DESCRIPTION
	"The total number of TC messages sent by the node, by message 
	 type.  This is a non-obligatory measurement taken on a 5 and 15 
	 minute interval basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.1"
    ::= { tcapOmMsgs5minIntEntry 1 }

tcapOmMsgs5minIntMessagesRecv OBJECT-TYPE
    SYNTAX	PerfIntervalCount
    UNITS	"Messages per Message Type"
    MAX-ACCESS	read-only
    STATUS	current
    DESCRIPTION
	"The total number of TC messages received by the node, by 
	 message type.  This is a non-obligatory measurement taken on a 
	 5 and 15 minute interval basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.2"
    ::= { tcapOmMsgs5minIntEntry 2 }


-- =============================================================================

tcapOmMsgs15minIntTable OBJECT-TYPE
    SYNTAX	SEQUENCE OF TcapOmMsgs15minIntEntry
    MAX-ACCESS	not-accessible
    STATUS	current
    DESCRIPTION
	""
    REFERENCE
	""
    ::= { tcapOmMsgMeasurements 4 }

tcapOmMsgs15minIntEntry OBJECT-TYPE
    SYNTAX	TcapOmMsgs15minIntEntry
    MAX-ACCESS	not-accessible
    STATUS	current
    DESCRIPTION
	""
    REFERENCE
	""
    INDEX	{
	sccpNetworkEntityId,	-- shared index
	tcapOmMessageType,	-- shared index
	tcapOmInterval		-- shared index
    }
    ::= { tcapOmMsgs15minIntTable 1 }

TcapOmMsgs15minIntEntry ::= SEQUENCE {
    tcapOmMsgs15minIntMessagesSent		PerfIntervalCount,
    tcapOmMsgs15minIntMessagesRecv		PerfIntervalCount
}

tcapOmMsgs15minIntMessagesSent OBJECT-TYPE
    SYNTAX	PerfIntervalCount
    UNITS	"Messages per Message Type"
    MAX-ACCESS	read-only
    STATUS	current
    DESCRIPTION
	"The total number of TC messages sent by the node, by message 
	 type.  This is a non-obligatory measurement taken on a 5 and 15 
	 minute interval basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.1"
    ::= { tcapOmMsgs15minIntEntry 1 }

tcapOmMsgs15minIntMessagesRecv OBJECT-TYPE
    SYNTAX	PerfIntervalCount
    UNITS	"Messages per Message Type"
    MAX-ACCESS	read-only
    STATUS	current
    DESCRIPTION
	"The total number of TC messages received by the node, by 
	 message type.  This is a non-obligatory measurement taken on a 
	 5 and 15 minute interval basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.2"
    ::= { tcapOmMsgs15minIntEntry 2 }


-- =============================================================================

tcapOmAETable OBJECT-TYPE
    SYNTAX	SEQUENCE OF TcapOmAEEntry
    MAX-ACCESS	not-accessible
    STATUS	current
    DESCRIPTION
	""
    REFERENCE
	""
    ::= { tcapOmAEMeasurements 1 }

tcapOmAEEntry OBJECT-TYPE
    SYNTAX	TcapOmAEEntry
    MAX-ACCESS	not-accessible
    STATUS	current
    DESCRIPTION
	""
    REFERENCE
	""
    INDEX	{
	tcapApplicationSubsystemId, -- shared index
	tcapApplicationEntityId	    -- shared index
    }
    ::= { tcapOmAETable 1 }

TcapOmAEEntry ::= SEQUENCE {
    tcapOmAEMeasurementDeleted			Counter,
    tcapOmAENewTransactions			Counter,
    tcapOmAEMeanOpenTransactions		Counter,
    tcapOmAENotUsed				Counter,
    tcapOmAECummulativeMeanDuration		Counter,
    tcapOmAEMaximumOpenTranactions		Counter,
    tcapOmAEThresholdExceeded			Counter,
    tcapOmAE5minValidIntervals			HCPerfValidIntervals,
    tcapOmAE15minValidIntervals			HCPerfValidIntervals
}

tcapOmAEMeasurementDeleted OBJECT-TYPE
    SYNTAX	Counter
    MAX-ACCESS	read-only
    STATUS	deprecated
    DESCRIPTION
	"Measurement deleted."
    REFERENCE
	"ITU-T Rec. Q.752 (06/97) Table 13, Item 13.5"
    ::= { tcapOmAEEntry 1 }

tcapOmAENewTransactions OBJECT-TYPE
    SYNTAX	Counter
    UNITS	"Transactions per Application Entity"
    MAX-ACCESS	read-only
    STATUS	current
    DESCRIPTION
	"The number of new transactions in this interval.  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.6"
    ::= { tcapOmAEEntry 2 }

tcapOmAEMeanOpenTransactions OBJECT-TYPE
    SYNTAX	Counter
    UNITS	"Transactions per Application Entity"
    MAX-ACCESS	read-only
    STATUS	current
    DESCRIPTION
	"The mean number of open transaction identities in this 
	 interval (measured at the start of transactions).  This is a 
	 non-obligatory measurement taken on a 5-minute interval 
	 (provisional) basis.

	 This is a count of all new transactions in the interval, 
	 including those closed immediately by an ABORT after the 
	 opening BEGIN.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.7"
    ::= { tcapOmAEEntry 3 }

tcapOmAENotUsed OBJECT-TYPE
    SYNTAX	Counter
    MAX-ACCESS	read-only
    STATUS	deprecated
    DESCRIPTION
	"Not used.
	 
	 Item 13.8 is a measurement of the mean number of open 
	 transactions in the interval.  An open transaction is one to 
	 which a transaction identity has been allocated, and this 
	 identity is not yet frozen."
    REFERENCE
	"ITU-T Rec. Q.752 (06/97) Table 13, Item 13.8"
    ::= { tcapOmAEEntry 4 }

tcapOmAECummulativeMeanDuration OBJECT-TYPE
    SYNTAX	Counter
    UNITS	"Mean Seconds per Transaction per Application Entity"
    MAX-ACCESS	read-only
    STATUS	current
    DESCRIPTION
	"The cummulative mean duration of transactions.  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.9"
    ::= { tcapOmAEEntry 5 }

tcapOmAEMaximumOpenTranactions OBJECT-TYPE
    SYNTAX	Counter
    UNITS	"Transactions per Application Entity"
    MAX-ACCESS	read-only
    STATUS	current
    DESCRIPTION
	"The maximum number of open transaction identities during 
	 this interval.  This is a non-obligatory measurement taken on a 
	 5-minute interval (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems.
	 
	 Measurement 13.10 (the cummulative mean duration of 
	 transactions) is the mean duration for all transactions that 
	 began between the start of measurements and the end of the 
	 measurement interval.  It includes the time from opening the 
	 transaction to the end of the interval, for those transactions 
	 that did not close during the interval.  Here, the trasnaction 
	 duration ia defined as the time from allocation of the 
	 transaction identity to freezing it.
	"
    REFERENCE
	"ITU-T Rec. Q.752 (06/97) Table 13, Item 13.10"
    ::= { tcapOmAEEntry 6 }

tcapOmAEThresholdExceeded OBJECT-TYPE
    SYNTAX	Counter
    UNITS	"Events per Application Entity"
    MAX-ACCESS	read-only
    STATUS	current
    DESCRIPTION
	"The number of open transaction identities greater than an 
	 Application Entity pre-defined threshold.  This is a 
	 non-obligatory measurement signalled on an on-occurence basis."
    REFERENCE
	"ITU-T Rec. Q.752 (06/97) Table 13, Item 13.11"
    ::= { tcapOmAEEntry 7 }

tcapOmAE5minValidIntervals OBJECT-TYPE
    SYNTAX	HCPerfValidIntervals
    MAX-ACCESS	read-only
    STATUS	current
    DESCRIPTION
	"Indicates the number of valid 5-minute intervals of historical 
	 data that is collected int the corresonding history data table."
    ::= { tcapOmAEEntry 8 }

tcapOmAE15minValidIntervals OBJECT-TYPE
    SYNTAX	HCPerfValidIntervals
    MAX-ACCESS	read-only
    STATUS	current
    DESCRIPTION
	"Indicates the number of valid 15-minute intervals of historical 
	 data that is collected in the corresponding history data 
	 table."
    ::= { tcapOmAEEntry 9 }


-- =============================================================================

tcapOmAECurrentTable OBJECT-TYPE
    SYNTAX	SEQUENCE OF TcapOmAECurrentEntry
    MAX-ACCESS	not-accessible
    STATUS	current
    DESCRIPTION
	""
    REFERENCE
	""
    ::= { tcapOmAEMeasurements 2 }

tcapOmAECurrentEntry OBJECT-TYPE
    SYNTAX	TcapOmAECurrentEntry
    MAX-ACCESS	not-accessible
    STATUS	current
    DESCRIPTION
	""
    REFERENCE
	""
    INDEX	{
	tcapApplicationSubsystemId, -- shared index
	tcapApplicationEntityId	    -- shared index
    }
    ::= { tcapOmAECurrentTable 1 }

TcapOmAECurrentEntry ::= SEQUENCE {
    tcapOmAECurrentMeasurementDeleted		PerfCurrentCount,
    tcapOmAECurrentNewTransactions		PerfCurrentCount,
    tcapOmAECurrentMeanOpenTransactions		PerfCurrentCount,
    tcapOmAECurrentNotUsed			PerfCurrentCount,
    tcapOmAECurrentCummulativeMeanDuration	PerfCurrentCount,
    tcapOmAECurrentMaximumOpenTranactions	PerfCurrentCount,
    tcapOmAECurrentThresholdExceeded		PerfCurrentCount
}

tcapOmAECurrentMeasurementDeleted OBJECT-TYPE
    SYNTAX	PerfCurrentCount
    MAX-ACCESS	read-only
    STATUS	deprecated
    DESCRIPTION
	"Measurement deleted."
    REFERENCE
	"ITU-T Rec. Q.752 (06/97) Table 13, Item 13.5"
    ::= { tcapOmAECurrentEntry 1 }

tcapOmAECurrentNewTransactions OBJECT-TYPE
    SYNTAX	PerfCurrentCount
    UNITS	"Transactions per Application Entity"
    MAX-ACCESS	read-only
    STATUS	current
    DESCRIPTION
	"The number of new transactions in this interval.  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.6"
    ::= { tcapOmAECurrentEntry 2 }

tcapOmAECurrentMeanOpenTransactions OBJECT-TYPE
    SYNTAX	PerfCurrentCount
    UNITS	"Transactions per Application Entity"
    MAX-ACCESS	read-only
    STATUS	current
    DESCRIPTION
	"The mean number of open transaction identities in this 
	 interval (measured at the start of transactions).  This is a 
	 non-obligatory measurement taken on a 5-minute interval 
	 (provisional) basis.

	 This is a count of all new transactions in the interval, 
	 including those closed immediately by an ABORT after the 
	 opening BEGIN.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.7"
    ::= { tcapOmAECurrentEntry 3 }

tcapOmAECurrentNotUsed OBJECT-TYPE
    SYNTAX	PerfCurrentCount
    MAX-ACCESS	read-only
    STATUS	deprecated
    DESCRIPTION
	"Not used.
	 
	 Item 13.8 is a measurement of the mean number of open 
	 transactions in the interval.  An open transaction is one to 
	 which a transaction identity has been allocated, and this 
	 identity is not yet frozen."
    REFERENCE
	"ITU-T Rec. Q.752 (06/97) Table 13, Item 13.8"
    ::= { tcapOmAECurrentEntry 4 }

tcapOmAECurrentCummulativeMeanDuration OBJECT-TYPE
    SYNTAX	PerfCurrentCount
    UNITS	"Mean Seconds per Transaction per Application Entity"
    MAX-ACCESS	read-only
    STATUS	current
    DESCRIPTION
	"The cummulative mean duration of transactions.  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.9"
    ::= { tcapOmAECurrentEntry 5 }

tcapOmAECurrentMaximumOpenTranactions OBJECT-TYPE
    SYNTAX	PerfCurrentCount
    UNITS	"Transactions per Application Entity"
    MAX-ACCESS	read-only
    STATUS	current
    DESCRIPTION
	"The maximum number of open transaction identities during 
	 this interval.  This is a non-obligatory measurement taken on a 
	 5-minute interval (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems.
	 
	 Measurement 13.10 (the cummulative mean duration of 
	 transactions) is the mean duration for all transactions that 
	 began between the start of measurements and the end of the 
	 measurement interval.  It includes the time from opening the 
	 transaction to the end of the interval, for those transactions 
	 that did not close during the interval.  Here, the trasnaction 
	 duration ia defined as the time from allocation of the 
	 transaction identity to freezing it.
	"
    REFERENCE
	"ITU-T Rec. Q.752 (06/97) Table 13, Item 13.10"
    ::= { tcapOmAECurrentEntry 6 }

tcapOmAECurrentThresholdExceeded OBJECT-TYPE
    SYNTAX	PerfCurrentCount
    UNITS	"Events per Application Entity"
    MAX-ACCESS	read-only
    STATUS	current
    DESCRIPTION
	"The number of open transaction identities greater than an 
	 Application Entity pre-defined threshold.  This is a 
	 non-obligatory measurement signalled on an on-occurence basis."
    REFERENCE
	"ITU-T Rec. Q.752 (06/97) Table 13, Item 13.11"
    ::= { tcapOmAECurrentEntry 7 }


-- =============================================================================

tcapOmAE5minIntTable OBJECT-TYPE
    SYNTAX	SEQUENCE OF TcapOmAE5minIntEntry
    MAX-ACCESS	not-accessible
    STATUS	current
    DESCRIPTION
	""
    REFERENCE
	""
    ::= { tcapOmAEMeasurements 3 }

tcapOmAE5minIntEntry OBJECT-TYPE
    SYNTAX	TcapOmAE5minIntEntry
    MAX-ACCESS	not-accessible
    STATUS	current
    DESCRIPTION
	""
    REFERENCE
	""
    INDEX	{
	tcapApplicationSubsystemId,	-- shared index
	tcapApplicationEntityId,	-- shared index
	tcapOmInterval			-- shared index
    }
    ::= { tcapOmAE5minIntTable 1 }

TcapOmAE5minIntEntry ::= SEQUENCE {
    tcapOmAE5minIntMeasurementDeleted		PerfIntervalCount,
    tcapOmAE5minIntNewTransactions		PerfIntervalCount,
    tcapOmAE5minIntMeanOpenTransactions		PerfIntervalCount,
    tcapOmAE5minIntNotUsed			PerfIntervalCount,
    tcapOmAE5minIntCummulativeMeanDuration	PerfIntervalCount,
    tcapOmAE5minIntMaximumOpenTranactions	PerfIntervalCount,
    tcapOmAE5minIntThresholdExceeded		PerfIntervalCount
}

tcapOmAE5minIntMeasurementDeleted OBJECT-TYPE
    SYNTAX	PerfIntervalCount
    MAX-ACCESS	read-only
    STATUS	deprecated
    DESCRIPTION
	"Measurement deleted."
    REFERENCE
	"ITU-T Rec. Q.752 (06/97) Table 13, Item 13.5"
    ::= { tcapOmAE5minIntEntry 1 }

tcapOmAE5minIntNewTransactions OBJECT-TYPE
    SYNTAX	PerfIntervalCount
    UNITS	"Transactions per Application Entity"
    MAX-ACCESS	read-only
    STATUS	current
    DESCRIPTION
	"The number of new transactions in this interval.  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.6"
    ::= { tcapOmAE5minIntEntry 2 }

tcapOmAE5minIntMeanOpenTransactions OBJECT-TYPE
    SYNTAX	PerfIntervalCount
    UNITS	"Transactions per Application Entity"
    MAX-ACCESS	read-only
    STATUS	current
    DESCRIPTION
	"The mean number of open transaction identities in this 
	 interval (measured at the start of transactions).  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.7"
    ::= { tcapOmAE5minIntEntry 3 }

tcapOmAE5minIntNotUsed OBJECT-TYPE
    SYNTAX	PerfIntervalCount
    MAX-ACCESS	read-only
    STATUS	deprecated
    DESCRIPTION
	"Not used.
	 
	 Item 13.8 is a measurement of the mean number of open 
	 transactions in the interval.  An open transaction is one to 
	 which a transaction identity has been allocated, and this 
	 identity is not yet frozen."
    REFERENCE
	"ITU-T Rec. Q.752 (06/97) Table 13, Item 13.8"
    ::= { tcapOmAE5minIntEntry 4 }

tcapOmAE5minIntCummulativeMeanDuration OBJECT-TYPE
    SYNTAX	PerfIntervalCount
    UNITS	"Mean Seconds per Transaction per Application Entity"
    MAX-ACCESS	read-only
    STATUS	current
    DESCRIPTION
	"The cummulative mean duration of transactions.  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.9"
    ::= { tcapOmAE5minIntEntry 5 }

tcapOmAE5minIntMaximumOpenTranactions OBJECT-TYPE
    SYNTAX	PerfIntervalCount
    UNITS	"Transactions per Application Entity"
    MAX-ACCESS	read-only
    STATUS	current
    DESCRIPTION
	"The maximum number of open transaction identities during 
	 this interval.  This is a non-obligatory measurement taken on a 
	 5-minute interval (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems.
	 
	 Measurement 13.10 (the cummulative mean duration of 
	 transactions) is the mean duration for all transactions that 
	 began between the start of measurements and the end of the 
	 measurement interval.  It includes the time from opening the 
	 transaction to the end of the interval, for those transactions 
	 that did not close during the interval.  Here, the trasnaction 
	 duration ia defined as the time from allocation of the 
	 transaction identity to freezing it.
	"
    REFERENCE
	"ITU-T Rec. Q.752 (06/97) Table 13, Item 13.10"
    ::= { tcapOmAE5minIntEntry 6 }

tcapOmAE5minIntThresholdExceeded OBJECT-TYPE
    SYNTAX	PerfIntervalCount
    UNITS	"Events per Application Entity"
    MAX-ACCESS	read-only
    STATUS	current
    DESCRIPTION
	"The number of open transaction identities greater than an 
	 Application Entity pre-defined threshold.  This is a 
	 non-obligatory measurement signalled on an on-occurence basis."
    REFERENCE
	"ITU-T Rec. Q.752 (06/97) Table 13, Item 13.11"
    ::= { tcapOmAE5minIntEntry 7 }


-- =============================================================================

tcapOmAE15minIntTable OBJECT-TYPE
    SYNTAX	SEQUENCE OF TcapOmAE15minIntEntry
    MAX-ACCESS	not-accessible
    STATUS	current
    DESCRIPTION
	""
    REFERENCE
	""
    ::= { tcapOmAEMeasurements 4 }

tcapOmAE15minIntEntry OBJECT-TYPE
    SYNTAX	TcapOmAE15minIntEntry
    MAX-ACCESS	not-accessible
    STATUS	current
    DESCRIPTION
	""
    REFERENCE
	""
    INDEX	{
	tcapApplicationSubsystemId,	-- shared index
	tcapApplicationEntityId,	-- shared index
	tcapOmInterval			-- shared index
    }
    ::= { tcapOmAE15minIntTable 1 }

TcapOmAE15minIntEntry ::= SEQUENCE {
    tcapOmAE15minIntMeasurementDeleted		PerfIntervalCount,
    tcapOmAE15minIntNewTransactions		PerfIntervalCount,
    tcapOmAE15minIntMeanOpenTransactions	PerfIntervalCount,
    tcapOmAE15minIntNotUsed			PerfIntervalCount,
    tcapOmAE15minIntCummulativeMeanDuration	PerfIntervalCount,
    tcapOmAE15minIntMaximumOpenTranactions	PerfIntervalCount,
    tcapOmAE15minIntThresholdExceeded		PerfIntervalCount
}

tcapOmAE15minIntMeasurementDeleted OBJECT-TYPE
    SYNTAX	PerfIntervalCount
    MAX-ACCESS	read-only
    STATUS	deprecated
    DESCRIPTION
	"Measurement deleted."
    REFERENCE
	"ITU-T Rec. Q.752 (06/97) Table 13, Item 13.5"
    ::= { tcapOmAE15minIntEntry 1 }

tcapOmAE15minIntNewTransactions OBJECT-TYPE
    SYNTAX	PerfIntervalCount
    UNITS	"Transactions per Application Entity"
    MAX-ACCESS	read-only
    STATUS	current
    DESCRIPTION
	"The number of new transactions in this interval.  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.6"
    ::= { tcapOmAE15minIntEntry 2 }

tcapOmAE15minIntMeanOpenTransactions OBJECT-TYPE
    SYNTAX	PerfIntervalCount
    UNITS	"Transactions per Application Entity"
    MAX-ACCESS	read-only
    STATUS	current
    DESCRIPTION
	"The mean number of open transaction identities in this 
	 interval (measured at the start of transactions).  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.7"
    ::= { tcapOmAE15minIntEntry 3 }

tcapOmAE15minIntNotUsed OBJECT-TYPE
    SYNTAX	PerfIntervalCount
    MAX-ACCESS	read-only
    STATUS	deprecated
    DESCRIPTION
	"Not used.
	 
	 Item 13.8 is a measurement of the mean number of open 
	 transactions in the interval.  An open transaction is one to 
	 which a transaction identity has been allocated, and this 
	 identity is not yet frozen."
    REFERENCE
	"ITU-T Rec. Q.752 (06/97) Table 13, Item 13.8"
    ::= { tcapOmAE15minIntEntry 4 }

tcapOmAE15minIntCummulativeMeanDuration OBJECT-TYPE
    SYNTAX	PerfIntervalCount
    UNITS	"Mean Seconds per Transaction per Application Entity"
    MAX-ACCESS	read-only
    STATUS	current
    DESCRIPTION
	"The cummulative mean duration of transactions.  This is a 
	 non-obligatory measurement taken on a 5-minute interval 
	 (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems."
    REFERENCE
	"ITU-T Rec. Q.752 (06/97) Table 13, Item 13.9"
    ::= { tcapOmAE15minIntEntry 5 }

tcapOmAE15minIntMaximumOpenTranactions OBJECT-TYPE
    SYNTAX	PerfIntervalCount
    UNITS	"Transactions per Application Entity"
    MAX-ACCESS	read-only
    STATUS	current
    DESCRIPTION
	"The maximum number of open transaction identities during 
	 this interval.  This is a non-obligatory measurement taken on a 
	 5-minute interval (provisional) basis.
	 
	 The loading of TC resources can be indicated through the volume 
	 of messages and components handled.  The dynamic loading of TC 
	 resources can be observed by counting the number of new 
	 transactions during an interval, the mean number of open 
	 transactions during an interval indicates the static loading of 
	 TC.  The cummulative mean duration of transactions can be used 
	 for dimensioning TC and TC user resources, and to indicate 
	 operational problems.
	 
	 Measurement 13.10 (the cummulative mean duration of 
	 transactions) is the mean duration for all transactions that 
	 began between the start of measurements and the end of the 
	 measurement interval.  It includes the time from opening the 
	 transaction to the end of the interval, for those transactions 
	 that did not close during the interval.  Here, the trasnaction 
	 duration ia defined as the time from allocation of the 
	 transaction identity to freezing it.
	"
    REFERENCE
	"ITU-T Rec. Q.752 (06/97) Table 13, Item 13.10"
    ::= { tcapOmAE15minIntEntry 6 }

tcapOmAE15minIntThresholdExceeded OBJECT-TYPE
    SYNTAX	PerfIntervalCount
    UNITS	"Events per Application Entity"
    MAX-ACCESS	read-only
    STATUS	current
    DESCRIPTION
	"The number of open transaction identities greater than an 
	 Application Entity pre-defined threshold.  This is a 
	 non-obligatory measurement signalled on an on-occurence basis."
    REFERENCE
	"ITU-T Rec. Q.752 (06/97) Table 13, Item 13.11"
    ::= { tcapOmAE15minIntEntry 7 }


-- =============================================================================
-- TC Operational Measurements
-- =============================================================================

tcapOmTcTable OBJECT-TYPE
    SYNTAX	SEQUENCE OF TcapOmTcEntry
    MAX-ACCESS	not-accessible
    STATUS	current
    DESCRIPTION
	""
    REFERENCE
	""
    ::= { tcapOmOperMeasurements 1 }

tcapOmTcEntry OBJECT-TYPE
    SYNTAX	TcapOmTcEntry
    MAX-ACCESS	not-accessible
    STATUS	current
    DESCRIPTION
	""
    REFERENCE
	""
    INDEX	{
	tcapApplicationSubsystemId, -- shared index
	tcapApplicationEntityId	    -- shared index
    }
    ::= { tcapOmTcTable 1 }

TcapOmTcEntry ::= SEQUENCE {
    tcapOmTcPabortRecvUnrecTid			Counter,
    tcapOmTcPabortRecvResourceLim		Counter,
    tcapOmTcRejectRecvResourceLim		Counter,
    tcapOmTcPabortSentUnrecTid			Counter,
    tcapOmTcPabortSentResourceLim		Counter,
    tcapOmTcRejectSentResourceLim		Counter,
    tcapOmTcTcUserCancel			Counter,
    tcapOmTcMessagesDiscarded			Counter,
    tcapOmTcNotUsed				Counter,
    tcapOmTcPabortsReceived			Counter,
    tcapOmTcTcUserRejectsReceived		Counter,
    tcapOmTcTpErrors				Counter,
    tcapOmTc5minValidIntervals			HCPerfValidIntervals,
    tcapOmTc15minValidIntervals			HCPerfValidIntervals
}

tcapOmTcPabortRecvUnrecTid OBJECT-TYPE
    SYNTAX	Counter
    UNITS	"Events"
    MAX-ACCESS	read-only
    STATUS	current
    DESCRIPTION
	"The number of protocol errors detected in the transaction 
	 portion (abort received) with P-Abort cause: unrecognized TID 
	 (including END messages).  This measurement is obligatory and 
	 is collected on a first-and-interval basis.
	 
	 Problem isolation during development may be assisted by 
	 measurements that indicate the reason for the protocol error 
	 being reported.  This includes protocol errors detected in the 
	 transaction portion that are not due to resource limitation.
	"
    REFERENCE
	"ITU-T Rec. Q.752 (06/97) Table 14, Item 14.1 d).
	 ITU-T Rec. Q.774, Clause 2.3."
    ::= { tcapOmTcEntry 1 }

tcapOmTcPabortRecvResourceLim OBJECT-TYPE
    SYNTAX	Counter
    UNITS	"Events"
    MAX-ACCESS	read-only
    STATUS	current
    DESCRIPTION
	"The number of protocol errors detected in the transaction 
	 portion (abort received) with P-Abort cause: resource 
	 limitation.  This measurement is obligatory and is collected on 
	 a first-and-interval basis.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 Problem isolation during development may be assisted by 
	 measurements that indicate the reason for the protocol error 
	 being reported.  This includes protocol errors detected in the 
	 transaction portion that are not due to resource limitation.
	"
    REFERENCE
	"ITU-T Rec. Q.752 (06/97) Table 14, Item 14.1 e).
	 ITU-T Rec. Q.774, Clause 2.3."
    ::= { tcapOmTcEntry 2 }

tcapOmTcRejectRecvResourceLim OBJECT-TYPE
    SYNTAX	Counter
    UNITS	"Events"
    MAX-ACCESS	read-only
    STATUS	current
    DESCRIPTION
	"The number of TC-user generated problems (TC-user Reject 
	 received) with problem resource limitation (invoke problem).  
	 This measurement is non-obligatory and is collected on a 
	 first-and-interval basis.
	 
	 Problem isolation during development may be assisted by 
	 measurements that indicate the reason for the protocol error 
	 being reported.  This includes TC-user generated problems.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 This measurement indicates TC user resource problems when 
	 processing an invoked operation.  It is included in the TC 
	 measurements as it might be applicable to a number of different 
	 TC users."
    REFERENCE
	"ITU-T Rec. Q.752 (06/97) Table 14, Item 14.3 d).
	 ITU-T Rec. Q.772, Clause 3.8."
    ::= { tcapOmTcEntry 3 }

tcapOmTcPabortSentUnrecTid OBJECT-TYPE
    SYNTAX	Counter
    UNITS	"Events"
    MAX-ACCESS	read-only
    STATUS	current
    DESCRIPTION
	"The number of protocol errors detected in the transaction 
	 portion (abort sent) with P-abort cause due to an unrecognized 
	 transaction identity, including END messages.  This measurement 
	 is non-obligatory and is collected on a first-and-interval 
	 basis.
	 
	 Problem isolation during development may be assisted by 
	 measurements that indicate the reason for the protocol error 
	 being reported.  This includes protocol errors detected in the 
	 transaction portion that are not of a resource limitation 
	 nature.
	 
	 Measurement 14.4 d) (unrecognized transaction identity) might 
	 indicate problems of an operational nature.  Possible examples 
	 are:
	 
	  - because of SCCP routing problems, the local TC has received 
	    a message for a transaction that never existed;
	    
	  - messages arriving for transactions that have timed-out and 
	    have been closed by the application.
	
	 To allow the source of the error to be traced, the originating 
	 address of the received message should be logged for later 
	 retrieval.
	 
	 At the first report, sufficient information should be provided 
	 to establish the fault's location."
    REFERENCE
	"ITU-T Rec. Q.752 (06/97) Table 14, Item 14.4 d).
	 ITU-T Rec. Q.772, Clause 2.3."
    ::= { tcapOmTcEntry 4 }

tcapOmTcPabortSentResourceLim OBJECT-TYPE
    SYNTAX	Counter
    UNITS	"Events"
    MAX-ACCESS	read-only
    STATUS	current
    DESCRIPTION
	"The number of protocol errors detected in the transaction 
	 portion (abort sent) with P-abort cause due to a resource 
	 limitation.  This measurement is non-obligatory and is 
	 collected on a first-and-interval basis.
	 
	 Measurement 14.4 e) (resource limitation) can indicate a local 
	 TC resource problem, and requires the maintenance staff to be 
	 notified.
	 
	 Problem isolation during development may be assisted by 
	 measurements that indicate the reason for the protocol error 
	 being reported.  This includes protocol errors detected in the 
	 transaction portion that are not of a resource limitation 
	 nature.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept."
    REFERENCE
	"ITU-T Rec. Q.752 (06/97) Table 14, Item 14.4 e).
	 ITU-T Rec. Q.772, Clause 2.3."
    ::= { tcapOmTcEntry 5 }

tcapOmTcRejectSentResourceLim OBJECT-TYPE
    SYNTAX	Counter
    UNITS	"Events/dest. User"
    MAX-ACCESS	read-only
    STATUS	current
    DESCRIPTION
	"The number of TC-user generated problems (TC-user reject sent) 
	 due to resource limitation (invoke problem).  This measurement 
	 is non-obligatory and is collected on a first-and-interval 
	 basis.
	 
	 Problem isolation during development may be assisted by 
	 measurements that indicate the reason for the protocol error 
	 being reported.  This includes TC-user generated problems.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 This measurement indicates TC user resource problems when 
	 processing an invoked operation.  It is included in the TC 
	 measurements as it might be applicable to a number of different 
	 TC users."
    REFERENCE
	"ITU-T Rec. Q.752 (06/97) Table 14, Item 14.6 d)."
    ::= { tcapOmTcEntry 6 }

tcapOmTcTcUserCancel OBJECT-TYPE
    SYNTAX	Counter
    UNITS	"Indications"
    MAX-ACCESS	read-only
    STATUS	current
    DESCRIPTION
	"The number of TC_L_CANCEL indications for operations class 1 
	 operations.  This measurement is a non-obligatory and is 
	 collected on a 5-minute interval (provisional) basis."
    REFERENCE
	"ITU-T Rec. Q.752 (06/97) Table 14, Item 14.7.
	 ITU-T Rec. Q.772, Clause 8."
    ::= { tcapOmTcEntry 7 }

tcapOmTcMessagesDiscarded OBJECT-TYPE
    SYNTAX	Counter
    UNITS	"Messages"
    MAX-ACCESS	read-only
    STATUS	current
    DESCRIPTION
	"Number of messages discarded (for all reasons), including END 
	 messages with unrecognized TIDs.  This measurement is 
	 non-obligatory and is collected on a 5-minute interval 
	 (provisional) basis."
    REFERENCE
	"ITU-T Rec. Q.752 (06/97) Table 14, Item 14.8.
	 ITU-T Rec. Q.772, Clause 8."
    ::= { tcapOmTcEntry 8 }

tcapOmTcNotUsed OBJECT-TYPE
    SYNTAX	Counter
    UNITS	""
    MAX-ACCESS	read-only
    STATUS	current
    DESCRIPTION
	"Not used."
    REFERENCE
	"ITU-T Rec. Q.752 (06/97) Table 14, Item 14.9."
    ::= { tcapOmTcEntry 9 }

tcapOmTcPabortsReceived OBJECT-TYPE
    SYNTAX	Counter
    UNITS	"Messages"
    MAX-ACCESS	read-only
    STATUS	current
    DESCRIPTION
	"The number of provider aborts received.  This measurement is 
	 non-obligatory and is collected on a 5-minute interval 
	 (provisional) basis."
    REFERENCE
	"ITU-T Rec. Q.752 (06/97) Table 14, Item 14.10.
	 ITU-T Rec. Q.772, Clause 8."
    ::= { tcapOmTcEntry 10 }

tcapOmTcTcUserRejectsReceived OBJECT-TYPE
    SYNTAX	Counter
    UNITS	"Components"
    MAX-ACCESS	read-only
    STATUS	current
    DESCRIPTION
	"The number of rejects received.  This measurement is 
	 non-obligatory and is collected on a 5-minute interval 
	 (provisional) basis."
    REFERENCE
	"ITU-T Rec. Q.752 (06/97) Table 14, Item 14.11.
	 ITU-T Rec. Q.772, Clause 8."
    ::= { tcapOmTcEntry 11 }

tcapOmTcTpErrors OBJECT-TYPE
    SYNTAX	Counter
    UNITS	"Messages"
    MAX-ACCESS	read-only
    STATUS	current
    DESCRIPTION
	"The number of errors detected in transaction portion.  This 
	 measurement is non-obligatory and is collected on a 5-minute 
	 interval (provisional) basis."
    REFERENCE
	"ITU-T Rec. Q.752 (06/97) Table 14, Item 14.12.
	 ITU-T Rec. Q.772, Clause 8."
    ::= { tcapOmTcEntry 12 }

tcapOmTc5minValidIntervals OBJECT-TYPE
    SYNTAX	HCPerfValidIntervals
    MAX-ACCESS	read-only
    STATUS	current
    DESCRIPTION
	"Indicates the number of valid 5-minute intervals of historical 
	 data that is collected int the corresonding history data table."
    ::= { tcapOmTcEntry 13 }

tcapOmTc15minValidIntervals OBJECT-TYPE
    SYNTAX	HCPerfValidIntervals
    MAX-ACCESS	read-only
    STATUS	current
    DESCRIPTION
	"Indicates the number of valid 15-minute intervals of historical 
	 data that is collected in the corresponding history data 
	 table."
    ::= { tcapOmTcEntry 14 }


-- =============================================================================

tcapOmTcCurrentTable OBJECT-TYPE
    SYNTAX	SEQUENCE OF TcapOmTcCurrentEntry
    MAX-ACCESS	not-accessible
    STATUS	current
    DESCRIPTION
	""
    REFERENCE
	""
    ::= { tcapOmOperMeasurements 2 }

tcapOmTcCurrentEntry OBJECT-TYPE
    SYNTAX	TcapOmTcCurrentEntry
    MAX-ACCESS	not-accessible
    STATUS	current
    DESCRIPTION
	""
    REFERENCE
	""
    INDEX	{
	tcapApplicationSubsystemId, -- shared index
	tcapApplicationEntityId	    -- shared index
    }
    ::= { tcapOmTcCurrentTable 1 }

TcapOmTcCurrentEntry ::= SEQUENCE {
    tcapOmTcCurrentPabortRecvUnrecTid		PerfCurrentCount,
    tcapOmTcCurrentPabortRecvResourceLim	PerfCurrentCount,
    tcapOmTcCurrentRejectRecvResourceLim	PerfCurrentCount,
    tcapOmTcCurrentPabortSentUnrecTid		PerfCurrentCount,
    tcapOmTcCurrentPabortSentResourceLim	PerfCurrentCount,
    tcapOmTcCurrentRejectSentResourceLim	PerfCurrentCount,
    tcapOmTcCurrentTcUserCancel			PerfCurrentCount,
    tcapOmTcCurrentMessagesDiscarded		PerfCurrentCount,
    tcapOmTcCurrentNotUsed			PerfCurrentCount,
    tcapOmTcCurrentPabortsReceived		PerfCurrentCount,
    tcapOmTcCurrentTcUserRejectsReceived	PerfCurrentCount,
    tcapOmTcCurrentTpErrors			PerfCurrentCount
}

tcapOmTcCurrentPabortRecvUnrecTid OBJECT-TYPE
    SYNTAX	PerfCurrentCount
    UNITS	"Events"
    MAX-ACCESS	read-only
    STATUS	current
    DESCRIPTION
	"The number of protocol errors detected in the transaction 
	 portion (abort received) with P-Abort cause: unrecognized TID 
	 (including END messages).  This measurement is obligatory and 
	 is collected on a first-and-interval basis.
	 
	 Problem isolation during development may be assisted by 
	 measurements that indicate the reason for the protocol error 
	 being reported.  This includes protocol errors detected in the 
	 transaction portion that are not due to resource limitation.
	"
    REFERENCE
	"ITU-T Rec. Q.752 (06/97) Table 14, Item 14.1 d).
	 ITU-T Rec. Q.774, Clause 2.3."
    ::= { tcapOmTcCurrentEntry 1 }

tcapOmTcCurrentPabortRecvResourceLim OBJECT-TYPE
    SYNTAX	PerfCurrentCount
    UNITS	"Events"
    MAX-ACCESS	read-only
    STATUS	current
    DESCRIPTION
	"The number of protocol errors detected in the transaction 
	 portion (abort received) with P-Abort cause: resource 
	 limitation.  This measurement is obligatory and is collected on 
	 a first-and-interval basis.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 Problem isolation during development may be assisted by 
	 measurements that indicate the reason for the protocol error 
	 being reported.  This includes protocol errors detected in the 
	 transaction portion that are not due to resource limitation.
	"
    REFERENCE
	"ITU-T Rec. Q.752 (06/97) Table 14, Item 14.1 e).
	 ITU-T Rec. Q.774, Clause 2.3."
    ::= { tcapOmTcCurrentEntry 2 }

tcapOmTcCurrentRejectRecvResourceLim OBJECT-TYPE
    SYNTAX	PerfCurrentCount
    UNITS	"Events"
    MAX-ACCESS	read-only
    STATUS	current
    DESCRIPTION
	"The number of TC-user generated problems (TC-user Reject 
	 received) with problem resource limitation (invoke problem).  
	 This measurement is non-obligatory and is collected on a 
	 first-and-interval basis.
	 
	 Problem isolation during development may be assisted by 
	 measurements that indicate the reason for the protocol error 
	 being reported.  This includes TC-user generated problems.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 This measurement indicates TC user resource problems when 
	 processing an invoked operation.  It is included in the TC 
	 measurements as it might be applicable to a number of different 
	 TC users."
    REFERENCE
	"ITU-T Rec. Q.752 (06/97) Table 14, Item 14.3 d).
	 ITU-T Rec. Q.772, Clause 3.8."
    ::= { tcapOmTcCurrentEntry 3 }

tcapOmTcCurrentPabortSentUnrecTid OBJECT-TYPE
    SYNTAX	PerfCurrentCount
    UNITS	"Events"
    MAX-ACCESS	read-only
    STATUS	current
    DESCRIPTION
	"The number of protocol errors detected in the transaction 
	 portion (abort sent) with P-abort cause due to an unrecognized 
	 transaction identity, including END messages.  This measurement 
	 is non-obligatory and is collected on a first-and-interval 
	 basis.
	 
	 Problem isolation during development may be assisted by 
	 measurements that indicate the reason for the protocol error 
	 being reported.  This includes protocol errors detected in the 
	 transaction portion that are not of a resource limitation 
	 nature.
	 
	 Measurement 14.4 d) (unrecognized transaction identity) might 
	 indicate problems of an operational nature.  Possible examples 
	 are:
	 
	  - because of SCCP routing problems, the local TC has received 
	    a message for a transaction that never existed;
	    
	  - messages arriving for transactions that have timed-out and 
	    have been closed by the application.
	
	 To allow the source of the error to be traced, the originating 
	 address of the received message should be logged for later 
	 retrieval.
	 
	 At the first report, sufficient information should be provided 
	 to establish the fault's location."
    REFERENCE
	"ITU-T Rec. Q.752 (06/97) Table 14, Item 14.4 d).
	 ITU-T Rec. Q.772, Clause 2.3."
    ::= { tcapOmTcCurrentEntry 4 }

tcapOmTcCurrentPabortSentResourceLim OBJECT-TYPE
    SYNTAX	PerfCurrentCount
    UNITS	"Events"
    MAX-ACCESS	read-only
    STATUS	current
    DESCRIPTION
	"The number of protocol errors detected in the transaction 
	 portion (abort sent) with P-abort cause due to a resource 
	 limitation.  This measurement is non-obligatory and is 
	 collected on a first-and-interval basis.
	 
	 Measurement 14.4 e) (resource limitation) can indicate a local 
	 TC resource problem, and requires the maintenance staff to be 
	 notified.
	 
	 Problem isolation during development may be assisted by 
	 measurements that indicate the reason for the protocol error 
	 being reported.  This includes protocol errors detected in the 
	 transaction portion that are not of a resource limitation 
	 nature.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept."
    REFERENCE
	"ITU-T Rec. Q.752 (06/97) Table 14, Item 14.4 e).
	 ITU-T Rec. Q.772, Clause 2.3."
    ::= { tcapOmTcCurrentEntry 5 }

tcapOmTcCurrentRejectSentResourceLim OBJECT-TYPE
    SYNTAX	PerfCurrentCount
    UNITS	"Events/dest. User"
    MAX-ACCESS	read-only
    STATUS	current
    DESCRIPTION
	"The number of TC-user generated problems (TC-user reject sent) 
	 due to resource limitation (invoke problem).  This measurement 
	 is non-obligatory and is collected on a first-and-interval 
	 basis.
	 
	 Problem isolation during development may be assisted by 
	 measurements that indicate the reason for the protocol error 
	 being reported.  This includes TC-user generated problems.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 This measurement indicates TC user resource problems when 
	 processing an invoked operation.  It is included in the TC 
	 measurements as it might be applicable to a number of different 
	 TC users."
    REFERENCE
	"ITU-T Rec. Q.752 (06/97) Table 14, Item 14.6 d)."
    ::= { tcapOmTcCurrentEntry 6 }

tcapOmTcCurrentTcUserCancel OBJECT-TYPE
    SYNTAX	PerfCurrentCount
    UNITS	"Indications"
    MAX-ACCESS	read-only
    STATUS	current
    DESCRIPTION
	"The number of TC_L_CANCEL indications for operations class 1 
	 operations.  This measurement is a non-obligatory and is 
	 collected on a 5-minute interval (provisional) basis."
    REFERENCE
	"ITU-T Rec. Q.752 (06/97) Table 14, Item 14.7.
	 ITU-T Rec. Q.772, Clause 8."
    ::= { tcapOmTcCurrentEntry 7 }

tcapOmTcCurrentMessagesDiscarded OBJECT-TYPE
    SYNTAX	PerfCurrentCount
    UNITS	"Messages"
    MAX-ACCESS	read-only
    STATUS	current
    DESCRIPTION
	"Number of messages discarded (for all reasons), including END 
	 messages with unrecognized TIDs.  This measurement is 
	 non-obligatory and is collected on a 5-minute interval 
	 (provisional) basis."
    REFERENCE
	"ITU-T Rec. Q.752 (06/97) Table 14, Item 14.8.
	 ITU-T Rec. Q.772, Clause 8."
    ::= { tcapOmTcCurrentEntry 8 }

tcapOmTcCurrentNotUsed OBJECT-TYPE
    SYNTAX	PerfCurrentCount
    UNITS	""
    MAX-ACCESS	read-only
    STATUS	current
    DESCRIPTION
	"Not used."
    REFERENCE
	"ITU-T Rec. Q.752 (06/97) Table 14, Item 14.9."
    ::= { tcapOmTcCurrentEntry 9 }

tcapOmTcCurrentPabortsReceived OBJECT-TYPE
    SYNTAX	PerfCurrentCount
    UNITS	"Messages"
    MAX-ACCESS	read-only
    STATUS	current
    DESCRIPTION
	"The number of provider aborts received.  This measurement is 
	 non-obligatory and is collected on a 5-minute interval 
	 (provisional) basis."
    REFERENCE
	"ITU-T Rec. Q.752 (06/97) Table 14, Item 14.10.
	 ITU-T Rec. Q.772, Clause 8."
    ::= { tcapOmTcCurrentEntry 10 }

tcapOmTcCurrentTcUserRejectsReceived OBJECT-TYPE
    SYNTAX	PerfCurrentCount
    UNITS	"Components"
    MAX-ACCESS	read-only
    STATUS	current
    DESCRIPTION
	"The number of rejects received.  This measurement is 
	 non-obligatory and is collected on a 5-minute interval 
	 (provisional) basis."
    REFERENCE
	"ITU-T Rec. Q.752 (06/97) Table 14, Item 14.11.
	 ITU-T Rec. Q.772, Clause 8."
    ::= { tcapOmTcCurrentEntry 11 }

tcapOmTcCurrentTpErrors OBJECT-TYPE
    SYNTAX	PerfCurrentCount
    UNITS	"Messages"
    MAX-ACCESS	read-only
    STATUS	current
    DESCRIPTION
	"The number of errors detected in transaction portion.  This 
	 measurement is non-obligatory and is collected on a 5-minute 
	 interval (provisional) basis."
    REFERENCE
	"ITU-T Rec. Q.752 (06/97) Table 14, Item 14.12.
	 ITU-T Rec. Q.772, Clause 8."
    ::= { tcapOmTcCurrentEntry 12 }


-- =============================================================================

tcapOmTc5minIntTable OBJECT-TYPE
    SYNTAX	SEQUENCE OF TcapOmTc5minIntEntry
    MAX-ACCESS	not-accessible
    STATUS	current
    DESCRIPTION
	""
    REFERENCE
	""
    ::= { tcapOmOperMeasurements 3 }

tcapOmTc5minIntEntry OBJECT-TYPE
    SYNTAX	TcapOmTc5minIntEntry
    MAX-ACCESS	not-accessible
    STATUS	current
    DESCRIPTION
	""
    REFERENCE
	""
    INDEX	{
	tcapApplicationSubsystemId, -- shared index
	tcapApplicationEntityId,    -- shared index
	tcapOmInterval		    -- shared index
    }
    ::= { tcapOmTc5minIntTable 1 }

TcapOmTc5minIntEntry ::= SEQUENCE {
    tcapOmTc5minIntPabortRecvUnrecTid		PerfIntervalCount,
    tcapOmTc5minIntPabortRecvResourceLim	PerfIntervalCount,
    tcapOmTc5minIntRejectRecvResourceLim	PerfIntervalCount,
    tcapOmTc5minIntPabortSentUnrecTid		PerfIntervalCount,
    tcapOmTc5minIntPabortSentResourceLim	PerfIntervalCount,
    tcapOmTc5minIntRejectSentResourceLim	PerfIntervalCount,
    tcapOmTc5minIntTcUserCancel			PerfIntervalCount,
    tcapOmTc5minIntMessagesDiscarded		PerfIntervalCount,
    tcapOmTc5minIntNotUsed			PerfIntervalCount,
    tcapOmTc5minIntPabortsReceived		PerfIntervalCount,
    tcapOmTc5minIntTcUserRejectsReceived	PerfIntervalCount,
    tcapOmTc5minIntTpErrors			PerfIntervalCount
}

tcapOmTc5minIntPabortRecvUnrecTid OBJECT-TYPE
    SYNTAX	PerfIntervalCount
    UNITS	"Events"
    MAX-ACCESS	read-only
    STATUS	current
    DESCRIPTION
	"The number of protocol errors detected in the transaction 
	 portion (abort received) with P-Abort cause: unrecognized TID 
	 (including END messages).  This measurement is obligatory and 
	 is collected on a first-and-interval basis.
	 
	 Problem isolation during development may be assisted by 
	 measurements that indicate the reason for the protocol error 
	 being reported.  This includes protocol errors detected in the 
	 transaction portion that are not due to resource limitation.
	"
    REFERENCE
	"ITU-T Rec. Q.752 (06/97) Table 14, Item 14.1 d).
	 ITU-T Rec. Q.774, Clause 2.3."
    ::= { tcapOmTc5minIntEntry 1 }

tcapOmTc5minIntPabortRecvResourceLim OBJECT-TYPE
    SYNTAX	PerfCurrentCount
    UNITS	"Events"
    MAX-ACCESS	read-only
    STATUS	current
    DESCRIPTION
	"The number of protocol errors detected in the transaction 
	 portion (abort received) with P-Abort cause: resource 
	 limitation.  This measurement is obligatory and is collected on 
	 a first-and-interval basis.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 Problem isolation during development may be assisted by 
	 measurements that indicate the reason for the protocol error 
	 being reported.  This includes protocol errors detected in the 
	 transaction portion that are not due to resource limitation.
	"
    REFERENCE
	"ITU-T Rec. Q.752 (06/97) Table 14, Item 14.1 e).
	 ITU-T Rec. Q.774, Clause 2.3."
    ::= { tcapOmTc5minIntEntry 2 }

tcapOmTc5minIntRejectRecvResourceLim OBJECT-TYPE
    SYNTAX	PerfIntervalCount
    UNITS	"Events"
    MAX-ACCESS	read-only
    STATUS	current
    DESCRIPTION
	"The number of TC-user generated problems (TC-user Reject 
	 received) with problem resource limitation (invoke problem).  
	 This measurement is non-obligatory and is collected on a 
	 first-and-interval basis.
	 
	 Problem isolation during development may be assisted by 
	 measurements that indicate the reason for the protocol error 
	 being reported.  This includes TC-user generated problems.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 This measurement indicates TC user resource problems when 
	 processing an invoked operation.  It is included in the TC 
	 measurements as it might be applicable to a number of different 
	 TC users."
    REFERENCE
	"ITU-T Rec. Q.752 (06/97) Table 14, Item 14.3 d).
	 ITU-T Rec. Q.772, Clause 3.8."
    ::= { tcapOmTc5minIntEntry 3 }

tcapOmTc5minIntPabortSentUnrecTid OBJECT-TYPE
    SYNTAX	PerfIntervalCount
    UNITS	"Events"
    MAX-ACCESS	read-only
    STATUS	current
    DESCRIPTION
	"The number of protocol errors detected in the transaction 
	 portion (abort sent) with P-abort cause due to an unrecognized 
	 transaction identity, including END messages.  This measurement 
	 is non-obligatory and is collected on a first-and-interval 
	 basis.
	 
	 Problem isolation during development may be assisted by 
	 measurements that indicate the reason for the protocol error 
	 being reported.  This includes protocol errors detected in the 
	 transaction portion that are not of a resource limitation 
	 nature.
	 
	 Measurement 14.4 d) (unrecognized transaction identity) might 
	 indicate problems of an operational nature.  Possible examples 
	 are:
	 
	  - because of SCCP routing problems, the local TC has received 
	    a message for a transaction that never existed;
	    
	  - messages arriving for transactions that have timed-out and 
	    have been closed by the application.
	
	 To allow the source of the error to be traced, the originating 
	 address of the received message should be logged for later 
	 retrieval.
	 
	 At the first report, sufficient information should be provided 
	 to establish the fault's location."
    REFERENCE
	"ITU-T Rec. Q.752 (06/97) Table 14, Item 14.4 d).
	 ITU-T Rec. Q.772, Clause 2.3."
    ::= { tcapOmTc5minIntEntry 4 }

tcapOmTc5minIntPabortSentResourceLim OBJECT-TYPE
    SYNTAX	PerfIntervalCount
    UNITS	"Events"
    MAX-ACCESS	read-only
    STATUS	current
    DESCRIPTION
	"The number of protocol errors detected in the transaction 
	 portion (abort sent) with P-abort cause due to a resource 
	 limitation.  This measurement is non-obligatory and is 
	 collected on a first-and-interval basis.
	 
	 Measurement 14.4 e) (resource limitation) can indicate a local 
	 TC resource problem, and requires the maintenance staff to be 
	 notified.
	 
	 Problem isolation during development may be assisted by 
	 measurements that indicate the reason for the protocol error 
	 being reported.  This includes protocol errors detected in the 
	 transaction portion that are not of a resource limitation 
	 nature.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept."
    REFERENCE
	"ITU-T Rec. Q.752 (06/97) Table 14, Item 14.4 e).
	 ITU-T Rec. Q.772, Clause 2.3."
    ::= { tcapOmTc5minIntEntry 5 }

tcapOmTc5minIntRejectSentResourceLim OBJECT-TYPE
    SYNTAX	PerfIntervalCount
    UNITS	"Events/dest. User"
    MAX-ACCESS	read-only
    STATUS	current
    DESCRIPTION
	"The number of TC-user generated problems (TC-user reject sent) 
	 due to resource limitation (invoke problem).  This measurement 
	 is non-obligatory and is collected on a first-and-interval 
	 basis.
	 
	 Problem isolation during development may be assisted by 
	 measurements that indicate the reason for the protocol error 
	 being reported.  This includes TC-user generated problems.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 This measurement indicates TC user resource problems when 
	 processing an invoked operation.  It is included in the TC 
	 measurements as it might be applicable to a number of different 
	 TC users."
    REFERENCE
	"ITU-T Rec. Q.752 (06/97) Table 14, Item 14.6 d)."
    ::= { tcapOmTc5minIntEntry 6 }

tcapOmTc5minIntTcUserCancel OBJECT-TYPE
    SYNTAX	PerfIntervalCount
    UNITS	"Indications"
    MAX-ACCESS	read-only
    STATUS	current
    DESCRIPTION
	"The number of TC_L_CANCEL indications for operations class 1 
	 operations.  This measurement is a non-obligatory and is 
	 collected on a 5-minute interval (provisional) basis."
    REFERENCE
	"ITU-T Rec. Q.752 (06/97) Table 14, Item 14.7.
	 ITU-T Rec. Q.772, Clause 8."
    ::= { tcapOmTc5minIntEntry 7 }

tcapOmTc5minIntMessagesDiscarded OBJECT-TYPE
    SYNTAX	PerfIntervalCount
    UNITS	"Messages"
    MAX-ACCESS	read-only
    STATUS	current
    DESCRIPTION
	"Number of messages discarded (for all reasons), including END 
	 messages with unrecognized TIDs.  This measurement is 
	 non-obligatory and is collected on a 5-minute interval 
	 (provisional) basis."
    REFERENCE
	"ITU-T Rec. Q.752 (06/97) Table 14, Item 14.8.
	 ITU-T Rec. Q.772, Clause 8."
    ::= { tcapOmTc5minIntEntry 8 }

tcapOmTc5minIntNotUsed OBJECT-TYPE
    SYNTAX	PerfIntervalCount
    UNITS	""
    MAX-ACCESS	read-only
    STATUS	current
    DESCRIPTION
	"Not used."
    REFERENCE
	"ITU-T Rec. Q.752 (06/97) Table 14, Item 14.9."
    ::= { tcapOmTc5minIntEntry 9 }

tcapOmTc5minIntPabortsReceived OBJECT-TYPE
    SYNTAX	PerfIntervalCount
    UNITS	"Messages"
    MAX-ACCESS	read-only
    STATUS	current
    DESCRIPTION
	"The number of provider aborts received.  This measurement is 
	 non-obligatory and is collected on a 5-minute interval 
	 (provisional) basis."
    REFERENCE
	"ITU-T Rec. Q.752 (06/97) Table 14, Item 14.10.
	 ITU-T Rec. Q.772, Clause 8."
    ::= { tcapOmTc5minIntEntry 10 }

tcapOmTc5minIntTcUserRejectsReceived OBJECT-TYPE
    SYNTAX	PerfIntervalCount
    UNITS	"Components"
    MAX-ACCESS	read-only
    STATUS	current
    DESCRIPTION
	"The number of rejects received.  This measurement is 
	 non-obligatory and is collected on a 5-minute interval 
	 (provisional) basis."
    REFERENCE
	"ITU-T Rec. Q.752 (06/97) Table 14, Item 14.11.
	 ITU-T Rec. Q.772, Clause 8."
    ::= { tcapOmTc5minIntEntry 11 }

tcapOmTc5minIntTpErrors OBJECT-TYPE
    SYNTAX	PerfIntervalCount
    UNITS	"Messages"
    MAX-ACCESS	read-only
    STATUS	current
    DESCRIPTION
	"The number of errors detected in transaction portion.  This 
	 measurement is non-obligatory and is collected on a 5-minute 
	 interval (provisional) basis."
    REFERENCE
	"ITU-T Rec. Q.752 (06/97) Table 14, Item 14.12.
	 ITU-T Rec. Q.772, Clause 8."
    ::= { tcapOmTc5minIntEntry 12 }


-- =============================================================================

tcapOmTc15minIntTable OBJECT-TYPE
    SYNTAX	SEQUENCE OF TcapOmTc15minIntEntry
    MAX-ACCESS	not-accessible
    STATUS	current
    DESCRIPTION
	""
    REFERENCE
	""
    ::= { tcapOmOperMeasurements 4 }

tcapOmTc15minIntEntry OBJECT-TYPE
    SYNTAX	TcapOmTc15minIntEntry
    MAX-ACCESS	not-accessible
    STATUS	current
    DESCRIPTION
	""
    REFERENCE
	""
    INDEX	{
	tcapApplicationSubsystemId, -- shared index
	tcapApplicationEntityId,    -- shared index
	tcapOmInterval		    -- shared index
    }
    ::= { tcapOmTc15minIntTable 1 }

TcapOmTc15minIntEntry ::= SEQUENCE {
    tcapOmTc15minIntPabortRecvUnrecTid		PerfIntervalCount,
    tcapOmTc15minIntPabortRecvResourceLim	PerfIntervalCount,
    tcapOmTc15minIntRejectRecvResourceLim	PerfIntervalCount,
    tcapOmTc15minIntPabortSentUnrecTid		PerfIntervalCount,
    tcapOmTc15minIntPabortSentResourceLim	PerfIntervalCount,
    tcapOmTc15minIntRejectSentResourceLim	PerfIntervalCount,
    tcapOmTc15minIntTcUserCancel		PerfIntervalCount,
    tcapOmTc15minIntMessagesDiscarded		PerfIntervalCount,
    tcapOmTc15minIntNotUsed			PerfIntervalCount,
    tcapOmTc15minIntPabortsReceived		PerfIntervalCount,
    tcapOmTc15minIntTcUserRejectsReceived	PerfIntervalCount,
    tcapOmTc15minIntTpErrors			PerfIntervalCount
}

tcapOmTc15minIntPabortRecvUnrecTid OBJECT-TYPE
    SYNTAX	PerfIntervalCount
    UNITS	"Events"
    MAX-ACCESS	read-only
    STATUS	current
    DESCRIPTION
	"The number of protocol errors detected in the transaction 
	 portion (abort received) with P-Abort cause: unrecognized TID 
	 (including END messages).  This measurement is obligatory and 
	 is collected on a first-and-interval basis.
	 
	 Problem isolation during development may be assisted by 
	 measurements that indicate the reason for the protocol error 
	 being reported.  This includes protocol errors detected in the 
	 transaction portion that are not due to resource limitation.
	"
    REFERENCE
	"ITU-T Rec. Q.752 (06/97) Table 14, Item 14.1 d).
	 ITU-T Rec. Q.774, Clause 2.3."
    ::= { tcapOmTc15minIntEntry 1 }

tcapOmTc15minIntPabortRecvResourceLim OBJECT-TYPE
    SYNTAX	PerfCurrentCount
    UNITS	"Events"
    MAX-ACCESS	read-only
    STATUS	current
    DESCRIPTION
	"The number of protocol errors detected in the transaction 
	 portion (abort received) with P-Abort cause: resource 
	 limitation.  This measurement is obligatory and is collected on 
	 a first-and-interval basis.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 Problem isolation during development may be assisted by 
	 measurements that indicate the reason for the protocol error 
	 being reported.  This includes protocol errors detected in the 
	 transaction portion that are not due to resource limitation.
	"
    REFERENCE
	"ITU-T Rec. Q.752 (06/97) Table 14, Item 14.1 e).
	 ITU-T Rec. Q.774, Clause 2.3."
    ::= { tcapOmTc15minIntEntry 2 }

tcapOmTc15minIntRejectRecvResourceLim OBJECT-TYPE
    SYNTAX	PerfIntervalCount
    UNITS	"Events"
    MAX-ACCESS	read-only
    STATUS	current
    DESCRIPTION
	"The number of TC-user generated problems (TC-user Reject 
	 received) with problem resource limitation (invoke problem).  
	 This measurement is non-obligatory and is collected on a 
	 first-and-interval basis.
	 
	 Problem isolation during development may be assisted by 
	 measurements that indicate the reason for the protocol error 
	 being reported.  This includes TC-user generated problems.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 This measurement indicates TC user resource problems when 
	 processing an invoked operation.  It is included in the TC 
	 measurements as it might be applicable to a number of different 
	 TC users."
    REFERENCE
	"ITU-T Rec. Q.752 (06/97) Table 14, Item 14.3 d).
	 ITU-T Rec. Q.772, Clause 3.8."
    ::= { tcapOmTc15minIntEntry 3 }

tcapOmTc15minIntPabortSentUnrecTid OBJECT-TYPE
    SYNTAX	PerfIntervalCount
    UNITS	"Events"
    MAX-ACCESS	read-only
    STATUS	current
    DESCRIPTION
	"The number of protocol errors detected in the transaction 
	 portion (abort sent) with P-abort cause due to an unrecognized 
	 transaction identity, including END messages.  This measurement 
	 is non-obligatory and is collected on a first-and-interval 
	 basis.
	 
	 Problem isolation during development may be assisted by 
	 measurements that indicate the reason for the protocol error 
	 being reported.  This includes protocol errors detected in the 
	 transaction portion that are not of a resource limitation 
	 nature.
	 
	 Measurement 14.4 d) (unrecognized transaction identity) might 
	 indicate problems of an operational nature.  Possible examples 
	 are:
	 
	  - because of SCCP routing problems, the local TC has received 
	    a message for a transaction that never existed;
	    
	  - messages arriving for transactions that have timed-out and 
	    have been closed by the application.
	
	 To allow the source of the error to be traced, the originating 
	 address of the received message should be logged for later 
	 retrieval.
	 
	 At the first report, sufficient information should be provided 
	 to establish the fault's location."
    REFERENCE
	"ITU-T Rec. Q.752 (06/97) Table 14, Item 14.4 d).
	 ITU-T Rec. Q.772, Clause 2.3."
    ::= { tcapOmTc15minIntEntry 4 }

tcapOmTc15minIntPabortSentResourceLim OBJECT-TYPE
    SYNTAX	PerfIntervalCount
    UNITS	"Events"
    MAX-ACCESS	read-only
    STATUS	current
    DESCRIPTION
	"The number of protocol errors detected in the transaction 
	 portion (abort sent) with P-abort cause due to a resource 
	 limitation.  This measurement is non-obligatory and is 
	 collected on a first-and-interval basis.
	 
	 Measurement 14.4 e) (resource limitation) can indicate a local 
	 TC resource problem, and requires the maintenance staff to be 
	 notified.
	 
	 Problem isolation during development may be assisted by 
	 measurements that indicate the reason for the protocol error 
	 being reported.  This includes protocol errors detected in the 
	 transaction portion that are not of a resource limitation 
	 nature.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept."
    REFERENCE
	"ITU-T Rec. Q.752 (06/97) Table 14, Item 14.4 e).
	 ITU-T Rec. Q.772, Clause 2.3."
    ::= { tcapOmTc15minIntEntry 5 }

tcapOmTc15minIntRejectSentResourceLim OBJECT-TYPE
    SYNTAX	PerfIntervalCount
    UNITS	"Events/dest. User"
    MAX-ACCESS	read-only
    STATUS	current
    DESCRIPTION
	"The number of TC-user generated problems (TC-user reject sent) 
	 due to resource limitation (invoke problem).  This measurement 
	 is non-obligatory and is collected on a first-and-interval 
	 basis.
	 
	 Problem isolation during development may be assisted by 
	 measurements that indicate the reason for the protocol error 
	 being reported.  This includes TC-user generated problems.
	 
	 During operation, resource limitation measurements are 
	 pertinent.  The purpose of this measurement is to monitor 
	 abnormal events of an operational nature, or peaks in errors 
	 that affect the quality of service offered to the TC users.  It 
	 also provides the means to collect adiitional information that 
	 allows the source of the errors to be traced.  To this end, a 
	 log of notifications that is retrievable on command (e.g. from 
	 an Operations System) could be kept.
	 
	 This measurement indicates TC user resource problems when 
	 processing an invoked operation.  It is included in the TC 
	 measurements as it might be applicable to a number of different 
	 TC users."
    REFERENCE
	"ITU-T Rec. Q.752 (06/97) Table 14, Item 14.6 d)."
    ::= { tcapOmTc15minIntEntry 6 }

tcapOmTc15minIntTcUserCancel OBJECT-TYPE
    SYNTAX	PerfIntervalCount
    UNITS	"Indications"
    MAX-ACCESS	read-only
    STATUS	current
    DESCRIPTION
	"The number of TC_L_CANCEL indications for operations class 1 
	 operations.  This measurement is a non-obligatory and is 
	 collected on a 5-minute interval (provisional) basis."
    REFERENCE
	"ITU-T Rec. Q.752 (06/97) Table 14, Item 14.7.
	 ITU-T Rec. Q.772, Clause 8."
    ::= { tcapOmTc15minIntEntry 7 }

tcapOmTc15minIntMessagesDiscarded OBJECT-TYPE
    SYNTAX	PerfIntervalCount
    UNITS	"Messages"
    MAX-ACCESS	read-only
    STATUS	current
    DESCRIPTION
	"Number of messages discarded (for all reasons), including END 
	 messages with unrecognized TIDs.  This measurement is 
	 non-obligatory and is collected on a 5-minute interval 
	 (provisional) basis."
    REFERENCE
	"ITU-T Rec. Q.752 (06/97) Table 14, Item 14.8.
	 ITU-T Rec. Q.772, Clause 8."
    ::= { tcapOmTc15minIntEntry 8 }

tcapOmTc15minIntNotUsed OBJECT-TYPE
    SYNTAX	PerfIntervalCount
    UNITS	""
    MAX-ACCESS	read-only
    STATUS	current
    DESCRIPTION
	"Not used."
    REFERENCE
	"ITU-T Rec. Q.752 (06/97) Table 14, Item 14.9."
    ::= { tcapOmTc15minIntEntry 9 }

tcapOmTc15minIntPabortsReceived OBJECT-TYPE
    SYNTAX	PerfIntervalCount
    UNITS	"Messages"
    MAX-ACCESS	read-only
    STATUS	current
    DESCRIPTION
	"The number of provider aborts received.  This measurement is 
	 non-obligatory and is collected on a 5-minute interval 
	 (provisional) basis."
    REFERENCE
	"ITU-T Rec. Q.752 (06/97) Table 14, Item 14.10.
	 ITU-T Rec. Q.772, Clause 8."
    ::= { tcapOmTc15minIntEntry 10 }

tcapOmTc15minIntTcUserRejectsReceived OBJECT-TYPE
    SYNTAX	PerfIntervalCount
    UNITS	"Components"
    MAX-ACCESS	read-only
    STATUS	current
    DESCRIPTION
	"The number of rejects received.  This measurement is 
	 non-obligatory and is collected on a 5-minute interval 
	 (provisional) basis."
    REFERENCE
	"ITU-T Rec. Q.752 (06/97) Table 14, Item 14.11.
	 ITU-T Rec. Q.772, Clause 8."
    ::= { tcapOmTc15minIntEntry 11 }

tcapOmTc15minIntTpErrors OBJECT-TYPE
    SYNTAX	PerfIntervalCount
    UNITS	"Messages"
    MAX-ACCESS	read-only
    STATUS	current
    DESCRIPTION
	"The number of errors detected in transaction portion.  This 
	 measurement is non-obligatory and is collected on a 5-minute 
	 interval (provisional) basis."
    REFERENCE
	"ITU-T Rec. Q.752 (06/97) Table 14, Item 14.12.
	 ITU-T Rec. Q.772, Clause 8."
    ::= { tcapOmTc15minIntEntry 12 }

-- =============================================================================
-- TC Development Measurements
-- =============================================================================

tcapOmDevelRecvTable OBJECT-TYPE
    SYNTAX	SEQUENCE OF TcapOmDevelEntry
    MAX-ACCESS	not-accessible
    STATUS	current
    DESCRIPTION
	""
    REFERENCE
	""
    ::= { tcapOmDevelMeasurements 1 }

tcapOmDevelRecvEntry OBJECT-TYPE
    SYNTAX	TcapOmDevelEntry
    MAX-ACCESS	not-accessible
    STATUS	current
    DESCRIPTION
	""
    REFERENCE
	""
    INDEX	{
	tcapApplicationSubsystemId, -- shared index
	tcapApplicationEntityId	    -- shared index
    }
    ::= { tcapOmDevelRecvTable 1 }

TcapOmDevelEntry ::= SEQUENCE {
    tcapOmDevelRecvPabortMessageType		Counter,
    tcapOmDevelRecvPabortIncorrectTp		Counter,
    tcapOmDevelRecvPabortBadTp			Counter,
    tcapOmDevelRecvRejectUnrecComp		Counter,
    tcapOmDevelRecvRejectMistypeComp		Counter,
    tcapOmDevelRecvRejectBadCompStruct		Counter,
    tcapOmDevelRecvRejectUnrecLinkId		Counter,
    tcapOmDevelRecvRejectUnrecIdRetRes		Counter,
    tcapOmDevelRecvRejectUnexpRetRes		Counter,
    tcapOmDevelRecvRejectUnrecIdRetErr		Counter,
    tcapOmDevelRecvRejectUnexpRetErr		Counter,
    tcapOmDevelRecvUsrRejDupInvokeId		Counter,
    tcapOmDevelRecvUsrRejUnrecOper		Counter,
    tcapOmDevelRecvUsrRejParmInvoke		Counter,
    tcapOmDevelRecvUsrRejReleasing		Counter,
    tcapOmDevelRecvUsrRejUnexpLinkResp		Counter,
    tcapOmDevelRecvUsrRejUnexpLinkOper		Counter,
    tcapOmDevelRecvUsrRejUnrecError		Counter,
    tcapOmDevelRecvUsrRejUnexpError		Counter,
    tcapOmDevelRecvUsrRejParmRetResult		Counter,
    tcapOmDevelRecvUsrRejParmRetError		Counter,
    tcapOmDevelRecv5minValidIntervals		HCPerfValidIntervals,
    tcapOmDevelRecv15minValidIntervals		HCPerfValidIntervals
}

tcapOmDevelRecvPabortMessageType OBJECT-TYPE
    SYNTAX	Counter
    UNITS	"Events"
    MAX-ACCESS	read-only
    STATUS	current
    DESCRIPTION
	"The number of protocol errors detected in the transaction 
	 portion (abort received) with P-abort cause unregonized message 
	 type.  This is an obligatory measurement collected on a 
	 first-and-interval basis.  This measurement is pertinent for 
	 development purposes only.
	 
	 Problem isolation during development may be assisted by 
	 measurements that indicate the reason for the protocol error 
	 being reported.  This includes protocol errors detected in the 
	 transaction portion that are not due to resource limitation.
	 
	 Note 14.1 a) was moved to A.1 a)."
    REFERENCE
	"ITU-T Rec. Q.752 (06/97) Table 14, Item 14.1 a).
	 ITU-T Rec. Q.752 (06/97) Table A.1, Item A.1 a)."
    ::= { tcapOmDevelRecvEntry 1 }

tcapOmDevelRecvPabortIncorrectTp OBJECT-TYPE
    SYNTAX	Counter
    UNITS	"Events"
    MAX-ACCESS	read-only
    STATUS	current
    DESCRIPTION
	"The number of protocol errors detected in the transaction 
	 portion (abort received) with P-abort cause incorrect 
	 transaction portion.  This is an obligatory measurement 
	 collected on a first-and-interval basis.  This measurement is 
	 pertinent for development purposes only.
	 
	 Problem isolation during development may be assisted by 
	 measurements that indicate the reason for the protocol error 
	 being reported.  This includes protocol errors detected in the 
	 transaction portion that are not due to resource limitation.
	 
	 Note 14.1 b) was moved to A.1 b)."
    REFERENCE
	"ITU-T Rec. Q.752 (06/97) Table 14, Item 14.1 b).
	 ITU-T Rec. Q.752 (06/97) Table A.1, Item A.1 b)."
    ::= { tcapOmDevelRecvEntry 2 }

tcapOmDevelRecvPabortBadTp OBJECT-TYPE
    SYNTAX	Counter
    UNITS	"Events"
    MAX-ACCESS	read-only
    STATUS	current
    DESCRIPTION
	"The number of protocol errors detected in the transaction 
	 portion (abort received) with P-abort cause badly formatted 
	 transaction portion.  This is an obligatory measurement 
	 collected on a first-and-interval basis.  This measurement is 
	 pertinent for development purposes only.
	 
	 Problem isolation during development may be assisted by 
	 measurements that indicate the reason for the protocol error 
	 being reported.  This includes protocol errors detected in the 
	 transaction portion that are not due to resource limitation.
	 
	 Note 14.1 c) was moved to A.1 c)."
    REFERENCE
	"ITU-T Rec. Q.752 (06/97) Table 14, Item 14.1 c).
	 ITU-T Rec. Q.752 (06/97) Table A.1, Item A.1 c)."
    ::= { tcapOmDevelRecvEntry 3 }

tcapOmDevelRecvRejectUnrecComp OBJECT-TYPE
    SYNTAX	Counter
    UNITS	"Events"
    MAX-ACCESS	read-only
    STATUS	current
    DESCRIPTION
	"Protocol error detected in component portion (reject received) 
	 with problem code unrecognized component (general problem).  
	 This measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 a) moved to A.1 a)."
    REFERENCE
	"ITU-T Rec. Q.752 (06/97) Table 14, Item 14.2 a).
	 ITU-T Rec. Q.752 (06/97) Table A.1, Item A.2 a).
	 ITU-T Rec. Q.772, Clause 3.8."
    ::= { tcapOmDevelRecvEntry 4 }

tcapOmDevelRecvRejectMistypeComp OBJECT-TYPE
    SYNTAX	Counter
    UNITS	"Events"
    MAX-ACCESS	read-only
    STATUS	current
    DESCRIPTION
	"Protocol error detected in component portion (reject received) 
	 with problem code mistyped component (general problem).  This 
	 measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 b) moved to A.1 b)."
    REFERENCE
	"ITU-T Rec. Q.752 (06/97) Table 14, Item 14.2 b).
	 ITU-T Rec. Q.752 (06/97) Table A.1, Item A.2 b).
	 ITU-T Rec. Q.772, Clause 3.8."
    ::= { tcapOmDevelRecvEntry 5 }

tcapOmDevelRecvRejectBadCompStruct OBJECT-TYPE
    SYNTAX	Counter
    UNITS	"Events"
    MAX-ACCESS	read-only
    STATUS	current
    DESCRIPTION
	"Protocol error detected in component portion (reject received) 
	 with problem code badly structured component (general problem).  
	 This measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 c) moved to A.1 c)."
    REFERENCE
	"ITU-T Rec. Q.752 (06/97) Table 14, Item 14.2 c).
	 ITU-T Rec. Q.752 (06/97) Table A.1, Item A.2 c).
	 ITU-T Rec. Q.772, Clause 3.8."
    ::= { tcapOmDevelRecvEntry 6 }

tcapOmDevelRecvRejectUnrecLinkId OBJECT-TYPE
    SYNTAX	Counter
    UNITS	"Events"
    MAX-ACCESS	read-only
    STATUS	current
    DESCRIPTION
	"Protocol error detected in component portion (reject received) 
	 with problem code unrecognized linked identity (invoke: invoke 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 d) moved to A.1 d)."
    REFERENCE
	"ITU-T Rec. Q.752 (06/97) Table 14, Item 14.2 d).
	 ITU-T Rec. Q.752 (06/97) Table A.1, Item A.2 d).
	 ITU-T Rec. Q.772, Clause 3.8."
    ::= { tcapOmDevelRecvEntry 7 }

tcapOmDevelRecvRejectUnrecIdRetRes OBJECT-TYPE
    SYNTAX	Counter
    UNITS	"Events"
    MAX-ACCESS	read-only
    STATUS	current
    DESCRIPTION
	"Protocol error detected in component portion (reject received) 
	 with problem code unrecognized invoke identity (return result 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 e) moved to A.1 e)."
    REFERENCE
	"ITU-T Rec. Q.752 (06/97) Table 14, Item 14.2 e).
	 ITU-T Rec. Q.752 (06/97) Table A.1, Item A.2 e).
	 ITU-T Rec. Q.772, Clause 3.8."
    ::= { tcapOmDevelRecvEntry 8 }

tcapOmDevelRecvRejectUnexpRetRes OBJECT-TYPE
    SYNTAX	Counter
    UNITS	"Events"
    MAX-ACCESS	read-only
    STATUS	current
    DESCRIPTION
	"Protocol error detected in component portion (reject received) 
	 with problem code return result (RR) unexpected (return result 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 f) moved to A.1 f)."
    REFERENCE
	"ITU-T Rec. Q.752 (06/97) Table 14, Item 14.2 f).
	 ITU-T Rec. Q.752 (06/97) Table A.1, Item A.2 f).
	 ITU-T Rec. Q.772, Clause 3.8."
    ::= { tcapOmDevelRecvEntry 9 }

tcapOmDevelRecvRejectUnrecIdRetErr OBJECT-TYPE
    SYNTAX	Counter
    UNITS	"Events"
    MAX-ACCESS	read-only
    STATUS	current
    DESCRIPTION
	"Protocol error detected in component portion (reject received) 
	 with problem code unrecognized invoke identity (RE) (return 
	 error problem).  This measurement is non-obligatory and is 
	 collected on a first-and-interval basis.  This measurement is 
	 pertinent for development purposes only.
	 
	 Problem isolation during development may be assisted by 
	 measurements that indicate the reason for the protocol error 
	 being reported.  This includes protocol errors detected in the 
	 component portion that are not due to resource limitation.
	 
	 Note 14.2 g) moved to A.1 g)."
    REFERENCE
	"ITU-T Rec. Q.752 (06/97) Table 14, Item 14.2 g).
	 ITU-T Rec. Q.752 (06/97) Table A.1, Item A.2 g).
	 ITU-T Rec. Q.772, Clause 3.8."
    ::= { tcapOmDevelRecvEntry 10 }

tcapOmDevelRecvRejectUnexpRetErr OBJECT-TYPE
    SYNTAX	Counter
    UNITS	"Events"
    MAX-ACCESS	read-only
    STATUS	current
    DESCRIPTION
	"Protocol error detected in component portion (reject received) 
	 with problem code return error (RE) unexpected (return error 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 h) moved to A.1 h)."
    REFERENCE
	"ITU-T Rec. Q.752 (06/97) Table 14, Item 14.2 h).
	 ITU-T Rec. Q.752 (06/97) Table A.1, Item A.2 h).
	 ITU-T Rec. Q.772, Clause 3.8."
    ::= { tcapOmDevelRecvEntry 11 }

tcapOmDevelRecvUsrRejDupInvokeId OBJECT-TYPE
    SYNTAX	Counter
    UNITS	"Events"
    MAX-ACCESS	read-only
    STATUS	current
    DESCRIPTION
	"The number of TC-user generated problems (TC-user Reject 
	 received) with problem duplicate invoke identity (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 a).
	 ITU-T Rec. Q.752 (06/97) Table A.1, Item A.3 a)."
    ::= { tcapOmDevelRecvEntry 12 }

tcapOmDevelRecvUsrRejUnrecOper OBJECT-TYPE
    SYNTAX	Counter
    UNITS	"Events"
    MAX-ACCESS	read-only
    STATUS	current
    DESCRIPTION
	"The number of TC-user generated problems (TC-user Reject 
	 received) with problem urecognized operation (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 b).
	 ITU-T Rec. Q.752 (06/97) Table A.1, Item A.3 b)."
    ::= { tcapOmDevelRecvEntry 13 }

tcapOmDevelRecvUsrRejParmInvoke OBJECT-TYPE
    SYNTAX	Counter
    UNITS	"Events"
    MAX-ACCESS	read-only
    STATUS	current
    DESCRIPTION
	"The number of TC-user generated problems (TC-user Reject 
	 received) with problem mistyped parameter (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 c).
	 ITU-T Rec. Q.752 (06/97) Table A.1, Item A.3 c)."
    ::= { tcapOmDevelRecvEntry 14 }

tcapOmDevelRecvUsrRejReleasing OBJECT-TYPE
    SYNTAX	Counter
    UNITS	"Events"
    MAX-ACCESS	read-only
    STATUS	current
    DESCRIPTION
	"The number of TC-user generated problems (TC-user Reject 
	 received) with problem initiating release (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 e).
	 ITU-T Rec. Q.752 (06/97) Table A.1, Item A.3 d)."
    ::= { tcapOmDevelRecvEntry 15 }

tcapOmDevelRecvUsrRejUnexpLinkResp OBJECT-TYPE
    SYNTAX	Counter
    UNITS	"Events"
    MAX-ACCESS	read-only
    STATUS	current
    DESCRIPTION
	"The number of TC-user generated problems (TC-user Reject 
	 received) with problem linked response unexpected (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 f).
	 ITU-T Rec. Q.752 (06/97) Table A.1, Item A.3 e)."
    ::= { tcapOmDevelRecvEntry 16 }

tcapOmDevelRecvUsrRejUnexpLinkOper OBJECT-TYPE
    SYNTAX	Counter
    UNITS	"Events"
    MAX-ACCESS	read-only
    STATUS	current
    DESCRIPTION
	"The number of TC-user generated problems (TC-user Reject 
	 received) with problem unexpected linked operation (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 g).
	 ITU-T Rec. Q.752 (06/97) Table A.1, Item A.3 f)."
    ::= { tcapOmDevelRecvEntry 17 }

tcapOmDevelRecvUsrRejUnrecError OBJECT-TYPE
    SYNTAX	Counter
    UNITS	"Events"
    MAX-ACCESS	read-only
    STATUS	current
    DESCRIPTION
	"The number of TC-user generated problems (TC-user Reject 
	 received) with problem unrecognized error (return error 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 h).
	 ITU-T Rec. Q.752 (06/97) Table A.1, Item A.3 g)."
    ::= { tcapOmDevelRecvEntry 18 }

tcapOmDevelRecvUsrRejUnexpError OBJECT-TYPE
    SYNTAX	Counter
    UNITS	"Events"
    MAX-ACCESS	read-only
    STATUS	current
    DESCRIPTION
	"The number of TC-user generated problems (TC-user Reject 
	 received) with problem unexpected error (return error problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 i).
	 ITU-T Rec. Q.752 (06/97) Table A.1, Item A.3 h)."
    ::= { tcapOmDevelRecvEntry 19 }

tcapOmDevelRecvUsrRejParmRetResult OBJECT-TYPE
    SYNTAX	Counter
    UNITS	"Events"
    MAX-ACCESS	read-only
    STATUS	current
    DESCRIPTION
	"The number of TC-user generated problems (TC-user Reject 
	 received) with problem mistyped parameter (return result 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 j).
	 ITU-T Rec. Q.752 (06/97) Table A.1, Item A.3 i)."
    ::= { tcapOmDevelRecvEntry 20 }

tcapOmDevelRecvUsrRejParmRetError OBJECT-TYPE
    SYNTAX	Counter
    UNITS	"Events"
    MAX-ACCESS	read-only
    STATUS	current
    DESCRIPTION
	"The number of TC-user generated problems (TC-user Reject 
	 received) with problem mystyped parameter (return error 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 k).
	 ITU-T Rec. Q.752 (06/97) Table A.1, Item A.3 j)."
    ::= { tcapOmDevelRecvEntry 21 }

tcapOmDevelRecv5minValidIntervals OBJECT-TYPE
    SYNTAX	HCPerfValidIntervals
    MAX-ACCESS	read-only
    STATUS	current
    DESCRIPTION
	"Indicates the number of valid 5-minute intervals of historical 
	 data that is collected int the corresonding history data table."
    ::= { tcapOmDevelRecvEntry 22 }

tcapOmDevelRecv15minValidIntervals OBJECT-TYPE
    SYNTAX	HCPerfValidIntervals
    MAX-ACCESS	read-only
    STATUS	current
    DESCRIPTION
	"Indicates the number of valid 15-minute intervals of historical 
	 data that is collected in the corresponding history data 
	 table."
    ::= { tcapOmDevelRecvEntry 23 }


-- =============================================================================

tcapOmDevelRecvCurrentTable OBJECT-TYPE
    SYNTAX	SEQUENCE OF TcapOmDevelCurrentEntry
    MAX-ACCESS	not-accessible
    STATUS	current
    DESCRIPTION
	""
    REFERENCE
	""
    ::= { tcapOmDevelMeasurements 2 }

tcapOmDevelRecvCurrentEntry OBJECT-TYPE
    SYNTAX	TcapOmDevelCurrentEntry
    MAX-ACCESS	not-accessible
    STATUS	current
    DESCRIPTION
	""
    REFERENCE
	""
    INDEX	{
	tcapApplicationSubsystemId, -- shared index
	tcapApplicationEntityId	    -- shared index
    }
    ::= { tcapOmDevelRecvCurrentTable 1 }

TcapOmDevelCurrentEntry ::= SEQUENCE {
    tcapOmDevelRecvCurrentPabortMessageType	PerfCurrentCount,
    tcapOmDevelRecvCurrentPabortIncorrectTp	PerfCurrentCount,
    tcapOmDevelRecvCurrentPabortBadTp		PerfCurrentCount,
    tcapOmDevelRecvCurrentRejectUnrecComp	PerfCurrentCount,
    tcapOmDevelRecvCurrentRejectMistypeComp	PerfCurrentCount,
    tcapOmDevelRecvCurrentRejectBadCompStruct	PerfCurrentCount,
    tcapOmDevelRecvCurrentRejectUnrecLinkId	PerfCurrentCount,
    tcapOmDevelRecvCurrentRejectUnrecIdRetRes	PerfCurrentCount,
    tcapOmDevelRecvCurrentRejectUnexpRetRes	PerfCurrentCount,
    tcapOmDevelRecvCurrentRejectUnrecIdRetErr	PerfCurrentCount,
    tcapOmDevelRecvCurrentRejectUnexpRetErr	PerfCurrentCount,
    tcapOmDevelRecvCurrentUsrRejDupInvokeId	PerfCurrentCount,
    tcapOmDevelRecvCurrentUsrRejUnrecOper	PerfCurrentCount,
    tcapOmDevelRecvCurrentUsrRejParmInvoke	PerfCurrentCount,
    tcapOmDevelRecvCurrentUsrRejReleasing	PerfCurrentCount,
    tcapOmDevelRecvCurrentUsrRejUnexpLinkResp	PerfCurrentCount,
    tcapOmDevelRecvCurrentUsrRejUnexpLinkOper	PerfCurrentCount,
    tcapOmDevelRecvCurrentUsrRejUnrecError	PerfCurrentCount,
    tcapOmDevelRecvCurrentUsrRejUnexpError	PerfCurrentCount,
    tcapOmDevelRecvCurrentUsrRejParmRetResult	PerfCurrentCount,
    tcapOmDevelRecvCurrentUsrRejParmRetError	PerfCurrentCount
}

tcapOmDevelRecvCurrentPabortMessageType OBJECT-TYPE
    SYNTAX	PerfCurrentCount
    UNITS	"Events"
    MAX-ACCESS	read-only
    STATUS	current
    DESCRIPTION
	"The number of protocol errors detected in the transaction 
	 portion (abort received) with P-abort cause unregonized message 
	 type.  This is an obligatory measurement collected on a 
	 first-and-interval basis.  This measurement is pertinent for 
	 development purposes only.
	 
	 Problem isolation during development may be assisted by 
	 measurements that indicate the reason for the protocol error 
	 being reported.  This includes protocol errors detected in the 
	 transaction portion that are not due to resource limitation.
	 
	 Note 14.1 a) was moved to A.1 a)."
    REFERENCE
	"ITU-T Rec. Q.752 (06/97) Table 14, Item 14.1 a).
	 ITU-T Rec. Q.752 (06/97) Table A.1, Item A.1 a)."
    ::= { tcapOmDevelRecvCurrentEntry 1 }

tcapOmDevelRecvCurrentPabortIncorrectTp OBJECT-TYPE
    SYNTAX	PerfCurrentCount
    UNITS	"Events"
    MAX-ACCESS	read-only
    STATUS	current
    DESCRIPTION
	"The number of protocol errors detected in the transaction 
	 portion (abort received) with P-abort cause incorrect 
	 transaction portion.  This is an obligatory measurement 
	 collected on a first-and-interval basis.  This measurement is 
	 pertinent for development purposes only.
	 
	 Problem isolation during development may be assisted by 
	 measurements that indicate the reason for the protocol error 
	 being reported.  This includes protocol errors detected in the 
	 transaction portion that are not due to resource limitation.
	 
	 Note 14.1 b) was moved to A.1 b)."
    REFERENCE
	"ITU-T Rec. Q.752 (06/97) Table 14, Item 14.1 b).
	 ITU-T Rec. Q.752 (06/97) Table A.1, Item A.1 b)."
    ::= { tcapOmDevelRecvCurrentEntry 2 }

tcapOmDevelRecvCurrentPabortBadTp OBJECT-TYPE
    SYNTAX	PerfCurrentCount
    UNITS	"Events"
    MAX-ACCESS	read-only
    STATUS	current
    DESCRIPTION
	"The number of protocol errors detected in the transaction 
	 portion (abort received) with P-abort cause badly formatted 
	 transaction portion.  This is an obligatory measurement 
	 collected on a first-and-interval basis.  This measurement is 
	 pertinent for development purposes only.
	 
	 Problem isolation during development may be assisted by 
	 measurements that indicate the reason for the protocol error 
	 being reported.  This includes protocol errors detected in the 
	 transaction portion that are not due to resource limitation.
	 
	 Note 14.1 c) was moved to A.1 c)."
    REFERENCE
	"ITU-T Rec. Q.752 (06/97) Table 14, Item 14.1 c).
	 ITU-T Rec. Q.752 (06/97) Table A.1, Item A.1 c)."
    ::= { tcapOmDevelRecvCurrentEntry 3 }

tcapOmDevelRecvCurrentRejectUnrecComp OBJECT-TYPE
    SYNTAX	PerfCurrentCount
    UNITS	"Events"
    MAX-ACCESS	read-only
    STATUS	current
    DESCRIPTION
	"Protocol error detected in component portion (reject received) 
	 with problem code unrecognized component (general problem).  
	 This measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 a) moved to A.1 a)."
    REFERENCE
	"ITU-T Rec. Q.752 (06/97) Table 14, Item 14.2 a).
	 ITU-T Rec. Q.752 (06/97) Table A.1, Item A.2 a).
	 ITU-T Rec. Q.772, Clause 3.8."
    ::= { tcapOmDevelRecvCurrentEntry 4 }

tcapOmDevelRecvCurrentRejectMistypeComp OBJECT-TYPE
    SYNTAX	PerfCurrentCount
    UNITS	"Events"
    MAX-ACCESS	read-only
    STATUS	current
    DESCRIPTION
	"Protocol error detected in component portion (reject received) 
	 with problem code mistyped component (general problem).  This 
	 measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 b) moved to A.1 b)."
    REFERENCE
	"ITU-T Rec. Q.752 (06/97) Table 14, Item 14.2 b).
	 ITU-T Rec. Q.752 (06/97) Table A.1, Item A.2 b).
	 ITU-T Rec. Q.772, Clause 3.8."
    ::= { tcapOmDevelRecvCurrentEntry 5 }

tcapOmDevelRecvCurrentRejectBadCompStruct OBJECT-TYPE
    SYNTAX	PerfCurrentCount
    UNITS	"Events"
    MAX-ACCESS	read-only
    STATUS	current
    DESCRIPTION
	"Protocol error detected in component portion (reject received) 
	 with problem code badly structured component (general problem).  
	 This measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 c) moved to A.1 c)."
    REFERENCE
	"ITU-T Rec. Q.752 (06/97) Table 14, Item 14.2 c).
	 ITU-T Rec. Q.752 (06/97) Table A.1, Item A.2 c).
	 ITU-T Rec. Q.772, Clause 3.8."
    ::= { tcapOmDevelRecvCurrentEntry 6 }

tcapOmDevelRecvCurrentRejectUnrecLinkId OBJECT-TYPE
    SYNTAX	PerfCurrentCount
    UNITS	"Events"
    MAX-ACCESS	read-only
    STATUS	current
    DESCRIPTION
	"Protocol error detected in component portion (reject received) 
	 with problem code unrecognized linked identity (invoke: invoke 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 d) moved to A.1 d)."
    REFERENCE
	"ITU-T Rec. Q.752 (06/97) Table 14, Item 14.2 d).
	 ITU-T Rec. Q.752 (06/97) Table A.1, Item A.2 d).
	 ITU-T Rec. Q.772, Clause 3.8."
    ::= { tcapOmDevelRecvCurrentEntry 7 }

tcapOmDevelRecvCurrentRejectUnrecIdRetRes OBJECT-TYPE
    SYNTAX	PerfCurrentCount
    UNITS	"Events"
    MAX-ACCESS	read-only
    STATUS	current
    DESCRIPTION
	"Protocol error detected in component portion (reject received) 
	 with problem code unrecognized invoke identity (return result 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 e) moved to A.1 e)."
    REFERENCE
	"ITU-T Rec. Q.752 (06/97) Table 14, Item 14.2 e).
	 ITU-T Rec. Q.752 (06/97) Table A.1, Item A.2 e).
	 ITU-T Rec. Q.772, Clause 3.8."
    ::= { tcapOmDevelRecvCurrentEntry 8 }

tcapOmDevelRecvCurrentRejectUnexpRetRes OBJECT-TYPE
    SYNTAX	PerfCurrentCount
    UNITS	"Events"
    MAX-ACCESS	read-only
    STATUS	current
    DESCRIPTION
	"Protocol error detected in component portion (reject received) 
	 with problem code return result (RR) unexpected (return result 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 f) moved to A.1 f)."
    REFERENCE
	"ITU-T Rec. Q.752 (06/97) Table 14, Item 14.2 f).
	 ITU-T Rec. Q.752 (06/97) Table A.1, Item A.2 f).
	 ITU-T Rec. Q.772, Clause 3.8."
    ::= { tcapOmDevelRecvCurrentEntry 9 }

tcapOmDevelRecvCurrentRejectUnrecIdRetErr OBJECT-TYPE
    SYNTAX	PerfCurrentCount
    UNITS	"Events"
    MAX-ACCESS	read-only
    STATUS	current
    DESCRIPTION
	"Protocol error detected in component portion (reject received) 
	 with problem code unrecognized invoke identity (RE) (return 
	 error problem).  This measurement is non-obligatory and is 
	 collected on a first-and-interval basis.  This measurement is 
	 pertinent for development purposes only.
	 
	 Problem isolation during development may be assisted by 
	 measurements that indicate the reason for the protocol error 
	 being reported.  This includes protocol errors detected in the 
	 component portion that are not due to resource limitation.
	 
	 Note 14.2 g) moved to A.1 g)."
    REFERENCE
	"ITU-T Rec. Q.752 (06/97) Table 14, Item 14.2 g).
	 ITU-T Rec. Q.752 (06/97) Table A.1, Item A.2 g).
	 ITU-T Rec. Q.772, Clause 3.8."
    ::= { tcapOmDevelRecvCurrentEntry 10 }

tcapOmDevelRecvCurrentRejectUnexpRetErr OBJECT-TYPE
    SYNTAX	PerfCurrentCount
    UNITS	"Events"
    MAX-ACCESS	read-only
    STATUS	current
    DESCRIPTION
	"Protocol error detected in component portion (reject received) 
	 with problem code return error (RE) unexpected (return error 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 h) moved to A.1 h)."
    REFERENCE
	"ITU-T Rec. Q.752 (06/97) Table 14, Item 14.2 h).
	 ITU-T Rec. Q.752 (06/97) Table A.1, Item A.2 h).
	 ITU-T Rec. Q.772, Clause 3.8."
    ::= { tcapOmDevelRecvCurrentEntry 11 }

tcapOmDevelRecvCurrentUsrRejDupInvokeId OBJECT-TYPE
    SYNTAX	PerfCurrentCount
    UNITS	"Events"
    MAX-ACCESS	read-only
    STATUS	current
    DESCRIPTION
	"The number of TC-user generated problems (TC-user Reject 
	 received) with problem duplicate invoke identity (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 a).
	 ITU-T Rec. Q.752 (06/97) Table A.1, Item A.3 a)."
    ::= { tcapOmDevelRecvCurrentEntry 12 }

tcapOmDevelRecvCurrentUsrRejUnrecOper OBJECT-TYPE
    SYNTAX	PerfCurrentCount
    UNITS	"Events"
    MAX-ACCESS	read-only
    STATUS	current
    DESCRIPTION
	"The number of TC-user generated problems (TC-user Reject 
	 received) with problem urecognized operation (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 b).
	 ITU-T Rec. Q.752 (06/97) Table A.1, Item A.3 b)."
    ::= { tcapOmDevelRecvCurrentEntry 13 }

tcapOmDevelRecvCurrentUsrRejParmInvoke OBJECT-TYPE
    SYNTAX	PerfCurrentCount
    UNITS	"Events"
    MAX-ACCESS	read-only
    STATUS	current
    DESCRIPTION
	"The number of TC-user generated problems (TC-user Reject 
	 received) with problem mistyped parameter (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 c).
	 ITU-T Rec. Q.752 (06/97) Table A.1, Item A.3 c)."
    ::= { tcapOmDevelRecvCurrentEntry 14 }

tcapOmDevelRecvCurrentUsrRejReleasing OBJECT-TYPE
    SYNTAX	PerfCurrentCount
    UNITS	"Events"
    MAX-ACCESS	read-only
    STATUS	current
    DESCRIPTION
	"The number of TC-user generated problems (TC-user Reject 
	 received) with problem initiating release (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 e).
	 ITU-T Rec. Q.752 (06/97) Table A.1, Item A.3 d)."
    ::= { tcapOmDevelRecvCurrentEntry 15 }

tcapOmDevelRecvCurrentUsrRejUnexpLinkResp OBJECT-TYPE
    SYNTAX	PerfCurrentCount
    UNITS	"Events"
    MAX-ACCESS	read-only
    STATUS	current
    DESCRIPTION
	"The number of TC-user generated problems (TC-user Reject 
	 received) with problem linked response unexpected (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 f).
	 ITU-T Rec. Q.752 (06/97) Table A.1, Item A.3 e)."
    ::= { tcapOmDevelRecvCurrentEntry 16 }

tcapOmDevelRecvCurrentUsrRejUnexpLinkOper OBJECT-TYPE
    SYNTAX	PerfCurrentCount
    UNITS	"Events"
    MAX-ACCESS	read-only
    STATUS	current
    DESCRIPTION
	"The number of TC-user generated problems (TC-user Reject 
	 received) with problem unexpected linked operation (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 g).
	 ITU-T Rec. Q.752 (06/97) Table A.1, Item A.3 f)."
    ::= { tcapOmDevelRecvCurrentEntry 17 }

tcapOmDevelRecvCurrentUsrRejUnrecError OBJECT-TYPE
    SYNTAX	PerfCurrentCount
    UNITS	"Events"
    MAX-ACCESS	read-only
    STATUS	current
    DESCRIPTION
	"The number of TC-user generated problems (TC-user Reject 
	 received) with problem unrecognized error (return error 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 h).
	 ITU-T Rec. Q.752 (06/97) Table A.1, Item A.3 g)."
    ::= { tcapOmDevelRecvCurrentEntry 18 }

tcapOmDevelRecvCurrentUsrRejUnexpError OBJECT-TYPE
    SYNTAX	PerfCurrentCount
    UNITS	"Events"
    MAX-ACCESS	read-only
    STATUS	current
    DESCRIPTION
	"The number of TC-user generated problems (TC-user Reject 
	 received) with problem unexpected error (return error problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 i).
	 ITU-T Rec. Q.752 (06/97) Table A.1, Item A.3 h)."
    ::= { tcapOmDevelRecvCurrentEntry 19 }

tcapOmDevelRecvCurrentUsrRejParmRetResult OBJECT-TYPE
    SYNTAX	PerfCurrentCount
    UNITS	"Events"
    MAX-ACCESS	read-only
    STATUS	current
    DESCRIPTION
	"The number of TC-user generated problems (TC-user Reject 
	 received) with problem mistyped parameter (return result 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 j).
	 ITU-T Rec. Q.752 (06/97) Table A.1, Item A.3 i)."
    ::= { tcapOmDevelRecvCurrentEntry 20 }

tcapOmDevelRecvCurrentUsrRejParmRetError OBJECT-TYPE
    SYNTAX	PerfCurrentCount
    UNITS	"Events"
    MAX-ACCESS	read-only
    STATUS	current
    DESCRIPTION
	"The number of TC-user generated problems (TC-user Reject 
	 received) with problem mystyped parameter (return error 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 k).
	 ITU-T Rec. Q.752 (06/97) Table A.1, Item A.3 j)."
    ::= { tcapOmDevelRecvCurrentEntry 21 }


-- =============================================================================

tcapOmDevelRecv5minIntTable OBJECT-TYPE
    SYNTAX	SEQUENCE OF TcapOmDevel5minIntEntry
    MAX-ACCESS	not-accessible
    STATUS	current
    DESCRIPTION
	""
    REFERENCE
	""
    ::= { tcapOmDevelMeasurements 3 }

tcapOmDevelRecv5minIntEntry OBJECT-TYPE
    SYNTAX	TcapOmDevel5minIntEntry
    MAX-ACCESS	not-accessible
    STATUS	current
    DESCRIPTION
	""
    REFERENCE
	""
    INDEX	{
	tcapApplicationSubsystemId, -- shared index
	tcapApplicationEntityId,    -- shared index
	tcapOmInterval		    -- shared index
    }
    ::= { tcapOmDevelRecv5minIntTable 1 }

TcapOmDevel5minIntEntry ::= SEQUENCE {
    tcapOmDevelRecv5minIntPabortMessageType	PerfIntervalCount,
    tcapOmDevelRecv5minIntPabortIncorrectTp	PerfIntervalCount,
    tcapOmDevelRecv5minIntPabortBadTp		PerfIntervalCount,
    tcapOmDevelRecv5minIntRejectUnrecComp	PerfIntervalCount,
    tcapOmDevelRecv5minIntRejectMistypeComp	PerfIntervalCount,
    tcapOmDevelRecv5minIntRejectBadCompStruct	PerfIntervalCount,
    tcapOmDevelRecv5minIntRejectUnrecLinkId	PerfIntervalCount,
    tcapOmDevelRecv5minIntRejectUnrecIdRetRes	PerfIntervalCount,
    tcapOmDevelRecv5minIntRejectUnexpRetRes	PerfIntervalCount,
    tcapOmDevelRecv5minIntRejectUnrecIdRetErr	PerfIntervalCount,
    tcapOmDevelRecv5minIntRejectUnexpRetErr	PerfIntervalCount,
    tcapOmDevelRecv5minIntUsrRejDupInvokeId	PerfIntervalCount,
    tcapOmDevelRecv5minIntUsrRejUnrecOper	PerfIntervalCount,
    tcapOmDevelRecv5minIntUsrRejParmInvoke	PerfIntervalCount,
    tcapOmDevelRecv5minIntUsrRejReleasing	PerfIntervalCount,
    tcapOmDevelRecv5minIntUsrRejUnexpLinkResp	PerfIntervalCount,
    tcapOmDevelRecv5minIntUsrRejUnexpLinkOper	PerfIntervalCount,
    tcapOmDevelRecv5minIntUsrRejUnrecError	PerfIntervalCount,
    tcapOmDevelRecv5minIntUsrRejUnexpError	PerfIntervalCount,
    tcapOmDevelRecv5minIntUsrRejParmRetResult	PerfIntervalCount,
    tcapOmDevelRecv5minIntUsrRejParmRetError	PerfIntervalCount
}

tcapOmDevelRecv5minIntPabortMessageType OBJECT-TYPE
    SYNTAX	PerfIntervalCount
    UNITS	"Events"
    MAX-ACCESS	read-only
    STATUS	current
    DESCRIPTION
	"The number of protocol errors detected in the transaction 
	 portion (abort received) with P-abort cause unregonized message 
	 type.  This is an obligatory measurement collected on a 
	 first-and-interval basis.  This measurement is pertinent for 
	 development purposes only.
	 
	 Problem isolation during development may be assisted by 
	 measurements that indicate the reason for the protocol error 
	 being reported.  This includes protocol errors detected in the 
	 transaction portion that are not due to resource limitation.
	 
	 Note 14.1 a) was moved to A.1 a)."
    REFERENCE
	"ITU-T Rec. Q.752 (06/97) Table 14, Item 14.1 a).
	 ITU-T Rec. Q.752 (06/97) Table A.1, Item A.1 a)."
    ::= { tcapOmDevelRecv5minIntEntry 1 }

tcapOmDevelRecv5minIntPabortIncorrectTp OBJECT-TYPE
    SYNTAX	PerfIntervalCount
    UNITS	"Events"
    MAX-ACCESS	read-only
    STATUS	current
    DESCRIPTION
	"The number of protocol errors detected in the transaction 
	 portion (abort received) with P-abort cause incorrect 
	 transaction portion.  This is an obligatory measurement 
	 collected on a first-and-interval basis.  This measurement is 
	 pertinent for development purposes only.
	 
	 Problem isolation during development may be assisted by 
	 measurements that indicate the reason for the protocol error 
	 being reported.  This includes protocol errors detected in the 
	 transaction portion that are not due to resource limitation.
	 
	 Note 14.1 b) was moved to A.1 b)."
    REFERENCE
	"ITU-T Rec. Q.752 (06/97) Table 14, Item 14.1 b).
	 ITU-T Rec. Q.752 (06/97) Table A.1, Item A.1 b)."
    ::= { tcapOmDevelRecv5minIntEntry 2 }

tcapOmDevelRecv5minIntPabortBadTp OBJECT-TYPE
    SYNTAX	PerfIntervalCount
    UNITS	"Events"
    MAX-ACCESS	read-only
    STATUS	current
    DESCRIPTION
	"The number of protocol errors detected in the transaction 
	 portion (abort received) with P-abort cause badly formatted 
	 transaction portion.  This is an obligatory measurement 
	 collected on a first-and-interval basis.  This measurement is 
	 pertinent for development purposes only.
	 
	 Problem isolation during development may be assisted by 
	 measurements that indicate the reason for the protocol error 
	 being reported.  This includes protocol errors detected in the 
	 transaction portion that are not due to resource limitation.
	 
	 Note 14.1 c) was moved to A.1 c)."
    REFERENCE
	"ITU-T Rec. Q.752 (06/97) Table 14, Item 14.1 c).
	 ITU-T Rec. Q.752 (06/97) Table A.1, Item A.1 c)."
    ::= { tcapOmDevelRecv5minIntEntry 3 }

tcapOmDevelRecv5minIntRejectUnrecComp OBJECT-TYPE
    SYNTAX	PerfIntervalCount
    UNITS	"Events"
    MAX-ACCESS	read-only
    STATUS	current
    DESCRIPTION
	"Protocol error detected in component portion (reject received) 
	 with problem code unrecognized component (general problem).  
	 This measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 a) moved to A.1 a)."
    REFERENCE
	"ITU-T Rec. Q.752 (06/97) Table 14, Item 14.2 a).
	 ITU-T Rec. Q.752 (06/97) Table A.1, Item A.2 a).
	 ITU-T Rec. Q.772, Clause 3.8."
    ::= { tcapOmDevelRecv5minIntEntry 4 }

tcapOmDevelRecv5minIntRejectMistypeComp OBJECT-TYPE
    SYNTAX	PerfIntervalCount
    UNITS	"Events"
    MAX-ACCESS	read-only
    STATUS	current
    DESCRIPTION
	"Protocol error detected in component portion (reject received) 
	 with problem code mistyped component (general problem).  This 
	 measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 b) moved to A.1 b)."
    REFERENCE
	"ITU-T Rec. Q.752 (06/97) Table 14, Item 14.2 b).
	 ITU-T Rec. Q.752 (06/97) Table A.1, Item A.2 b).
	 ITU-T Rec. Q.772, Clause 3.8."
    ::= { tcapOmDevelRecv5minIntEntry 5 }

tcapOmDevelRecv5minIntRejectBadCompStruct OBJECT-TYPE
    SYNTAX	PerfIntervalCount
    UNITS	"Events"
    MAX-ACCESS	read-only
    STATUS	current
    DESCRIPTION
	"Protocol error detected in component portion (reject received) 
	 with problem code badly structured component (general problem).  
	 This measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 c) moved to A.1 c)."
    REFERENCE
	"ITU-T Rec. Q.752 (06/97) Table 14, Item 14.2 c).
	 ITU-T Rec. Q.752 (06/97) Table A.1, Item A.2 c).
	 ITU-T Rec. Q.772, Clause 3.8."
    ::= { tcapOmDevelRecv5minIntEntry 6 }

tcapOmDevelRecv5minIntRejectUnrecLinkId OBJECT-TYPE
    SYNTAX	PerfIntervalCount
    UNITS	"Events"
    MAX-ACCESS	read-only
    STATUS	current
    DESCRIPTION
	"Protocol error detected in component portion (reject received) 
	 with problem code unrecognized linked identity (invoke: invoke 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 d) moved to A.1 d)."
    REFERENCE
	"ITU-T Rec. Q.752 (06/97) Table 14, Item 14.2 d).
	 ITU-T Rec. Q.752 (06/97) Table A.1, Item A.2 d).
	 ITU-T Rec. Q.772, Clause 3.8."
    ::= { tcapOmDevelRecv5minIntEntry 7 }

tcapOmDevelRecv5minIntRejectUnrecIdRetRes OBJECT-TYPE
    SYNTAX	PerfIntervalCount
    UNITS	"Events"
    MAX-ACCESS	read-only
    STATUS	current
    DESCRIPTION
	"Protocol error detected in component portion (reject received) 
	 with problem code unrecognized invoke identity (return result 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 e) moved to A.1 e)."
    REFERENCE
	"ITU-T Rec. Q.752 (06/97) Table 14, Item 14.2 e).
	 ITU-T Rec. Q.752 (06/97) Table A.1, Item A.2 e).
	 ITU-T Rec. Q.772, Clause 3.8."
    ::= { tcapOmDevelRecv5minIntEntry 8 }

tcapOmDevelRecv5minIntRejectUnexpRetRes OBJECT-TYPE
    SYNTAX	PerfIntervalCount
    UNITS	"Events"
    MAX-ACCESS	read-only
    STATUS	current
    DESCRIPTION
	"Protocol error detected in component portion (reject received) 
	 with problem code return result (RR) unexpected (return result 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 f) moved to A.1 f)."
    REFERENCE
	"ITU-T Rec. Q.752 (06/97) Table 14, Item 14.2 f).
	 ITU-T Rec. Q.752 (06/97) Table A.1, Item A.2 f).
	 ITU-T Rec. Q.772, Clause 3.8."
    ::= { tcapOmDevelRecv5minIntEntry 9 }

tcapOmDevelRecv5minIntRejectUnrecIdRetErr OBJECT-TYPE
    SYNTAX	PerfIntervalCount
    UNITS	"Events"
    MAX-ACCESS	read-only
    STATUS	current
    DESCRIPTION
	"Protocol error detected in component portion (reject received) 
	 with problem code unrecognized invoke identity (RE) (return 
	 error problem).  This measurement is non-obligatory and is 
	 collected on a first-and-interval basis.  This measurement is 
	 pertinent for development purposes only.
	 
	 Problem isolation during development may be assisted by 
	 measurements that indicate the reason for the protocol error 
	 being reported.  This includes protocol errors detected in the 
	 component portion that are not due to resource limitation.
	 
	 Note 14.2 g) moved to A.1 g)."
    REFERENCE
	"ITU-T Rec. Q.752 (06/97) Table 14, Item 14.2 g).
	 ITU-T Rec. Q.752 (06/97) Table A.1, Item A.2 g).
	 ITU-T Rec. Q.772, Clause 3.8."
    ::= { tcapOmDevelRecv5minIntEntry 10 }

tcapOmDevelRecv5minIntRejectUnexpRetErr OBJECT-TYPE
    SYNTAX	PerfIntervalCount
    UNITS	"Events"
    MAX-ACCESS	read-only
    STATUS	current
    DESCRIPTION
	"Protocol error detected in component portion (reject received) 
	 with problem code return error (RE) unexpected (return error 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 h) moved to A.1 h)."
    REFERENCE
	"ITU-T Rec. Q.752 (06/97) Table 14, Item 14.2 h).
	 ITU-T Rec. Q.752 (06/97) Table A.1, Item A.2 h).
	 ITU-T Rec. Q.772, Clause 3.8."
    ::= { tcapOmDevelRecv5minIntEntry 11 }

tcapOmDevelRecv5minIntUsrRejDupInvokeId OBJECT-TYPE
    SYNTAX	PerfIntervalCount
    UNITS	"Events"
    MAX-ACCESS	read-only
    STATUS	current
    DESCRIPTION
	"The number of TC-user generated problems (TC-user Reject 
	 received) with problem duplicate invoke identity (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 a).
	 ITU-T Rec. Q.752 (06/97) Table A.1, Item A.3 a)."
    ::= { tcapOmDevelRecv5minIntEntry 12 }

tcapOmDevelRecv5minIntUsrRejUnrecOper OBJECT-TYPE
    SYNTAX	PerfIntervalCount
    UNITS	"Events"
    MAX-ACCESS	read-only
    STATUS	current
    DESCRIPTION
	"The number of TC-user generated problems (TC-user Reject 
	 received) with problem urecognized operation (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 b).
	 ITU-T Rec. Q.752 (06/97) Table A.1, Item A.3 b)."
    ::= { tcapOmDevelRecv5minIntEntry 13 }

tcapOmDevelRecv5minIntUsrRejParmInvoke OBJECT-TYPE
    SYNTAX	PerfIntervalCount
    UNITS	"Events"
    MAX-ACCESS	read-only
    STATUS	current
    DESCRIPTION
	"The number of TC-user generated problems (TC-user Reject 
	 received) with problem mistyped parameter (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 c).
	 ITU-T Rec. Q.752 (06/97) Table A.1, Item A.3 c)."
    ::= { tcapOmDevelRecv5minIntEntry 14 }

tcapOmDevelRecv5minIntUsrRejReleasing OBJECT-TYPE
    SYNTAX	PerfIntervalCount
    UNITS	"Events"
    MAX-ACCESS	read-only
    STATUS	current
    DESCRIPTION
	"The number of TC-user generated problems (TC-user Reject 
	 received) with problem initiating release (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 e).
	 ITU-T Rec. Q.752 (06/97) Table A.1, Item A.3 d)."
    ::= { tcapOmDevelRecv5minIntEntry 15 }

tcapOmDevelRecv5minIntUsrRejUnexpLinkResp OBJECT-TYPE
    SYNTAX	PerfIntervalCount
    UNITS	"Events"
    MAX-ACCESS	read-only
    STATUS	current
    DESCRIPTION
	"The number of TC-user generated problems (TC-user Reject 
	 received) with problem linked response unexpected (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 f).
	 ITU-T Rec. Q.752 (06/97) Table A.1, Item A.3 e)."
    ::= { tcapOmDevelRecv5minIntEntry 16 }

tcapOmDevelRecv5minIntUsrRejUnexpLinkOper OBJECT-TYPE
    SYNTAX	PerfIntervalCount
    UNITS	"Events"
    MAX-ACCESS	read-only
    STATUS	current
    DESCRIPTION
	"The number of TC-user generated problems (TC-user Reject 
	 received) with problem unexpected linked operation (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 g).
	 ITU-T Rec. Q.752 (06/97) Table A.1, Item A.3 f)."
    ::= { tcapOmDevelRecv5minIntEntry 17 }

tcapOmDevelRecv5minIntUsrRejUnrecError OBJECT-TYPE
    SYNTAX	PerfIntervalCount
    UNITS	"Events"
    MAX-ACCESS	read-only
    STATUS	current
    DESCRIPTION
	"The number of TC-user generated problems (TC-user Reject 
	 received) with problem unrecognized error (return error 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 h).
	 ITU-T Rec. Q.752 (06/97) Table A.1, Item A.3 g)."
    ::= { tcapOmDevelRecv5minIntEntry 18 }

tcapOmDevelRecv5minIntUsrRejUnexpError OBJECT-TYPE
    SYNTAX	PerfIntervalCount
    UNITS	"Events"
    MAX-ACCESS	read-only
    STATUS	current
    DESCRIPTION
	"The number of TC-user generated problems (TC-user Reject 
	 received) with problem unexpected error (return error problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 i).
	 ITU-T Rec. Q.752 (06/97) Table A.1, Item A.3 h)."
    ::= { tcapOmDevelRecv5minIntEntry 19 }

tcapOmDevelRecv5minIntUsrRejParmRetResult OBJECT-TYPE
    SYNTAX	PerfIntervalCount
    UNITS	"Events"
    MAX-ACCESS	read-only
    STATUS	current
    DESCRIPTION
	"The number of TC-user generated problems (TC-user Reject 
	 received) with problem mistyped parameter (return result 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 j).
	 ITU-T Rec. Q.752 (06/97) Table A.1, Item A.3 i)."
    ::= { tcapOmDevelRecv5minIntEntry 20 }

tcapOmDevelRecv5minIntUsrRejParmRetError OBJECT-TYPE
    SYNTAX	PerfIntervalCount
    UNITS	"Events"
    MAX-ACCESS	read-only
    STATUS	current
    DESCRIPTION
	"The number of TC-user generated problems (TC-user Reject 
	 received) with problem mystyped parameter (return error 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 k).
	 ITU-T Rec. Q.752 (06/97) Table A.1, Item A.3 j)."
    ::= { tcapOmDevelRecv5minIntEntry 21 }


-- =============================================================================

tcapOmDevelRecv15minIntTable OBJECT-TYPE
    SYNTAX	SEQUENCE OF TcapOmDevel15minIntEntry
    MAX-ACCESS	not-accessible
    STATUS	current
    DESCRIPTION
	""
    REFERENCE
	""
    ::= { tcapOmDevelMeasurements 4 }

tcapOmDevelRecv15minIntEntry OBJECT-TYPE
    SYNTAX	TcapOmDevel15minIntEntry
    MAX-ACCESS	not-accessible
    STATUS	current
    DESCRIPTION
	""
    REFERENCE
	""
    INDEX	{
	tcapApplicationSubsystemId, -- shared index
	tcapApplicationEntityId,    -- shared index
	tcapOmInterval		    -- shared index
    }
    ::= { tcapOmDevelRecv15minIntTable 1 }

TcapOmDevel15minIntEntry ::= SEQUENCE {
    tcapOmDevelRecv15minIntPabortMessageType	PerfIntervalCount,
    tcapOmDevelRecv15minIntPabortIncorrectTp	PerfIntervalCount,
    tcapOmDevelRecv15minIntPabortBadTp		PerfIntervalCount,
    tcapOmDevelRecv15minIntRejectUnrecComp	PerfIntervalCount,
    tcapOmDevelRecv15minIntRejectMistypeComp	PerfIntervalCount,
    tcapOmDevelRecv15minIntRejectBadCompStruct	PerfIntervalCount,
    tcapOmDevelRecv15minIntRejectUnrecLinkId	PerfIntervalCount,
    tcapOmDevelRecv15minIntRejectUnrecIdRetRes	PerfIntervalCount,
    tcapOmDevelRecv15minIntRejectUnexpRetRes	PerfIntervalCount,
    tcapOmDevelRecv15minIntRejectUnrecIdRetErr	PerfIntervalCount,
    tcapOmDevelRecv15minIntRejectUnexpRetErr	PerfIntervalCount,
    tcapOmDevelRecv15minIntUsrRejDupInvokeId	PerfIntervalCount,
    tcapOmDevelRecv15minIntUsrRejUnrecOper	PerfIntervalCount,
    tcapOmDevelRecv15minIntUsrRejParmInvoke	PerfIntervalCount,
    tcapOmDevelRecv15minIntUsrRejReleasing	PerfIntervalCount,
    tcapOmDevelRecv15minIntUsrRejUnexpLinkResp	PerfIntervalCount,
    tcapOmDevelRecv15minIntUsrRejUnexpLinkOper	PerfIntervalCount,
    tcapOmDevelRecv15minIntUsrRejUnrecError	PerfIntervalCount,
    tcapOmDevelRecv15minIntUsrRejUnexpError	PerfIntervalCount,
    tcapOmDevelRecv15minIntUsrRejParmRetResult	PerfIntervalCount,
    tcapOmDevelRecv15minIntUsrRejParmRetError	PerfIntervalCount
}

tcapOmDevelRecv15minIntPabortMessageType OBJECT-TYPE
    SYNTAX	PerfIntervalCount
    UNITS	"Events"
    MAX-ACCESS	read-only
    STATUS	current
    DESCRIPTION
	"The number of protocol errors detected in the transaction 
	 portion (abort received) with P-abort cause unregonized message 
	 type.  This is an obligatory measurement collected on a 
	 first-and-interval basis.  This measurement is pertinent for 
	 development purposes only.
	 
	 Problem isolation during development may be assisted by 
	 measurements that indicate the reason for the protocol error 
	 being reported.  This includes protocol errors detected in the 
	 transaction portion that are not due to resource limitation.
	 
	 Note 14.1 a) was moved to A.1 a)."
    REFERENCE
	"ITU-T Rec. Q.752 (06/97) Table 14, Item 14.1 a).
	 ITU-T Rec. Q.752 (06/97) Table A.1, Item A.1 a)."
    ::= { tcapOmDevelRecv15minIntEntry 1 }

tcapOmDevelRecv15minIntPabortIncorrectTp OBJECT-TYPE
    SYNTAX	PerfIntervalCount
    UNITS	"Events"
    MAX-ACCESS	read-only
    STATUS	current
    DESCRIPTION
	"The number of protocol errors detected in the transaction 
	 portion (abort received) with P-abort cause incorrect 
	 transaction portion.  This is an obligatory measurement 
	 collected on a first-and-interval basis.  This measurement is 
	 pertinent for development purposes only.
	 
	 Problem isolation during development may be assisted by 
	 measurements that indicate the reason for the protocol error 
	 being reported.  This includes protocol errors detected in the 
	 transaction portion that are not due to resource limitation.
	 
	 Note 14.1 b) was moved to A.1 b)."
    REFERENCE
	"ITU-T Rec. Q.752 (06/97) Table 14, Item 14.1 b).
	 ITU-T Rec. Q.752 (06/97) Table A.1, Item A.1 b)."
    ::= { tcapOmDevelRecv15minIntEntry 2 }

tcapOmDevelRecv15minIntPabortBadTp OBJECT-TYPE
    SYNTAX	PerfIntervalCount
    UNITS	"Events"
    MAX-ACCESS	read-only
    STATUS	current
    DESCRIPTION
	"The number of protocol errors detected in the transaction 
	 portion (abort received) with P-abort cause badly formatted 
	 transaction portion.  This is an obligatory measurement 
	 collected on a first-and-interval basis.  This measurement is 
	 pertinent for development purposes only.
	 
	 Problem isolation during development may be assisted by 
	 measurements that indicate the reason for the protocol error 
	 being reported.  This includes protocol errors detected in the 
	 transaction portion that are not due to resource limitation.
	 
	 Note 14.1 c) was moved to A.1 c)."
    REFERENCE
	"ITU-T Rec. Q.752 (06/97) Table 14, Item 14.1 c).
	 ITU-T Rec. Q.752 (06/97) Table A.1, Item A.1 c)."
    ::= { tcapOmDevelRecv15minIntEntry 3 }

tcapOmDevelRecv15minIntRejectUnrecComp OBJECT-TYPE
    SYNTAX	PerfIntervalCount
    UNITS	"Events"
    MAX-ACCESS	read-only
    STATUS	current
    DESCRIPTION
	"Protocol error detected in component portion (reject received) 
	 with problem code unrecognized component (general problem).  
	 This measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 a) moved to A.1 a)."
    REFERENCE
	"ITU-T Rec. Q.752 (06/97) Table 14, Item 14.2 a).
	 ITU-T Rec. Q.752 (06/97) Table A.1, Item A.2 a).
	 ITU-T Rec. Q.772, Clause 3.8."
    ::= { tcapOmDevelRecv15minIntEntry 4 }

tcapOmDevelRecv15minIntRejectMistypeComp OBJECT-TYPE
    SYNTAX	PerfIntervalCount
    UNITS	"Events"
    MAX-ACCESS	read-only
    STATUS	current
    DESCRIPTION
	"Protocol error detected in component portion (reject received) 
	 with problem code mistyped component (general problem).  This 
	 measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 b) moved to A.1 b)."
    REFERENCE
	"ITU-T Rec. Q.752 (06/97) Table 14, Item 14.2 b).
	 ITU-T Rec. Q.752 (06/97) Table A.1, Item A.2 b).
	 ITU-T Rec. Q.772, Clause 3.8."
    ::= { tcapOmDevelRecv15minIntEntry 5 }

tcapOmDevelRecv15minIntRejectBadCompStruct OBJECT-TYPE
    SYNTAX	PerfIntervalCount
    UNITS	"Events"
    MAX-ACCESS	read-only
    STATUS	current
    DESCRIPTION
	"Protocol error detected in component portion (reject received) 
	 with problem code badly structured component (general problem).  
	 This measurement is obligatory and is collected on a 
	 first-and-interval basis.  This measurement is pertinent for 
	 development purposes only.
	 
	 Problem isolation during development may be assisted by 
	 measurements that indicate the reason for the protocol error 
	 being reported.  This includes protocol errors detected in the 
	 component portion that are not due to resource limitation.
	 
	 Note 14.2 c) moved to A.1 c)."
    REFERENCE
	"ITU-T Rec. Q.752 (06/97) Table 14, Item 14.2 c).
	 ITU-T Rec. Q.752 (06/97) Table A.1, Item A.2 c).
	 ITU-T Rec. Q.772, Clause 3.8."
    ::= { tcapOmDevelRecv15minIntEntry 6 }

tcapOmDevelRecv15minIntRejectUnrecLinkId OBJECT-TYPE
    SYNTAX	PerfIntervalCount
    UNITS	"Events"
    MAX-ACCESS	read-only
    STATUS	current
    DESCRIPTION
	"Protocol error detected in component portion (reject received) 
	 with problem code unrecognized linked identity (invoke: invoke 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 d) moved to A.1 d)."
    REFERENCE
	"ITU-T Rec. Q.752 (06/97) Table 14, Item 14.2 d).
	 ITU-T Rec. Q.752 (06/97) Table A.1, Item A.2 d).
	 ITU-T Rec. Q.772, Clause 3.8."
    ::= { tcapOmDevelRecv15minIntEntry 7 }

tcapOmDevelRecv15minIntRejectUnrecIdRetRes OBJECT-TYPE
    SYNTAX	PerfIntervalCount
    UNITS	"Events"
    MAX-ACCESS	read-only
    STATUS	current
    DESCRIPTION
	"Protocol error detected in component portion (reject received) 
	 with problem code unrecognized invoke identity (return result 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 e) moved to A.1 e)."
    REFERENCE
	"ITU-T Rec. Q.752 (06/97) Table 14, Item 14.2 e).
	 ITU-T Rec. Q.752 (06/97) Table A.1, Item A.2 e).
	 ITU-T Rec. Q.772, Clause 3.8."
    ::= { tcapOmDevelRecv15minIntEntry 8 }

tcapOmDevelRecv15minIntRejectUnexpRetRes OBJECT-TYPE
    SYNTAX	PerfIntervalCount
    UNITS	"Events"
    MAX-ACCESS	read-only
    STATUS	current
    DESCRIPTION
	"Protocol error detected in component portion (reject received) 
	 with problem code return result (RR) unexpected (return result 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 f) moved to A.1 f)."
    REFERENCE
	"ITU-T Rec. Q.752 (06/97) Table 14, Item 14.2 f).
	 ITU-T Rec. Q.752 (06/97) Table A.1, Item A.2 f).
	 ITU-T Rec. Q.772, Clause 3.8."
    ::= { tcapOmDevelRecv15minIntEntry 9 }

tcapOmDevelRecv15minIntRejectUnrecIdRetErr OBJECT-TYPE
    SYNTAX	PerfIntervalCount
    UNITS	"Events"
    MAX-ACCESS	read-only
    STATUS	current
    DESCRIPTION
	"Protocol error detected in component portion (reject received) 
	 with problem code unrecognized invoke identity (RE) (return 
	 error problem).  This measurement is non-obligatory and is 
	 collected on a first-and-interval basis.  This measurement is 
	 pertinent for development purposes only.
	 
	 Problem isolation during development may be assisted by 
	 measurements that indicate the reason for the protocol error 
	 being reported.  This includes protocol errors detected in the 
	 component portion that are not due to resource limitation.
	 
	 Note 14.2 g) moved to A.1 g)."
    REFERENCE
	"ITU-T Rec. Q.752 (06/97) Table 14, Item 14.2 g).
	 ITU-T Rec. Q.752 (06/97) Table A.1, Item A.2 g).
	 ITU-T Rec. Q.772, Clause 3.8."
    ::= { tcapOmDevelRecv15minIntEntry 10 }

tcapOmDevelRecv15minIntRejectUnexpRetErr OBJECT-TYPE
    SYNTAX	PerfIntervalCount
    UNITS	"Events"
    MAX-ACCESS	read-only
    STATUS	current
    DESCRIPTION
	"Protocol error detected in component portion (reject received) 
	 with problem code return error (RE) unexpected (return error 
	 problem).  This measurement is non-obligatory and is collected 
	 on a first-and-interval basis.  This measurement is pertinent 
	 for development purposes only.
	 
	 Problem isolation during development may be assisted by 
	 measurements that indicate the reason for the protocol error 
	 being reported.  This includes protocol errors detected in the 
	 component portion that are not due to resource limitation.
	 
	 Note 14.2 h) moved to A.1 h)."
    REFERENCE
	"ITU-T Rec. Q.752 (06/97) Table 14, Item 14.2 h).
	 ITU-T Rec. Q.752 (06/97) Table A.1, Item A.2 h).
	 ITU-T Rec. Q.772, Clause 3.8."
    ::= { tcapOmDevelRecv15minIntEntry 11 }

tcapOmDevelRecv15minIntUsrRejDupInvokeId OBJECT-TYPE
    SYNTAX	PerfIntervalCount
    UNITS	"Events"
    MAX-ACCESS	read-only
    STATUS	current
    DESCRIPTION
	"The number of TC-user generated problems (TC-user Reject 
	 received) with problem duplicate invoke identity (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 a).
	 ITU-T Rec. Q.752 (06/97) Table A.1, Item A.3 a)."
    ::= { tcapOmDevelRecv15minIntEntry 12 }

tcapOmDevelRecv15minIntUsrRejUnrecOper OBJECT-TYPE
    SYNTAX	PerfIntervalCount
    UNITS	"Events"
    MAX-ACCESS	read-only
    STATUS	current
    DESCRIPTION
	"The number of TC-user generated problems (TC-user Reject 
	 received) with problem urecognized operation (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 b).
	 ITU-T Rec. Q.752 (06/97) Table A.1, Item A.3 b)."
    ::= { tcapOmDevelRecv15minIntEntry 13 }

tcapOmDevelRecv15minIntUsrRejParmInvoke OBJECT-TYPE
    SYNTAX	PerfIntervalCount
    UNITS	"Events"
    MAX-ACCESS	read-only
    STATUS	current
    DESCRIPTION
	"The number of TC-user generated problems (TC-user Reject 
	 received) with problem mistyped parameter (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 c).
	 ITU-T Rec. Q.752 (06/97) Table A.1, Item A.3 c)."
    ::= { tcapOmDevelRecv15minIntEntry 14 }

tcapOmDevelRecv15minIntUsrRejReleasing OBJECT-TYPE
    SYNTAX	PerfIntervalCount
    UNITS	"Events"
    MAX-ACCESS	read-only
    STATUS	current
    DESCRIPTION
	"The number of TC-user generated problems (TC-user Reject 
	 received) with problem initiating release (invoke problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 e).
	 ITU-T Rec. Q.752 (06/97) Table A.1, Item A.3 d)."
    ::= { tcapOmDevelRecv15minIntEntry 15 }

tcapOmDevelRecv15minIntUsrRejUnexpLinkResp OBJECT-TYPE
    SYNTAX	PerfIntervalCount
    UNITS	"Events"
    MAX-ACCESS	read-only
    STATUS	current
    DESCRIPTION
	"The number of TC-user generated problems (TC-user Reject 
	 received) with problem linked response unexpected (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 f).
	 ITU-T Rec. Q.752 (06/97) Table A.1, Item A.3 e)."
    ::= { tcapOmDevelRecv15minIntEntry 16 }

tcapOmDevelRecv15minIntUsrRejUnexpLinkOper OBJECT-TYPE
    SYNTAX	PerfIntervalCount
    UNITS	"Events"
    MAX-ACCESS	read-only
    STATUS	current
    DESCRIPTION
	"The number of TC-user generated problems (TC-user Reject 
	 received) with problem unexpected linked operation (invoke 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 g).
	 ITU-T Rec. Q.752 (06/97) Table A.1, Item A.3 f)."
    ::= { tcapOmDevelRecv15minIntEntry 17 }

tcapOmDevelRecv15minIntUsrRejUnrecError OBJECT-TYPE
    SYNTAX	PerfIntervalCount
    UNITS	"Events"
    MAX-ACCESS	read-only
    STATUS	current
    DESCRIPTION
	"The number of TC-user generated problems (TC-user Reject 
	 received) with problem unrecognized error (return error 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 h).
	 ITU-T Rec. Q.752 (06/97) Table A.1, Item A.3 g)."
    ::= { tcapOmDevelRecv15minIntEntry 18 }

tcapOmDevelRecv15minIntUsrRejUnexpError OBJECT-TYPE
    SYNTAX	PerfIntervalCount
    UNITS	"Events"
    MAX-ACCESS	read-only
    STATUS	current
    DESCRIPTION
	"The number of TC-user generated problems (TC-user Reject 
	 received) with problem unexpected error (return error problem).  
	 This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 i).
	 ITU-T Rec. Q.752 (06/97) Table A.1, Item A.3 h)."
    ::= { tcapOmDevelRecv15minIntEntry 19 }

tcapOmDevelRecv15minIntUsrRejParmRetResult OBJECT-TYPE
    SYNTAX	PerfIntervalCount
    UNITS	"Events"
    MAX-ACCESS	read-only
    STATUS	current
    DESCRIPTION
	"The number of TC-user generated problems (TC-user Reject 
	 received) with problem mistyped parameter (return result 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 j).
	 ITU-T Rec. Q.752 (06/97) Table A.1, Item A.3 i)."
    ::= { tcapOmDevelRecv15minIntEntry 20 }

tcapOmDevelRecv15minIntUsrRejParmRetError OBJECT-TYPE
    SYNTAX	PerfIntervalCount
    UNITS	"Events"
    MAX-ACCESS	read-only
    STATUS	current
    DESCRIPTION
	"The number of TC-user generated problems (TC-user Reject 
	 received) with problem mystyped parameter (return error 
	 problem).  This is a non-obligatory measurement collected on a 
	 first-and-interval basis.  This measurement is pertinent for 
	 development purposes only.
	 
	 Problem isolation during development may be assisted by 
	 measurements that indicate the reason for the protocol error 
	 being reported.  This includes TC-user generated problems.
	 
	 Moved to Annex A."
    REFERENCE
	"ITU-T Rec. Q.752 (06/97) Table 14, Item 14.3 k).
	 ITU-T Rec. Q.752 (06/97) Table A.1, Item A.3 j)."
    ::= { tcapOmDevelRecv15minIntEntry 21 }


-- =============================================================================

tcapOmDevelSentTable OBJECT-TYPE
    SYNTAX	SEQUENCE OF TcapOmDevelSentEntry
    MAX-ACCESS	not-accessible
    STATUS	current
    DESCRIPTION
	""
    REFERENCE
	""
    ::= { tcapOmDevelMeasurements 5 }

tcapOmDevelSentEntry OBJECT-TYPE
    SYNTAX	TcapOmDevelSentEntry
    MAX-ACCESS	not-accessible
    STATUS	current
    DESCRIPTION
	""
    REFERENCE
	""
    INDEX	{
	tcapApplicationSubsystemId,	-- shared index
	tcapTcUserId			-- shared index
    }
    ::= { tcapOmDevelSentTable 1 }

TcapOmDevelSentEntry ::= SEQUENCE {
    tcapOmDevelSentPabortMessageType		Counter,
    tcapOmDevelSentPabortIncorrectTp		Counter,
    tcapOmDevelSentPabortBadTp			Counter,
    tcapOmDevelSentRejectUnrecComp		Counter,
    tcapOmDevelSentRejectMistypeComp		Counter,
    tcapOmDevelSentRejectBadCompStruct		Counter,
    tcapOmDevelSentRejectUnrecLinkId		Counter,
    tcapOmDevelSentRejectUnrecIdRetRes		Counter,
    tcapOmDevelSentRejectUnexpRetRes		Counter,
    tcapOmDevelSentRejectUnrecIdRetErr		Counter,
    tcapOmDevelSentRejectUnexpRetErr		Counter,
    tcapOmDevelSentUsrRejDupInvokeId		Counter,
    tcapOmDevelSentUsrRejUnrecOper		Counter,
    tcapOmDevelSentUsrRejParmInvoke		Counter,
    tcapOmDevelSentUsrRejReleasing		Counter,
    tcapOmDevelSentUsrRejUnexpLinkResp		Counter,
    tcapOmDevelSentUsrRejUnexpLinkOper		Counter,
    tcapOmDevelSentUsrRejUnrecError		Counter,
    tcapOmDevelSentUsrRejUnexpError		Counter,
    tcapOmDevelSentUsrRejParmRetResult		Counter,
    tcapOmDevelSentUsrRejParmRetError		Counter,
    tcapOmDevelSent5minValidIntervals		HCPerfValidIntervals,
    tcapOmDevelSent15minValidIntervals		HCPerfValidIntervals
}

tcapOmDevelSentPabortMessageType OBJECT-TYPE
    SYNTAX	Counter
    UNITS	"Events/dest. User"
    MAX-ACCESS	read-only
    STATUS	current
    DESCRIPTION
	"Protocol error detected in transaction portion (abort sent) 
	 with P-abort cause unrecognized message type.  This is a 
	 non-obligatory measurement collected on a first-and-interval 
	 basis.  This measurement is pertinent for development purposes 
	 only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 a).
	 ITU-T Rec. Q.752 (06/97) Table A.1, Item A.4 a)."
    ::= { tcapOmDevelSentEntry 1 }

tcapOmDevelSentPabortIncorrectTp OBJECT-TYPE
    SYNTAX	Counter
    UNITS	"Events/dest. User"
    MAX-ACCESS	read-only
    STATUS	current
    DESCRIPTION
	"Protocol error detected in transaction portion (abort sent) 
	 with P-abort cause incorrect transaction portion.  This is a 
	 non-obligatory measurement collected on a first-and-interval 
	 basis.  This measurement is pertinent for development purposes 
	 only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 b).
	 ITU-T Rec. Q.752 (06/97) Table A.1, Item A.4 b)."
    ::= { tcapOmDevelSentEntry 2 }

tcapOmDevelSentPabortBadTp OBJECT-TYPE
    SYNTAX	Counter
    UNITS	"Events/dest. User"
    MAX-ACCESS	read-only
    STATUS	current
    DESCRIPTION
	"Protocol error detected in transaction portion (abort sent) 
	 with P-abort cause badly formatted transaction portion.  This 
	 is a non-obligatory measurement collected on a 
	 first-and-interval basis.  This measurement is pertinent for 
	 development purposes only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 c).
	 ITU-T Rec. Q.752 (06/97) Table A.1, Item A.4 c)."
    ::= { tcapOmDevelSentEntry 3 }

tcapOmDevelSentRejectUnrecComp OBJECT-TYPE
    SYNTAX	Counter
    UNITS	"Events"
    MAX-ACCESS	read-only
    STATUS	current
    DESCRIPTION
	"The number of protocol errors detected in component portion 
	 (reject sent) with problem code unrecognized component (general 
	 problem).  This is a non-obligatory measurement collected on a 
	 first-and-interval basis.  This measurement is pertinent for 
	 development purposes only.

	 Problem isolation during development may be assisted by 
	 measurements that indicate the reason for the protocol error 
	 being reported.  This includes protocol errors detected in the 
	 component portion that are not due to resource limitation.
	 
	 Note item 14.5 a) moved to item A.5 a)."
    REFERENCE
	"ITU-T Rec. Q.752 (06/97) Table 14, Item 14.5 a).
	 ITU-T Rec. Q.752 (06/97) Table A.1, Item A.5 a)."
    ::= { tcapOmDevelSentEntry 4 }

tcapOmDevelSentRejectMistypeComp OBJECT-TYPE
    SYNTAX	Counter
    UNITS	"Events"
    MAX-ACCESS	read-only
    STATUS	current
    DESCRIPTION
	"The number of protocol errors detected in component portion 
	 (reject sent) with problem code  mistyped component (general 
	 problem).  This is a non-obligatory measurement collected on a 
	 first-and-interval basis.  This measurement is pertinent for 
	 development purposes only.

	 Problem isolation during development may be assisted by 
	 measurements that indicate the reason for the protocol error 
	 being reported.  This includes protocol errors detected in the 
	 component portion that are not due to resource limitation.
	 
	 Note item 14.5 b) moved to item A.5 b)."
    REFERENCE
	"ITU-T Rec. Q.752 (06/97) Table 14, Item 14.5 b).
	 ITU-T Rec. Q.752 (06/97) Table A.1, Item A.5 b)."
    ::= { tcapOmDevelSentEntry 5 }

tcapOmDevelSentRejectBadCompStruct OBJECT-TYPE
    SYNTAX	Counter
    UNITS	"Events"
    MAX-ACCESS	read-only
    STATUS	current
    DESCRIPTION
	"The number of protocol errors detected in component portion 
	 (reject sent) with problem code badly structured component 
	 (general problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 c) moved to item A.5 c)."
    REFERENCE
	"ITU-T Rec. Q.752 (06/97) Table 14, Item 14.5 c).
	 ITU-T Rec. Q.752 (06/97) Table A.1, Item A.5 c)."
    ::= { tcapOmDevelSentEntry 6 }

tcapOmDevelSentRejectUnrecLinkId OBJECT-TYPE
    SYNTAX	Counter
    UNITS	"Events"
    MAX-ACCESS	read-only
    STATUS	current
    DESCRIPTION
	"The number of protocol errors detected in component portion 
	 (reject sent) with problem code unrecognized linked identity 
	 (invoke problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 d) moved to item A.5 d)."
    REFERENCE
	"ITU-T Rec. Q.752 (06/97) Table 14, Item 14.5 d).
	 ITU-T Rec. Q.752 (06/97) Table A.1, Item A.5 d)."
    ::= { tcapOmDevelSentEntry 7 }

tcapOmDevelSentRejectUnrecIdRetRes OBJECT-TYPE
    SYNTAX	Counter
    UNITS	"Events"
    MAX-ACCESS	read-only
    STATUS	current
    DESCRIPTION
	"The number of protocol errors detected in component portion 
	 (reject sent) with problem code unrecognized invoke identity 
	 (return result problem).  This is a non-obligatory measurement 
	 collected on a first-and-interval basis.  This measurement is 
	 pertinent for development purposes only.

	 Note Problem isolation during development may be assisted by 
	 measurements that indicate the reason for the protocol error 
	 being reported.  This includes protocol errors detected in the 
	 component portion that are not due to resource limitation.
	 
	 item 14.5 e) moved to item A.5 e)."
    REFERENCE
	"ITU-T Rec. Q.752 (06/97) Table 14, Item 14.5 e).
	 ITU-T Rec. Q.752 (06/97) Table A.1, Item A.5 e)."
    ::= { tcapOmDevelSentEntry 8 }

tcapOmDevelSentRejectUnexpRetRes OBJECT-TYPE
    SYNTAX	Counter
    UNITS	"Events"
    MAX-ACCESS	read-only
    STATUS	current
    DESCRIPTION
	"The number of protocol errors detected in component portion 
	 (reject sent) with problem code return result unexpected 
	 (return result problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 f) moved to item A.5 f)."
    REFERENCE
	"ITU-T Rec. Q.752 (06/97) Table 14, Item 14.5 f).
	 ITU-T Rec. Q.752 (06/97) Table A.1, Item A.5 f)."
    ::= { tcapOmDevelSentEntry 9 }

tcapOmDevelSentRejectUnrecIdRetErr OBJECT-TYPE
    SYNTAX	Counter
    UNITS	"Events"
    MAX-ACCESS	read-only
    STATUS	current
    DESCRIPTION
	"The number of protocol errors detected in component portion 
	 (reject sent) with problem code unrecognized invoke identity 
	 (return error problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 g) moved to item A.5 g)."
    REFERENCE
	"ITU-T Rec. Q.752 (06/97) Table 14, Item 14.5 g).
	 ITU-T Rec. Q.752 (06/97) Table A.1, Item A.5 g)."
    ::= { tcapOmDevelSentEntry 10 }

tcapOmDevelSentRejectUnexpRetErr OBJECT-TYPE
    SYNTAX	Counter
    UNITS	"Events"
    MAX-ACCESS	read-only
    STATUS	current
    DESCRIPTION
	"The number of protocol errors detected in component portion 
	 (reject sent) with problem code return error unexpected (return 
	 error problem).  This is a non-obligatory measurement collected 
	 on a first-and-interval basis.  This measurement is pertinent 
	 for development purposes only.

	 Problem isolation during development may be assisted by 
	 measurements that indicate the reason for the protocol error 
	 being reported.  This includes protocol errors detected in the 
	 component portion that are not due to resource limitation.
	 
	 Note item 14.5 h) moved to item A.5 h)."
    REFERENCE
	"ITU-T Rec. Q.752 (06/97) Table 14, Item 14.5 h).
	 ITU-T Rec. Q.752 (06/97) Table A.1, Item A.5 h)."
    ::= { tcapOmDevelSentEntry 11 }

tcapOmDevelSentUsrRejDupInvokeId OBJECT-TYPE
    SYNTAX	Counter
    UNITS	"Events/dest. User"
    MAX-ACCESS	read-only
    STATUS	current
    DESCRIPTION
	"The number of TC-user generated problems (TC-user reject sent) 
	 due to duplicate invoke identity (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 a).
	 ITU-T Rec. Q.752 (06/97) Table A.1, Item A.6 a)."
    ::= { tcapOmDevelSentEntry 12 }

tcapOmDevelSentUsrRejUnrecOper OBJECT-TYPE
    SYNTAX	Counter
    UNITS	"Events/dest. User"
    MAX-ACCESS	read-only
    STATUS	current
    DESCRIPTION
	"The number of TC-user generated problems (TC-user reject sent) 
	 due to unrecognized operation (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 b).
	 ITU-T Rec. Q.752 (06/97) Table A.1, Item A.6 b)."
    ::= { tcapOmDevelSentEntry 13 }

tcapOmDevelSentUsrRejParmInvoke OBJECT-TYPE
    SYNTAX	Counter
    UNITS	"Events/dest. User"
    MAX-ACCESS	read-only
    STATUS	current
    DESCRIPTION
	"The number of TC-user generated problems (TC-user reject sent) 
	 due to mistyped parameter (invoked problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 c).
	 ITU-T Rec. Q.752 (06/97) Table A.1, Item A.6 c)."
    ::= { tcapOmDevelSentEntry 14 }

tcapOmDevelSentUsrRejReleasing OBJECT-TYPE
    SYNTAX	Counter
    UNITS	"Events/dest. User"
    MAX-ACCESS	read-only
    STATUS	current
    DESCRIPTION
	"The number of TC-user generated problems (TC-user reject sent) 
	 due to initiating release (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 e).
	 ITU-T Rec. Q.752 (06/97) Table A.1, Item A.6 d)."
    ::= { tcapOmDevelSentEntry 15 }

tcapOmDevelSentUsrRejUnexpLinkResp OBJECT-TYPE
    SYNTAX	Counter
    UNITS	"Events/dest. User"
    MAX-ACCESS	read-only
    STATUS	current
    DESCRIPTION
	"The number of TC-user generated problems (TC-user reject sent) 
	 due to linked reponse unexpected (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 f).
	 ITU-T Rec. Q.752 (06/97) Table A.1, Item A.6 e)."
    ::= { tcapOmDevelSentEntry 16 }

tcapOmDevelSentUsrRejUnexpLinkOper OBJECT-TYPE
    SYNTAX	Counter
    UNITS	"Events/dest. User"
    MAX-ACCESS	read-only
    STATUS	current
    DESCRIPTION
	"The number of TC-user generated problems (TC-user reject sent) 
	 due to unexpected linked operation (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 g).
	 ITU-T Rec. Q.752 (06/97) Table A.1, Item A.6 f)."
    ::= { tcapOmDevelSentEntry 17 }

tcapOmDevelSentUsrRejUnrecError OBJECT-TYPE
    SYNTAX	Counter
    UNITS	"Events/dest. User"
    MAX-ACCESS	read-only
    STATUS	current
    DESCRIPTION
	"The number of TC-user generated problems (TC-user reject sent) 
	 due to unrecognized error (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 h).
	 ITU-T Rec. Q.752 (06/97) Table A.1, Item A.6 g)."
    ::= { tcapOmDevelSentEntry 18 }

tcapOmDevelSentUsrRejUnexpError OBJECT-TYPE
    SYNTAX	Counter
    UNITS	"Events/dest. User"
    MAX-ACCESS	read-only
    STATUS	current
    DESCRIPTION
	"The number of TC-user generated problems (TC-user reject sent) 
	 due to unexpected error (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 i).
	 ITU-T Rec. Q.752 (06/97) Table A.1, Item A.6 h)."
    ::= { tcapOmDevelSentEntry 19 }

tcapOmDevelSentUsrRejParmRetResult OBJECT-TYPE
    SYNTAX	Counter
    UNITS	"Events/dest. User"
    MAX-ACCESS	read-only
    STATUS	current
    DESCRIPTION
	"The number of TC-user generated problems (TC-user reject sent) 
	 due to mistyped parameter (return result problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 j).
	 ITU-T Rec. Q.752 (06/97) Table A.1, Item A.6 i)."
    ::= { tcapOmDevelSentEntry 20 }

tcapOmDevelSentUsrRejParmRetError OBJECT-TYPE
    SYNTAX	Counter
    UNITS	"Events/dest. User"
    MAX-ACCESS	read-only
    STATUS	current
    DESCRIPTION
	"The number of TC-user generated problems (TC-user reject sent) 
	 due to mistyped parameter (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 k).
	 ITU-T Rec. Q.752 (06/97) Table A.1, Item A.6 j)."
    ::= { tcapOmDevelSentEntry 21 }

tcapOmDevelSent5minValidIntervals OBJECT-TYPE
    SYNTAX	HCPerfValidIntervals
    MAX-ACCESS	read-only
    STATUS	current
    DESCRIPTION
	"Indicates the number of valid 5-minute intervals of historical 
	 data that is collected int the corresonding history data table."
    ::= { tcapOmDevelSentEntry 22 }

tcapOmDevelSent15minValidIntervals OBJECT-TYPE
    SYNTAX	HCPerfValidIntervals
    MAX-ACCESS	read-only
    STATUS	current
    DESCRIPTION
	"Indicates the number of valid 15-minute intervals of historical 
	 data that is collected in the corresponding history data 
	 table."
    ::= { tcapOmDevelSentEntry 23 }


-- =============================================================================

tcapOmDevelSentCurrentTable OBJECT-TYPE
    SYNTAX	SEQUENCE OF TcapOmDevelSentCurrentEntry
    MAX-ACCESS	not-accessible
    STATUS	current
    DESCRIPTION
	""
    REFERENCE
	""
    ::= { tcapOmDevelMeasurements 6 }

tcapOmDevelSentCurrentEntry OBJECT-TYPE
    SYNTAX	TcapOmDevelSentCurrentEntry
    MAX-ACCESS	not-accessible
    STATUS	current
    DESCRIPTION
	""
    REFERENCE
	""
    INDEX	{
	tcapApplicationSubsystemId,	-- shared index
	tcapTcUserId			-- shared index
    }
    ::= { tcapOmDevelSentCurrentTable 1 }

TcapOmDevelSentCurrentEntry ::= SEQUENCE {
    tcapOmDevelSentCurrentPabortMessageType	PerfCurrentCount,
    tcapOmDevelSentCurrentPabortIncorrectTp	PerfCurrentCount,
    tcapOmDevelSentCurrentPabortBadTp		PerfCurrentCount,
    tcapOmDevelSentCurrentRejectUnrecComp	PerfCurrentCount,
    tcapOmDevelSentCurrentRejectMistypeComp	PerfCurrentCount,
    tcapOmDevelSentCurrentRejectBadCompStruct	PerfCurrentCount,
    tcapOmDevelSentCurrentRejectUnrecLinkId	PerfCurrentCount,
    tcapOmDevelSentCurrentRejectUnrecIdRetRes	PerfCurrentCount,
    tcapOmDevelSentCurrentRejectUnexpRetRes	PerfCurrentCount,
    tcapOmDevelSentCurrentRejectUnrecIdRetErr	PerfCurrentCount,
    tcapOmDevelSentCurrentRejectUnexpRetErr	PerfCurrentCount,
    tcapOmDevelSentCurrentUsrRejDupInvokeId	PerfCurrentCount,
    tcapOmDevelSentCurrentUsrRejUnrecOper	PerfCurrentCount,
    tcapOmDevelSentCurrentUsrRejParmInvoke	PerfCurrentCount,
    tcapOmDevelSentCurrentUsrRejReleasing	PerfCurrentCount,
    tcapOmDevelSentCurrentUsrRejUnexpLinkResp	PerfCurrentCount,
    tcapOmDevelSentCurrentUsrRejUnexpLinkOper	PerfCurrentCount,
    tcapOmDevelSentCurrentUsrRejUnrecError	PerfCurrentCount,
    tcapOmDevelSentCurrentUsrRejUnexpError	PerfCurrentCount,
    tcapOmDevelSentCurrentUsrRejParmRetResult	PerfCurrentCount,
    tcapOmDevelSentCurrentUsrRejParmRetError	PerfCurrentCount
}

tcapOmDevelSentCurrentPabortMessageType OBJECT-TYPE
    SYNTAX	PerfCurrentCount
    UNITS	"Events/dest. User"
    MAX-ACCESS	read-only
    STATUS	current
    DESCRIPTION
	"Protocol error detected in transaction portion (abort sent) 
	 with P-abort cause unrecognized message type.  This is a 
	 non-obligatory measurement collected on a first-and-interval 
	 basis.  This measurement is pertinent for development purposes 
	 only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 a).
	 ITU-T Rec. Q.752 (06/97) Table A.1, Item A.4 a)."
    ::= { tcapOmDevelSentCurrentEntry 1 }

tcapOmDevelSentCurrentPabortIncorrectTp OBJECT-TYPE
    SYNTAX	PerfCurrentCount
    UNITS	"Events/dest. User"
    MAX-ACCESS	read-only
    STATUS	current
    DESCRIPTION
	"Protocol error detected in transaction portion (abort sent) 
	 with P-abort cause incorrect transaction portion.  This is a 
	 non-obligatory measurement collected on a first-and-interval 
	 basis.  This measurement is pertinent for development purposes 
	 only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 b).
	 ITU-T Rec. Q.752 (06/97) Table A.1, Item A.4 b)."
    ::= { tcapOmDevelSentCurrentEntry 2 }

tcapOmDevelSentCurrentPabortBadTp OBJECT-TYPE
    SYNTAX	PerfCurrentCount
    UNITS	"Events/dest. User"
    MAX-ACCESS	read-only
    STATUS	current
    DESCRIPTION
	"Protocol error detected in transaction portion (abort sent) 
	 with P-abort cause badly formatted transaction portion.  This 
	 is a non-obligatory measurement collected on a 
	 first-and-interval basis.  This measurement is pertinent for 
	 development purposes only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 c).
	 ITU-T Rec. Q.752 (06/97) Table A.1, Item A.4 c)."
    ::= { tcapOmDevelSentCurrentEntry 3 }

tcapOmDevelSentCurrentRejectUnrecComp OBJECT-TYPE
    SYNTAX	PerfCurrentCount
    UNITS	"Events"
    MAX-ACCESS	read-only
    STATUS	current
    DESCRIPTION
	"The number of protocol errors detected in component portion 
	 (reject sent) with problem code unrecognized component (general 
	 problem).  This is a non-obligatory measurement collected on a 
	 first-and-interval basis.  This measurement is pertinent for 
	 development purposes only.

	 Problem isolation during development may be assisted by 
	 measurements that indicate the reason for the protocol error 
	 being reported.  This includes protocol errors detected in the 
	 component portion that are not due to resource limitation.
	 
	 Note item 14.5 a) moved to item A.5 a)."
    REFERENCE
	"ITU-T Rec. Q.752 (06/97) Table 14, Item 14.5 a).
	 ITU-T Rec. Q.752 (06/97) Table A.1, Item A.5 a)."
    ::= { tcapOmDevelSentCurrentEntry 4 }

tcapOmDevelSentCurrentRejectMistypeComp OBJECT-TYPE
    SYNTAX	PerfCurrentCount
    UNITS	"Events"
    MAX-ACCESS	read-only
    STATUS	current
    DESCRIPTION
	"The number of protocol errors detected in component portion 
	 (reject sent) with problem code  mistyped component (general 
	 problem).  This is a non-obligatory measurement collected on a 
	 first-and-interval basis.  This measurement is pertinent for 
	 development purposes only.

	 Problem isolation during development may be assisted by 
	 measurements that indicate the reason for the protocol error 
	 being reported.  This includes protocol errors detected in the 
	 component portion that are not due to resource limitation.
	 
	 Note item 14.5 b) moved to item A.5 b)."
    REFERENCE
	"ITU-T Rec. Q.752 (06/97) Table 14, Item 14.5 b).
	 ITU-T Rec. Q.752 (06/97) Table A.1, Item A.5 b)."
    ::= { tcapOmDevelSentCurrentEntry 5 }

tcapOmDevelSentCurrentRejectBadCompStruct OBJECT-TYPE
    SYNTAX	PerfCurrentCount
    UNITS	"Events"
    MAX-ACCESS	read-only
    STATUS	current
    DESCRIPTION
	"The number of protocol errors detected in component portion 
	 (reject sent) with problem code badly structured component 
	 (general problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 c) moved to item A.5 c)."
    REFERENCE
	"ITU-T Rec. Q.752 (06/97) Table 14, Item 14.5 c).
	 ITU-T Rec. Q.752 (06/97) Table A.1, Item A.5 c)."
    ::= { tcapOmDevelSentCurrentEntry 6 }

tcapOmDevelSentCurrentRejectUnrecLinkId OBJECT-TYPE
    SYNTAX	PerfCurrentCount
    UNITS	"Events"
    MAX-ACCESS	read-only
    STATUS	current
    DESCRIPTION
	"The number of protocol errors detected in component portion 
	 (reject sent) with problem code unrecognized linked identity 
	 (invoke problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 d) moved to item A.5 d)."
    REFERENCE
	"ITU-T Rec. Q.752 (06/97) Table 14, Item 14.5 d).
	 ITU-T Rec. Q.752 (06/97) Table A.1, Item A.5 d)."
    ::= { tcapOmDevelSentCurrentEntry 7 }

tcapOmDevelSentCurrentRejectUnrecIdRetRes OBJECT-TYPE
    SYNTAX	PerfCurrentCount
    UNITS	"Events"
    MAX-ACCESS	read-only
    STATUS	current
    DESCRIPTION
	"The number of protocol errors detected in component portion 
	 (reject sent) with problem code unrecognized invoke identity 
	 (return result problem).  This is a non-obligatory measurement 
	 collected on a first-and-interval basis.  This measurement is 
	 pertinent for development purposes only.

	 Note Problem isolation during development may be assisted by 
	 measurements that indicate the reason for the protocol error 
	 being reported.  This includes protocol errors detected in the 
	 component portion that are not due to resource limitation.
	 
	 item 14.5 e) moved to item A.5 e)."
    REFERENCE
	"ITU-T Rec. Q.752 (06/97) Table 14, Item 14.5 e).
	 ITU-T Rec. Q.752 (06/97) Table A.1, Item A.5 e)."
    ::= { tcapOmDevelSentCurrentEntry 8 }

tcapOmDevelSentCurrentRejectUnexpRetRes OBJECT-TYPE
    SYNTAX	PerfCurrentCount
    UNITS	"Events"
    MAX-ACCESS	read-only
    STATUS	current
    DESCRIPTION
	"The number of protocol errors detected in component portion 
	 (reject sent) with problem code return result unexpected 
	 (return result problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 f) moved to item A.5 f)."
    REFERENCE
	"ITU-T Rec. Q.752 (06/97) Table 14, Item 14.5 f).
	 ITU-T Rec. Q.752 (06/97) Table A.1, Item A.5 f)."
    ::= { tcapOmDevelSentCurrentEntry 9 }

tcapOmDevelSentCurrentRejectUnrecIdRetErr OBJECT-TYPE
    SYNTAX	PerfCurrentCount
    UNITS	"Events"
    MAX-ACCESS	read-only
    STATUS	current
    DESCRIPTION
	"The number of protocol errors detected in component portion 
	 (reject sent) with problem code unrecognized invoke identity 
	 (return error problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 g) moved to item A.5 g)."
    REFERENCE
	"ITU-T Rec. Q.752 (06/97) Table 14, Item 14.5 g).
	 ITU-T Rec. Q.752 (06/97) Table A.1, Item A.5 g)."
    ::= { tcapOmDevelSentCurrentEntry 10 }

tcapOmDevelSentCurrentRejectUnexpRetErr OBJECT-TYPE
    SYNTAX	PerfCurrentCount
    UNITS	"Events"
    MAX-ACCESS	read-only
    STATUS	current
    DESCRIPTION
	"The number of protocol errors detected in component portion 
	 (reject sent) with problem code return error unexpected (return 
	 error problem).  This is a non-obligatory measurement collected 
	 on a first-and-interval basis.  This measurement is pertinent 
	 for development purposes only.

	 Problem isolation during development may be assisted by 
	 measurements that indicate the reason for the protocol error 
	 being reported.  This includes protocol errors detected in the 
	 component portion that are not due to resource limitation.
	 
	 Note item 14.5 h) moved to item A.5 h)."
    REFERENCE
	"ITU-T Rec. Q.752 (06/97) Table 14, Item 14.5 h).
	 ITU-T Rec. Q.752 (06/97) Table A.1, Item A.5 h)."
    ::= { tcapOmDevelSentCurrentEntry 11 }

tcapOmDevelSentCurrentUsrRejDupInvokeId OBJECT-TYPE
    SYNTAX	PerfCurrentCount
    UNITS	"Events/dest. User"
    MAX-ACCESS	read-only
    STATUS	current
    DESCRIPTION
	"The number of TC-user generated problems (TC-user reject sent) 
	 due to duplicate invoke identity (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 a).
	 ITU-T Rec. Q.752 (06/97) Table A.1, Item A.6 a)."
    ::= { tcapOmDevelSentCurrentEntry 12 }

tcapOmDevelSentCurrentUsrRejUnrecOper OBJECT-TYPE
    SYNTAX	PerfCurrentCount
    UNITS	"Events/dest. User"
    MAX-ACCESS	read-only
    STATUS	current
    DESCRIPTION
	"The number of TC-user generated problems (TC-user reject sent) 
	 due to unrecognized operation (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 b).
	 ITU-T Rec. Q.752 (06/97) Table A.1, Item A.6 b)."
    ::= { tcapOmDevelSentCurrentEntry 13 }

tcapOmDevelSentCurrentUsrRejParmInvoke OBJECT-TYPE
    SYNTAX	PerfCurrentCount
    UNITS	"Events/dest. User"
    MAX-ACCESS	read-only
    STATUS	current
    DESCRIPTION
	"The number of TC-user generated problems (TC-user reject sent) 
	 due to mistyped parameter (invoked problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 c).
	 ITU-T Rec. Q.752 (06/97) Table A.1, Item A.6 c)."
    ::= { tcapOmDevelSentCurrentEntry 14 }

tcapOmDevelSentCurrentUsrRejReleasing OBJECT-TYPE
    SYNTAX	PerfCurrentCount
    UNITS	"Events/dest. User"
    MAX-ACCESS	read-only
    STATUS	current
    DESCRIPTION
	"The number of TC-user generated problems (TC-user reject sent) 
	 due to initiating release (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 e).
	 ITU-T Rec. Q.752 (06/97) Table A.1, Item A.6 d)."
    ::= { tcapOmDevelSentCurrentEntry 15 }

tcapOmDevelSentCurrentUsrRejUnexpLinkResp OBJECT-TYPE
    SYNTAX	PerfCurrentCount
    UNITS	"Events/dest. User"
    MAX-ACCESS	read-only
    STATUS	current
    DESCRIPTION
	"The number of TC-user generated problems (TC-user reject sent) 
	 due to linked reponse unexpected (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 f).
	 ITU-T Rec. Q.752 (06/97) Table A.1, Item A.6 e)."
    ::= { tcapOmDevelSentCurrentEntry 16 }

tcapOmDevelSentCurrentUsrRejUnexpLinkOper OBJECT-TYPE
    SYNTAX	PerfCurrentCount
    UNITS	"Events/dest. User"
    MAX-ACCESS	read-only
    STATUS	current
    DESCRIPTION
	"The number of TC-user generated problems (TC-user reject sent) 
	 due to unexpected linked operation (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 g).
	 ITU-T Rec. Q.752 (06/97) Table A.1, Item A.6 f)."
    ::= { tcapOmDevelSentCurrentEntry 17 }

tcapOmDevelSentCurrentUsrRejUnrecError OBJECT-TYPE
    SYNTAX	PerfCurrentCount
    UNITS	"Events/dest. User"
    MAX-ACCESS	read-only
    STATUS	current
    DESCRIPTION
	"The number of TC-user generated problems (TC-user reject sent) 
	 due to unrecognized error (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 h).
	 ITU-T Rec. Q.752 (06/97) Table A.1, Item A.6 g)."
    ::= { tcapOmDevelSentCurrentEntry 18 }

tcapOmDevelSentCurrentUsrRejUnexpError OBJECT-TYPE
    SYNTAX	PerfCurrentCount
    UNITS	"Events/dest. User"
    MAX-ACCESS	read-only
    STATUS	current
    DESCRIPTION
	"The number of TC-user generated problems (TC-user reject sent) 
	 due to unexpected error (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 i).
	 ITU-T Rec. Q.752 (06/97) Table A.1, Item A.6 h)."
    ::= { tcapOmDevelSentCurrentEntry 19 }

tcapOmDevelSentCurrentUsrRejParmRetResult OBJECT-TYPE
    SYNTAX	PerfCurrentCount
    UNITS	"Events/dest. User"
    MAX-ACCESS	read-only
    STATUS	current
    DESCRIPTION
	"The number of TC-user generated problems (TC-user reject sent) 
	 due to mistyped parameter (return result problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 j).
	 ITU-T Rec. Q.752 (06/97) Table A.1, Item A.6 i)."
    ::= { tcapOmDevelSentCurrentEntry 20 }

tcapOmDevelSentCurrentUsrRejParmRetError OBJECT-TYPE
    SYNTAX	PerfCurrentCount
    UNITS	"Events/dest. User"
    MAX-ACCESS	read-only
    STATUS	current
    DESCRIPTION
	"The number of TC-user generated problems (TC-user reject sent) 
	 due to mistyped parameter (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 k).
	 ITU-T Rec. Q.752 (06/97) Table A.1, Item A.6 j)."
    ::= { tcapOmDevelSentCurrentEntry 21 }


-- =============================================================================

tcapOmDevelSent5minIntTable OBJECT-TYPE
    SYNTAX	SEQUENCE OF TcapOmDevelSent5minIntEntry
    MAX-ACCESS	not-accessible
    STATUS	current
    DESCRIPTION
	""
    REFERENCE
	""
    ::= { tcapOmDevelMeasurements 7 }

tcapOmDevelSent5minIntEntry OBJECT-TYPE
    SYNTAX	TcapOmDevelSent5minIntEntry
    MAX-ACCESS	not-accessible
    STATUS	current
    DESCRIPTION
	""
    REFERENCE
	""
    INDEX	{
	tcapApplicationSubsystemId,	-- shared index
	tcapTcUserId,			-- shared index
	tcapOmInterval			-- shared index
    }
    ::= { tcapOmDevelSent5minIntTable 1 }

TcapOmDevelSent5minIntEntry ::= SEQUENCE {
    tcapOmDevelSent5minIntPabortMessageType	PerfIntervalCount,
    tcapOmDevelSent5minIntPabortIncorrectTp	PerfIntervalCount,
    tcapOmDevelSent5minIntPabortBadTp		PerfIntervalCount,
    tcapOmDevelSent5minIntRejectUnrecComp	PerfIntervalCount,
    tcapOmDevelSent5minIntRejectMistypeComp	PerfIntervalCount,
    tcapOmDevelSent5minIntRejectBadCompStruct	PerfIntervalCount,
    tcapOmDevelSent5minIntRejectUnrecLinkId	PerfIntervalCount,
    tcapOmDevelSent5minIntRejectUnrecIdRetRes	PerfIntervalCount,
    tcapOmDevelSent5minIntRejectUnexpRetRes	PerfIntervalCount,
    tcapOmDevelSent5minIntRejectUnrecIdRetErr	PerfIntervalCount,
    tcapOmDevelSent5minIntRejectUnexpRetErr	PerfIntervalCount,
    tcapOmDevelSent5minIntUsrRejDupInvokeId	PerfIntervalCount,
    tcapOmDevelSent5minIntUsrRejUnrecOper	PerfIntervalCount,
    tcapOmDevelSent5minIntUsrRejParmInvoke	PerfIntervalCount,
    tcapOmDevelSent5minIntUsrRejReleasing	PerfIntervalCount,
    tcapOmDevelSent5minIntUsrRejUnexpLinkResp	PerfIntervalCount,
    tcapOmDevelSent5minIntUsrRejUnexpLinkOper	PerfIntervalCount,
    tcapOmDevelSent5minIntUsrRejUnrecError	PerfIntervalCount,
    tcapOmDevelSent5minIntUsrRejUnexpError	PerfIntervalCount,
    tcapOmDevelSent5minIntUsrRejParmRetResult	PerfIntervalCount,
    tcapOmDevelSent5minIntUsrRejParmRetError	PerfIntervalCount
}

tcapOmDevelSent5minIntPabortMessageType OBJECT-TYPE
    SYNTAX	PerfIntervalCount
    UNITS	"Events/dest. User"
    MAX-ACCESS	read-only
    STATUS	current
    DESCRIPTION
	"Protocol error detected in transaction portion (abort sent) 
	 with P-abort cause unrecognized message type.  This is a 
	 non-obligatory measurement collected on a first-and-interval 
	 basis.  This measurement is pertinent for development purposes 
	 only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 a).
	 ITU-T Rec. Q.752 (06/97) Table A.1, Item A.4 a)."
    ::= { tcapOmDevelSent5minIntEntry 1 }

tcapOmDevelSent5minIntPabortIncorrectTp OBJECT-TYPE
    SYNTAX	PerfIntervalCount
    UNITS	"Events/dest. User"
    MAX-ACCESS	read-only
    STATUS	current
    DESCRIPTION
	"Protocol error detected in transaction portion (abort sent) 
	 with P-abort cause incorrect transaction portion.  This is a 
	 non-obligatory measurement collected on a first-and-interval 
	 basis.  This measurement is pertinent for development purposes 
	 only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 b).
	 ITU-T Rec. Q.752 (06/97) Table A.1, Item A.4 b)."
    ::= { tcapOmDevelSent5minIntEntry 2 }

tcapOmDevelSent5minIntPabortBadTp OBJECT-TYPE
    SYNTAX	PerfIntervalCount
    UNITS	"Events/dest. User"
    MAX-ACCESS	read-only
    STATUS	current
    DESCRIPTION
	"Protocol error detected in transaction portion (abort sent) 
	 with P-abort cause badly formatted transaction portion.  This 
	 is a non-obligatory measurement collected on a 
	 first-and-interval basis.  This measurement is pertinent for 
	 development purposes only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 c).
	 ITU-T Rec. Q.752 (06/97) Table A.1, Item A.4 c)."
    ::= { tcapOmDevelSent5minIntEntry 3 }

tcapOmDevelSent5minIntRejectUnrecComp OBJECT-TYPE
    SYNTAX	PerfIntervalCount
    UNITS	"Events"
    MAX-ACCESS	read-only
    STATUS	current
    DESCRIPTION
	"The number of protocol errors detected in component portion 
	 (reject sent) with problem code unrecognized component (general 
	 problem).  This is a non-obligatory measurement collected on a 
	 first-and-interval basis.  This measurement is pertinent for 
	 development purposes only.

	 Problem isolation during development may be assisted by 
	 measurements that indicate the reason for the protocol error 
	 being reported.  This includes protocol errors detected in the 
	 component portion that are not due to resource limitation.
	 
	 Note item 14.5 a) moved to item A.5 a)."
    REFERENCE
	"ITU-T Rec. Q.752 (06/97) Table 14, Item 14.5 a).
	 ITU-T Rec. Q.752 (06/97) Table A.1, Item A.5 a)."
    ::= { tcapOmDevelSent5minIntEntry 4 }

tcapOmDevelSent5minIntRejectMistypeComp OBJECT-TYPE
    SYNTAX	PerfIntervalCount
    UNITS	"Events"
    MAX-ACCESS	read-only
    STATUS	current
    DESCRIPTION
	"The number of protocol errors detected in component portion 
	 (reject sent) with problem code  mistyped component (general 
	 problem).  This is a non-obligatory measurement collected on a 
	 first-and-interval basis.  This measurement is pertinent for 
	 development purposes only.

	 Problem isolation during development may be assisted by 
	 measurements that indicate the reason for the protocol error 
	 being reported.  This includes protocol errors detected in the 
	 component portion that are not due to resource limitation.
	 
	 Note item 14.5 b) moved to item A.5 b)."
    REFERENCE
	"ITU-T Rec. Q.752 (06/97) Table 14, Item 14.5 b).
	 ITU-T Rec. Q.752 (06/97) Table A.1, Item A.5 b)."
    ::= { tcapOmDevelSent5minIntEntry 5 }

tcapOmDevelSent5minIntRejectBadCompStruct OBJECT-TYPE
    SYNTAX	PerfIntervalCount
    UNITS	"Events"
    MAX-ACCESS	read-only
    STATUS	current
    DESCRIPTION
	"The number of protocol errors detected in component portion 
	 (reject sent) with problem code badly structured component 
	 (general problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 c) moved to item A.5 c)."
    REFERENCE
	"ITU-T Rec. Q.752 (06/97) Table 14, Item 14.5 c).
	 ITU-T Rec. Q.752 (06/97) Table A.1, Item A.5 c)."
    ::= { tcapOmDevelSent5minIntEntry 6 }

tcapOmDevelSent5minIntRejectUnrecLinkId OBJECT-TYPE
    SYNTAX	PerfIntervalCount
    UNITS	"Events"
    MAX-ACCESS	read-only
    STATUS	current
    DESCRIPTION
	"The number of protocol errors detected in component portion 
	 (reject sent) with problem code unrecognized linked identity 
	 (invoke problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 d) moved to item A.5 d)."
    REFERENCE
	"ITU-T Rec. Q.752 (06/97) Table 14, Item 14.5 d).
	 ITU-T Rec. Q.752 (06/97) Table A.1, Item A.5 d)."
    ::= { tcapOmDevelSent5minIntEntry 7 }

tcapOmDevelSent5minIntRejectUnrecIdRetRes OBJECT-TYPE
    SYNTAX	PerfIntervalCount
    UNITS	"Events"
    MAX-ACCESS	read-only
    STATUS	current
    DESCRIPTION
	"The number of protocol errors detected in component portion 
	 (reject sent) with problem code unrecognized invoke identity 
	 (return result problem).  This is a non-obligatory measurement 
	 collected on a first-and-interval basis.  This measurement is 
	 pertinent for development purposes only.

	 Note Problem isolation during development may be assisted by 
	 measurements that indicate the reason for the protocol error 
	 being reported.  This includes protocol errors detected in the 
	 component portion that are not due to resource limitation.
	 
	 item 14.5 e) moved to item A.5 e)."
    REFERENCE
	"ITU-T Rec. Q.752 (06/97) Table 14, Item 14.5 e).
	 ITU-T Rec. Q.752 (06/97) Table A.1, Item A.5 e)."
    ::= { tcapOmDevelSent5minIntEntry 8 }

tcapOmDevelSent5minIntRejectUnexpRetRes OBJECT-TYPE
    SYNTAX	PerfIntervalCount
    UNITS	"Events"
    MAX-ACCESS	read-only
    STATUS	current
    DESCRIPTION
	"The number of protocol errors detected in component portion 
	 (reject sent) with problem code return result unexpected 
	 (return result problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 f) moved to item A.5 f)."
    REFERENCE
	"ITU-T Rec. Q.752 (06/97) Table 14, Item 14.5 f).
	 ITU-T Rec. Q.752 (06/97) Table A.1, Item A.5 f)."
    ::= { tcapOmDevelSent5minIntEntry 9 }

tcapOmDevelSent5minIntRejectUnrecIdRetErr OBJECT-TYPE
    SYNTAX	PerfIntervalCount
    UNITS	"Events"
    MAX-ACCESS	read-only
    STATUS	current
    DESCRIPTION
	"The number of protocol errors detected in component portion 
	 (reject sent) with problem code unrecognized invoke identity 
	 (return error problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 g) moved to item A.5 g)."
    REFERENCE
	"ITU-T Rec. Q.752 (06/97) Table 14, Item 14.5 g).
	 ITU-T Rec. Q.752 (06/97) Table A.1, Item A.5 g)."
    ::= { tcapOmDevelSent5minIntEntry 10 }

tcapOmDevelSent5minIntRejectUnexpRetErr OBJECT-TYPE
    SYNTAX	PerfIntervalCount
    UNITS	"Events"
    MAX-ACCESS	read-only
    STATUS	current
    DESCRIPTION
	"The number of protocol errors detected in component portion 
	 (reject sent) with problem code return error unexpected (return 
	 error problem).  This is a non-obligatory measurement collected 
	 on a first-and-interval basis.  This measurement is pertinent 
	 for development purposes only.

	 Problem isolation during development may be assisted by 
	 measurements that indicate the reason for the protocol error 
	 being reported.  This includes protocol errors detected in the 
	 component portion that are not due to resource limitation.
	 
	 Note item 14.5 h) moved to item A.5 h)."
    REFERENCE
	"ITU-T Rec. Q.752 (06/97) Table 14, Item 14.5 h).
	 ITU-T Rec. Q.752 (06/97) Table A.1, Item A.5 h)."
    ::= { tcapOmDevelSent5minIntEntry 11 }

tcapOmDevelSent5minIntUsrRejDupInvokeId OBJECT-TYPE
    SYNTAX	PerfIntervalCount
    UNITS	"Events/dest. User"
    MAX-ACCESS	read-only
    STATUS	current
    DESCRIPTION
	"The number of TC-user generated problems (TC-user reject sent) 
	 due to duplicate invoke identity (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 a).
	 ITU-T Rec. Q.752 (06/97) Table A.1, Item A.6 a)."
    ::= { tcapOmDevelSent5minIntEntry 12 }

tcapOmDevelSent5minIntUsrRejUnrecOper OBJECT-TYPE
    SYNTAX	PerfIntervalCount
    UNITS	"Events/dest. User"
    MAX-ACCESS	read-only
    STATUS	current
    DESCRIPTION
	"The number of TC-user generated problems (TC-user reject sent) 
	 due to unrecognized operation (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 b).
	 ITU-T Rec. Q.752 (06/97) Table A.1, Item A.6 b)."
    ::= { tcapOmDevelSent5minIntEntry 13 }

tcapOmDevelSent5minIntUsrRejParmInvoke OBJECT-TYPE
    SYNTAX	PerfIntervalCount
    UNITS	"Events/dest. User"
    MAX-ACCESS	read-only
    STATUS	current
    DESCRIPTION
	"The number of TC-user generated problems (TC-user reject sent) 
	 due to mistyped parameter (invoked problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 c).
	 ITU-T Rec. Q.752 (06/97) Table A.1, Item A.6 c)."
    ::= { tcapOmDevelSent5minIntEntry 14 }

tcapOmDevelSent5minIntUsrRejReleasing OBJECT-TYPE
    SYNTAX	PerfIntervalCount
    UNITS	"Events/dest. User"
    MAX-ACCESS	read-only
    STATUS	current
    DESCRIPTION
	"The number of TC-user generated problems (TC-user reject sent) 
	 due to initiating release (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 e).
	 ITU-T Rec. Q.752 (06/97) Table A.1, Item A.6 d)."
    ::= { tcapOmDevelSent5minIntEntry 15 }

tcapOmDevelSent5minIntUsrRejUnexpLinkResp OBJECT-TYPE
    SYNTAX	PerfIntervalCount
    UNITS	"Events/dest. User"
    MAX-ACCESS	read-only
    STATUS	current
    DESCRIPTION
	"The number of TC-user generated problems (TC-user reject sent) 
	 due to linked reponse unexpected (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 f).
	 ITU-T Rec. Q.752 (06/97) Table A.1, Item A.6 e)."
    ::= { tcapOmDevelSent5minIntEntry 16 }

tcapOmDevelSent5minIntUsrRejUnexpLinkOper OBJECT-TYPE
    SYNTAX	PerfIntervalCount
    UNITS	"Events/dest. User"
    MAX-ACCESS	read-only
    STATUS	current
    DESCRIPTION
	"The number of TC-user generated problems (TC-user reject sent) 
	 due to unexpected linked operation (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 g).
	 ITU-T Rec. Q.752 (06/97) Table A.1, Item A.6 f)."
    ::= { tcapOmDevelSent5minIntEntry 17 }

tcapOmDevelSent5minIntUsrRejUnrecError OBJECT-TYPE
    SYNTAX	PerfIntervalCount
    UNITS	"Events/dest. User"
    MAX-ACCESS	read-only
    STATUS	current
    DESCRIPTION
	"The number of TC-user generated problems (TC-user reject sent) 
	 due to unrecognized error (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 h).
	 ITU-T Rec. Q.752 (06/97) Table A.1, Item A.6 g)."
    ::= { tcapOmDevelSent5minIntEntry 18 }

tcapOmDevelSent5minIntUsrRejUnexpError OBJECT-TYPE
    SYNTAX	PerfIntervalCount
    UNITS	"Events/dest. User"
    MAX-ACCESS	read-only
    STATUS	current
    DESCRIPTION
	"The number of TC-user generated problems (TC-user reject sent) 
	 due to unexpected error (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 i).
	 ITU-T Rec. Q.752 (06/97) Table A.1, Item A.6 h)."
    ::= { tcapOmDevelSent5minIntEntry 19 }

tcapOmDevelSent5minIntUsrRejParmRetResult OBJECT-TYPE
    SYNTAX	PerfIntervalCount
    UNITS	"Events/dest. User"
    MAX-ACCESS	read-only
    STATUS	current
    DESCRIPTION
	"The number of TC-user generated problems (TC-user reject sent) 
	 due to mistyped parameter (return result problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 j).
	 ITU-T Rec. Q.752 (06/97) Table A.1, Item A.6 i)."
    ::= { tcapOmDevelSent5minIntEntry 20 }

tcapOmDevelSent5minIntUsrRejParmRetError OBJECT-TYPE
    SYNTAX	PerfIntervalCount
    UNITS	"Events/dest. User"
    MAX-ACCESS	read-only
    STATUS	current
    DESCRIPTION
	"The number of TC-user generated problems (TC-user reject sent) 
	 due to mistyped parameter (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 k).
	 ITU-T Rec. Q.752 (06/97) Table A.1, Item A.6 j)."
    ::= { tcapOmDevelSent5minIntEntry 21 }


-- =============================================================================

tcapOmDevelSent15minIntTable OBJECT-TYPE
    SYNTAX	SEQUENCE OF TcapOmDevelSent15minIntEntry
    MAX-ACCESS	not-accessible
    STATUS	current
    DESCRIPTION
	""
    REFERENCE
	""
    ::= { tcapOmDevelMeasurements 8 }

tcapOmDevelSent15minIntEntry OBJECT-TYPE
    SYNTAX	TcapOmDevelSent15minIntEntry
    MAX-ACCESS	not-accessible
    STATUS	current
    DESCRIPTION
	""
    REFERENCE
	""
    INDEX	{
	tcapApplicationSubsystemId,	-- shared index
	tcapTcUserId,			-- shared index
	tcapOmInterval			-- shared index
    }
    ::= { tcapOmDevelSent15minIntTable 1 }

TcapOmDevelSent15minIntEntry ::= SEQUENCE {
    tcapOmDevelSent15minIntPabortMessageType	PerfIntervalCount,
    tcapOmDevelSent15minIntPabortIncorrectTp	PerfIntervalCount,
    tcapOmDevelSent15minIntPabortBadTp		PerfIntervalCount,
    tcapOmDevelSent15minIntRejectUnrecComp	PerfIntervalCount,
    tcapOmDevelSent15minIntRejectMistypeComp	PerfIntervalCount,
    tcapOmDevelSent15minIntRejectBadCompStruct	PerfIntervalCount,
    tcapOmDevelSent15minIntRejectUnrecLinkId	PerfIntervalCount,
    tcapOmDevelSent15minIntRejectUnrecIdRetRes	PerfIntervalCount,
    tcapOmDevelSent15minIntRejectUnexpRetRes	PerfIntervalCount,
    tcapOmDevelSent15minIntRejectUnrecIdRetErr	PerfIntervalCount,
    tcapOmDevelSent15minIntRejectUnexpRetErr	PerfIntervalCount,
    tcapOmDevelSent15minIntUsrRejDupInvokeId	PerfIntervalCount,
    tcapOmDevelSent15minIntUsrRejUnrecOper	PerfIntervalCount,
    tcapOmDevelSent15minIntUsrRejParmInvoke	PerfIntervalCount,
    tcapOmDevelSent15minIntUsrRejReleasing	PerfIntervalCount,
    tcapOmDevelSent15minIntUsrRejUnexpLinkResp	PerfIntervalCount,
    tcapOmDevelSent15minIntUsrRejUnexpLinkOper	PerfIntervalCount,
    tcapOmDevelSent15minIntUsrRejUnrecError	PerfIntervalCount,
    tcapOmDevelSent15minIntUsrRejUnexpError	PerfIntervalCount,
    tcapOmDevelSent15minIntUsrRejParmRetResult	PerfIntervalCount,
    tcapOmDevelSent15minIntUsrRejParmRetError	PerfIntervalCount
}

tcapOmDevelSent15minIntPabortMessageType OBJECT-TYPE
    SYNTAX	PerfIntervalCount
    UNITS	"Events/dest. User"
    MAX-ACCESS	read-only
    STATUS	current
    DESCRIPTION
	"Protocol error detected in transaction portion (abort sent) 
	 with P-abort cause unrecognized message type.  This is a 
	 non-obligatory measurement collected on a first-and-interval 
	 basis.  This measurement is pertinent for development purposes 
	 only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 a).
	 ITU-T Rec. Q.752 (06/97) Table A.1, Item A.4 a)."
    ::= { tcapOmDevelSent15minIntEntry 1 }

tcapOmDevelSent15minIntPabortIncorrectTp OBJECT-TYPE
    SYNTAX	PerfIntervalCount
    UNITS	"Events/dest. User"
    MAX-ACCESS	read-only
    STATUS	current
    DESCRIPTION
	"Protocol error detected in transaction portion (abort sent) 
	 with P-abort cause incorrect transaction portion.  This is a 
	 non-obligatory measurement collected on a first-and-interval 
	 basis.  This measurement is pertinent for development purposes 
	 only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 b).
	 ITU-T Rec. Q.752 (06/97) Table A.1, Item A.4 b)."
    ::= { tcapOmDevelSent15minIntEntry 2 }

tcapOmDevelSent15minIntPabortBadTp OBJECT-TYPE
    SYNTAX	PerfIntervalCount
    UNITS	"Events/dest. User"
    MAX-ACCESS	read-only
    STATUS	current
    DESCRIPTION
	"Protocol error detected in transaction portion (abort sent) 
	 with P-abort cause badly formatted transaction portion.  This 
	 is a non-obligatory measurement collected on a 
	 first-and-interval basis.  This measurement is pertinent for 
	 development purposes only.
	 
	 Problem isolation during development may be assisted by 
	 measurements that indicate the reason for the protocol error 
	 being reported.  This includes protocol errors detected in the 
	 transaction portion that are not of a resource limitation 
	 nature.
	 
	 Moved to Annex A."
    REFERENCE
	"ITU-T Rec. Q.752 (06/97) Table 14, Item 14.4 c).
	 ITU-T Rec. Q.752 (06/97) Table A.1, Item A.4 c)."
    ::= { tcapOmDevelSent15minIntEntry 3 }

tcapOmDevelSent15minIntRejectUnrecComp OBJECT-TYPE
    SYNTAX	PerfIntervalCount
    UNITS	"Events"
    MAX-ACCESS	read-only
    STATUS	current
    DESCRIPTION
	"The number of protocol errors detected in component portion 
	 (reject sent) with problem code unrecognized component (general 
	 problem).  This is a non-obligatory measurement collected on a 
	 first-and-interval basis.  This measurement is pertinent for 
	 development purposes only.

	 Problem isolation during development may be assisted by 
	 measurements that indicate the reason for the protocol error 
	 being reported.  This includes protocol errors detected in the 
	 component portion that are not due to resource limitation.
	 
	 Note item 14.5 a) moved to item A.5 a)."
    REFERENCE
	"ITU-T Rec. Q.752 (06/97) Table 14, Item 14.5 a).
	 ITU-T Rec. Q.752 (06/97) Table A.1, Item A.5 a)."
    ::= { tcapOmDevelSent15minIntEntry 4 }

tcapOmDevelSent15minIntRejectMistypeComp OBJECT-TYPE
    SYNTAX	PerfIntervalCount
    UNITS	"Events"
    MAX-ACCESS	read-only
    STATUS	current
    DESCRIPTION
	"The number of protocol errors detected in component portion 
	 (reject sent) with problem code  mistyped component (general 
	 problem).  This is a non-obligatory measurement collected on a 
	 first-and-interval basis.  This measurement is pertinent for 
	 development purposes only.

	 Problem isolation during development may be assisted by 
	 measurements that indicate the reason for the protocol error 
	 being reported.  This includes protocol errors detected in the 
	 component portion that are not due to resource limitation.
	 
	 Note item 14.5 b) moved to item A.5 b)."
    REFERENCE
	"ITU-T Rec. Q.752 (06/97) Table 14, Item 14.5 b).
	 ITU-T Rec. Q.752 (06/97) Table A.1, Item A.5 b)."
    ::= { tcapOmDevelSent15minIntEntry 5 }

tcapOmDevelSent15minIntRejectBadCompStruct OBJECT-TYPE
    SYNTAX	PerfIntervalCount
    UNITS	"Events"
    MAX-ACCESS	read-only
    STATUS	current
    DESCRIPTION
	"The number of protocol errors detected in component portion 
	 (reject sent) with problem code badly structured component 
	 (general problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 c) moved to item A.5 c)."
    REFERENCE
	"ITU-T Rec. Q.752 (06/97) Table 14, Item 14.5 c).
	 ITU-T Rec. Q.752 (06/97) Table A.1, Item A.5 c)."
    ::= { tcapOmDevelSent15minIntEntry 6 }

tcapOmDevelSent15minIntRejectUnrecLinkId OBJECT-TYPE
    SYNTAX	PerfIntervalCount
    UNITS	"Events"
    MAX-ACCESS	read-only
    STATUS	current
    DESCRIPTION
	"The number of protocol errors detected in component portion 
	 (reject sent) with problem code unrecognized linked identity 
	 (invoke problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 d) moved to item A.5 d)."
    REFERENCE
	"ITU-T Rec. Q.752 (06/97) Table 14, Item 14.5 d).
	 ITU-T Rec. Q.752 (06/97) Table A.1, Item A.5 d)."
    ::= { tcapOmDevelSent15minIntEntry 7 }

tcapOmDevelSent15minIntRejectUnrecIdRetRes OBJECT-TYPE
    SYNTAX	PerfIntervalCount
    UNITS	"Events"
    MAX-ACCESS	read-only
    STATUS	current
    DESCRIPTION
	"The number of protocol errors detected in component portion 
	 (reject sent) with problem code unrecognized invoke identity 
	 (return result problem).  This is a non-obligatory measurement 
	 collected on a first-and-interval basis.  This measurement is 
	 pertinent for development purposes only.

	 Note Problem isolation during development may be assisted by 
	 measurements that indicate the reason for the protocol error 
	 being reported.  This includes protocol errors detected in the 
	 component portion that are not due to resource limitation.
	 
	 item 14.5 e) moved to item A.5 e)."
    REFERENCE
	"ITU-T Rec. Q.752 (06/97) Table 14, Item 14.5 e).
	 ITU-T Rec. Q.752 (06/97) Table A.1, Item A.5 e)."
    ::= { tcapOmDevelSent15minIntEntry 8 }

tcapOmDevelSent15minIntRejectUnexpRetRes OBJECT-TYPE
    SYNTAX	PerfIntervalCount
    UNITS	"Events"
    MAX-ACCESS	read-only
    STATUS	current
    DESCRIPTION
	"The number of protocol errors detected in component portion 
	 (reject sent) with problem code return result unexpected 
	 (return result problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 f) moved to item A.5 f)."
    REFERENCE
	"ITU-T Rec. Q.752 (06/97) Table 14, Item 14.5 f).
	 ITU-T Rec. Q.752 (06/97) Table A.1, Item A.5 f)."
    ::= { tcapOmDevelSent15minIntEntry 9 }

tcapOmDevelSent15minIntRejectUnrecIdRetErr OBJECT-TYPE
    SYNTAX	PerfIntervalCount
    UNITS	"Events"
    MAX-ACCESS	read-only
    STATUS	current
    DESCRIPTION
	"The number of protocol errors detected in component portion 
	 (reject sent) with problem code unrecognized invoke identity 
	 (return error problem).  This is a non-obligatory measurement 
	 collected on a first-and-interval basis.  This measurement is 
	 pertinent for development purposes only.

	 Problem isolation during development may be assisted by 
	 measurements that indicate the reason for the protocol error 
	 being reported.  This includes protocol errors detected in the 
	 component portion that are not due to resource limitation.
	 
	 Note item 14.5 g) moved to item A.5 g)."
    REFERENCE
	"ITU-T Rec. Q.752 (06/97) Table 14, Item 14.5 g).
	 ITU-T Rec. Q.752 (06/97) Table A.1, Item A.5 g)."
    ::= { tcapOmDevelSent15minIntEntry 10 }

tcapOmDevelSent15minIntRejectUnexpRetErr OBJECT-TYPE
    SYNTAX	PerfIntervalCount
    UNITS	"Events"
    MAX-ACCESS	read-only
    STATUS	current
    DESCRIPTION
	"The number of protocol errors detected in component portion 
	 (reject sent) with problem code return error unexpected (return 
	 error problem).  This is a non-obligatory measurement collected 
	 on a first-and-interval basis.  This measurement is pertinent 
	 for development purposes only.

	 Problem isolation during development may be assisted by 
	 measurements that indicate the reason for the protocol error 
	 being reported.  This includes protocol errors detected in the 
	 component portion that are not due to resource limitation.
	 
	 Note item 14.5 h) moved to item A.5 h)."
    REFERENCE
	"ITU-T Rec. Q.752 (06/97) Table 14, Item 14.5 h).
	 ITU-T Rec. Q.752 (06/97) Table A.1, Item A.5 h)."
    ::= { tcapOmDevelSent15minIntEntry 11 }

tcapOmDevelSent15minIntUsrRejDupInvokeId OBJECT-TYPE
    SYNTAX	PerfIntervalCount
    UNITS	"Events/dest. User"
    MAX-ACCESS	read-only
    STATUS	current
    DESCRIPTION
	"The number of TC-user generated problems (TC-user reject sent) 
	 due to duplicate invoke identity (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 a).
	 ITU-T Rec. Q.752 (06/97) Table A.1, Item A.6 a)."
    ::= { tcapOmDevelSent15minIntEntry 12 }

tcapOmDevelSent15minIntUsrRejUnrecOper OBJECT-TYPE
    SYNTAX	PerfIntervalCount
    UNITS	"Events/dest. User"
    MAX-ACCESS	read-only
    STATUS	current
    DESCRIPTION
	"The number of TC-user generated problems (TC-user reject sent) 
	 due to unrecognized operation (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 b).
	 ITU-T Rec. Q.752 (06/97) Table A.1, Item A.6 b)."
    ::= { tcapOmDevelSent15minIntEntry 13 }

tcapOmDevelSent15minIntUsrRejParmInvoke OBJECT-TYPE
    SYNTAX	PerfIntervalCount
    UNITS	"Events/dest. User"
    MAX-ACCESS	read-only
    STATUS	current
    DESCRIPTION
	"The number of TC-user generated problems (TC-user reject sent) 
	 due to mistyped parameter (invoked problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 c).
	 ITU-T Rec. Q.752 (06/97) Table A.1, Item A.6 c)."
    ::= { tcapOmDevelSent15minIntEntry 14 }

tcapOmDevelSent15minIntUsrRejReleasing OBJECT-TYPE
    SYNTAX	PerfIntervalCount
    UNITS	"Events/dest. User"
    MAX-ACCESS	read-only
    STATUS	current
    DESCRIPTION
	"The number of TC-user generated problems (TC-user reject sent) 
	 due to initiating release (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 e).
	 ITU-T Rec. Q.752 (06/97) Table A.1, Item A.6 d)."
    ::= { tcapOmDevelSent15minIntEntry 15 }

tcapOmDevelSent15minIntUsrRejUnexpLinkResp OBJECT-TYPE
    SYNTAX	PerfIntervalCount
    UNITS	"Events/dest. User"
    MAX-ACCESS	read-only
    STATUS	current
    DESCRIPTION
	"The number of TC-user generated problems (TC-user reject sent) 
	 due to linked reponse unexpected (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 f).
	 ITU-T Rec. Q.752 (06/97) Table A.1, Item A.6 e)."
    ::= { tcapOmDevelSent15minIntEntry 16 }

tcapOmDevelSent15minIntUsrRejUnexpLinkOper OBJECT-TYPE
    SYNTAX	PerfIntervalCount
    UNITS	"Events/dest. User"
    MAX-ACCESS	read-only
    STATUS	current
    DESCRIPTION
	"The number of TC-user generated problems (TC-user reject sent) 
	 due to unexpected linked operation (invoke problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 g).
	 ITU-T Rec. Q.752 (06/97) Table A.1, Item A.6 f)."
    ::= { tcapOmDevelSent15minIntEntry 17 }

tcapOmDevelSent15minIntUsrRejUnrecError OBJECT-TYPE
    SYNTAX	PerfIntervalCount
    UNITS	"Events/dest. User"
    MAX-ACCESS	read-only
    STATUS	current
    DESCRIPTION
	"The number of TC-user generated problems (TC-user reject sent) 
	 due to unrecognized error (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 h).
	 ITU-T Rec. Q.752 (06/97) Table A.1, Item A.6 g)."
    ::= { tcapOmDevelSent15minIntEntry 18 }

tcapOmDevelSent15minIntUsrRejUnexpError OBJECT-TYPE
    SYNTAX	PerfIntervalCount
    UNITS	"Events/dest. User"
    MAX-ACCESS	read-only
    STATUS	current
    DESCRIPTION
	"The number of TC-user generated problems (TC-user reject sent) 
	 due to unexpected error (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 i).
	 ITU-T Rec. Q.752 (06/97) Table A.1, Item A.6 h)."
    ::= { tcapOmDevelSent15minIntEntry 19 }

tcapOmDevelSent15minIntUsrRejParmRetResult OBJECT-TYPE
    SYNTAX	PerfIntervalCount
    UNITS	"Events/dest. User"
    MAX-ACCESS	read-only
    STATUS	current
    DESCRIPTION
	"The number of TC-user generated problems (TC-user reject sent) 
	 due to mistyped parameter (return result problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 j).
	 ITU-T Rec. Q.752 (06/97) Table A.1, Item A.6 i)."
    ::= { tcapOmDevelSent15minIntEntry 20 }

tcapOmDevelSent15minIntUsrRejParmRetError OBJECT-TYPE
    SYNTAX	PerfIntervalCount
    UNITS	"Events/dest. User"
    MAX-ACCESS	read-only
    STATUS	current
    DESCRIPTION
	"The number of TC-user generated problems (TC-user reject sent) 
	 due to mistyped parameter (return error problem).  This is a 
	 non-obligatory measurement collected on a first-and-interval 
	 basis.  This measurement is pertinent for development purposes 
	 only.
	 
	 Problem isolation during development may be assisted by 
	 measurements that indicate the reason for the protocol error 
	 being reported.  This includes TC-user generated problems.
	 
	 Moved to Annex A."
    REFERENCE
	"ITU-T Rec. Q.752 (06/97) Table 14, Item 14.6 k).
	 ITU-T Rec. Q.752 (06/97) Table A.1, Item A.6 j)."
    ::= { tcapOmDevelSent15minIntEntry 21 }


-- =============================================================================
-- SCALARS
-- =============================================================================

tcapOm1stAndIntervalActivate OBJECT-TYPE
    SYNTAX	InstancePointer
    MAX-ACCESS	write-only
    STATUS	current
    DESCRIPTION
	"Some measurements in this MIB that are to be collected on a 
	 first-and-interval basis are marked as obligatory but requiring 
	 activation.  Writing the instance pointer of the columnar 
	 object corresponding to the PerfCurrentCount for the 
	 measurement will activate the first-and-interval measurement if 
	 not already activated.  When the object cannot be activated, an 
	 SNMP error will be returned.
	 
	 The activation state of a measurement can be determined by 
	 attempting to read its PerfCurrentValue.  This is because these 
	 texutal conventions will return an error ('wrong value') if the 
	 particular columnar object is not activated (the data collected 
	 is invalid or missing).
	 
	 Activating first-and-interval for a given measurement causes 
	 ss7OnOccurEvent notifications to be issued for the first event 
	 within the interval that occurs for the corresponding measure.  
	 However, it has no effect on the communicationsAlarm or 
	 qualityOfServiceAalarm notifications that are generated for 
	 maintenance purposes."
    REFERENCE
	""
    ::= { tcapOmScalars 1 }

tcapOm1stAndIntervalDeactivate OBJECT-TYPE
    SYNTAX	InstancePointer
    MAX-ACCESS	write-only
    STATUS	current
    DESCRIPTION
	"Some measurements in this MIB that are to be collected on a 
	 first-and-interval basis are marked as obligatory but requiring 
	 activation.  Writing the instance pointer of the columnar 
	 object corresponding to the PerfCurrentCount for the 
	 measurement will deactivate the first-and-interval measurement 
	 if not already activated.  When the object cannot be 
	 deactivated, an SNMP error will be returned.
	 
	 The activation state of a measurement can be determined by 
	 attempting to read its PerfCurrentValue.  This is because these 
	 texutal conventions will return an error if they particular 
	 columnar object is not activated (the data collected is invalid 
	 or missing).
	 
	 Activating first-and-interval for a given measurement causes 
	 ss7OnOccurEvent notifications to be issued for the first event 
	 within the interval that occurs for the corresponding measure.  
	 However, it has no effect on the communicationsAlarm or 
	 qualityOfServiceAalarm notifications that are generated for 
	 maintenance purposes."
    REFERENCE
	""
    ::= { tcapOmScalars 2 }

tcapOm5MinActivate OBJECT-TYPE
    SYNTAX	InstancePointer
    MAX-ACCESS	write-only
    STATUS	current
    DESCRIPTION
	"Some measurements in this MIB that are to be collected on a 
	 5-minute basis are marked as obligatory by requiring 
	 activation.  Writing the instance pointer of the columnar 
	 object coresponding to the PerfCurrentCount for the measurement 
	 will activate the 5-minute measurement if not already 
	 activated.  When the object cannot be activated, an SNMP error 
	 will be returned.
	 
	 The activation state of a measurement can be determined by 
	 attempting to read its PerfCurrentValue.  This is because these 
	 texutal conventions will return an error if they particular 
	 columnar object is not activated (the data collected is invalid 
	 or missing)."
    REFERENCE
	""
    ::= { tcapOmScalars 3 }

tcapOm5MinDeaActivate OBJECT-TYPE
    SYNTAX	InstancePointer
    MAX-ACCESS	write-only
    STATUS	current
    DESCRIPTION
	"Some measurements in this MIB that are to be collected on a 
	 5-minute basis are marked as obligatory by requiring 
	 activation.  Writing the instance pointer of the columnar 
	 object coresponding to the PerfCurrentCount for the measurement 
	 will deactivate the 5-minute measurement if not already 
	 deactivated.  When the object cannot be deactivated, an SNMP 
	 error will be returned.

	 The activation state of a measurement can be determined by 
	 attempting to read its PerfCurrentValue.  This is because these 
	 texutal conventions will return an error if they particular 
	 columnar object is not activated (the data collected is invalid 
	 or missing)."
    REFERENCE
	""
    ::= { tcapOmScalars 4 }

tcapOm15MinActivate OBJECT-TYPE
    SYNTAX	InstancePointer
    MAX-ACCESS	write-only
    STATUS	current
    DESCRIPTION
	"Some measurements in this MIB that are to be collected on a 
	 15-minute basis are marked as obligatory by requiring 
	 activation.  Writing the instance pointer of the columnar 
	 object coresponding to the PerfCurrentCount for the measurement 
	 will activate the 15-minute measurement if not already 
	 activated.  When the object cannot be activated, an SNMP error 
	 will be returned.
	 
	 The activation state of a measurement can be determined by 
	 attempting to read its PerfCurrentValue.  This is because these 
	 texutal conventions will return an error if they particular 
	 columnar object is not activated (the data collected is invalid 
	 or missing)."
    REFERENCE
	""
    ::= { tcapOmScalars 5 }

tcapOm15MinDeaActivate OBJECT-TYPE
    SYNTAX	InstancePointer
    MAX-ACCESS	write-only
    STATUS	current
    DESCRIPTION
	"Some measurements in this MIB that are to be collected on a 
	 15-minute basis are marked as obligatory by requiring 
	 activation.  Writing the instance pointer of the columnar 
	 object coresponding to the PerfCurrentCount for the measurement 
	 will deactivate the 15-minute measurement if not already 
	 deactivated.  When the object cannot be deactivated, an SNMP 
	 error will be returned.
	 
	 The activation state of a measurement can be determined by 
	 attempting to read its PerfCurrentValue.  This is because these 
	 texutal conventions will return an error if they particular 
	 columnar object is not activated (the data collected is invalid 
	 or missing)."
    REFERENCE
	""
    ::= { tcapOmScalars 6 }

tcapOmInterval OBJECT-TYPE
    SYNTAX	Integer32 (1..672)
    MAX-ACCESS	not-accessible
    STATUS	current
    DESCRIPTION
	"A historical data collection interval for use as an index.  
	 Specifies the historical data collection interval as a 
	 time-sequence with the lowest ordinal value '1' representing 
	 the newest data collected and the highest ordinal value 
	 (typically '96') being the oldest data collected."
    ::= { tcapOmScalars 7 }

tcapOmDiscontinuityTime OBJECT-TYPE
    SYNTAX	TimeStamp
    MAX-ACCESS	read-only
    STATUS	current
    DESCRIPTION
	"The time of the last discontinuity."
    ::= { tcapOmScalars 8 }

tcapOmTimeStamp OBJECT-TYPE
    SYNTAX	TimeStamp
    MAX-ACCESS	read-only
    STATUS	current
    DESCRIPTION
	"The time stamp of the beggining of the last completed 15-minute 
	 time interval when read, the beginning of an interval report 
	 for notifications."
    ::= { tcapOmScalars 9 }

tcapOm5MinMaxIntervals OBJECT-TYPE
    SYNTAX	Unsigned32 (0..288)
    MAX-ACCESS	read-write
    STATUS	current
    DESCRIPTION
	"Indicates the maximum number of historical 5-minute intervals 
	 that will be collected.  This is in the range from zero (0), no 
	 historical data collected, to 288, 1 day of historical 5-minute 
	 data collected.  Some implementations may support longer 
	 periods of time, or some, a more restricted range.  The default 
	 value that should be supported by all managed systems by 
	 element configuration is 96, or 8 hours of historical 5-minute 
	 data.
	 
	 Increasing or decreasing this value may increase or descrease 
	 respectively the local storage demands of the agent.  
	 Decreasing this value may or may not cause historical interval 
	 data beyond the maximum to be discarded.  Increasing this value 
	 might not restore valid intervals beyond the point to which 
	 this maximum was previously decreased.
	 
	 Therefore, the setting of this value must be retained in 
	 permanent storage and should be altered only infrequently, if 
	 at all, by management stations."
    DEFVAL	{ 96 }
    ::= { tcapOmScalars 10 }

tcapOm15MinMaxIntervals OBJECT-TYPE
    SYNTAX	Unsigned32 (0..672)
    MAX-ACCESS	read-write
    STATUS	current
    DESCRIPTION
	"Indicates and specifies the maximum number of historical 
	 15-minute intervals that will be collected.  This is in the 
	 range from zero (0), no historical data collected, to 672, 7 
	 days of historical 15-minute data collected.  Some 
	 implementations may support longer periods of time, or a some, 
	 a more restricted range.  The default value that should be 
	 supported by all managed systems by element configuration is 
	 96, or 24 hours of historical 15-minute data.
	 
	 Increasing or decreasing this value may increase or descrease 
	 respectively the local storage demands of the agent.  
	 Decreasing this value may or may not cause historical interval 
	 data beyond the maximum to be discarded.  Increasing this value 
	 might not restore valid intervals beyond the point to which 
	 this maximum was previously decreased.
	 
	 Therefore, the setting of this value must be retained in 
	 permanent storage and should be altered only infrequently, if 
	 at all, by management stations."
    DEFVAL	{ 96 }
    ::= { tcapOmScalars 11 }

-- =============================================================================
-- NOTIFICATION PARAMETERS
-- =============================================================================

tcapOmMessageType OBJECT-TYPE
    SYNTAX	Unsigned32
    MAX-ACCESS	accessible-for-notify
    STATUS	current
    DESCRIPTION
	""
    ::= { tcapOmNotifs 1 }

END

-- vim: ft=mib comments=\f\:\",\b\:\-\-,\:\-\-,\f\b\:- fo+=tcqlornw tw=72 nocin nosi sts=4 sw=4
