-- vim: ft=mib comments=\f\:\",\b\:\-\-,\:\-\-,\f\b\:- fo+=tcqlornw tw=72 nocin nosi sts=4 sw=4
-- =============================================================================
-- 
-- @(#) $RCSfile: OPENSS7-SCCP2-MIB.mib,v $ $Name: OpenSS7-0_9_2 $($Revision: 0.9.2.1 $) $Date: 2009-03-05 15:51:27 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-03-05 15:51:27 $ by $Author: brian $
--
-- -----------------------------------------------------------------------------
--
-- $Log: OPENSS7-SCCP2-MIB.mib,v $
-- Revision 0.9.2.1  2009-03-05 15:51:27  brian
-- - new files for map library
--
-- =============================================================================

OPENSS7-SCCP-MIB DEFINITIONS ::= BEGIN

sccpMIB MODULE-IDENTITY
    LAST-UPDATED "200903032246Z"
    ORGANIZATION
	"The OpenSS7 Project"
    CONTACT-INFO
        "Brian Bidulock
         OpenSS7 Corporation
         1469 Jefferys Crescent
         Edmonton, Alberta T6L 6T1
         CANADA
         Tel: +1 780 490 1141
         Fax: +1 780 490 1241
         Mob: +1 780 953 0557
         E-mail: bidulock@openss7.org"
    DESCRIPTION 
        "This is a MIB providing management information is 
         accordance with ITU-T Rec. Q.751.1, ITU-T Rec. 
         Q.2751.1, ANSI T1.116.1."
    REVISION "200903032246Z"
    DESCRIPTION
	"First release of this module."
    ::= { openss7Q751 2 }

sccpNotifications OBJECT IDENTIFIER
    ::= { sccpMIB 0 }

sccpDefaults OBJECT IDENTIFIER
    ::= { sccpMIB 1 }

sccpTables OBJECT IDENTIFIER
    ::= { sccpMIB 2 }

-- =============================================================================

-- This object should not be necessary and any references to this object 
-- should be replaced with a row pointer to an mtpNaTable entry.

sccpNetwork OBJECT IDENTIFIER
    ::= { sccpTables yy }

-- =============================================================================

-- This object should not be necessary and any reference to this object 
-- should be replaced with a row pointer to an mtpMsTable, mtpSpTable  
-- or mtpL3Table entry.

sccpSignallingPoint OBJECT IDENTIFIER
    ::= { sccpTables yy }

-- =============================================================================

-- This object corresponds to an instance of an sccpAccessPoint 
-- invocation.  That is, it corresponds to an upper stream on the SCCP 
-- STREAMS driver.

sccpUser OBJECT IDENTIFIER
    ::= { sccpTables yy }

-- =============================================================================

-- This is an SCCP entity set.  It models a group of subsystems that, in 
-- concert, provided an SCCP entity service.

sccpEntitySet OBJECT IDENTIFIER
    ::= { sccpTables yy }

-- =============================================================================

-- This is a signalling relation that is a relationship between the 
-- local SCCP (sccpSignallingPoint) and a remote SCCP.  It tracks the 
-- status of remote signalling points reachable from the local 
-- signalling point via the associated linkages.

sccpSignallingRelation OBJECT IDENTIFIER
    ::= { sccpTables yy }

-- =============================================================================

-- This is a local SCCP subsystem or SCCP-SAP.  It corresponds to the 
-- local version of the sccpAccessPoint MOC defined in Q.752.2.

sccpSubsystem OBJECT IDENTIFIER
    ::= { sccpTables yy }

sccpSubsystemTable OBJECT-TYPE
    SYNTAX SEQUENCE OF SccpSubsystemEntry
    MAX-ACCESS not-accessible
    STATUS current
    DESCRIPTION
	""
    REFERENCE
	""
    ::= { sccpSubsystem 1 }

sccpSubsystemEntry OBJECT-TYPE
    SYNTAX SccpSubsystemEntry
    MAX-ACCESS not-accessible
    STATUS current
    DESCRIPTION
	""
    REFERENCE
	""
    INDEX {
	sccpSubsystemSapId
    }
    ::= { sccpSubsystemTable 1 }

SccpSubsystemEntry ::=
    SEQUENCE {
	-- sap2 attributes
	sccpSubsystemSapId			Unsigned32,
	sccpSubsystemAlarmStatus		AlarmStatus,
	sccpSubsystemSap2Address		SubSystemNumber,
	sccpSubsystemUserEntityNames		OCTET STRING,
	sccpSubsystemProviderEntityNames	PointCodeList,
	-- nSAP attributes: (none)
	-- sccpAccessPoint attributes
	sccpSubsystemAvailabilityStatus		AvailabilityStatus,
	sccpSubsystemConcernedAreaPointer	Unsigned32,
	sccpSubsystemLinkagePointer		Unsigned32,
	-- ssAvailableAfterRestartPackage
	sccpSubsystemSsAvailableAfterRestart	TruthValue,
	sccpSubsystemAsaProfilePointer		RowPointer,
	sccpSubsystemName			CommonLanguageName,
	sccpSubsystemRowStatus			RowStatus
    }

-- =============================================================================

-- This is a remote SCCP subsystem or SCCP-SAP.  It corresponds to the
-- remote version of the sccpAccessPoint MOC defined in Q.752.2.

sccpRemoteSubsystem OBJECT IDENTIFIER
    ::= { sccpTables yy }

sccpRemoteSubsystemTable OBJECT-TYPE
    SYNTAX SEQUENCE OF SccpRemoteSubsystemEntry
    MAX-ACCESS not-accessible
    STATUS current
    DESCRIPTION
	""
    REFERENCE
	""
    ::= { sccpRemoteSubsystem 1 }

sccpRemoteSubsystemEntry OBJECT-TYPE
    SYNTAX SccpRemoteSubsystemEntry
    MAX-ACCESS not-accessible
    STATUS current
    DESCRIPTION
	""
    REFERENCE
	""
    INDEX {
	sccpRemoteSubsystemSapId
    }
    ::= { sccpRemoteSubsystemTable 1 }

SccpRemoteSubsystemEntry ::=
    SEQUENCE {
	-- sap2 attributes
	sccpRemoteSubsystemSapId		Unsigned32,
	sccpRemoteSubsystemAlarmStatus		AlarmStatus,
	sccpRemoteSubsystemSap2Address		SubSystemNumber,
	sccpRemoteSubsystemUserEntityNames	OCTET STRING,
	sccpRemoteSubsystemProviderEntityNames	PointCodeList,
	-- nSAP attributes: (none)
	-- sccpAccessPoint attributes
	sccpRemoteSubsystemAvailabilityStatus	AvailabilityStatus,
	sccpRemoteSubsystemConcernedAreaPointer	Unsigned32,
	sccpRemoteSubsystemLinkagePointer	Unsigned32,
	-- ssAvailableAfterRestartPackage
	sccpRemoteSubsystemSsAvailableAfterRestart TruthValue,
	sccpRemoteSubsystemAsaProfilePointer	RowPointer,
	sccpRemoteSubsystemName			CommonLanguageName,
	sccpRemoteSubsystemRowStatus		RowStatus
    }

-- =============================================================================


sccpConcernedArea OBJECT IDENTIFIER
    ::= { sccpTables yy }

-- =============================================================================


sccpLinkage OBJECT IDENTIFIER
    ::= { sccpTables yy }

-- =============================================================================


sccpCoupling OBJECT IDENTIFIER
    ::= { sccpTables yy }

-- =============================================================================


END -- OPENSS7-SCCP-MIB

-- vim: ft=mib comments=\f\:\",\b\:\-\-,\:\-\-,\f\b\:- fo+=tcqlornw tw=72 nocin nosi sts=4 sw=4
