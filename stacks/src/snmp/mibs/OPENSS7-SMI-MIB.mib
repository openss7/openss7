-- vim: ft=mib comments=\f\b\:\"ITU\-T,\f\b\:ITU\-T,\f\:\",\b\:\-\-,\:\-\-,\f\b\:\- fo+=tcqlornw12 tw=64 ai nocin nosi sts=4 sw=4 et
-- =============================================================================
-- 
-- @(#) $RCSfile: OPENSS7-SMI-MIB.mib,v $ $Name:  $($Revision: 0.9.2.17 $) $Date: 2009-02-18 02:11:49 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-02-18 02:11:49 $ by $Author: brian $
--
-- -----------------------------------------------------------------------------
--
-- $Log: OPENSS7-SMI-MIB.mib,v $
-- Revision 0.9.2.17  2009-02-18 02:11:49  brian
-- - minor corrections
--
-- Revision 0.9.2.16  2009-01-28 06:21:13  brian
-- - typo
--
-- Revision 0.9.2.15  2009-01-21 06:16:29  brian
-- - updated mibs
--
-- Revision 0.9.2.14  2009-01-14 09:23:31  brian
-- - typo
--
-- Revision 0.9.2.13  2009-01-14 09:08:46  brian
-- - mib updates
--
-- Revision 0.9.2.12  2009-01-10 17:18:43  brian
-- - updated headers
--
-- Revision 0.9.2.11  2009-01-10 17:09:26  brian
-- - updated agents
--
-- Revision 0.9.2.10  2009/01/04 05:19:27  brian
-- - correct conflicts and errors
--
-- Revision 0.9.2.9  2008-12-27 10:01:51  brian
-- - updated mibs and stubs
--
-- Revision 0.9.2.8  2008-12-20 12:55:44  brian
-- - add new mibs and agents
--
-- Revision 0.9.2.7  2008-12-14 10:33:06  brian
-- - spelling correction
--
-- Revision 0.9.2.6  2008-07-28 08:51:42  brian
-- - SNMP updates
--
-- Revision 0.9.2.5  2008-04-29 07:11:22  brian
-- - updating headers for release
--
-- Revision 0.9.2.4  2008/01/24 17:40:57  brian
-- - updated mibs
--
-- Revision 0.9.2.3  2008/01/16 01:35:43  brian
-- - added GMI (X.723) mib.
--
-- Revision 0.9.2.2  2008/01/14 16:55:12  brian
-- - updated mibs
--
-- Revision 0.9.2.1  2008/01/10 19:55:43  brian
-- - updating mibs
--
-- =============================================================================

OPENSS7-SMI-MIB DEFINITIONS ::= BEGIN

IMPORTS
    openss7, openss7Ms, openss7MsSmi
        FROM OPENSS7-SMI
    MODULE-COMPLIANCE, NOTIFICATION-GROUP, OBJECT-GROUP
        FROM SNMPv2-CONF
    Gauge32, Integer32, MODULE-IDENTITY, NOTIFICATION-TYPE, 
    OBJECT-IDENTITY, OBJECT-TYPE, TimeTicks, Unsigned32, zeroDotZero
        FROM SNMPv2-SMI
    RowStatus, TEXTUAL-CONVENTION, TimeStamp, TruthValue
        FROM SNMPv2-TC;

smiMIB MODULE-IDENTITY
    LAST-UPDATED "200901210441Z"
    ORGANIZATION "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         E-mail: bidulock@openss7.org"
    DESCRIPTION
        "This is a basic MIB module providing definitions of 
         objects based on TMN (ITU-T Rec. X.721 (1992) | ISO/IEC 
         10165-2 : 1992)"
    REVISION "200901210441Z"
    DESCRIPTION
        "Flattened organization."
    REVISION "200812201153Z"
    DESCRIPTION
        "Additional workup."
    REVISION "200801071407Z"
    DESCRIPTION
        "This is the first release of this module."
    ::= { openss7MsSmi 2 } -- 10165-2


ObjectClass ::= TEXTUAL-CONVENTION
    STATUS current
    DESCRIPTION
        "Provides a specification of a managed object class.  
         Under SNMP a managed object class is equivalent to an 
         Entry object for a Table, that identifies a table in 
         which managed objects are instantiated as conceptual 
         rows.  Therefore, this specification is 
         a VariablePointer textual convention but is restricted 
         to identifying the Entry object associated with a given 
         table."
    REFERENCE
        "ITU-T Rec. X.711 | ISO/IEC 9596-1, CMIP-1.ObjectClass"
    SYNTAX OBJECT IDENTIFIER

ObjectInstance ::= TEXTUAL-CONVENTION
    STATUS current
    DESCRIPTION
        "Provides a specification of a managed object instance.  
         Under SNMP a managed object instance is equivalent to 
         an entry in a concepual table where the table 
         represents the managed object class.  Therefore, this 
         specification is a RowPointer textual convention 
         identifying the conceptual row associated within 
         a given table."
    REFERENCE
        "ITU-T Rec. X.711 | ISO/IEC 9596-1, 
               CMIP-1.ObjectInstance"
    SYNTAX OBJECT IDENTIFIER

GroupObjects ::= TEXTUAL-CONVENTION
    STATUS      current
    DESCRIPTION
        "Provides specification of a group of managed object 
         instances.  The octet string is a BER encoded SEQUENCE 
         OF OCTET IDENTIFIER."
    REFERENCE
        "ITU-T Rec. X.711 | ISO/IEC 9596-1, CMIP-1.GroupObjects"
    SYNTAX OCTET STRING

AttributeId ::= TEXTUAL-CONVENTION
    STATUS current
    DESCRIPTION
        "Provides a specification of a manage object class 
         attribute.  Under SNMP, a managed object class 
         attribute is equivalent to a columnar object for 
         a table, that identifies the column in which the 
         instantiated attribute values appear.  Therefore, this 
         specification is a VariablePointer textual convention 
         but is restricted to identifying the accessible 
         columnar object associated with the column of a given 
         table."
    REFERENCE
        "ITU-T Rec. X.711 | ISO/IEC 959601, CMIP-1.AttributeId"
    SYNTAX OBJECT IDENTIFIER

AlarmType ::= TEXTUAL-CONVENTION
    STATUS current
    DESCRIPTION
        "The alarm type textual convention is an object 
         identifier that is one of the object identifiers 
         assigned to TMN notifications of an alarm type.  The 
         actual alarm type values from X.721 (i.e. in the 
         { joint-iso-ccitt(2) ms(9) smi(3) part2(2) 
         notifications(10) } arc) may be used directly.  
         Additional defined alarm type extensions defined by 
         other documents such as Q.751.1 may also be used.  
         Alternately, the corresponding notification values 
         registered in OPENSS7-SMI-MIB can be used directly.
         
         Object identifiers used with the AlarmType textual 
         convention must be defined in an OBJECT-IDENTITY macro 
         and their use and meaning must be described in the 
         DESCRIPTION clause of that macro."
    REFERENCE
        "ITU-T Rec. X.711 | ISO/IEC 9596-1, CMIP-1.AlarmType"
    SYNTAX OBJECT IDENTIFIER

ProbableCause ::= TEXTUAL-CONVENTION
    STATUS current
    DESCRIPTION
        "This is either an object identifier or an integer.  
         When valued as an integer, the integer is coded in the 
         first and only element of the object identifier.  When 
         coded as an integer, because of the way that object 
         identifiers are BER encoded, the value might be 
         displayed as two elements.
         
         This parameter defines further qualification as to the 
         probable cause of the alarm.  Probable cause values for 
         notifications shall be indicated in the behaviour 
         clause of the object class definition.
         
         The probable cause textual convention is an object 
         identifier that is one of the object identifiers 
         assigned to probable causes.  The actual probable cause 
         values from X.721 (i.e. in the { joint-iso-ccitt(2) 
         ms(9) smi(3) part2(2) standardsSpecificExtensions(0) 
         arf(0) } arc) may be used directly.  Additional defined 
         probable cause extensions defined by other documents 
         such as Q.751.1 and Q.751.2 may also be used.
         
         Object identifiers used with the ProbableCause textual 
         convention must be defined in an OBJECT-IDENTITY macro 
         and their use and meaning must be described in the 
         DESCRIPTION
         clause of that macro."
    REFERENCE
        "ITU-T Rec. X.721 (1992) | ISO/IEC 10165-2 : 1992, 
               Attribute-ASN1Module ProbableCause.
         ITU-T Rec. X.733 (1992) | ISO/IEC 10164-4 : 1992,
               Section 8.1.2.1."
    SYNTAX OBJECT IDENTIFIER

SpecificIdentifier ::= TEXTUAL-CONVENTION
    STATUS current
    DESCRIPTION
        "Provides the specification of the syntax of the 
         identification of a specific problem.  It is either an 
         object identifier or an integer.  When valued as an 
         integer, the integer is coded in the first an donly 
         element of the object identifier.  When coded as an 
         integer, because of the way that non-relative object 
         identifiers are BER encoded, the value might be 
         displayed as two elements.
         
         This element of a SpecificProblems parameter defines 
         further qualification as the the sepcific problem 
         identified by the alarm.  Specific problem values for 
         notifications shall be indicated in the behaviour claus 
         of the object class definition.
         
         The specific identifier textual convention is an object 
         identifier that is one of the object identifiers 
         assigned to specific problems.  The actual specific 
         problem values from X.271 (i.e. in the { } ) may be 
         used directly.  Additional defined specific problems 
         extensionss defined by other doucments such as Q.751.1 
         and Q.751.2 may also be used.
         
         Object identifiers used with the SpecificIdentifier 
         textual convention must be defined in an 
         OBJECT-IDENTITY macro and their use and meaning must be 
         described in the DESCRIPTION
         clause of that macro."
    REFERENCE
        "ITU-T Rec. X.721 (1992) | ISO/IEC 10165-2 : 1992, 
               Attribute-ASN1Module SpecificIdentifier."
    SYNTAX OBJECT IDENTIFIER

SpecificProblems ::= TEXTUAL-CONVENTION
    STATUS current
    DESCRIPTION
        "This parameter, when present, identifies further 
         refinements to the probable cause of the alarm.  This 
         parameter qualifies the chosen probable cause and may 
         be used by the managed object class definer to specify 
         a set of identifiers for use in managed object classes.
         
         This parameter is either a set of integers or a set of 
         object identifiers.  However, only object identifiers 
         shall be used within the system management context 
         defined in ITU-T Rec.  X.701 | ISO/IEC 10040.
         
         This is either an object identifier or an integer.  
         When valued as an integer, the integer is coded in the 
         first and only element of the object identifier.
         When coded as an integer, because of the way that 
         object identifiers are BER encoded, the value will 
         likely be displayed as two elements.
         
         The specific problems textual convention is an object 
         identifier that is one of the object identifiers 
         assigned to a specific problem.  The actual specific
         problem values from TMN specifications may be used 
         directly.  Additional defined specific problem 
         extensions defined by other documents such a Q.751.1 
         may also be used.
         
         Object identifiers used with the SpecificProblems 
         textual convention must be defined in an 
         OBJECT-IDENTITY macro and their use and meaning must be 
         described in the DESCRIPTION
         clause of that macro."
    REFERENCE
        "ITU-T Rec. X.721 (1992) | ISO/IEC 10165-2 : 1992, 
               Attribute-ASN1Module SpecificProblems.
         ITU-T Rec. X.733 (1992) | ISO/IEC 10164-2 : 1992, 
               Section 8.1.2.2."
    SYNTAX OBJECT IDENTIFIER

PerceivedSeverity ::= TEXTUAL-CONVENTION
    STATUS current
    DESCRIPTION
        "This parameter defines six severity levels that provide 
         an indication of how it is perceived that the 
         capability of the managed object has been affected.  
         Those severity levels that represent service affecting 
         conditions ordered from most sever to lease severe are 
         Critical, Major, Minor and Warning.  The levels defined 
         for use with this mandatory parameter of alarm 
         notifications are:
         
          - cleared: The Cleared severity level indicates the 
            clearing of one or more previously reported alarms.  
            This alarm clears all alarms for this managed object 
            that have the same Alarm type, Probable cause and 
            Specific problems (if given).  Multiple associated 
            notifications may be cleared by using the Correlated 
            notifications parameter (defined below).  ITU-T Rec.  
            X.733 | ISO/IEC 10164-2 does not require that the 
            clearing of previously reported alarms be reported.  
            Therefore, a managing system cannot assume that the 
            absence of an alarm with the Cleared severity level 
            means that the condition that caused the generation 
            of previous alarms is still present. Managed object 
            definers shall state if, and under which conditions, 
            the Cleared severity level is used.
         
          - indeterminate: The Indeterminate severity level 
            indicates that the severity level cannot be 
            determined.
         
          - critical: The Critical severity level indicates that 
            a service affecting condition has occurred and an 
            immediate corrective action is required. Such 
            a severity can be reported, for example, when 
            a managed object becomes totally out of service and 
            its capability must be restored.
         
          - major: The Major severity level indicates that 
            a service affecting condition has developed and an 
            urgent corrective action is required. Such 
            a severity can be reported, for example, when there 
            is a severe degradation in the capability of the 
            managed object and its full capability must be 
            restored.
         
          - minor: The Minor severity level indicates the 
            existence of a non-service affecting fault condition 
            and that corrective action should be taken in order 
            to prevent a more serious (for example, service 
            affecting) fault. Such a severity can be reported, 
            for example, when the detected alarm condition is 
            not currently degrading the capacity of the managed 
            object.
         
          - warning: The Warning severity level indicates the 
            detection of a potential or impending service 
            affecting fault, before any significant effects have 
            been felt. Action should be taken to further 
            diagnose (if necessary) and correct the problem to 
            prevent it from becoming a more serious service 
            affecting fault.
         
         This is the perceived severity of an alarm defined in 
         accordance with the definitions in the OSI SMI.  When 
         it appears within a scalar defined for use in 
         a notification, it represents the severity of the 
         notification.  Under OSI SMI, the perceived severity is 
         used to indicate both the onset of an alarm condition 
         and the clearing of an alarm condition.
         
         When set to any value other than cleared(5), the 
         notification represents the onset of the alarm 
         corresponding to the notification with a severity level 
         indicated by the value.  Normal telecommunications 
         warning, minor, major, critical alarm indications can 
         be indicated.  (Note that the setting of 
         indeterminate(0) is only applied when none of the other 
         characterizations will suffice.)
         
         When set to to cleared(5), the notification represents 
         the clearing of the alarm condition corresponding to 
         the notification."
    REFERENCE
        "ITU-T Rec. X.721 (1992) | ISO/IEC 10165-2 : 1992, 
               Attribute-ASN1Module PerceivedSeverity.
         ITU-T Rec. X.733 (1992) | ISO/IEC 10164-2 : 1992, 
               Section 8.1.2.3."
    SYNTAX INTEGER { 
        indeterminate(0), critical(1), major(2), minor(3), 
        warning(4), cleared(5) }

BackedUpStatus ::= TEXTUAL-CONVENTION
    STATUS current
    DESCRIPTION
        "This parameter, when present, specifies whether or not 
         the object emitting the alarm has been backed-up, and 
         services provided to the user have, therefore, not been 
         disrupted. The use of this field in conjunction with 
         the severity field provides information in an 
         independent form to qualify the seriousness of the 
         alarm and the ability of the system as a whole to 
         continue to provide services. If the value of this 
         parameter is true, it indicates that the object 
         emitting the alarm has been backed-up; if false, the 
         object has not been backed-up."
    REFERENCE
        "ITU-T Rec. X.721 (1992) | ISO/IEC 10165-2 : 1992, 
               Attribute-ASN1Module BackedUpStatus.
         ITU-T Rec. X.733 (1992) | ISO/IEC 10164-2 : 1992, 
               Section 8.1.2.4."
    SYNTAX INTEGER { 
        none(0), backedUp(1) }

BackUpObject ::= TEXTUAL-CONVENTION
    STATUS current
    DESCRIPTION
        "This parameter shall be present when the Backed-up 
         status parameter is present and has the value true.  
         This parameter specifies the managed object instance 
         that is providing back-up services for the managed 
         object about which the notification pertains. This 
         parameter is useful, for example, when the back-up 
         object is from a pool of objects any of which may be 
         dynamically allocated to replace a faulty object.
         
         The Back-up object parameter is related to the Back-up 
         object relationship attribute defined in CCITT Rec.  
         X.732 | ISO/IEC 10164-3. The value of this parameter 
         shall be the same as the Back-up object attribute value 
         when the alarm is emitted."
    REFERENCE
        "ITU-T Rec. X.721 (1992) | ISO/IEC 10165-2 : 1992, 
               Attribute-ASN1Module.ObjectInstance.
         ITU-T Rec. X.733 (1992) | ISO/IEC 10164-2 : 1992, 
               Section 8.1.2.5."
    SYNTAX OBJECT IDENTIFIER

TrendIndication ::= TEXTUAL-CONVENTION
    STATUS current
    DESCRIPTION
        "This parameter, when present, specifies the current 
         severity trend of the managed object. If present it 
         indicates that there are one or more alarms 
         ('outstanding alarms') which have not been cleared, and 
         pertain to the same managed object as that to which 
         this alarm ('current alarm') pertains. The Trend 
         indication parameter has three possible values:
         
          - more severe: The Perceived severity in the current 
            alarm is higher (more severe) than that reported in 
            any of the outstanding alarms;
         
          - no change: The Perceived severity reported in the 
            current alarm is the same as the highest (most 
            severe) of any of the outstanding alarms;
           
          - less severe: There is at least one outstanding alarm 
            of a severity higher (more severe) than that in the 
            current alarm.
         
         For Trend indication to be meaningful, the Perceived 
         severity parameter value of each alarm that may be 
         emitted by the managed object must be defined 
         consistently over all of the defined alarm types for 
         that managed object class. Trend indication information 
         is of particular use to managing systems which receive 
         alarm reports from an event forwarding discriminator 
         configured to pass alarms above a Perceived severity 
         level. The severity trend can also be determined by 
         a managing system that monitors the Perceived severity 
         parameter in received alarm reports.
         
         The Trend indication parameter shall not be present if 
         there are no outstanding alarms.
         
         The absence of the Trend indication parameter cannot be 
         taken to indicate the existence or non-existence of 
         outstanding alarms."
    REFERENCE
        "ITU-T Rec. X.721 (1992) | ISO/IEC 10165-2 : 1992, 
               Attribute-ASN1Module TrendIndication.
         ITU-T Rec. X.733 (1992) | ISO/IEC 10164-2 : 1992, 
               Section 8.1.2.6."
    SYNTAX INTEGER { 
        lessSevere(0), noChange(1), moreSevere(2) }

ThresholdInfo ::= TEXTUAL-CONVENTION
    STATUS current
    DESCRIPTION
        "This parameter shall be present when the alarm is 
         a result of crossing a threshold. It consists of four 
         subparameters.
         
          - triggered threshold: The identifier of the threshold 
            attribute that caused the notification;
         
          - threshold level: In the case of a gauge the 
            threshold level specifies a pair of threshold 
            values, the first being the value of the crossed 
            threshold and the second, its corresponding 
            hysteresis; in the case of a counter the threshold 
            level specifies only the threshold value.
         
          - observed value: The value of the gauge or counter 
            which crossed the threshold. This may be different 
            from the threshold value if, for example, the gauge 
            may only take on discrete values.
         
          - arm time: For a gauge threshold, the time at which 
            the threshold was last re-armed, namely the time 
            after the previous threshold crossing at which the 
            hysteresis value of the threshold was exceeded thus 
            again permitting generation of notifications when 
            the threshold is crossed. For a counter threshold, 
            the later of the time at which the threshold offset 
            was last applied, or the time at which the counter 
            was last initialized (for resettable counters)."
    REFERENCE
        "ITU-T Rec. X.721 (1992) | ISO/IEC 10165-2 : 1992, 
               Attribute-ASN1Module ThresholdInfo.
         ITU-T Rec. X.733 (1992) | ISO/IEC 10164-2 : 1992, 
               Section 8.1.2.7."
    SYNTAX OCTET STRING

NotificationIdentifier ::= TEXTUAL-CONVENTION
    DISPLAY-HINT "d-0"
    STATUS current
    DESCRIPTION
        "This parameter, when present, provides an identifier 
         for the notification, which may be carried in the 
         Correlated notifications parameter (see below) of 
         future notifications.  Notification identifiers must be 
         chosen to be unique across all notifications of 
         a particular managed object throughout the time that 
         correlation is significant.
         
         A Notification identifier may be reused if there is no 
         requirement that the previous notification using that 
         Notification identifier be correlated with future 
         notifications. Generally, Notification identifiers 
         should be chosen to ensure uniqueness over as long 
         a time as is feasible for the managed system."
    REFERENCE
        "ITU-T Rec. X.721 (1992) | ISO/IEC 10165-2 : 1992, 
               Attribute-ASN1Module NotificationIdentifier.
         ITU-T Rec. X.733 (1992) | ISO/IEC 10164-2 : 1992, 
               Section 8.1.2.8."
    SYNTAX Integer32

CorrelatedNotifications ::= TEXTUAL-CONVENTION
    STATUS current
    DESCRIPTION
        "This parameter, when present, contains a set of 
         Notification identifiers and, if necessary, their 
         associated managed object instance names. This set is 
         defined to be the set of all notifications to which 
         this notification is considered to be correlated. The 
         source object instance shall be present if the 
         correlated event report is from a managed object 
         instance other than the one in which the Correlated 
         notifications parameter appears.
         
         The algorithm by which correlation is accomplished is 
         outside the scope of X.733.
         
         CorrelatedNotifications ::= SET OF SEQUENCE {
            correlatedNotifications SET OF NotificationIdentifier,
            sourceObjectInst ObjectInstance OPTIONAL }"
    REFERENCE
        "ITU-T Rec. X.721 (1992) | ISO/IEC 10165-2 : 1992, 
               Attribute-ASN1Module CorrelatedNotifications.
         ITU-T Rec. X.733 (1992) | ISO/IEC 10164-2 : 1992, 
               Section 8.1.2.9."
    SYNTAX OCTET STRING

AttributeValueChangeDefinition ::= TEXTUAL-CONVENTION
    STATUS current
    DESCRIPTION
        "This parameter, when present, is used to indicate 
         a state transition, as specified in CCITT Rec. X.731 
         | ISO/IEC 10164-2, associated with the alarm. In this 
         case, if the managed object class definition includes 
         state change notifications it shall also emit a state 
         change notification as specified in CCITT Rec. X.731 
         | ISO/IEC 10164-2.
         
         This parameter set consists of a set of sequences of 
         the three parameters: Attribute identifier, Old 
         attribute value and new attribute value described 
         below. Each individual sequence describes a single 
         relationship attribute value change. At least one new 
         relationship attribute value shall be present in this 
         list."
    REFERENCE
        "ITU-T Rec. X.721 (1992) | ISO/IEC 10165-2 : 1992, 
               Attribute-ASN1Module.AttributeValueChangeDefinition.
         ITU-T Rec. X.732 (1992) | ISO/IEC 10164-3 : 1993, 
               Section 8.2.2.3.
         ITU-T Rec. X.733 (1992) | ISO/IEC 10164-2 : 1992, 
               Section 8.1.2.10."
    SYNTAX OCTET STRING

MonitoredAttributes ::= TEXTUAL-CONVENTION
    STATUS current
    DESCRIPTION
        "The Monitored attributes parameter, when present, 
         defines one or more attributes of the managed object 
         and their corresponding values at the time of the 
         alarm. Managed object definers may specify the set of 
         attributes which are of interest, if any. This allows, 
         for example, the timely reporting of changing 
         conditions prevalent at the time of the alarm."
    REFERENCE
        "ITU-T Rec. X.721 (1992) | ISO/IEC 10165-2 : 1992, 
               Attribute-ASN1Module MonitoredAttributes.
         ITU-T Rec. X.733 (1992) | ISO/IEC 10164-2 : 1992, 
               Section 8.1.2.11."
    SYNTAX OCTET STRING

ProposedRepairActions ::= TEXTUAL-CONVENTION
    STATUS current
    DESCRIPTION
        "This parameter, when present, is used if the cause is 
         known and the system being managed can suggest one or 
         more solutions (such as switch in standby equipment, 
         retry, replace media).  This parameter is a set of 
         possibilities specified by the object class definer.
         
         This parameter is either a set of integers or a set of 
         object identifiers.  However, only object identifiers 
         shall be used within the Systems management context 
         defined in CCITT Rec.  X.701 | ISO/IEC 10040.  Such 
         identifiers may be registered using the registration 
         procedures defined for ASN.1 Object Identifier values 
         in CCITT Rec. X.208 | ISO/IEC 8824.
         
         The following note applies to ITU-T applications only.  
         Two values with the following semantics have been 
         assigned to this parameter in X.733 and X.721:
         
          - no repair action required: This value is used to 
            indicate that the manager is not required to 
            initiate any repair action because it is not the 
            manager s responsibility;
         
          - repair action required: This value is used to 
            indicate that the manager is required to initiate 
            repair action to correct the problem reported in the 
            alarm report.  This value also indicates that no 
            specific repair action is proposed by the agent 
            system.
         
         This is either an object identifier or an integer.  
         When valued as an integer, the integer is coded in the 
         first and only element of the object identifier."
    REFERENCE
        "ITU-T Rec. X.721 (1992) | ISO/IEC 10165-2 : 1992, 
               Attribute-ASN1Module ProposedRepairActions.
         ITU-T Rec. X.733 (1992) | ISO/IEC 10164-2 : 1992, 
               Section 8.1.2.12."
    SYNTAX OBJECT IDENTIFIER

AdditionalText ::= TEXTUAL-CONVENTION
    STATUS current
    DESCRIPTION
        "This parameter, when present, allows a free form text 
         description to be reported. Understanding the semantics 
         of this field is not required for interpretation of the 
         notification.
         
         This X.733 does not specify the format or meaning of 
         the data contained in the Additional text parameter.  
         The contents are not subject to any test of OSI 
         Management conformance.
         
         This textual convention represents additional text to 
         be added to a TMN notification in TMN style."
    REFERENCE
        "ITU-T Rec. X.721 (1992) | ISO/IEC 10165-2 : 1992, 
               Attribute-ASN1Module AdditionalText.
         ITU-T Rec. X.733 (1992) | ISO/IEC 10164-2 : 1992, 
               Section 8.1.2.13."
    SYNTAX OCTET STRING

AdditionalInformation ::= TEXTUAL-CONVENTION
    STATUS current
    DESCRIPTION
        "This parameter, when present, allows the inclusion of 
         a set of additional information in the event report.  
         It is a series of data structures each of which 
         contains three items of information: an identifier, 
         a significance indicator, and the problem information.
         
         The identifier subparameter carries a registered object 
         identifier which defines the data type of the 
         information subparameter.  The data type must be 
         understood by the managing system in order for the 
         contents of the information subparameter to be parsed.  
         
         The significance subparameter is a boolean value which 
         is set to true if the receiving system must be able to 
         parse the contents of the information subparameter for 
         the event report to be fully understood.  Even if the 
         Additional information parameter is not fully 
         understood, an event report indication shall be issued 
         to the user.  Indication that the Additional 
         information parameter is not fully understood is 
         a local matter.
         
         The information subparameter carries information about 
         the event.  This information can be parsed if the 
         identifier is understood.
         
         SET OF ManagementExtension.
         
         This textual convention represents additional 
         information to be added to a TMN notification in TMN 
         style.  This could contain things like an entire 
         communications PDU.  The additionalText should 
         described this data."
    REFERENCE
        "ITU-T Rec. X.721 (1992) | ISO/IEC 10165-2 : 1992, 
               Attribute-ASN1Module AdditionalInformation.
         ITU-T Rec. X.733 (1992) | ISO/IEC 10164-2 : 1992, 
               Section 8.1.2.14."
    SYNTAX OCTET STRING

SourceIndicator ::= TEXTUAL-CONVENTION
    STATUS current
    DESCRIPTION
        "This parameter, when present, indicates the source of 
         the operation that led to the generation of this 
         notification type or event record.  It can have one of 
         the following values:
         
          - resource operation: The notification was generated 
            in response to a state attribute value change 
            effected through the internal operation of the 
            resource.
         
          - management operation: The notification was generated 
            in response to a state attribute value change 
            effected through an SMI management operation applied 
            accross the managed object boundary external to the 
            managed object.
         
          - unknown: It is not possible to determine the source 
            of the operation.
         
         This parameter, when present, indicates the source of 
         the operation that led to the generation of this 
         notification type.  It can have one of the following 
         values.
         
          - resource operation: The notification was generated 
            in response to a relationship attribute value change 
            effected through the internal operation of the 
            resource;
         
          - management operation: The notification was generated 
            in response to a relationship attribute value change 
            effected through an SMI management operation applied 
            across the managed object boundary external to the 
            managed object;
         
          - unknown: It is not possible to determine the source 
            of the operation.
         
         This textual convention provides the source of an 
         action that resulted in the change in state of 
         a managed object, alteration of its attributes or 
         addition or deletion of the object.  
         resourceOperation(0) indicates that the managed element 
         or agent performed the change; managementOperation(1) 
         indicates that a management station was the source of 
         the change; and unknown(2) indicates that the souce of 
         the change is unknown."
    REFERENCE
        "ITU-T Rec. X.721 (1992) | ISO/IEC 10165-2 : 1992, 
               Attribute-ASN1Module SourceIndicator.
         ITU-T Rec. X.731 (1992) | ISO/IEC 10164-2 : 1993, 
               Section 8.2.2.1.
         ITU-T Rec. X.732 (1992) | ISO/IEC 10164-3 : 1993, 
               Section 8.2.2.1."
    SYNTAX INTEGER { 
        resourceOperation(0), managementOperation(1), unknown(2) 
        }

AttributeIdentifierList ::= TEXTUAL-CONVENTION
    STATUS current
    DESCRIPTION
        "This parameter, when present, identifies the set of 
         state attributes whose value changes are being 
         reported.
         
         This parameter, when present, identifies the set of 
         relationship attributes whose value changes are being 
         reported."
    REFERENCE
        "ITU-T Rec. X.721 (1992) | ISO/IEC 10165-2 : 1992, 
               Attribute-ASN1Module AttributeIdentifierList.
         ITU-T Rec. X.731 (1992) | ISO/IEC 10164-2 : 1993, 
               Section 8.2.2.2.
         ITU-T Rec. X.732 (1992) | ISO/IEC 10164-3 : 1993, 
               Section 8.2.2.2."
    SYNTAX OBJECT IDENTIFIER

SecurityAlarmCause ::= TEXTUAL-CONVENTION
    STATUS current
    DESCRIPTION
        "The security alarm cause textual convention is an 
         object identifier that is one of the object identifiers 
         assigned to security alarm causes.  The actual security 
         alarm cause values from X.721 object identifier arcs 
         may be used directly.  Additional defined security 
         alarm cause extensions defined by other documents such 
         as Q.751.1 may also be used.
         
         Object identifiers used with the SecurityAlarmCause 
         textual convention must be defined in an 
         OBJECT-IDENTITY marco an their use and meaning must be 
         described in the DESCRIPTION clause of that macro."
    REFERENCE
        "ITU-T Rec. X.721 (1992) | ISO/IEC 10165-2 : 1992, 
               Attribute-ASN1Module SecurityAlarmCause"
    SYNTAX OBJECT IDENTIFIER

SecurityAlarmSeverity ::= TEXTUAL-CONVENTION
    STATUS current
    DESCRIPTION
        "This is the same as PerceivedSeverity but does not have 
         a cleared(5) value."
    REFERENCE
        "ITU-T Rec. X.721 (1992) | ISO/IEC 10165-2 : 1992, 
               Attribute-ASN1Module SecurityAlarmSeverity"
    SYNTAX INTEGER { 
        indeterminate(0), critical(1), major(2), minor(3), 
        warning(4) }

SecurityAlarmDetector ::= TEXTUAL-CONVENTION
    STATUS current
    DESCRIPTION
        "This is either a mechanism identified by an object 
         identifier, or an object instance (in the same manner 
         as a RowPointer) or an application object identifier.  
         All except for the RowPointer should be defined 
         previously in an OBJECT-IDENTITY marco with a full 
         description of the detector.
         
         SecurityAlarmDetector ::= CHOICE {
            mechanism [0] OBJECT IDENTIFIER,
            object [1] ObjectInstance,
            application [2] AE-title }"
    REFERENCE
        "ITU-T Rec. X.721 (1992) | ISO/IEC 10165-2 : 1992, 
               Attribute-ASN1Module SecurityAlarmDetector"
    SYNTAX OBJECT IDENTIFIER

ServiceUser ::= TEXTUAL-CONVENTION
    STATUS current
    DESCRIPTION
        "Identification of the service user.  In TMN this is an 
         any defined by type.  Here it is an octet string.
         
         ServiceUser ::= SEQUENCE {
            identifier OBJECT IDENTIFIER,
            details ANY DEFINED BY identifier }"
    REFERENCE
        "ITU-T Rec. X.721 (1992) | ISO/IEC 10165-2 : 1992, 
               Attribute-ASN1Module ServiceUser"
    SYNTAX OCTET STRING

ServiceProvider ::= TEXTUAL-CONVENTION
    STATUS current
    DESCRIPTION
        "Identification of the service provider.  In TMN this is 
         an any defined by type.  Here it is an octet string.
         
         ServiceUser ::= SEQUENCE {
            identifier OBJECT IDENTIFIER,
            details ANY DEFINED BY identifier }
         ServiceProvider ::= ServiceUser"
    REFERENCE
        "ITU-T Rec. X.721 (1992) | ISO/IEC 10165-2 : 1992, 
               Attribute-ASN1Module ServiceProvider"
    SYNTAX OCTET STRING

AttributeList ::= TEXTUAL-CONVENTION
    STATUS current
    DESCRIPTION
        "Should be SET OF VariablePointer."
    REFERENCE
        "ITU-T Rec. X.721 (1992) | ISO/IEC 10165-2 : 1992, 
               Attribute-ASN1Module AttributeList"
    SYNTAX OBJECT IDENTIFIER

InformationType ::= TEXTUAL-CONVENTION
    STATUS current
    DESCRIPTION
        "The information type textual convention is an object 
         identifier that is one of the object identifiers 
         assigned to an information type.  The actual 
         information type values from TMN specifications may be 
         used directly.  Additional defined information type 
         extensions defined by other documents such as X.283 may 
         also be used.
         
         Object identifiers used with the InformationType 
         textual convention must be defined in an 
         OBJECT-IDENTITY macro and their use and meaning must be 
         described in the DESCRIPTION
         clause of that macro."
    REFERENCE
        "ITU-T Rec. X.723 (1993) | ISO/IEC 10165-5 : 1993, ASN.1 
               GMI-AttributeModule.InformationType."
    SYNTAX OBJECT IDENTIFIER

InformationData ::= TEXTUAL-CONVENTION
    STATUS current
    DESCRIPTION
        "This textual convention represents additional 
         information to be added to a TMN notification in TMN 
         style.  This could contain things like an entire 
         communications PDU.  The information should be 
         self-defining."
    REFERENCE
        "ITU-T Rec. X.723 (1993) | ISO/IEC 10165-5 : 1993, ASN.1 
               GMI-AttributeModule.InformationData."
    SYNTAX OCTET STRING

EventTimeStamp ::= TEXTUAL-CONVENTION
    DISPLAY-HINT "d-0"
    STATUS current
    DESCRIPTION
        "Provides a specification of an event time."
    REFERENCE
        "ITU-T Rec. X.721 (1992) | ISO/IEC 10165-2 : 1992, 
               Attribute-ASN1Module AttributeList"
    SYNTAX TimeTicks

EventTypeId ::= TEXTUAL-CONVENTION
    STATUS current
    DESCRIPTION
        "Provides a specification of an event type for 
         notifications.
         
         This is either an object identifier or an integer.  
         When valued as an integer, the integer is coded in the 
         first and only element of the object identifier.
         When coded as an integer, because of the way that 
         object identifiers are BER encoded, the value will 
         likely be displayed as two elements."
    REFERENCE
        "ITU-T Rec. X.711 | ISO/IEC 9596-1, CMIP-1.EventTypeId"
    SYNTAX OBJECT IDENTIFIER

EventDiscriminatorConstruct ::= TEXTUAL-CONVENTION
    STATUS current
    DESCRIPTION
        "Provides specificationo of a discriminator construct."
    REFERENCE
        "ITU-T Rec. X.721 (1992) | ISO/IEC 10165-2 : 1992, 
               Attribute-ASN1Module.DiscriminatorConstruct"
    SYNTAX OCTET STRING

EventForwardingDestination ::= TEXTUAL-CONVENTION
    STATUS current
    DESCRIPTION
        "Provides specificatino of an event destination.  This 
         is the SnmpAdminString with the same value as an 
         snmpTargetAddrName from the SNMP-TARGET-MIB module."
    REFERENCE
        "ITU-T Rec. X.721 (1992) | ISO/IEC 10165-2 : 1992, 
               Attribute-ASN1Module.Destination"
    SYNTAX OCTET STRING

EventForwardingDestinationList ::= TEXTUAL-CONVENTION
    STATUS current
    DESCRIPTION
        "Provides specificatino of an event destination list.  
         This is a list of space separated SnmpAdminString's 
         with the same value as the snmpTargetAddrName's from 
         the SNMP-TARGET-MIB module."
    REFERENCE
        "ITU-T Rec. X.721 (1992) | ISO/IEC 10165-2 : 1992, 
               Attribute-ASN1Module.DestinationList"
    SYNTAX OCTET STRING

Time24 ::= TEXTUAL-CONVENTION
    DISPLAY-HINT "1d:1d"
    STATUS current
    DESCRIPTION
        "This textual convention specifies an hour and minute of 
         the day and replaces the following ASN.1 syntax:
         
         Time24 ::= SEQUENCE {
            hour INTEGER(0..23),
            minute INTEGER(0..59) }
         
         This is specified as 2 octets in an octet string where 
         the first octet is the hour(0..23) and the second octet 
         is the minute(0..59)."
    REFERENCE
        "ITU-T Rec. X.721 (1992) | ISO/IEC 10165-2 : 1992, 
               Attribute-ASN1Module.Time24"
    SYNTAX OCTET STRING (SIZE(4))

IntervalsOfDay ::= TEXTUAL-CONVENTION
    DISPLAY-HINT "1d:1d-1d:1d,"
    STATUS current
    DESCRIPTION
        "This textual convention specifies intervals in the day 
         by start hour and minute and end hour and minute and 
         replaces the following ASN.1 syntax:
         
         IntervalsOfDay ::= SET OF SEQUENCE {
            intervalStart Time24,
            intervalEnd Time24 }
         
         It consists of an octet string that is an integral 
         multiple of 
         4 octets.  For each 4 octet grouping, the first two 
         octets are coded as a Time24 textual convention 
         representing the start time for the interval, and the 
         last two octets are coded as a Time24 textual 
         convention representing the end time for the interval.  
         Each 4-tuple of octets represents a separate interval."
    REFERENCE
        "ITU-T Rec. X.721 (1992) | ISO/IEC 10165-2 : 1992, 
               Attribute-ASN1Module.IntervalsOfDay"
    SYNTAX OCTET STRING

WeekMask ::= TEXTUAL-CONVENTION
    STATUS current
    DESCRIPTION
        "This textual convention specifies intervals in the day 
         for days of the week and replaces the following ASN.1 
         syntax:
         
         WeekMask ::= SET OF SEQUENCE {
            daysOfWeek BIT STRING {
                sunday(0),
                monday(1),
                tuesday(2),
                wednesday(3),
                thursday(4),
                friday(5),
                saturday(6) }(SIZE(7)),
            intervalsOfDay IntervalsOfDay }
         
         The first octet of the octet string is a day of week 
         indicator that can have bit values: sunday(0), 
         monday(1), tuesday(2), wednesday(3), thursday(4), 
         friday(5) and saturday(6), with bit position 7 unused 
         and set to zero.  The second octet of the string is an 
         interval count indicating the number, 'n', of time 
         intervals (multiples of 4 octets) to follow.  The next 
         nx4 octets represent the time intervals following the 
         IntervalsOfDay textual convention.  The pattern is 
         repeated again beginning with the week octet."
    REFERENCE
        "ITU-T Rec. X.721 (1992) | ISO/IEC 10165-2 : 1992, 
               Attribute-ASN1Module.WeekMask"
    SYNTAX OCTET STRING

LogCapacityAlarmThreshold ::= TEXTUAL-CONVENTION
    DISPLAY-HINT "1d:"
    STATUS current
    DESCRIPTION
        "This textual convention specifies the alarm thresholds 
         as a percentage of capacity and replaces the following 
         ASN.1 syntax:
         
         CapacityAlarmThreshold ::= SET OF INTEGER(0..100)
         
         Each octet in the octet string consists of one 
         threshold.  Thresholds should be ordered from lowest to 
         highest.  Each threshold value must be in the range 
         from 1 to 100 (%)."
    REFERENCE
        "ITU-T Rec. X.721 (1992) | ISO/IEC 10165-2 : 1992, 
               Attribute-ASN1Module.CapacityAlarmThreshold"
    SYNTAX OCTET STRING

FullAction ::= TEXTUAL-CONVENTION
    STATUS current
    DESCRIPTION
        "Provides a specification of the action be taken when 
         the maximum size of the log has been reached.  Options 
         are:
         
          - wrap: The oldest records in the log, as determined 
            by the log record identifier, will be deleted to 
            free resources for the creation of new records.
         
          - halt: No more records will be logged.  Records 
            already in the log will be retained.
         
         Both options are supported by every log."
    REFERENCE
        "ITU-T Rec. X.721 (1992) | ISO/IEC 10165-2 : 1992, 
               Attribute-ASN1Module.LogFullAction"
    SYNTAX INTEGER { 
        wrap(0), halt(1) }

SimpleNameType ::= TEXTUAL-CONVENTION
    STATUS current
    DESCRIPTION
        "The simple name type textual convention is used to 
         specify a name for a conceptual row in a table for use 
         as an index that is both an integer representation as 
         well as a string representation.  When representing an 
         integer, the convention is coded as a string that 
         represents the displayed value of the integer.  When 
         representing a string, the string is coded directly.  
         Some implementations might not be able to accept 
         arbitrary string values for this textual convention and 
         may require integer representations.  When representing 
         a string, the string must not contain whitespace, 
         control characters or commas.  A null string represent 
         the integer zero (0).
         
         Note that the X.721 SimpleNameType is a choice between 
         an INTEGER and a GraphicString.  This textual 
         convention cannot faithfully represent all values 
         possible for the X.721 SimpleNameType."
    REFERENCE
        "ITU-T Rec. X.721 (1992) | ISO/IEC 10165-2 : 1992 ASN.1 
               ManagedObjectClassDefinitions.SimpleNameType"
    SYNTAX OCTET STRING (SIZE(1..32))

OperationalState ::= TEXTUAL-CONVENTION
    STATUS current
    DESCRIPTION
        "This is the operational state of an Entry in accordance 
         with the definitions in ITU-T Recommendation X.731 
         (1992).  When it appears within a row of a conceptual 
         table, it refers to the operational state of the 
         managed object represented by the row.
         
         The operational state textual convention is 
         single-valued and read-only.  It can have one of the 
         following values:
         
          - disabled: The resource is totally inoperable and 
            unable to provide service to the user(s).
         
          - enabled: The resource is partially or fully operable 
            and available for use.
         
         Precise definition of the states is specific to the 
         managed object represented.
         
         When placed in a column of a conceptual table, this 
         textual convention is given a MAX-ACCESS of read-only, 
         permitting management stations to simply retrieve the 
         state.  The default value associated with this entry is 
         disabled(0).  Precise definitions of what conditions 
         exist in each state must appear in the DESCRIPTION for 
         the object type definition using this textual 
         convention."
    REFERENCE
        "ITU-T Rec. X.721 (1992) | ISO/IEC 10165-2 : 1992, 
               Attribute-ASN1Module.OperationalState.
         ITU-T Rec. X.731 (1992) | ISO/IEC 10164-2 : 1993, 
               Section 8.1.1.1."
    SYNTAX INTEGER { 
        disabled(0), enabled(1) }

UsageState ::= TEXTUAL-CONVENTION
    STATUS current
    DESCRIPTION
        "This is the usage state of an Entry in accordance with 
         the definitions in ITU-T Recommendation X.731 (1992).  
         When it appears within a row of a conceptual table, it 
         refers to the usage state of the object represented by 
         the row.
         
         The usage state textual convention is single-valued and 
         read-only.  It can have one of the following values, 
         not all of which are applicable to every class of 
         managed object:
         
          - idle: The resource is not currently in use.
         
          - active: The resource is in used, and has sufficient 
            spare operating capcity to provide for additional 
            users simultaneously.
         
          - busy: The resource is in use, but it has no spare 
            operating capacity to provide for additional users 
            at this instant.
         
         Precise definition of the states is specific to the 
         managed object represented.
         
         When placed in a conceptual column, this textual 
         convention is given a MAX-ACCESS of read-only, 
         permitting management stations to simply retrieve the 
         state.  The default value associated with this entry is 
         idle(0).  Precise definitions of what conditions exist 
         in each state must appear in the DESCRIPTION
         for the object type definition using this textual 
         convention."
    REFERENCE
        "ITU-T Rec. X.721 (1992) | ISO/IEC 10165-2 : 1992, 
               Attribute-ASN1Module.UsageState.
         ITU-T Rec. X.731 (1992) | ISO/IEC 10164-2 : 1993, 
               Section 8.1.1.2."
    SYNTAX INTEGER { 
        idle(0), active(1), busy(2) }

AdministrativeState ::= TEXTUAL-CONVENTION
    STATUS current
    DESCRIPTION
        "This is the adminstrative state of an Entry in 
         accordance with the definitions in ITU-T Recommendation 
         X.731 (1992).  When it appears within a row  of 
         a conceptual table it refers to the administrative 
         state of the object represented by the row.
         
         The admninistrative state textual convention is single 
         valued and read-write.  It can have one of the 
         following values, not all of which are applicable to 
         every class of managed object:
         
          - locked: The resource is administratively prohibited 
            from performing services for its users.
         
          - unlocked: The resource is administratively permitted 
            to perform services for its users.  This is 
            independent of its inherent operability.
         
          - shutting down: Use of the resource is 
            administratively permitted to existing instances of 
            use only.  While the system remains in the shutting 
            down state, the manager may at any time cause the 
            managed object to revert to the unlocked state.
         
         Precise definition of the states is specific to the 
         managed object represented.
         
         When placed in a column of a conceptual table, this 
         textual convention is given an MAX-ACCESS of read-write 
         or read-create, permitting management stations the 
         ability to set the value.
         
         Values that can be set are locked(0), unlocked(1) or 
         shuttingDown(2).  The actions performed when set to 
         locked(0), unlocked(1) or shuttingDown(2) will be 
         described specifically in the DESCRIPTION section for 
         the object. however, in general, setting the object to 
         locked(0) results in immediate and disruptive 
         withdrawal from service of the object represented by 
         the row and all contained objects.  Setting the object 
         to shuttingDown(2) results in the graceful withdrawal 
         from service of the object represented by the row and 
         all contained objects.  Setting the object to 
         unlocked(1) results in placing back into service the 
         represented object and all contained objects that do 
         not have an administrative state of their own, or that 
         have an administrative state which is also unlocked(1).
         
         The default value associated with this row is locked(0) 
         and the managed object represented by the conceptual 
         row is created in the administratively locked state.
         
         Precise defintions of both the conditions when the 
         state is fetched and the conditions when the state is 
         set must appear in the DESCRIPTION of the object type 
         definition using this textual convention."
    REFERENCE
        "ITU-T Rec. X.721 (1992) | ISO/IEC 10165-2 : 1992, 
               Attribute-ASN1Module.AdministrativeState.
         ITU-T Rec. X.731 (1992) | ISO/IEC 10164-2 : 1993, 
               Section 8.1.1.3."
    SYNTAX INTEGER { 
        locked(0), unlocked(1), shuttingDown(2) }

AlarmStatus ::= TEXTUAL-CONVENTION
    STATUS current
    DESCRIPTION
        "This textual convention represents the alarm status of 
         an managed object in accordance with the definitions in 
         the OSI SMI.  When it appears within a row in 
         a conceptual table, it refers to the alarm status of 
         the managed object represented by the row.  Rows in 
         conceptual tables representing managed objects that may 
         generate alarms should contain this textual convention.
         
         The alarm status textual convention is set-valued and 
         read-write.  It can have zero or more of the following 
         values, not all of which are applicable to every class 
         of managed object:
         
          - under repair: The resource is currently being 
            repaired.  When the under repair value is present, 
            the operational state is either disabled or enabled.
         
          - critical: One or more citical alarms indicating 
            a fault have been detected in the resource, and have 
            not been cleared.  The operational state of the 
            managed object can be disabled or enabled.
         
          - major: One or more major alarms indicating a fault 
            have been detected in the resource, and have not yet 
            been cleared.  The operational state of the managed 
            object can be disabled or enabled.
         
          - minor: One or more minor alarms indicating a fault 
            have been detected in the resource, and have not yet 
            been cleared.  The operational state of the managed 
            object can be disabled or enabled.
         
          - alarm outstanding: One or more alarms have been 
            detected in the resource, the condition of which may 
            or may not be disabling.  If the operational state 
            is enabled, additional attributes, particular to the 
            managed object class, may indicate the nature and 
            cause of the condition and the services that are 
            affected.
         
         The presence of the above alarm state conditions do not 
         suppress the generation of future fault related 
         notifications.
         
         When placed in a column of a conceptual table, this 
         textual convention is given a MAX-ACCESS of read-write 
         or read-create, permitting management stations the 
         ability to set the value.
         
         Values that can be added to the set are underRepair(0).  
         Values that can be removed from the set are 
         critical(1), major(2), minor(3), and 
         alarmOutstanding(4).
         
         The default value associated with this row is the empty 
         set ('00000'B) and the managed object created by the 
         conceptual row is created without alarms or repair 
         conditions.
         
         Precise defintions of which values are applicable must 
         appear in the DESCRIPTION clause of the object type 
         definition using this textual convention."
    REFERENCE
        "ITU-T Rec. X.721 (1992) | ISO/IEC 10165-2 : 1992, 
               Attribute-ASN1Module.AlarmStatus.
         ITU-T Rec. X.731 (1992) | ISO/IEC 10164-2 : 1993, 
               Section 8.1.2.1."
    SYNTAX BITS { 
        underRepair(0), critical(1), major(2), minor(3), 
        alarmOutstanding(4) }

GnmAlarmStatus ::= TEXTUAL-CONVENTION
    STATUS current
    DESCRIPTION
        "This textual convention represents the alarm status 
         according to ITU-T Rec. M.3100 which is different from 
         that of ITU-T Rec.  X.721 and X.733.  When it appears 
         within a row in a conceptual table, it refers to the 
         alarm status of the managed object represented by the 
         row.  Rows in conceptual tables representing managed 
         objects that may generate alarms should contain this 
         textual convention (or that of X.721, the AlarmStatus).

         The alarm status textual convention is single-valued 
         and read-only.  It can have one of the following 
         values, not all of which are applicable to every class 
         of managed object.
         
         In order of severity from most severe to least severe:
         
         - activeReportable-Critical(5), one or more active and 
           reportable critical alarms indicating a fault have 
           been detected;
         
         - activeReportable-Major(4), one or more active and 
           reportable major alarms indicating a fault have been 
           detected;
         
         - activeReportable-Minor(3), one or more active and 
           reportable minor alarms have been detected;
         
         - activeReportable-Indeterminate(1), one or more active 
           and reportable alarms of indeterminate severity have 
           been detected;
         
         - activeReportable-Warning(2), one or more active and 
           reportable warning alarms have been detected;
         
         - activePending(6), one ore more activate but pending 
           alarms (either pending severity assignment or pending 
           reporting) have been detected;
         
         - cleared(0), no active alarms have been detected that 
           have not been cleared.

         The value of the alarm state condition does not 
         suppress the generation of future fault related 
         notifications.

         When placed in a column of a conceptual table, this 
         textual convention is given a MAX-ACCESS of read-only.

         The default value associated with this row is 
         cleared(0) and the managed object created by the 
         conceptual row is created wtihout active alarms.

         Precise defintions of which values are applicable must 
         appear in the DESCRIPTION clause of the object type 
         definition using this textual convention."
    REFERENCE
        "ITU-T Rec. M.3100 (2005) 
               ASN1DefinedTypesModule.AlarmStatus."
    SYNTAX INTEGER { 
        cleared(0), activeReportable-Indeterminate(1), 
        activeReportable-Warning(2), activeReportable-Minor(3), 
        activeReportable-Major(4), activeReportable-Critical(5), 
        activePending(6) }

ProceduralStatus ::= TEXTUAL-CONVENTION
    STATUS current
    DESCRIPTION
        "This is the procedural status of an Entry in accodance 
         with the definitions in ITU-T Recommendation X.731 
         (1992).  Under X.731 the syntax of a ProceduralStatus 
         is a SET OF INTEGER with these defined values, however, 
         SNMP can't do that, so we use BITS instead.  When it 
         appears in an entry in a conceptual table, this textual 
         convention refers to the procedural or active status of 
         the managed object represented by the entry.
         
         The procedural status textual convention is supported 
         only by those managed objects that represent some 
         procedure (e.g, a test process) which progresses 
         through a sequence of phases.  Depending upon the 
         managed object class definition, the procedure may be 
         required to reach certain phase for the resource to be 
         operational and available for use (i.e, for the managed 
         object to be enabled).  Not all phases may be 
         applicable to every class of managed object.  If the 
         value of this textual convention is an emtpy set, the 
         managed object is ready, for example, the 
         initialization is complete.
         
          - intialization required: The resource requires 
            initialization to be invoked by the manager before 
            it can perform its normal functions, and this 
            procedure has not been initiated.  The manager may 
            be able to invoke such initialization through an 
            action.  The terminating condition may also be 
            present.  The operational state is disabled.
         
          - not initialized: The resource requires 
            initialization before it can perform its normal 
            functions, and this procedure has not been 
            initiated.  The resource initializes itself 
            autonomously, but the operational state may be 
            either disabled or enabled, depending upon the 
            managed object class definition.
         
          - initializing: The resource requires initialization 
            before it can perform its normal functions, and this 
            procedure has been initiated but is not yet 
            complete.  When this condition is present, the 
            intitialization required condition is absent, since 
            initialization has already begun.  The operational 
            state may be disabled or enabled, depending upon the 
            managed object class defintion.
         
          - terminating: The resource is in a termination phase.  
            If the resource does not reinitialize itself 
            autonomously, the initialization required condition 
            is also present and the operational state is 
            disabled; otherwise, the operational state may be 
            either disabled or enabled, depending upon the 
            managed object class definition.
         
         When placed in a column of a conceptual table, this 
         textual convention is given a MAX-ACCESS of read-only, 
         permitting management station to ability to fetch the 
         value.
         
         The default value associated with this row is the empty 
         set ('00000'B) and the managed object created by the 
         conceptual row is created in the functional state.
         
         Precise definition of the status is specific to the 
         managed object represented.  Not all status members are 
         applicable to all managed objects.  Precise definitions 
         of which members are applicable and what conditions 
         exist for each applicable member of the state must 
         appear in the DESCRIPTION of the object type definition 
         using this textual convention."
    REFERENCE
        "ITU-T Rec. X.721 (1992) | ISO/IEC 10165-2 : 1992, 
               Attribute-ASN1Module.ProceduralStatus.
         ITU-T Rec. X.731 (1992) | ISO/IEC 10164-2 : 1993, 
               Section 8.1.2.2."
    SYNTAX BITS { 
        initializationRequired(0), notInitialized(1), 
        initializing(2), reporting(3), terminating(4) }

AvailabilityStatus ::= TEXTUAL-CONVENTION
    STATUS current
    DESCRIPTION
        "This is the availability status of an Entry in 
         accordance with the definitions in the OSI SMI.  When 
         it appears within a conceptual row it refers to the 
         availability status of the manage objected represented 
         by the conceptual row.
         
         The availability status textual convention is 
         set-valued and read-only.  It can have zero or more of 
         the following values, not all of which are applicable 
         to every class of managed object.  When the value of 
         this attribute is empty, this implies that none of the 
         status conditions described below are present.
         
          - in test: The resource is undergoing a test 
            procedure.  If the administrative state is locked or 
            shutting down then normal users are precluded from 
            using the resource and the control status attribute 
            has the value reserved for test.  Tests that do not 
            exclude additional users can be present in any 
            operational or administrative state but the reserved 
            for test condition should not be present.
         
          - failed: The resource has an internal fault that 
            prevents it from operating.  The operational state 
            is disabled.
         
          - power off: The resource requires power to be applied 
            and is not powered on.  For example, a fuse or other 
            protection device is known to have removed power or 
            a low voltage condition has been detected.  The 
            operational state is disabled.
         
          - offline: The resource requires a routing operation 
            to be performed to place it online and make it 
            available for use.  The operation may be manual or 
            automatic, or both.  The operational state is 
            disabled.
         
          - off duty: The resource has been made inactive by an 
            internal control process in accordance with 
            a predetermined time schedule.  Under normal 
            conditions the control process can be expected to 
            reactivate the resource at some scheduled time, and 
            it is therefore considered to be optional.  The 
            operational state is enabled or disabled.
         
          - dependency: The resource cannot operate because some 
            other resource on which it depends is (i.e, 
            a resource not represented by the same managed 
            object) unavailable.  For example, a device is not 
            accessible because its controller is powered off.  
            The operational state is disabled.
         
          - degraded: The service available from the resource is 
            degraded in some respect, such as in speed or 
            operating capacity.  Failure of a test or an 
            unacceptable performance measurement has established 
            that some or all services are not functional or are 
            degraded due to presence of a defect.  However, the 
            resource remains available for service, either 
            because some services are satisfactory or because 
            degraded service is preferable to no service at all.  
            Object specific attributes may be deinfed to 
            represent further information indicating, for 
            example, which serivces are not functional and the 
            nature of the degradation.  The operational state is 
            enabled.
         
          - not installed: The resource represented by the 
            managed object is not present, or is incomplete.  
            For example, a plug-in module is missing, a cable is 
            disconnected or a software module is not loaded.  
            The operational state is disabled.
         
          - log full: This indicates a log full condition the 
            semantics of which are defined in ITU-T Rec. X.735.
         
         When placed in a column of a conceptual table, this 
         textual convention is given a MAX-ACCESS of read-only, 
         permitting management stations the ability to retrieve 
         the value only.
         
         The default value associated with this row is the empty 
         set ('000000000'B) and the managed object created by 
         the conceptual row is created is an available state.
         
         Precise definition of the states is specific to the 
         managed object represented.  Not all states are 
         applicable to all managed objects.  Precise definitions 
         of which states are applicable and what conditions 
         exist in each applicable state must appear in the 
         DESCRIPTION of the object type definition using this 
         textual convention."
    REFERENCE
        "ITU-T Rec. X.721 (1992) | ISO/IEC 10165-2 : 1992, 
               Attribute-ASN1Module.AvailabilityStatus
         ITU-T Rec. X.731 (1992) | ISO/IEC 10164-2 : 1993, 
               Section 8.1.2.3."
    SYNTAX BITS { 
        inTest(0), failed(1), powerOff(2), offLine(3), 
        offDuty(4), dependency(5), degraded(6), notInstalled(7), 
        logFull(8) }

ControlStatus ::= TEXTUAL-CONVENTION
    STATUS current
    DESCRIPTION
        "This textual convention represents the control status 
         of an managed object in accordance with the definitions 
         in ITU-T Recommendation X.731 (1992).  When it appears 
         within a row of a coneceptual table, it refers to the 
         control status of the managed object represented by the 
         row.
         
         The control status textual convention is read-write and 
         set-valued.  It can have zero or more of the following 
         values, not all of which are applicable to every class 
         of managed object.  When the value of this textual 
         convention is empty, this implies that none of the 
         status conditions described below are present.
         
          - subject to test: The resource is available to normal 
            users, but tests may be conducted on it 
            simultaneously at unpredicatble times, which may 
            cause it to exhibit unusual characteristics to 
            users.
         
          - part of services locked: This value indicates 
            whether a manager has administratively restricted 
            a particular part of a service from the user(s) of 
            a resource.  The administrative state is unlocked.  
            Examples are incoming service barred, outgoing 
            service barred, write locked by media key, read 
            locked.
         
          - reserved for test: The resource has been made 
            administratively unavailable to normal users because 
            it is undergoing a test procedure.  The 
            administrative state is locked.
         
          - suspended: Service has been administratively 
            suspended to the users of the resource.  The 
            resource may retain knowledge of current users 
            and/or requests for usage, depending upon the 
            managed object class definition, but does not resume 
            performing serivces until the suspended condition is 
            revoked.  The administrative state is unlocked.
         
         When placed in a column of a conceptual table, this 
         textual convention is given a MAX-ACCESS of read-write 
         or read-create, permitting management stations the 
         ability to set or retrieve the value.
         
         The default value associated with this row is the empty 
         set ('0000'B) and the managed object created by the 
         conceptual row is created in a state available to 
         users.
         
         Precise definition of the status is specific to the 
         managed object represented.  Not all status values are 
         applicable to all managed objects.  Precise definition 
         of which status values are applicable, and what 
         conditions exist when each status exists must appear in 
         the DESCRIPTION clause of the object type definition 
         using this textual convention."
    REFERENCE
        "ITU-T Rec. X.721 (1992) | ISO/IEC 10165-2 : 1992, 
               Attribute-ASN1Module.ControlStatus.
         ITU-T Rec. X.731 (1992) | ISO/IEC 10164-2 : 1993, 
               Section 8.1.2.4."
    SYNTAX BITS { 
        subjectToTest(0), partOfServicesLocked(1), 
        reservedForTest(2), suspended(3) }

StandbyStatus ::= TEXTUAL-CONVENTION
    STATUS current
    DESCRIPTION
        "This textual convention represents the standby status 
         of an Entry in accordance with the defintions in ITU-T 
         Recommendation X.731 (1992).  When it appears within 
         a row of a conceptual table it refers to the standby 
         status of the managed object represented by the row.
         
         The standby status textual convention is single-valued 
         and read-only.  It shall have one of the following 
         values.  The value is only meaningful when the back-up 
         relationship role exists.
         
          - hot standby: The resource is not providing service, 
            but is operating in synchronism with another 
            resource that is to be backed-up (e.g, a computer 
            shadowing another computer).  A resource with a hot 
            standby status will be immediately able to take over 
            the role of the resource to be backed-up, without 
            the need for intialization activity, and will 
            contain the same information as the resource being 
            backed up.  The hot standby condition is mutually 
            exclusive with the cold standby and providing 
            service conditions.  The operational state is 
            enabled.  The administrative state is unlocked.  The 
            availability status is offline.
         
          - cold standby: The resource is to back-up another 
            resource, but is not syncrhonized with that 
            resource.  A resource with a cold standby status 
            will not be immediately able to take over the role 
            of a resource to be backed up, and will require some 
            initialization activity.  The cold standby condition 
            is mutually exclusive with the hot standby and 
            providing service condition.  The operational state 
            is enabled or disabled.  The administrative state is 
            locked or unlocked.  The procedural status contains 
            not initialized or initialization required.  The 
            availability status is offline.
         
          - providing service: The back-up resource is providing 
            service and is backing up another resource.  The 
            providing service condition is mutually exclusive 
            with the hot stanbdy and cold standby conditions.  
            The operational state is enabled.  The 
            administrative state is unlocked.  The availability 
            status is online.
         
         When placed in a column of a conceptual table, this 
         textual convention is given a MAX-ACCESS of read-only, 
         permitting management stations the ability to retrieve 
         the value only.
         
         The default value associated with this row is 
         coldStandby(1).
         
         Precise definition of the states is specific to the 
         managed object represented.  Not all states are 
         applicable to all managed objects.  Precise definition 
         of which states are applicable, and what conditions 
         exist in each applicable state must appear in the 
         DESCRIPTION claus of the object type definition using 
         this textual convention."
    REFERENCE
        "ITU-T Rec. X.721 (1992) | ISO/IEC 10165-2 : 1992, 
               Attribute-ASN1Module.StandbyStatus.
         ITU-T Rec. X.731 (1992) | ISO/IEC 10164-2 : 1993, 
               Section 8.1.2.5."
    SYNTAX INTEGER { 
        hotStandby(0), coldStandby(1), providingService(2) }

UnknownStatus ::= TEXTUAL-CONVENTION
    STATUS current
    DESCRIPTION
        "The unknown status textual convention is used to 
         indicated that the state of the resource represented by 
         the managed object is unknown.  When the unknown status 
         textual convention value is true, the value of the 
         other state textual conventions may not reflect the 
         actual state of the resource."
    REFERENCE
        "ITU-T Rec. X.721 (1992) | ISO/IEC 10165-2 : 1992, 
               Attribute-ASN1Module.UnknownStatus.
         ITU-T Rec. X.731 (1992) | ISO/IEC 10164-2 : 1993, 
               Section 8.1.2.6."
    SYNTAX INTEGER { 
        false(0), true(1) }

smiNotifications OBJECT IDENTIFIER
    ::= { smiMIB 0 }

smi2Notifications OBJECT IDENTIFIER
    ::= { smiNotifications 0 }

attributeValueChangeType OBJECT-IDENTITY
    STATUS current
    DESCRIPTION
        "The event type for the attributeValueChange 
         notification."
    REFERENCE
        "ITU-T Rec. X.721 (1992) | ISO/IEC 10165-2 : 1992 
               attributeValueChangeType."
    ::= { smi2Notifications 1 }

communicationsAlarmType OBJECT-IDENTITY
    STATUS current
    DESCRIPTION
        "The event type for the communicationsAlarm 
         notification.  An alarm of this type is principally 
         associated with the procedures or processes required to 
         convey information from one point to another."
    REFERENCE
        "ITU-T Rec. X.721 (1992) | ISO/IEC 10165-2 : 1992 
               communicationsAlarmType."
    ::= { smi2Notifications 2 }

environmentalAlarmType OBJECT-IDENTITY
    STATUS current
    DESCRIPTION
        "The event type for the environmentalAlarm notification.  
         An alarm of this type is principally associated with 
         a condition relating to an enclosure in which the 
         equipment resides."
    REFERENCE
        "ITU-T Rec. X.721 (1992) | ISO/IEC 10165-2 : 1992 
               environmentalAlarmType."
    ::= { smi2Notifications 3 }

equipmentAlarmType OBJECT-IDENTITY
    STATUS current
    DESCRIPTION
        "The event type for the equipmentAlarm notification.  An 
         alarm of this type is principally associated with an 
         equipment fault."
    REFERENCE
        "ITU-T Rec. X.721 (1992) | ISO/IEC 10165-2 : 1992 
               equipmentAlarmType."
    ::= { smi2Notifications 4 }

integrityViolationType OBJECT-IDENTITY
    STATUS current
    DESCRIPTION
        "The event type for the integrityViolation 
         notification."
    REFERENCE
        "ITU-T Rec. X.721 (1992) | ISO/IEC 10165-2 : 1992 
               integrityViolationType."
    ::= { smi2Notifications 5 }

objectCreationType OBJECT-IDENTITY
    STATUS current
    DESCRIPTION
        "The event type for the objectCreation notification."
    REFERENCE
        "ITU-T Rec. X.721 (1992) | ISO/IEC 10165-2 : 1992 
               objectCreationType."
    ::= { smi2Notifications 6 }

objectDeletionType OBJECT-IDENTITY
    STATUS current
    DESCRIPTION
        "The event type for the objectDeletion notification."
    REFERENCE
        "ITU-T Rec. X.721 (1992) | ISO/IEC 10165-2 : 1992 
               objectDeletionType."
    ::= { smi2Notifications 7 }

operationalViolationType OBJECT-IDENTITY
    STATUS current
    DESCRIPTION
        "The event type for the operationalViolation 
         notification."
    REFERENCE
        "ITU-T Rec. X.721 (1992) | ISO/IEC 10165-2 : 1992 
               operationalViolationType."
    ::= { smi2Notifications 8 }

physicalViolationType OBJECT-IDENTITY
    STATUS current
    DESCRIPTION
        "The event type for the physicalViolation notification."
    REFERENCE
        "ITU-T Rec. X.721 (1992) | ISO/IEC 10165-2 : 1992 
               physicalViolationType."
    ::= { smi2Notifications 9 }

processingErrorAlarmType OBJECT-IDENTITY
    STATUS current
    DESCRIPTION
        "The event type for the processingErrorAlarm 
         notification.  An alarm of this type is principally 
         associated with a software or processing fault."
    REFERENCE
        "ITU-T Rec. X.721 (1992) | ISO/IEC 10165-2 : 1992 
               processingErrorAlarmType."
    ::= { smi2Notifications 10 }

qualityofServiceAlarmType OBJECT-IDENTITY
    STATUS current
    DESCRIPTION
        "The event type for the qualityofServiceAlarm 
         notification.  An alarm of this type is principally 
         associated with a degradation in the quality of 
         service."
    REFERENCE
        "ITU-T Rec. X.721 (1992) | ISO/IEC 10165-2 : 1992 
               qualityofServiceAlarmType."
    ::= { smi2Notifications 11 }

relationshipChangeType OBJECT-IDENTITY
    STATUS current
    DESCRIPTION
        "The event type for the relationshipChange notification.  
         This notification type is used to report the change of 
         one or more relationship attributes of a managed 
         object, that result through either the internal 
         operation of the resource or via management operation.  
         It is also used to report changes in object class 
         specific relationship attributes."
    REFERENCE
        "ITU-T Rec. X.721 (1992) | ISO/IEC 10165-2 : 1992 
               relationshipChangeType.
         ITU-T Rec. X.732 (1992) | ISO/IEC 10164-3 : 1993 
               Section 8.2.1."
    ::= { smi2Notifications 12 }

securityServiceOrMechanismViolationType OBJECT-IDENTITY
    STATUS current
    DESCRIPTION
        "The event type for the 
         securityServiceOrMechanismViolation notification."
    REFERENCE
        "ITU-T Rec. X.721 (1992) | ISO/IEC 10165-2 : 1992 
               securityServiceOrMechanismViolationType."
    ::= { smi2Notifications 13 }

stateChangeType OBJECT-IDENTITY
    STATUS current
    DESCRIPTION
        "The event type for the stateChange notification."
    REFERENCE
        "ITU-T Rec. X.721 (1992) | ISO/IEC 10165-2 : 1992 
               stateChangeType."
    ::= { smi2Notifications 14 }

timeDomainViolationType OBJECT-IDENTITY
    STATUS current
    DESCRIPTION
        "The event type for the timeDomainViolation 
         notification."
    REFERENCE
        "ITU-T Rec. X.721 (1992) | ISO/IEC 10165-2 : 1992 
               timeDomainViolationType."
    ::= { smi2Notifications 15 }

communicationsInformationType OBJECT-IDENTITY
    STATUS current
    DESCRIPTION
        "The event type for the communicationsInformation 
         notification."
    REFERENCE
        "ITU-T Recommendation X.723 (1993) | ISO/IEC 10165-5 
               : 1993, communicationInformation."
    ::= { smi2Notifications 16 }

smiNotifs OBJECT IDENTIFIER
    ::= { smiMIB 1 }

tmnObjectInstance OBJECT-TYPE
    SYNTAX ObjectInstance
    MAX-ACCESS accessible-for-notify
    STATUS current
    DESCRIPTION
        "Provides an object for use with notifications.  This is 
         a pointer to an object instance to be included in 
         notifications where the generating object instances 
         needs be included."
    REFERENCE
        "ITU-T Rec. X.721 (1992) | ISO/IEC 10165-2 : 1992, 
               objectInstance."
    ::= { smiNotifs 1 }

tmnNotificationIdentifier OBJECT-TYPE
    SYNTAX NotificationIdentifier
    MAX-ACCESS accessible-for-notify
    STATUS current
    DESCRIPTION
        "Provides an object for use with notifications."
    REFERENCE
        "ITU-T Rec. X.721 (1992) | ISO/IEC 10165-2 : 1992, 
               notificationIdentifier."
    ::= { smiNotifs 2 }

tmnCorrelatedNotifications OBJECT-TYPE
    SYNTAX CorrelatedNotifications
    MAX-ACCESS accessible-for-notify
    STATUS current
    DESCRIPTION
        "Provides an object for use with notifications."
    REFERENCE
        "ITU-T Rec. X.721 (1992) | ISO/IEC 10165-2 : 1992, 
               correlatedNotifications."
    ::= { smiNotifs 3 }

tmnProbableCause OBJECT-TYPE
    SYNTAX ProbableCause
    MAX-ACCESS accessible-for-notify
    STATUS current
    DESCRIPTION
        "This is the probable cause of the alarm condition in 
         accordance with TMN SMI defintions.  The probable cause 
         is a required parameter of the communications alarm, 
         environmental alarm, equipment alarm, processing error 
         alarm and quality of service alarm notification.  It 
         also appears in the alarm record entry.  It contains an 
         object identity which indicates the probable cause of 
         the alarm in accordance with the ProbableCause textual 
         convention.
         
         The meaning and purpose of object identifiers that are 
         used to populate this parameter for the communications 
         alarm, environmental alarm, equipment alarm, 
         processingError alarm and qualityofService alarm 
         notification must be specified in the DESCRIPTION 
         clause of an OBJECT-IDENTITY macro defining the object 
         identifier associated with the probable cause.  The 
         precise conditions under which the alarm is raised and 
         cleared (see perceivedSeverity) must also be defined in 
         the DESCRIPTION
         clause whenever the value is used to raise generic 
         alarms such as the communications alarm.  When used 
         with a specific notification, the use of the probable 
         cause parameter must be defined in the 
         NOTIFICATION-TYPE macro's DESCRIPTION clause.
         
         In all cases, the object identifier defined by the 
         corresponding standard (i.e.  TMN specification) should 
         be used as specified in the corresponding standard.  
         Private values of the probable cause may also be 
         defined in OBJECT-IDENTITY macros within a private or 
         enterprise module definition.  Where possible, however, 
         a standard values should be used."
    REFERENCE
        "ITU-T Rec. X.721 (1992) | ISO/IEC 10165-2 : 1992, 
               probableCause."
    ::= { smiNotifs 4 }

tmnSpecificProblems OBJECT-TYPE
    SYNTAX SpecificProblems
    MAX-ACCESS accessible-for-notify
    STATUS current
    DESCRIPTION
        "This is a specific problem of an alarm condition in 
         accordance with the TMN SMI definitions.  It is an 
         optional parameter of the communications alarm, 
         environmental alarm, equipment alarm, processing error 
         alarm or quality of service alarm notifications and may 
         occur multiply in that notification when an alarm 
         condition is set (it is not normally included when an 
         alarm condition is cleared).  This is a specific 
         problem indication that supplements the probable cause.  
         It contains a single object identity which indiates the 
         specific problem in accordance with the 
         SpecificProblems textual convention.
         
         The meaning and purpose of the object identifiers that 
         are used to populate this parameter for the 
         communications alarm, environmental alarm, equipment 
         alarm, processing error alarm or quality of service 
         alarm notification must be specified in the DESCRIPTION 
         clause of an OBJECT-IDENTITY macro defining the object 
         identifier associated with the specific problem.  The 
         precise conditions under which the alarm is raised and 
         cleared (see perceivedSeverity) must also be defined in 
         the DESCRIPTION
         clause whenever the value is used to raise generic 
         alarms such as the communications alarm.  When used 
         with a specific notification, the use of the specific 
         problem parameter must be defined in the 
         NOTIFICATION-TYPE macro's DESCRIPTION clause.
         
         In all cases, the object identifier defined by the 
         corresponding standard (i.e.  TMN specification) should 
         be used as specified in the corresponding standard.  
         Private values of the specific problem may also be 
         defined in OBJECT-IDENTITY marcos within a private or 
         enterprise module definition.  Where possible, however, 
         standard values should be used."
    REFERENCE
        "ITU-T Rec. X.721 (1992) | ISO/IEC 10165-2 : 1992, 
               specificProblems."
    ::= { smiNotifs 5 }

tmnPerceivedSeverity OBJECT-TYPE
    SYNTAX PerceivedSeverity
    MAX-ACCESS accessible-for-notify
    STATUS current
    DESCRIPTION
        "This is the perceived severity level which is set 
         according to the PerceiveSeverity textual convention.  
         This value is used along with a probableCause and 
         specificProblem identifiers with a generic alarm such 
         as the communications alarm, or is used with 
         a specifically defined alarm.  The value of the 
         parameter to the notification should be set to other 
         than cleared(5) to indicate that onset or assertion of 
         an alarm condition and set to cleared(5) to indicate 
         the cessation or deassertion of the alarm condition.
         
         The DESCRIPTION of the OBJECT-IDENTITY associated with 
         this perceived severity, such as the probableCause 
         paraemter, should describe the conditions under which 
         the alarm is asserted and cleared, as well a specifying 
         the applicable severities."
    REFERENCE
        "ITU-T Rec. X.721 (1992) | ISO/IEC 10165-2 : 1992, 
               perceivedSeverity."
    ::= { smiNotifs 6 }

tmnBackedUpStatus OBJECT-TYPE
    SYNTAX BackedUpStatus
    MAX-ACCESS accessible-for-notify
    STATUS current
    DESCRIPTION
        "Provides an object for use with notifications."
    REFERENCE
        "ITU-T Rec. X.721 (1992) | ISO/IEC 10165-2 : 1992, 
               backedUpStatus."
    ::= { smiNotifs 7 }

tmnBackUpObject OBJECT-TYPE
    SYNTAX ObjectInstance
    MAX-ACCESS accessible-for-notify
    STATUS current
    DESCRIPTION
        "Provides an object for use with notifications."
    REFERENCE
        "ITU-T Rec. X.721 (1992) | ISO/IEC 10165-2 : 1992, 
               backUpObject."
    ::= { smiNotifs 8 }

tmnTrendIndication OBJECT-TYPE
    SYNTAX TrendIndication
    MAX-ACCESS accessible-for-notify
    STATUS current
    DESCRIPTION
        "Provides an object for use with notifications."
    REFERENCE
        "ITU-T Rec. X.721 (1992) | ISO/IEC 10165-2 : 1992, 
               trendIndication."
    ::= { smiNotifs 9 }

tmnThresholdInfo OBJECT-TYPE
    SYNTAX ThresholdInfo
    MAX-ACCESS accessible-for-notify
    STATUS current
    DESCRIPTION
        "Provides an object for use with notifications."
    REFERENCE
        "ITU-T Rec. X.721 (1992) | ISO/IEC 10165-2 : 1992, 
               thresholdInfo."
    ::= { smiNotifs 10 }

tmnStateChangeDefinition OBJECT-TYPE
    SYNTAX AttributeValueChangeDefinition
    MAX-ACCESS accessible-for-notify
    STATUS current
    DESCRIPTION
        "Provides an object for use with notifications."
    REFERENCE
        "ITU-T Rec. X.721 (1992) | ISO/IEC 10165-2 : 1992, 
               stateChangeDefinition."
    ::= { smiNotifs 11 }

tmnMonitoredAttributes OBJECT-TYPE
    SYNTAX MonitoredAttributes
    MAX-ACCESS accessible-for-notify
    STATUS current
    DESCRIPTION
        "Provides an object for use with notifications."
    REFERENCE
        "ITU-T Rec. X.721 (1992) | ISO/IEC 10165-2 : 1992, 
               monitoredAttributes."
    ::= { smiNotifs 12 }

tmnProposedRepairActions OBJECT-TYPE
    SYNTAX ProposedRepairActions
    MAX-ACCESS accessible-for-notify
    STATUS current
    DESCRIPTION
        "Provides an object for use with notifications."
    REFERENCE
        "ITU-T Rec. X.721 (1992) | ISO/IEC 10165-2 : 1992, 
               proposedRepairActions."
    ::= { smiNotifs 13 }

tmnSourceIndicator OBJECT-TYPE
    SYNTAX SourceIndicator
    MAX-ACCESS accessible-for-notify
    STATUS current
    DESCRIPTION
        "Provides an object for use with notifications.
         
         This is the source indicator which indicates the source 
         of the change for notifications according to the 
         SourceIndicator textual convention.
         
         This is optionally added tot he attributeValueChange, 
         objectCreation, objectDeletion, relationshipChange or 
         stateChange notifications."
    REFERENCE
        "ITU-T Rec. X.721 (1992) | ISO/IEC 10165-2 : 1992, 
               sourceIndicator."
    ::= { smiNotifs 14 }

tmnAttributeIdentifierList OBJECT-TYPE
    SYNTAX AttributeIdentifierList
    MAX-ACCESS accessible-for-notify
    STATUS current
    DESCRIPTION
        "Provides an object for use with notifications."
    REFERENCE
        "ITU-T Rec. X.721 (1992) | ISO/IEC 10165-2 : 1992, 
               attributeIdentifierList."
    ::= { smiNotifs 15 }

tmnAttributeValueChangeDefinition OBJECT-TYPE
    SYNTAX AttributeValueChangeDefinition
    MAX-ACCESS accessible-for-notify
    STATUS current
    DESCRIPTION
        "Provides an object for use with notifications."
    REFERENCE
        "ITU-T Rec. X.721 (1992) | ISO/IEC 10165-2 : 1992, 
               attributeValueChangeDefinition."
    ::= { smiNotifs 16 }

tmnAdditionalText OBJECT-TYPE
    SYNTAX AdditionalText
    MAX-ACCESS accessible-for-notify
    STATUS current
    DESCRIPTION
        "Provides an object for use with notifications.  This is 
         the additional text for an alarm notification following 
         the AdditionalText textual convention."
    REFERENCE
        "ITU-T Rec. X.721 (1992) | ISO/IEC 10165-2 : 1992, 
               additionalText."
    ::= { smiNotifs 17 }

tmnAdditionalInformation OBJECT-TYPE
    SYNTAX AdditionalInformation
    MAX-ACCESS accessible-for-notify
    STATUS current
    DESCRIPTION
        "Provides an object for use with notifications.  This is 
         the additional information for an alarm notification 
         following the AdditionalInformation textual 
         convention."
    REFERENCE
        "ITU-T Rec. X.721 (1992) | ISO/IEC 10165-2 : 1992, 
               additionalInformation."
    ::= { smiNotifs 18 }

tmnSecurityAlarmCause OBJECT-TYPE
    SYNTAX SecurityAlarmCause
    MAX-ACCESS accessible-for-notify
    STATUS current
    DESCRIPTION
        "This is the security alarm cause of the security alarm 
         condition in accordance with TMN SMI defintions.  The 
         security alarm cause is a required parameter of the 
         intergrity violation, operational violation, physical 
         violation, security service or mechanism violation, and 
         time domain violation notifications.  It contains an 
         object identity which indicates the cause of the alarm 
         in accordance with SecurityAlarmCause textual 
         convention.
         
         The meaning and purpose of object identifiers that are 
         used to populate this parameter for these alarm 
         notifications must be specified in the DESCRIPTION 
         clause of an OBJECT-IDENTITY macro defining the object 
         identifier associated with the security alarm cause.  
         The precise conditions under which the alarm is raised 
         and cleared (see perceivedSeverity) must also be 
         defined in the DESCRIPTION clause whenever the value is 
         used to raise generic alarms such as the integrity 
         violation.  When used with a specific notification, the 
         use of the security alarm cause parameter must be 
         defined in the NOTIFICATION-TYPE marco's DESCRIPTION 
         clause.
         
         In all cases, the object identifier defined by the 
         corresponding standard (i.e.  TMN specification) should 
         be used as specified in the corresponding standard.  
         Private values of the probable cuase may also be 
         defined in OBJECT-IDENTITY marcos within a private or 
         enterprise module definition.  Where possible, however, 
         a standard value should be used."
    REFERENCE
        "ITU-T Rec. X.721 (1992) | ISO/IEC 10165-2 : 1992, 
               securityAlarmCause."
    ::= { smiNotifs 19 }

tmnSecurityAlarmSeverity OBJECT-TYPE
    SYNTAX SecurityAlarmSeverity
    MAX-ACCESS accessible-for-notify
    STATUS current
    DESCRIPTION
        "This is the same as perceivedSeverity but for security 
         alarms.  Security alarms do not clear and this has no 
         cleared(5) value."
    REFERENCE
        "ITU-T Rec. X.721 (1992) | ISO/IEC 10165-2 : 1992, 
               securityAlarmSeverity."
    ::= { smiNotifs 20 }

tmnSecurityAlarmDetector OBJECT-TYPE
    SYNTAX SecurityAlarmDetector
    MAX-ACCESS accessible-for-notify
    STATUS current
    DESCRIPTION
        "Provides an object for use with notifications.  This is 
         an identifier of the detector following the 
         SecurityAlarmDetector textual convention."
    REFERENCE
        "ITU-T Rec. X.721 (1992) | ISO/IEC 10165-2 : 1992, 
               securityAlarmDetector."
    ::= { smiNotifs 21 }

tmnServiceUser OBJECT-TYPE
    SYNTAX ServiceUser
    MAX-ACCESS accessible-for-notify
    STATUS current
    DESCRIPTION
        "Provides an object for use with notifications.  This is 
         the identification of the service user following the 
         ServiceUser textual convention."
    REFERENCE
        "ITU-T Rec. X.721 (1992) | ISO/IEC 10165-2 : 1992, 
               serviceUser."
    ::= { smiNotifs 22 }

tmnServiceProvider OBJECT-TYPE
    SYNTAX ServiceProvider
    MAX-ACCESS accessible-for-notify
    STATUS current
    DESCRIPTION
        "Provides an object for use with notifications.  This is the 
         identification of the service provider following the 
         ServiceProvider textual convention."
    REFERENCE
        "ITU-T Rec. X.721 (1992) | ISO/IEC 10165-2 : 1992, 
               serviceProvider."
    ::= { smiNotifs 23 }

tmnAttributeList OBJECT-TYPE
    SYNTAX AttributeList
    MAX-ACCESS accessible-for-notify
    STATUS current
    DESCRIPTION
        "Provides an object for use with notifications."
    REFERENCE
        "ITU-T Rec. X.721 (1992) | ISO/IEC 10165-2 : 1992, 
               attributeList."
    ::= { smiNotifs 24 }

tmnRelationshipChangeDefinition OBJECT-TYPE
    SYNTAX AttributeValueChangeDefinition
    MAX-ACCESS accessible-for-notify
    STATUS current
    DESCRIPTION
        "Provides an object for use with notifications."
    REFERENCE
        "ITU-T Rec. X.721 (1992) | ISO/IEC 10165-2 : 1992, 
               relationshipChangeDefinition."
    ::= { smiNotifs 25 }

tmnInformationType OBJECT-TYPE
    SYNTAX InformationType
    MAX-ACCESS accessible-for-notify
    STATUS current
    DESCRIPTION
        "This is the information type of an information event in 
         accordacne with the TMN SMI definitions.  It is an 
         required parameter of the communicationInformation 
         notification. It contains an object identity which 
         indicates the information type of the event in 
         according with the InformationType textual convention.
         
         The meaning and purpose of object identifiers that are 
         used to populate this parameter for the 
         communicationsInformation notification must be 
         specified in the DESCRIPTION clause of an 
         OBJECT-IDENTITY macro defining the object identifiers 
         associated with the information type.  The precise 
         conditions under which the event is notified must also 
         be defined in the DESCRIPTION clause whenever the value 
         is used to raise generic information notifications such 
         as the communicationsInformation notification.  When 
         used with a specific notification, the use of the 
         information type parameter must be defined inthe 
         NOTIFICATION-TYPE macro's DESCRIPTION clause.
         
         In all cases, the object identifier defined by the 
         corresponding standard (i.e. TMN specification) should 
         be used as specified in the corresponding standard.  
         Private values of the information type may also be 
         defined in OBJECT-IDENTITY macros within a private or 
         enterprise module definition.  Where possible, however, 
         a standard value should be used."
    REFERENCE
        "ITU-T Recommendation X.723 (1993) | ISO/IEC 10165-5 
               : 1993, 
         informationType."
    ::= { smiNotifs 26 }

tmnInformationData OBJECT-TYPE
    SYNTAX InformationData
    MAX-ACCESS accessible-for-notify
    STATUS current
    DESCRIPTION
        "This is the information data for an information notification 
         following the InformationData textual convention."
    REFERENCE
        "ITU-T Recommendation X.723 (1993) | ISO/IEC 10165-5 
               : 1993, informationData."
    ::= { smiNotifs 27 }

smiScalars OBJECT IDENTIFIER
    ::= { smiMIB 2 }

smiTables OBJECT IDENTIFIER
    ::= { smiMIB 3 }

discriminator OBJECT IDENTIFIER
    ::= { smiTables 1 }

discriminatorTable OBJECT-TYPE
    SYNTAX SEQUENCE OF DiscriminatorEntry
    MAX-ACCESS not-accessible
    STATUS current
    DESCRIPTION
        "This managed object is used to represent the criteria 
         for controlling management services."
    REFERENCE
        "ITU-T Rec. X.721 (1992) | ISO/IEC 10165-2 : 1992, 
               discriminator MO."
    ::= { discriminator 1 }

discriminatorEntry OBJECT-TYPE
    SYNTAX DiscriminatorEntry
    MAX-ACCESS not-accessible
    STATUS current
    DESCRIPTION
        "
         NOTIFICATIONS
            stateChange,
            attributeValueChange,
            objectCreation,
            objectDeletion;;;"
    REFERENCE
        "ITU-T Rec. X.721 (1992) | ISO/IEC 10165-2 : 1992, 
               discriminator MO."
    INDEX       { discriminatorId }
    ::= { discriminatorTable 1 }

DiscriminatorEntry ::=
    SEQUENCE {
        discriminatorId
            SimpleNameType,
        discriminatorConstruct
            EventDiscriminatorConstruct,
        discriminatorAdministrativeState
            AdministrativeState,
        discriminatorOperationalState
            OperationalState,
        discriminatorAvailabilityStatus
            AvailabilityStatus,
        discriminatorStartTime
            TimeStamp,
        discriminatorStopTime
            TimeStamp,
        discriminatorIntervalsOfDay
            IntervalsOfDay,
        discriminatorWeekMask
            WeekMask,
        discriminatorSchedulerName
            ObjectInstance,
        discriminatorEntryStatus
            RowStatus
    }

discriminatorId OBJECT-TYPE
    SYNTAX SimpleNameType
    MAX-ACCESS not-accessible
    STATUS current
    DESCRIPTION
        ""
    REFERENCE
        "ITU-T Rec. X.721 (1992) | ISO/IEC 10165-2 : 1992, 
               discriminatorId attribute."
    ::= { discriminatorEntry 1 }

discriminatorConstruct OBJECT-TYPE
    SYNTAX EventDiscriminatorConstruct
    MAX-ACCESS read-create
    STATUS current
    DESCRIPTION
        ""
    REFERENCE
        "ITU-T Rec. X.721 (1992) | ISO/IEC 10165-2 : 1992, 
               discriminatorConstruct attribute."
    ::= { discriminatorEntry 2 }

discriminatorAdministrativeState OBJECT-TYPE
    SYNTAX AdministrativeState
    MAX-ACCESS read-create
    STATUS current
    DESCRIPTION
        ""
    REFERENCE
        "ITU-T Rec. X.721 (1992) | ISO/IEC 10165-2 : 1992, 
               administrativeState attribute."
    ::= { discriminatorEntry 3 }

discriminatorOperationalState OBJECT-TYPE
    SYNTAX OperationalState
    MAX-ACCESS read-only
    STATUS current
    DESCRIPTION
        ""
    REFERENCE
        "ITU-T Rec. X.721 (1992) | ISO/IEC 10165-2 : 1992, 
               operationalState attribute."
    ::= { discriminatorEntry 4 }

discriminatorAvailabilityStatus OBJECT-TYPE
    SYNTAX AvailabilityStatus
    MAX-ACCESS read-only
    STATUS current
    DESCRIPTION
        ""
    REFERENCE
        "ITU-T Rec. X.721 (1992) | ISO/IEC 10165-2 : 1992, 
               availabilityStatus attribute."
    ::= { discriminatorEntry 5 }

discriminatorStartTime OBJECT-TYPE
    SYNTAX TimeStamp
    MAX-ACCESS read-create
    STATUS current
    DESCRIPTION
        ""
    REFERENCE
        "ITU-T Rec. X.721 (1992) | ISO/IEC 10165-2 : 1992, 
               startTime attribute."
    ::= { discriminatorEntry 6 }

discriminatorStopTime OBJECT-TYPE
    SYNTAX TimeStamp
    MAX-ACCESS read-create
    STATUS current
    DESCRIPTION
        ""
    REFERENCE
        "ITU-T Rec. X.721 (1992) | ISO/IEC 10165-2 : 1992, 
               stopTime attribute."
    ::= { discriminatorEntry 7 }

discriminatorIntervalsOfDay OBJECT-TYPE
    SYNTAX IntervalsOfDay
    MAX-ACCESS read-create
    STATUS current
    DESCRIPTION
        ""
    REFERENCE
        "ITU-T Rec. X.721 (1992) | ISO/IEC 10165-2 : 1992, 
               intervalsOfDay attribute."
    ::= { discriminatorEntry 8 }

discriminatorWeekMask OBJECT-TYPE
    SYNTAX WeekMask
    MAX-ACCESS read-create
    STATUS current
    DESCRIPTION
        ""
    REFERENCE
        "ITU-T Rec. X.721 (1992) | ISO/IEC 10165-2 : 1992, 
               weekMask attribute."
    ::= { discriminatorEntry 9 }

discriminatorSchedulerName OBJECT-TYPE
    SYNTAX ObjectInstance
    MAX-ACCESS read-create
    STATUS current
    DESCRIPTION
        ""
    REFERENCE
        "ITU-T Rec. X.721 (1992) | ISO/IEC 10165-2 : 1992, 
               schedulerName attribute."
    ::= { discriminatorEntry 10 }

discriminatorEntryStatus OBJECT-TYPE
    SYNTAX RowStatus
    MAX-ACCESS read-create
    STATUS current
    DESCRIPTION
        ""
    REFERENCE
        "STD 58, SNMPv2-TC RowStatus"
    ::= { discriminatorEntry 11 }


eventForwardingDiscriminatorTable OBJECT-TYPE
    SYNTAX SEQUENCE OF EventForwardingDiscriminatorEntry
    MAX-ACCESS not-accessible
    STATUS current
    DESCRIPTION
        "This managed object is used to represent the criteria 
         that shall be satisfied by potential event reports 
         before the event report is forwarded to a particular 
         destination."
    ::= { discriminator 2 }

eventForwardingDiscriminatorEntry OBJECT-TYPE
    SYNTAX EventForwardingDiscriminatorEntry
    MAX-ACCESS not-accessible
    STATUS current
    DESCRIPTION
        "
         discriminatorConstruct attribute is defined using the 
         attributes of a potential event report object described 
         in CCITT Rec. X.734 | ISO/IEC 10164-5."
    INDEX       { discriminatorId }
    ::= { eventForwardingDiscriminatorTable 1 }

EventForwardingDiscriminatorEntry ::=
    SEQUENCE {
        destination
            EventForwardingDestination,
        activeDestination
            EventForwardingDestination,
        backUpDestinationList
            EventForwardingDestinationList,
        confirmedMode
            TruthValue,
        eventForwardingDiscriminatorEntryStatus
            RowStatus
    }

destination OBJECT-TYPE
    SYNTAX EventForwardingDestination
    MAX-ACCESS read-create
    STATUS current
    DESCRIPTION
        ""
    ::= { eventForwardingDiscriminatorEntry 1 }

activeDestination OBJECT-TYPE
    SYNTAX EventForwardingDestination
    MAX-ACCESS read-create
    STATUS current
    DESCRIPTION
        ""
    ::= { eventForwardingDiscriminatorEntry 2 }

backUpDestinationList OBJECT-TYPE
    SYNTAX EventForwardingDestinationList
    MAX-ACCESS read-create
    STATUS current
    DESCRIPTION
        ""
    ::= { eventForwardingDiscriminatorEntry 3 }

confirmedMode OBJECT-TYPE
    SYNTAX TruthValue
    MAX-ACCESS read-create
    STATUS current
    DESCRIPTION
        ""
    ::= { eventForwardingDiscriminatorEntry 4 }

eventForwardingDiscriminatorEntryStatus OBJECT-TYPE
    SYNTAX RowStatus
    MAX-ACCESS read-create
    STATUS current
    DESCRIPTION
        ""
    ::= { eventForwardingDiscriminatorEntry 5 }

log OBJECT IDENTIFIER
    ::= { smiTables 2 }

logTable OBJECT-TYPE
    SYNTAX SEQUENCE OF LogEntry
    MAX-ACCESS not-accessible
    STATUS current
    DESCRIPTION
        ""
    ::= { log 1 }

logEntry OBJECT-TYPE
    SYNTAX LogEntry
    MAX-ACCESS not-accessible
    STATUS current
    DESCRIPTION
        "
         NOTIFICATIONS
            objectCreation,
            objectDeletion,
            attributeValueChange,
            stateChange,
            processingErrorAlarm;;;"
    INDEX       { logId }
    ::= { logTable 1 }

LogEntry ::=
    SEQUENCE {
        logId
            SimpleNameType,
        logDiscriminatorConstruct
            EventDiscriminatorConstruct,
        logAdministrativeState
            AdministrativeState,
        logOperationalState
            OperationalState,
        logAvailabilityStatus
            AvailabilityStatus,
        logFullAction
            FullAction,
        maxLogSize
            Unsigned32,
        currentLogSize
            Gauge32,
        numberOfRecords
            Gauge32,
        capacityAlarmThreshold
            LogCapacityAlarmThreshold,
        logStartTime
            TimeStamp,
        logStopTime
            TimeStamp,
        logIntervalsOfDay
            IntervalsOfDay,
        logWeekMask
            WeekMask,
        logSchedulerName
            ObjectInstance,
        logEntryStatus
            RowStatus
    }

logId OBJECT-TYPE
    SYNTAX SimpleNameType
    MAX-ACCESS not-accessible
    STATUS current
    DESCRIPTION
        "This attribute is used to uniquely identify the 
         instance of a log."
    REFERENCE
        "ITU-T Rec. X.735 (1992) | ISO/IEC 10164-6 : 1993, 
               Section 8.1.1.1.1."
    ::= { logEntry 1 }

logDiscriminatorConstruct OBJECT-TYPE
    SYNTAX EventDiscriminatorConstruct
    MAX-ACCESS read-create
    STATUS current
    DESCRIPTION
        "This attribute specifies tesets on the information that 
         is to be logged.  The discriminator construct may 
         operate on any of the parameters of the information to 
         be logged."
    REFERENCE
        "ITU-T Rec. X.735 (1992) | ISO/IEC 10164-6 : 1993, 
               Section 8.1.1.1.2."
    DEFVAL      { } -- ""
    ::= { logEntry 2 }

logAdministrativeState OBJECT-TYPE
    SYNTAX AdministrativeState
    MAX-ACCESS read-create
    STATUS current
    DESCRIPTION
        "This attribute represents the adminstrative capability 
         of the log to perform its function.  The following 
         administrative states are defined:
         
          - unlocked: Use of the log has been permitted by 
            a managing system.  Information from subordinate 
            records may be retrieved and, conditional on the 
            values of other state and status attribtues, new 
            records may be created.
         
          - locked: Use of the log has been prohibited by 
            a managing system.  Information from subordinate 
            records may be retrieved but new records shall not 
            be created.  Records may be deleted.
         
         Whenever the administrative state of a log is changed 
         a state change notification is generated."
    REFERENCE
        "ITU-T Rec. X.735 (1992) | ISO/IEC 10164-6 : 1993, 
               Section 8.1.1.1.3."
    DEFVAL      { 1 } -- unlocked(1)
    ::= { logEntry 3 }

logOperationalState OBJECT-TYPE
    SYNTAX OperationalState
    MAX-ACCESS read-only
    STATUS current
    DESCRIPTION
        "This attribute represents the operational capability of 
         the log to perform its function.  The following 
         operational states are defined:
         
          - enabled: The log is operational and ready for use.  
            Information from subordinate records may be 
            retrieved and, conditional on the values of other 
            state and status attributes, new records may be 
            created.
         
          - disabled: The log is not available for use.  New 
            records cannot be created.
         
         A change in operational state shall generate a state 
         chnage notification."
    REFERENCE
        "ITU-T Rec. X.735 (1992) | ISO/IEC 10164-6 : 1993, 
               Section 8.1.1.1.4."
    ::= { logEntry 4 }

logAvailabilityStatus OBJECT-TYPE
    SYNTAX AvailabilityStatus
    MAX-ACCESS read-create
    STATUS current
    DESCRIPTION
        "This attribute reflects th availability status of the 
         managed object.  The attribute may indicate 
         a 'log-full' condition; indicating that records can be 
         retrieved but that no new records can be added.
         
         The avaiability status package shall be present if any 
         of the scheduling packages are instantiated. This 
         attribute reflects the availability status of the 
         managed object.  When the resource has been made 
         unavailable in accordance with a predetermined time 
         schedule its value will be 'Off-Duty'.  The attribute 
         is read-only.  The value on creation is determined by 
         the scheduling parameters specified and the status of 
         the resource.  The required value set for this 
         attribute in this package is 'Off-Duty'.
         
         No state change notification is generated when this 
         attribute changes value.  Note: the log makes use of 
         the availability status to indicate the 'log-full' 
         condition; the presence fo this conditional package 
         makes available the 'Off-Duty' value to the object."
    REFERENCE
        "ITU-T Rec. X.735 (1992) | ISO/IEC 10164-6 : 1993, 
               Section 8.1.1.1.6.
         ITU-T Rec. X.735 (1992) | ISO/IEC 10164-6 : 1993, 
         Section 8.1.1.4.1."
    ::= { logEntry 5 }

logFullAction OBJECT-TYPE
    SYNTAX FullAction
    MAX-ACCESS read-create
    STATUS current
    DESCRIPTION
        "This attribute specifies the action to be taken when the 
         maximum size of the log has been reached.  Options are:
         
          - wrap: The oldest records in the log, as determined by the 
            log record identifier, will be deleted to free resources for 
            the creation of new records.
         
          - halt: No more records will be logged.  Records already in 
            the log will be retained.
         
         Both options shall be supported by any log."
    REFERENCE
        "ITU-T Rec. X.735 (1992) | ISO/IEC 10164-6 : 1993, 
               Section 8.1.1.1.5."
    DEFVAL      { 0 } -- wrap(0)
    ::= { logEntry 6 }

maxLogSize OBJECT-TYPE
    SYNTAX Unsigned32
    MAX-ACCESS read-create
    STATUS current
    DESCRIPTION
        "This attribute specifies the size of the log measured 
         in number of octets.  A log may have an indeterminate 
         size.  A maximum log size of zero shall be used to 
         specify that the log size has no predefined limit.
         
         Note: Since the log size is specified in octets, the 
         actual amount of information that is contained in a log 
         will be determined by data representation in the log.  
         This data representation is not subject to 
         standardization.  The maximum log size does not include 
         the system overhead involved in establishing the log.  
         Thus, immediately after creation, the current log size 
         should read zero."
    REFERENCE
        "ITU-T Rec. X.735 (1992) | ISO/IEC 10164-6 : 1993, 
               Section 8.1.1.2.1."
    DEFVAL      { 0 }
    ::= { logEntry 7 }

currentLogSize OBJECT-TYPE
    SYNTAX Gauge32
    MAX-ACCESS read-only
    STATUS current
    DESCRIPTION
        "This attribute specifies the current size of the log 
         measured in octets.
         
         Note: Since the log size is specified in octets, the 
         actual amount of information that is contained in a log 
         will be determined by data representation in the log.  
         This data representation is not subject to 
         standardization.  The maximum log size does not include 
         the system overhead involved in establishing the log.  
         Thus, immediately after creation, the current log size 
         should read zero."
    REFERENCE
        "ITU-T Rec. X.735 (1992) | ISO/IEC 10164-6 : 1993, 
               Section 8.1.1.2.2."
    DEFVAL      { 0 }
    ::= { logEntry 8 }

numberOfRecords OBJECT-TYPE
    SYNTAX Gauge32
    MAX-ACCESS read-only
    STATUS current
    DESCRIPTION
        "This attribute specifies the current number of records 
         contained in the log."
    REFERENCE
        "ITU-T Rec. X.735 (1992) | ISO/IEC 10164-6 : 1993, 
               Section 8.1.1.2.3."
    DEFVAL      { 0 }
    ::= { logEntry 9 }

capacityAlarmThreshold OBJECT-TYPE
    SYNTAX LogCapacityAlarmThreshold
    MAX-ACCESS read-create
    STATUS current
    DESCRIPTION
        "The log alarm package provides for transmission of 
         alarms when a log full condition approaches.  This 
         package shall be present whenever a log is of finite 
         size and halts logging when the log full availability 
         status occurs.
         
         This attribute specifies, as a percentage of maximum 
         log size, the points at which an event will be 
         generated to indicate that a log full or log wrap 
         condition is approaching.  This attribute is 
         set-valued.  Support of this attribute is mandatory for 
         the halt behaviour.  When a log is created with the 
         wrap option the capacity threshold events are triggered 
         as if coupled to a gauge that counts from zero to the 
         highest capacity threshold value defined and then 
         resets to zero."
    REFERENCE
        "ITU-T Rec. X.735 (1992) | ISO/IEC 10164-6 : 1993, 
               Section 8.1.1.3."
    DEFVAL      { "\x64" }
    ::= { logEntry 10 }

logStartTime OBJECT-TYPE
    SYNTAX TimeStamp
    MAX-ACCESS read-create
    STATUS current
    DESCRIPTION
        "The duration package provides the ability to 
         automatically control the time that a managed object 
         starts and stops functioning through the use of the 
         start and stop time attribtues.
         
         This attribute defines the date and time at which an 
         unlocked and enabled managed object starts functioning.  
         If the value of the start time attribute is not 
         specified in the create request, its value defaults to 
         the time of creation of the managed object and thus 
         causing it to function immediately.
         
         A change in the start time attribute results in an 
         attribute change notification."
    REFERENCE
        "ITU-T Rec. X.735 (1992) | ISO/IEC 10164-6 : 1993, 
               Section 8.1.1.4.2."
    ::= { logEntry 11 }

logStopTime OBJECT-TYPE
    SYNTAX TimeStamp
    MAX-ACCESS read-create
    STATUS current
    DESCRIPTION
        "The duration package provides the ability to 
         automatically control the time that a managed object 
         starts and stops functioning through the use of the 
         start and stop time attribtues.
         
         This attribute defines the date and time at which 
         a managed object stops functioning.  If the value of 
         the stop time attribute is not specified in the create 
         request, its value defaults to 'continuous operation'.  
         Continuous operation is represented by a null value for 
         the stop time.
         
         A change in the stop time attribute results in an 
         attribute change notification."
    REFERENCE
        "ITU-T Rec. X.735 (1992) | ISO/IEC 10164-6 : 1993, 
               Section 8.1.1.4.2."
    DEFVAL      { 6983120 }
    ::= { logEntry 12 }

logIntervalsOfDay OBJECT-TYPE
    SYNTAX IntervalsOfDay
    MAX-ACCESS read-create
    STATUS current
    DESCRIPTION
        "The daily scheduling conditional package provides the 
         capability of scheduling logging with a periodicity of 
         24 hours.
         
         This attribute defines the list of time intervals 
         (interval-start and interval-end times of day) for 
         which the logs will exhibit the logging-on condition.  
         During excluded intervals the log exhibits the 
         logging-off condition.  If not specified in the create 
         request, the value of this component defaults to 
         a single interval encompassing the entire 24 hour 
         period of a day."
    REFERENCE
        "ITU-T Rec. X.735 (1992) | ISO/IEC 10164-6 : 1993, 
               Section 8.1.1.4.3."
    DEFVAL      { "\x00\x00\x17\x3B" }
    ::= { logEntry 13 }

logWeekMask OBJECT-TYPE
    SYNTAX WeekMask
    MAX-ACCESS read-create
    STATUS current
    DESCRIPTION
        "The weekly scheduling conditional package provides the 
         capability of scheduling logging with a periodicity of 
         one week.  This structured attribute defines a set of 
         mask components, each specifying a set of time 
         intervals on a 24-hout time-of-day clock, pertaining to 
         selected days of the week.  The week mask attribute 
         defaults to a scheduling criteria of 'always-on' at 
         logs creation.
         
         The days of wekk component defines the days of the week 
         on which the log's scheduling mechansim will allow the 
         log to have intervals during which logging may occur.  
         This component, if not present is a create, will 
         default to all seven days of the week.
         
         The intervals of day component defines the list of time 
         intervals (interval-start and interval-end times of 
         day) for which the log will exhibit the logging-on 
         condition, if the current days is one of the days that 
         is selected within the corresponding dyas of week.  
         
         During excluded intervals the log exhibits the 
         logging-off condition.  If not specified in the create 
         report, the value of this component defaults to 
         a single interval encompassing the entire 24 hour 
         period of a day."
    REFERENCE
        "ITU-T Rec. X.735 (1992) | ISO/IEC 10164-6 : 1993, 
               Section 8.1.1.4.4."
    DEFVAL      { "\x7F\x01\x00\x00\x17\x3B" }
    ::= { logEntry 14 }

logSchedulerName OBJECT-TYPE
    SYNTAX ObjectInstance
    MAX-ACCESS read-create
    STATUS current
    DESCRIPTION
        "The external shceduler scheduling conditional package 
         provides the capability of scheduling logging based on 
         a schedule defined in an external scheduler managed 
         object.  The log's logging-on and logging-off condition 
         will be changed in accordance with the scheduling 
         characeteristics specified by a scheduler managed 
         object.
         
         This attribute specifies the name of the scheduler 
         managed object that is related to the logs.  This 
         relationship imiplies that the log's logging-on and 
         logging-off conditions wil be scheduled by the external 
         scheduler.  This attribute is read-only once the object 
         has been created.  It defaults to NULL if not specified 
         upon creation."
    REFERENCE
        "ITU-T Rec. X.735 (1992) | ISO/IEC 10164-6 : 1993, 
               Section 8.1.1.4.5."
    DEFVAL      { zeroDotZero }
    ::= { logEntry 15 }

logEntryStatus OBJECT-TYPE
    SYNTAX RowStatus
    MAX-ACCESS read-create
    STATUS current
    DESCRIPTION
        "Provides a mechanism whereby management stations may 
         explicitly create and delete entries in this table."
    REFERENCE
        "STD 58, SNMPv2-TC RowStatus"
    ::= { logEntry 16 }

logRecord OBJECT IDENTIFIER
    ::= { smiTables 3 }

logRecordTable OBJECT-TYPE
    SYNTAX SEQUENCE OF LogRecordEntry
    MAX-ACCESS not-accessible
    STATUS current
    DESCRIPTION
        "This managed object represents the information stored 
         in the logs"
    ::= { logRecord 1 }

logRecordEntry OBJECT-TYPE
    SYNTAX LogRecordEntry
    MAX-ACCESS not-accessible
    STATUS current
    DESCRIPTION
        "Log records are managed objects that represent 
         information stored in logs.  The log record managed 
         object class serves as a superclass for other record 
         classes.  As a part of the specialization of the log 
         record class additional attributes may be assigned to 
         the new subclass.
         
         Log records are created as a result of the receipt of 
         an event report or notifications, they are not created 
         by explicit management operations.  Log records may 
         only be retrieved and deleted; attributes of og record 
         cannot be modified.
         
         The operations that can be performed on a log record 
         depend on the state of the log in which the records are 
         contained and may also be subject to security 
         constraints."
    REFERENCE
        "ITU-T Rec. X.735 (1992) | ISO/IEC 10164-6 : 1993, 
               Section 8.1.2."
    INDEX       { logId, logRecordId }
    ::= { logRecordTable 1 }

LogRecordEntry ::=
    SEQUENCE {
        logRecordId
            SimpleNameType,
        loggingTime
            TimeStamp,
        logRecordEntryStatus
            RowStatus
    }

logRecordId OBJECT-TYPE
    SYNTAX SimpleNameType
    MAX-ACCESS not-accessible
    STATUS current
    DESCRIPTION
        "This attribute uniquely identifies each record in the 
         log.  The log record identifier is a number that is 
         unique within the scope of the log and is assigned 
         sequentially.  The identification number used may wrap; 
         however, at no time shall there be more than one record 
         with the same identifier in the log.
         
         The logRecordId uses an integer interpretation of the 
         SimpleNameType."
    REFERENCE
        "ITU-T Rec. X.735 (1992) | ISO/IEC 10164-6 : 1993, 
               Section 8.1.2.2.1"
    ::= { logRecordEntry 1 }

loggingTime OBJECT-TYPE
    SYNTAX TimeStamp
    MAX-ACCESS read-only
    STATUS current
    DESCRIPTION
        "This attribute identifies the time at which the record 
         was entered into the log.  In the absence of time 
         synchronization this time may be greater or less than 
         the source time (if specified)."
    REFERENCE
        "ITU-T Rec. X.735 (1992) | ISO/IEC 10164-6 : 1993, 
               Section 8.1.2.2.2"
    ::= { logRecordEntry 2 }

logRecordEntryStatus OBJECT-TYPE
    SYNTAX RowStatus
    MAX-ACCESS read-write
    STATUS current
    DESCRIPTION
        "Provides a mechanism whereby management stations may 
         delete entries in this table.  Log records cannot be 
         created explicitly by management stations but may only 
         be deleted.  The only value that may be written to this 
         status is the 'delete' value."
    REFERENCE
        "STD 58, SNMPv2-TC RowStatus"
    ::= { logRecordEntry 3 }


eventLogRecordTable OBJECT-TYPE
    SYNTAX SEQUENCE OF EventLogRecordEntry
    MAX-ACCESS not-accessible
    STATUS current
    DESCRIPTION
        "This managed object represents the information stored 
         in the log as a result of receiving notifications or 
         incoming event reports."
    ::= { logRecord 2 }

eventLogRecordEntry OBJECT-TYPE
    SYNTAX EventLogRecordEntry
    MAX-ACCESS not-accessible
    STATUS current
    DESCRIPTION
        ""
    INDEX       { logId, logRecordId }
    ::= { eventLogRecordTable 1 }

EventLogRecordEntry ::=
    SEQUENCE {
        managedObjectClass
            ObjectClass,
        managedObjectInstance
            ObjectInstance,
        eventType
            EventTypeId,
        eventTimes
            EventTimeStamp,
        eventNotificationIdentifier
            NotificationIdentifier,
        eventCorrelatedNotifications
            CorrelatedNotifications,
        eventAdditionalText
            AdditionalText,
        eventAdditionalInformation
            AdditionalInformation
    }

managedObjectClass OBJECT-TYPE
    SYNTAX ObjectClass
    MAX-ACCESS read-only
    STATUS current
    DESCRIPTION
        ""
    ::= { eventLogRecordEntry 1 }

managedObjectInstance OBJECT-TYPE
    SYNTAX ObjectInstance
    MAX-ACCESS read-only
    STATUS current
    DESCRIPTION
        ""
    ::= { eventLogRecordEntry 2 }

eventType OBJECT-TYPE
    SYNTAX EventTypeId
    MAX-ACCESS read-only
    STATUS current
    DESCRIPTION
        ""
    ::= { eventLogRecordEntry 3 }

eventTimes OBJECT-TYPE
    SYNTAX EventTimeStamp
    MAX-ACCESS read-only
    STATUS current
    DESCRIPTION
        ""
    ::= { eventLogRecordEntry 4 }

eventNotificationIdentifier OBJECT-TYPE
    SYNTAX NotificationIdentifier
    MAX-ACCESS read-only
    STATUS current
    DESCRIPTION
        ""
    ::= { eventLogRecordEntry 5 }

eventCorrelatedNotifications OBJECT-TYPE
    SYNTAX CorrelatedNotifications
    MAX-ACCESS read-only
    STATUS current
    DESCRIPTION
        ""
    ::= { eventLogRecordEntry 6 }

eventAdditionalText OBJECT-TYPE
    SYNTAX AdditionalText
    MAX-ACCESS read-only
    STATUS current
    DESCRIPTION
        ""
    ::= { eventLogRecordEntry 7 }

eventAdditionalInformation OBJECT-TYPE
    SYNTAX AdditionalInformation
    MAX-ACCESS read-only
    STATUS current
    DESCRIPTION
        ""
    ::= { eventLogRecordEntry 8 }


alarmRecordTable OBJECT-TYPE
    SYNTAX SEQUENCE OF AlarmRecordEntry
    MAX-ACCESS not-accessible
    STATUS current
    DESCRIPTION
        "This managed object is used to represent logged 
         information that resulted from alarm notifications or 
         event reports"
    ::= { logRecord 3 }

alarmRecordEntry OBJECT-TYPE
    SYNTAX AlarmRecordEntry
    MAX-ACCESS not-accessible
    STATUS current
    DESCRIPTION
        "
         The appropriate object identifier values for the 
         eventType attribute, inherited from eventLogRecord 
         managed object class are communicationAlarm, 
         qualityofServiceAlarm, processingErrorAlarm, 
         equipmentAlarm and environmentalAlarm."
    INDEX       { logId, logRecordId }
    ::= { alarmRecordTable 1 }

AlarmRecordEntry ::=
    SEQUENCE {
        alarmRecordProbableCause
            ProbableCause,
        alarmRecordPerceivedSeverity
            PerceivedSeverity,
        alarmRecordSpecificProblems
            SpecificProblems,
        alarmRecordBackedUpStatus
            BackedUpStatus,
        alarmRecordBackUpObject
            BackUpObject,
        alarmRecordTrendIndication
            TrendIndication,
        alarmRecordThresholdInfo
            ThresholdInfo,
        alarmRecordStateChangeDefinition
            AttributeValueChangeDefinition,
        alarmRecordMonitoredAttributes
            MonitoredAttributes,
        alarmRecordProposedRepairActions
            ProposedRepairActions
    }

alarmRecordProbableCause OBJECT-TYPE
    SYNTAX ProbableCause
    MAX-ACCESS read-only
    STATUS current
    DESCRIPTION
        ""
    ::= { alarmRecordEntry 1 }

alarmRecordPerceivedSeverity OBJECT-TYPE
    SYNTAX PerceivedSeverity
    MAX-ACCESS read-only
    STATUS current
    DESCRIPTION
        ""
    ::= { alarmRecordEntry 2 }

alarmRecordSpecificProblems OBJECT-TYPE
    SYNTAX SpecificProblems
    MAX-ACCESS read-only
    STATUS current
    DESCRIPTION
        ""
    DEFVAL      { zeroDotZero }
    ::= { alarmRecordEntry 3 }

alarmRecordBackedUpStatus OBJECT-TYPE
    SYNTAX BackedUpStatus
    MAX-ACCESS read-only
    STATUS current
    DESCRIPTION
        ""
    DEFVAL      { 0 } -- none(0)
    ::= { alarmRecordEntry 4 }

alarmRecordBackUpObject OBJECT-TYPE
    SYNTAX BackUpObject
    MAX-ACCESS read-only
    STATUS current
    DESCRIPTION
        ""
    DEFVAL      { zeroDotZero }
    ::= { alarmRecordEntry 5 }

alarmRecordTrendIndication OBJECT-TYPE
    SYNTAX TrendIndication
    MAX-ACCESS read-only
    STATUS current
    DESCRIPTION
        ""
    DEFVAL      { 0 } -- noChange
    ::= { alarmRecordEntry 6 }

alarmRecordThresholdInfo OBJECT-TYPE
    SYNTAX ThresholdInfo
    MAX-ACCESS read-only
    STATUS current
    DESCRIPTION
        ""
    DEFVAL      { } -- ""
    ::= { alarmRecordEntry 7 }

alarmRecordStateChangeDefinition OBJECT-TYPE
    SYNTAX AttributeValueChangeDefinition
    MAX-ACCESS read-only
    STATUS current
    DESCRIPTION
        ""
    DEFVAL      { } -- ""
    ::= { alarmRecordEntry 8 }

alarmRecordMonitoredAttributes OBJECT-TYPE
    SYNTAX MonitoredAttributes
    MAX-ACCESS read-only
    STATUS current
    DESCRIPTION
        ""
    DEFVAL      { } -- ""
    ::= { alarmRecordEntry 9 }

alarmRecordProposedRepairActions OBJECT-TYPE
    SYNTAX ProposedRepairActions
    MAX-ACCESS read-only
    STATUS current
    DESCRIPTION
        ""
    DEFVAL      { zeroDotZero }
    ::= { alarmRecordEntry 10 }


attributeValueChangeRecordTable OBJECT-TYPE
    SYNTAX SEQUENCE OF AttributeValueChangeRecordEntry
    MAX-ACCESS not-accessible
    STATUS current
    DESCRIPTION
        "This managed object is used to represent logged 
         information that resulted from attribute value change 
         notifications or event reports"
    ::= { logRecord 4 }

attributeValueChangeRecordEntry OBJECT-TYPE
    SYNTAX AttributeValueChangeRecordEntry
    MAX-ACCESS not-accessible
    STATUS current
    DESCRIPTION
        "
         The appropriate object identifier values for the 
         eventType attribute, inherited from eventLogRecord 
         managed object class, is attributeValueChange"
    INDEX       { logId, logRecordId }
    ::= { attributeValueChangeRecordTable 1 }

AttributeValueChangeRecordEntry ::=
    SEQUENCE {
        attributeValueChangeRecordDefinition
            AttributeValueChangeDefinition,
        attributeValueChangeSourceIndicator
            SourceIndicator,
        attributeValueChangeAttributeIdentifierList
            AttributeIdentifierList
    }

attributeValueChangeRecordDefinition OBJECT-TYPE
    SYNTAX AttributeValueChangeDefinition
    MAX-ACCESS read-only
    STATUS current
    DESCRIPTION
        ""
    ::= { attributeValueChangeRecordEntry 1 }

attributeValueChangeSourceIndicator OBJECT-TYPE
    SYNTAX SourceIndicator
    MAX-ACCESS read-only
    STATUS current
    DESCRIPTION
        ""
    ::= { attributeValueChangeRecordEntry 2 }

attributeValueChangeAttributeIdentifierList OBJECT-TYPE
    SYNTAX AttributeIdentifierList
    MAX-ACCESS read-only
    STATUS current
    DESCRIPTION
        ""
    ::= { attributeValueChangeRecordEntry 3 }


objectCreationRecordTable OBJECT-TYPE
    SYNTAX SEQUENCE OF ObjectCreationRecordEntry
    MAX-ACCESS not-accessible
    STATUS current
    DESCRIPTION
        "This managed object is used to represent logged 
         information that resulted from object creation 
         notifications or event reports"
    ::= { logRecord 5 }

objectCreationRecordEntry OBJECT-TYPE
    SYNTAX ObjectCreationRecordEntry
    MAX-ACCESS not-accessible
    STATUS current
    DESCRIPTION
        "
         The appropriate object identifier value for the 
         eventType attribute, inherited from eventLogRecord 
         managed object class, is objectCreation"
    INDEX       { logId, logRecordId }
    ::= { objectCreationRecordTable 1 }

ObjectCreationRecordEntry ::=
    SEQUENCE {
        objectCreationSourceIndicator
            SourceIndicator,
        objectCreationAttributeIdentifierList
            AttributeIdentifierList
    }

objectCreationSourceIndicator OBJECT-TYPE
    SYNTAX SourceIndicator
    MAX-ACCESS read-only
    STATUS current
    DESCRIPTION
        ""
    ::= { objectCreationRecordEntry 1 }

objectCreationAttributeIdentifierList OBJECT-TYPE
    SYNTAX AttributeIdentifierList
    MAX-ACCESS read-only
    STATUS current
    DESCRIPTION
        ""
    ::= { objectCreationRecordEntry 2 }


objectDeletionRecordTable OBJECT-TYPE
    SYNTAX SEQUENCE OF ObjectDeletionRecordEntry
    MAX-ACCESS not-accessible
    STATUS current
    DESCRIPTION
        "This managed object is used to represent logged 
         information that resulted from object deletion 
         notifications or event reports"
    ::= { logRecord 6 }

objectDeletionRecordEntry OBJECT-TYPE
    SYNTAX ObjectDeletionRecordEntry
    MAX-ACCESS not-accessible
    STATUS current
    DESCRIPTION
        "
         The appropriate object identifier value for the 
         eventType attribute, inherited from eventLogRecord 
         managed object class, is objectDeletion"
    INDEX       { logId, logRecordId }
    ::= { objectDeletionRecordTable 1 }

ObjectDeletionRecordEntry ::=
    SEQUENCE {
        objectDeletionSourceIndicator
            SourceIndicator,
        objectDeletionAttributeIdentifierList
            AttributeIdentifierList
    }

objectDeletionSourceIndicator OBJECT-TYPE
    SYNTAX SourceIndicator
    MAX-ACCESS read-only
    STATUS current
    DESCRIPTION
        ""
    ::= { objectDeletionRecordEntry 1 }

objectDeletionAttributeIdentifierList OBJECT-TYPE
    SYNTAX AttributeIdentifierList
    MAX-ACCESS read-only
    STATUS current
    DESCRIPTION
        ""
    ::= { objectDeletionRecordEntry 2 }


relationshipChangeRecordTable OBJECT-TYPE
    SYNTAX SEQUENCE OF RelationshipChangeRecordEntry
    MAX-ACCESS not-accessible
    STATUS current
    DESCRIPTION
        "This managed object is used to represent logged 
         information that resulted from relationship change 
         notifications or event reports"
    ::= { logRecord 7 }

relationshipChangeRecordEntry OBJECT-TYPE
    SYNTAX RelationshipChangeRecordEntry
    MAX-ACCESS not-accessible
    STATUS current
    DESCRIPTION
        "
         The appropriate object identifier value for the 
         eventType attribute, inherited from eventLogRecord 
         managed object class, is relationshipChange"
    INDEX       { logId, logRecordId }
    ::= { relationshipChangeRecordTable 1 }

RelationshipChangeRecordEntry ::=
    SEQUENCE {
        relationshipChangeRecordDefinition
            AttributeValueChangeDefinition,
        relationshipChangeSourceIndicator
            SourceIndicator,
        relationshipChangeAttributeIdentifierList
            AttributeIdentifierList
    }

relationshipChangeRecordDefinition OBJECT-TYPE
    SYNTAX AttributeValueChangeDefinition
    MAX-ACCESS read-only
    STATUS current
    DESCRIPTION
        ""
    ::= { relationshipChangeRecordEntry 1 }

relationshipChangeSourceIndicator OBJECT-TYPE
    SYNTAX SourceIndicator
    MAX-ACCESS read-only
    STATUS current
    DESCRIPTION
        ""
    ::= { relationshipChangeRecordEntry 2 }

relationshipChangeAttributeIdentifierList OBJECT-TYPE
    SYNTAX AttributeIdentifierList
    MAX-ACCESS read-only
    STATUS current
    DESCRIPTION
        ""
    ::= { relationshipChangeRecordEntry 3 }


securityAlarmReportRecordTable OBJECT-TYPE
    SYNTAX SEQUENCE OF SecurityAlarmReportRecordEntry
    MAX-ACCESS not-accessible
    STATUS current
    DESCRIPTION
        "This managed object is used to represent logged 
         information that resulted from security alarm 
         notifications or event reports"
    ::= { logRecord 8 }

securityAlarmReportRecordEntry OBJECT-TYPE
    SYNTAX SecurityAlarmReportRecordEntry
    MAX-ACCESS not-accessible
    STATUS current
    DESCRIPTION
        "
         The appropriate object identifier values for the 
         eventType attribute, inherited from eventLogRecord 
         managed object class, are integrityViolation, 
         operationalViolation, physicalViolation, 
         securityServiceOrMechanismViolation and 
         timeDomainViolation"
    INDEX       { logId, logRecordId }
    ::= { securityAlarmReportRecordTable 1 }

SecurityAlarmReportRecordEntry ::=
    SEQUENCE {
        securityAlarmRecordCause
            SecurityAlarmCause,
        securityAlarmRecordSeverity
            SecurityAlarmSeverity,
        securityAlarmRecordDetector
            SecurityAlarmDetector,
        securityServiceUser
            ServiceUser,
        securityServiceProvider
            ServiceProvider
    }

securityAlarmRecordCause OBJECT-TYPE
    SYNTAX SecurityAlarmCause
    MAX-ACCESS read-only
    STATUS current
    DESCRIPTION
        ""
    ::= { securityAlarmReportRecordEntry 1 }

securityAlarmRecordSeverity OBJECT-TYPE
    SYNTAX SecurityAlarmSeverity
    MAX-ACCESS read-only
    STATUS current
    DESCRIPTION
        ""
    ::= { securityAlarmReportRecordEntry 2 }

securityAlarmRecordDetector OBJECT-TYPE
    SYNTAX SecurityAlarmDetector
    MAX-ACCESS read-only
    STATUS current
    DESCRIPTION
        ""
    ::= { securityAlarmReportRecordEntry 3 }

securityServiceUser OBJECT-TYPE
    SYNTAX ServiceUser
    MAX-ACCESS read-only
    STATUS current
    DESCRIPTION
        ""
    ::= { securityAlarmReportRecordEntry 4 }

securityServiceProvider OBJECT-TYPE
    SYNTAX ServiceProvider
    MAX-ACCESS read-only
    STATUS current
    DESCRIPTION
        ""
    ::= { securityAlarmReportRecordEntry 5 }


stateChangeRecordTable OBJECT-TYPE
    SYNTAX SEQUENCE OF StateChangeRecordEntry
    MAX-ACCESS not-accessible
    STATUS current
    DESCRIPTION
        "This managed object is used to represent logged 
         information that resulted from state change 
         notifications or event reports"
    ::= { logRecord 9 }

stateChangeRecordEntry OBJECT-TYPE
    SYNTAX StateChangeRecordEntry
    MAX-ACCESS not-accessible
    STATUS current
    DESCRIPTION
        "
         The appropriate object identifier value for the 
         eventType attribute, inherited from eventLogRecord 
         managed object class, is stateChange"
    INDEX       { logId, logRecordId }
    ::= { stateChangeRecordTable 1 }

StateChangeRecordEntry ::=
    SEQUENCE {
        stateChangeRecordDefinition
            AttributeValueChangeDefinition,
        stateChangeSourceIndicator
            SourceIndicator,
        stateChangeAttributeIdentifierList
            AttributeIdentifierList
    }

stateChangeRecordDefinition OBJECT-TYPE
    SYNTAX AttributeValueChangeDefinition
    MAX-ACCESS read-only
    STATUS current
    DESCRIPTION
        ""
    ::= { stateChangeRecordEntry 1 }

stateChangeSourceIndicator OBJECT-TYPE
    SYNTAX SourceIndicator
    MAX-ACCESS read-only
    STATUS current
    DESCRIPTION
        ""
    ::= { stateChangeRecordEntry 2 }

stateChangeAttributeIdentifierList OBJECT-TYPE
    SYNTAX AttributeIdentifierList
    MAX-ACCESS read-only
    STATUS current
    DESCRIPTION
        ""
    ::= { stateChangeRecordEntry 3 }


smiOids OBJECT IDENTIFIER
    ::= { smiMIB 4 }

arfProbableCause OBJECT IDENTIFIER
    ::= { smiOids 1 }

adapterError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry."
    REFERENCE
        "ITU-T Rec. X.721 (1992) | ISO/IEC 10165-2 : 1992, 
               adapterError"
    ::= { arfProbableCause 1 }

applicationSubsystemFailure OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A failure in an application subsystem has occured (an 
         application subsystem may include software to support 
         the Session, Presentation or Application layers)."
    REFERENCE
        "ITU-T Rec. X.721 (1992) | ISO/IEC 10165-2 : 1992, 
               applicationSubsystemFailure"
    ::= { arfProbableCause 2 }

bandwidthReduced OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         The available transmission bandwidth has decreased."
    REFERENCE
        "ITU-T Rec. X.721 (1992) | ISO/IEC 10165-2 : 1992, 
               bandwidthReduced"
    ::= { arfProbableCause 3 }

callEstablishmentError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An error occured while attempting to establish 
    a connection."
    REFERENCE
        "ITU-T Rec. X.721 (1992) | ISO/IEC 10165-2 : 1992, 
               callEstablishmentError"
    ::= { arfProbableCause 4 }

communicationsProtocolError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A communications protocol has been violated."
    REFERENCE
        "ITU-T Rec. X.721 (1992) | ISO/IEC 10165-2 : 1992, 
               communicationsProtocolError"
    ::= { arfProbableCause 5 }

communicationsSubsystemFailure OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A failure in a subsystem that supports communications 
         over telecommunications links, there may be implemented 
         via leased telephone lines, by X.25 networks, 
         token-ring LAN, or otherwise."
    REFERENCE
        "ITU-T Rec. X.721 (1992) | ISO/IEC 10165-2 : 1992, 
               communicationsSubsystemFailure"
    ::= { arfProbableCause 6 }

configurationOrCustomizationError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A system or device generation or customization 
         parameter has been specified incorrectly, or is 
         inconsistent with the actual configuration."
    REFERENCE
        "ITU-T Rec. X.721 (1992) | ISO/IEC 10165-2 : 1992, 
               configurationOrCustomizationError"
    ::= { arfProbableCause 7 }

congestion OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A system or network component has reached its capacity 
         or is approaching it."
    REFERENCE
        "ITU-T Rec. X.721 (1992) | ISO/IEC 10165-2 : 1992, 
               congestion"
    ::= { arfProbableCause 8 }

corruptData OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An error has caused data to be incorrect and thus 
    unreliable."
    REFERENCE
        "ITU-T Rec. X.721 (1992) | ISO/IEC 10165-2 : 1992, 
               corruptData"
    ::= { arfProbableCause 9 }

cpuCyclesLimitExceeded OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A Central Processing Unit has issued an unacceptable 
         number of instructions to accomplish a task."
    REFERENCE
        "ITU-T Rec. X.721 (1992) | ISO/IEC 10165-2 : 1992, 
               cpuCyclesLimitExceeded"
    ::= { arfProbableCause 10 }

dataSetOrModemError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An internal error has occured on a dataset or modem."
    REFERENCE
        "ITU-T Rec. X.721 (1992) | ISO/IEC 10165-2 : 1992, 
               dataSetOrModemError"
    ::= { arfProbableCause 11 }

degradedSignal OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         The quiality or reliability of transmitted data has 
    decreased."
    REFERENCE
        "ITU-T Rec. X.721 (1992) | ISO/IEC 10165-2 : 1992, 
               degradedSignal"
    ::= { arfProbableCause 12 }

dTE-DCEInterfaceError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A problem in a DTE-DCE interface, which includes the 
         interface between the DTE and DCE, any protocol used to 
         communicate between the DTE and DCE and information 
         provided by the DCE about the circuit."
    REFERENCE
        "ITU-T Rec. X.721 (1992) | ISO/IEC 10165-2 : 1992, 
               dTE-DCEInterfaceError"
    ::= { arfProbableCause 13 }

enclosureDoorOpen OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An enclosure door is open."
    REFERENCE
        "ITU-T Rec. X.721 (1992) | ISO/IEC 10165-2 : 1992, 
               enclosureDoorOpen"
    ::= { arfProbableCause 14 }

equipmentMalfunction OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An internal machine error has occured for which no more 
         specific probable cause has been identified."
    REFERENCE
        "ITU-T Rec. X.721 (1992) | ISO/IEC 10165-2 : 1992, 
               equipmentMalfunction"
    ::= { arfProbableCause 15 }

excessiveVibration OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         Vibratory or siesmic limits have been exceeded."
    REFERENCE
        "ITU-T Rec. X.721 (1992) | ISO/IEC 10165-2 : 1992, 
               excessiveVibration"
    ::= { arfProbableCause 16 }

fileError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         The format of a file (or set of files) is incorrect and 
         thus cannot be used reliably in processing."
    REFERENCE
        "ITU-T Rec. X.721 (1992) | ISO/IEC 10165-2 : 1992, 
               fileError"
    ::= { arfProbableCause 17 }

fireDetected OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A fire has been detected."
    REFERENCE
        "ITU-T Rec. X.721 (1992) | ISO/IEC 10165-2 : 1992, 
               fireDetected"
    ::= { arfProbableCause 18 }

floodDetected OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A flood has been detected."
    REFERENCE
        "ITU-T Rec. X.721 (1992) | ISO/IEC 10165-2 : 1992, 
               floodDetected"
    ::= { arfProbableCause 19 }

framingError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An error in the information that delimits the bit 
         groups within a continuous stream of bits has occured."
    REFERENCE
        "ITU-T Rec. X.721 (1992) | ISO/IEC 10165-2 : 1992, 
               framingError"
    ::= { arfProbableCause 20 }

heatingOrVentilationOrCoolingSystemProblem OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A heating, ventilation or cooling system problem has 
         been detected."
    REFERENCE
        "ITU-T Rec. X.721 (1992) | ISO/IEC 10165-2 : 1992, 
               heatingOrVentilationCoolingSystemProblem"
    ::= { arfProbableCause 21 }

humidityUnacceptable OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         The humidity is not within acceptable limits."
    REFERENCE
        "ITU-T Rec. X.721 (1992) | ISO/IEC 10165-2 : 1992, 
               humidityUnacceptable"
    ::= { arfProbableCause 22 }

inputOutputDeviceError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An error has occured on the input-output device."
    REFERENCE
        "ITU-T Rec. X.721 (1992) | ISO/IEC 10165-2 : 1992, 
               inputOutputDeviceError"
    ::= { arfProbableCause 23 }

inputDeviceError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry."
    REFERENCE
        "ITU-T Rec. X.721 (1992) | ISO/IEC 10165-2 : 1992, 
               adapterError"
    ::= { arfProbableCause 24 }

lANError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An error has occured in the input device."
    REFERENCE
        "ITU-T Rec. X.721 (1992) | ISO/IEC 10165-2 : 1992, 
               inputDeviceError"
    ::= { arfProbableCause 25 }

leakDetected OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A leakage or (non-toxic) fluid or gas has been 
    detected."
    REFERENCE
        "ITU-T Rec. X.721 (1992) | ISO/IEC 10165-2 : 1992, 
               leakDetected"
    ::= { arfProbableCause 26 }

localNodeTransmissionError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An error occured on a communications channel between 
         the local node and an adjacent node."
    REFERENCE
        "ITU-T Rec. X.721 (1992) | ISO/IEC 10165-2 : 1992, 
               localNodeTransmissionError"
    ::= { arfProbableCause 27 }

lossOfFrame OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An inability to locate the information that delimits 
         the bit grouping within a continuous stream of bits has 
         occured."
    REFERENCE
        "ITU-T Rec. X.721 (1992) | ISO/IEC 10165-2 : 1992, 
               lossOfFrame"
    ::= { arfProbableCause 28 }

lossOfSignal OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An error condition in which no data is present on 
         a communications circuit or channel."
    REFERENCE
        "ITU-T Rec. X.721 (1992) | ISO/IEC 10165-2 : 1992, 
               lossOfSignal"
    ::= { arfProbableCause 29 }

materialSupplyExhausted OBJECT-IDENTITY
    STATUS current
    DESCRIPTION
        "X.721 probable cause value for use in notifications and event 
         records.  May be used in a communicationsAlarm, 
         environmentalAlarm, equipmentAlarm, processingErrorAlarm or 
         qualityofServiceAlarm notification, and may appear in an 
         AlarmRecordEntry.
         
         A supply of needed material has been exhausted."
    REFERENCE
        "ITU-T Rec. X.721 (1992) | ISO/IEC 10165-2 : 1992, 
               materialSupplyExhausted"
    ::= { arfProbableCause 30 }

multiplexerProblem OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An error has occured while multiplexing communications 
         signals."
    REFERENCE
        "ITU-T Rec. X.721 (1992) | ISO/IEC 10165-2 : 1992, 
               multiplexerProblem"
    ::= { arfProbableCause 31 }

outOfMemory OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         There is no program-addressable storage available."
    REFERENCE
        "ITU-T Rec. X.721 (1992) | ISO/IEC 10165-2 : 1992, 
               outOfMemory"
    ::= { arfProbableCause 32 }

ouputDeviceError OBJECT-IDENTITY
    STATUS current
    DESCRIPTION
        "X.721 probable cause value for use in notifications and event 
         records.  May be used in a communicationsAlarm, 
         environmentalAlarm, equipmentAlarm, processingErrorAlarm or 
         qualityofServiceAlarm notification, and may appear in an 
         AlarmRecordEntry.
         
         An error has occured on the output device."
    REFERENCE
        "ITU-T Rec. X.721 (1992) | ISO/IEC 10165-2 : 1992, 
               outputDeviceError"
    ::= { arfProbableCause 33 }

performanceDegraded OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         Service agreements or service limits are outside 
         acceptable limits."
    REFERENCE
        "ITU-T Rec. X.721 (1992) | ISO/IEC 10165-2 : 1992, 
               performanceDegraded"
    ::= { arfProbableCause 34 }

powerProblem OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         There is a problem with the power supply for one or 
         more resources."
    REFERENCE
        "ITU-T Rec. X.721 (1992) | ISO/IEC 10165-2 : 1992, 
               powerProblem"
    ::= { arfProbableCause 35 }

pressureUnacceptable OBJECT-IDENTITY
    STATUS current
    DESCRIPTION
        "X.721 probable cause value for use in notifications and event 
         records.  May be used in a communicationsAlarm, 
         environmentalAlarm, equipmentAlarm, processingErrorAlarm or 
         qualityofServiceAlarm notification, and may appear in an 
         AlarmRecordEntry.
         
         A fluid or gas pressure is not within acceptable limits."
    REFERENCE
        "ITU-T Rec. X.721 (1992) | ISO/IEC 10165-2 : 1992, 
               pressureUnacceptable"
    ::= { arfProbableCause 36 }

processorProblem OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An internal machine error has occured on a Central 
         Processing Unit."
    REFERENCE
        "ITU-T Rec. X.721 (1992) | ISO/IEC 10165-2 : 1992, 
               processorProblem"
    ::= { arfProbableCause 37 }

pumpFailure OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         Failure of mechanism that transports a fluid by 
         inducing pressure differentials within the fluid."
    REFERENCE
        "ITU-T Rec. X.721 (1992) | ISO/IEC 10165-2 : 1992, 
               pumpFailure"
    ::= { arfProbableCause 38 }

queueSizeExceeded OBJECT-IDENTITY
    STATUS current
    DESCRIPTION
        "X.721 probable cause value for use in notifications and event 
         records.  May be used in a communicationsAlarm, 
         environmentalAlarm, equipmentAlarm, processingErrorAlarm or 
         qualityofServiceAlarm notification, and may appear in an 
         AlarmRecordEntry.
         
         The number of items to be processed (configurable or not) has 
         exceeded the maximum allowable."
    REFERENCE
        "ITU-T Rec. X.721 (1992) | ISO/IEC 10165-2 : 1992, 
               queueSizeExceeded"
    ::= { arfProbableCause 39 }

receiveFailure OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         Receive failure."
    REFERENCE
        "ITU-T Rec. X.721 (1992) | ISO/IEC 10165-2 : 1992, 
               receiveFailure"
    ::= { arfProbableCause 40 }

receiverFailure OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         Receiver failure."
    REFERENCE
        "ITU-T Rec. X.721 (1992) | ISO/IEC 10165-2 : 1992, 
               receiverFailure"
    ::= { arfProbableCause 41 }

remoteNodeTransmissionError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An error occured on a communication channel beyond the 
         adjacent node."
    REFERENCE
        "ITU-T Rec. X.721 (1992) | ISO/IEC 10165-2 : 1992, 
               remoteNodeTransmissionError"
    ::= { arfProbableCause 42 }

resourceAtOrNearingCapacity OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         The usage of a resource is at or nearing the maximum 
         allowable capacity."
    REFERENCE
        "ITU-T Rec. X.721 (1992) | ISO/IEC 10165-2 : 1992, 
               resourceAtOrNearingCapacity"
    ::= { arfProbableCause 43 }

responseTimeExcessive OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         The elapsed time between the end of an inquiry and 
         beginning of the answer to the inquiry is outside 
         acceptable limits."
    REFERENCE
        "ITU-T Rec. X.721 (1992) | ISO/IEC 10165-2 : 1992, 
               responseTimeExcessive"
    ::= { arfProbableCause 44 }

retransmissionRateExcessive OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         The number of repeat transmissions is outside of 
         acceptable limits."
    REFERENCE
        "ITU-T Rec. X.721 (1992) | ISO/IEC 10165-2 : 1992, 
               retransmissionRateExcessive"
    ::= { arfProbableCause 45 }

softwareError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A software error has occured for which no more specific 
         probable cause can be identified."
    REFERENCE
        "ITU-T Rec. X.721 (1992) | ISO/IEC 10165-2 : 1992, 
               softwareError"
    ::= { arfProbableCause 46 }

softwareProgramAbnormallyTerminated OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A software program has abnormally terminated due to 
         some unrecoverable error condition."
    REFERENCE
        "ITU-T Rec. X.721 (1992) | ISO/IEC 10165-2 : 1992, 
               softwareProgramAbnormallyTerminated"
    ::= { arfProbableCause 47 }

softwareProgramError OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A software program has abnormally terminated due to 
         some unrecoverable error condition."
    REFERENCE
        "ITU-T Rec. X.721 (1992) | ISO/IEC 10165-2 : 1992, 
               softwareProgramError"
    ::= { arfProbableCause 48 }

storageCapacityProblem OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A storage device has very little or no space available 
         to store additional data."
    REFERENCE
        "ITU-T Rec. X.721 (1992) | ISO/IEC 10165-2 : 1992, 
               storageCapacityProblem"
    ::= { arfProbableCause 49 }

temperatureUnacceptable OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A temperature is not within acceptable limits."
    REFERENCE
        "ITU-T Rec. X.721 (1992) | ISO/IEC 10165-2 : 1992, 
               temperatureUnacceptable"
    ::= { arfProbableCause 50 }

thresholdCrossed OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A limit (configurable or not) has been exceeded."
    REFERENCE
        "ITU-T Rec. X.721 (1992) | ISO/IEC 10165-2 : 1992, 
               thresholdCrossed"
    ::= { arfProbableCause 51 }

timingProblem OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A process that requires timed execution or coordination 
         cannot complete, or has completed but cannot be 
         considered reliable."
    REFERENCE
        "ITU-T Rec. X.721 (1992) | ISO/IEC 10165-2 : 1992, 
               timingProblem"
    ::= { arfProbableCause 52 }

toxicLeakDetected OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         A leakage of toxic fluid or gas has been detected."
    REFERENCE
        "ITU-T Rec. X.721 (1992) | ISO/IEC 10165-2 : 1992, 
               toxicLeaKDetected"
    ::= { arfProbableCause 53 }

transmitFailure OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         Transmit failure."
    REFERENCE
        "ITU-T Rec. X.721 (1992) | ISO/IEC 10165-2 : 1992, 
               transmitFailure"
    ::= { arfProbableCause 54 }

transmitterFailure OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         Transmitter failure."
    REFERENCE
        "ITU-T Rec. X.721 (1992) | ISO/IEC 10165-2 : 1992, 
               transmitterFailure"
    ::= { arfProbableCause 55 }

underlyingResourceUnavailable OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         An entity upon which the reporting object depends has 
         become unavailable."
    REFERENCE
        "ITU-T Rec. X.721 (1992) | ISO/IEC 10165-2 : 1992, 
               underlyingResourceUnavailable"
    ::= { arfProbableCause 56 }

versionMismatch OBJECT-IDENTITY
    STATUS current
    DESCRIPTION
        "X.721 probable cause value for use in notifications and 
         event records.  May be used in a communicationsAlarm, 
         environmentalAlarm, equipmentAlarm, 
         processingErrorAlarm or qualityofServiceAlarm 
         notification, and may appear in an AlarmRecordEntry.
         
         There is a conflict in the functionality of version of 
         two or more communicating entites which may affect any 
         processing involving those entities."
    REFERENCE
        "ITU-T Rec. X.721 (1992) | ISO/IEC 10165-2 : 1992, 
               versionMismatch"
    ::= { arfProbableCause 57 }

arfSecurityAlarmCause OBJECT IDENTIFIER
    ::= { smiOids 2 }

authenticationFailure OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               authenticationFailure"
    ::= { arfSecurityAlarmCause 1 }

breachOfConfidentiality OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               breachOfConfidentiality"
    ::= { arfSecurityAlarmCause 2 }

cableTamper OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               cableTamper"
    ::= { arfSecurityAlarmCause 3 }

delayedInformation OBJECT-IDENTITY
    STATUS current
    DESCRIPTION
        "X.721 security alarm cause for use in notifications and event 
         records.  May be used in an integrityViolation, 
         operationalViolation, physicalViolation, 
         securityServiceOrMechanismViolation or timeDomainViolation 
         notification, and may appear in a 
         SecurityAlarmReportRecordEntry."
    REFERENCE
        "ITU-T Rec. X.721 (1992) | ISO/IEC 10165-2 : 1992, 
               delayedInformation"
    ::= { arfSecurityAlarmCause 4 }

denialOfService OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               denialOfService"
    ::= { arfSecurityAlarmCause 5 }

duplicateInformation OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               duplicateInformation"
    ::= { arfSecurityAlarmCause 6 }

informationMissing OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               informationMissing"
    ::= { arfSecurityAlarmCause 7 }

informationModificationDetected OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               informationModificationDetected"
    ::= { arfSecurityAlarmCause 8 }

informationOutOfSequence OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               informationOutOfSequence"
    ::= { arfSecurityAlarmCause 9 }

intrusionDetection OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               intrusionDetection"
    ::= { arfSecurityAlarmCause 10 }

keyExpired OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               keyExpired"
    ::= { arfSecurityAlarmCause 11 }

nonRepudiationFailure OBJECT-IDENTITY
    STATUS current
    DESCRIPTION
        "X.721 security alarm cause for use in notifications and event 
         records.  May be used in an integrityViolation, 
         operationalViolation, physicalViolation, 
         securityServiceOrMechanismViolation or timeDomainViolation 
         notification, and may appear in a 
         SecurityAlarmReportRecordEntry."
    REFERENCE
        "ITU-T Rec. X.721 (1992) | ISO/IEC 10165-2 : 1992, 
               nonRepudiationFailure"
    ::= { arfSecurityAlarmCause 12 }

outOfHoursActivity OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               outOfHoursActivity"
    ::= { arfSecurityAlarmCause 13 }

outOfService OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               outOfService"
    ::= { arfSecurityAlarmCause 14 }

proceduralError OBJECT-IDENTITY
    STATUS current
    DESCRIPTION
        "X.721 security alarm cause for use in notifications and event 
         records.  May be used in an integrityViolation, 
         operationalViolation, physicalViolation, 
         securityServiceOrMechanismViolation or timeDomainViolation 
         notification, and may appear in a 
         SecurityAlarmReportRecordEntry."
    REFERENCE
        "ITU-T Rec. X.721 (1992) | ISO/IEC 10165-2 : 1992, 
               proceduralError"
    ::= { arfSecurityAlarmCause 15 }

unauthorizedAccessAttempt OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               unauthorizedAccessAttempt"
    ::= { arfSecurityAlarmCause 16 }

unexpectedInformation OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               unexpectedInformation"
    ::= { arfSecurityAlarmCause 17 }

unspecifiedReason OBJECT-IDENTITY
    STATUS current
    DESCRIPTION
        "X.721 security alarm cause for use in notifications and 
         event records.  May be used in an integrityViolation, 
         operationalViolation, physicalViolation, 
         securityServiceOrMechanismViolation or 
         timeDomainViolation notification, and may appear in 
         a SecurityAlarmReportRecordEntry."
    REFERENCE
        "ITU-T Rec. X.721 (1992) | ISO/IEC 10165-2 : 1992, 
               unspecifiedReason"
    ::= { arfSecurityAlarmCause 18 }

arfProposedRepairAction OBJECT IDENTIFIER
    ::= { smiOids 3 }

noActionRequired OBJECT-IDENTITY
    STATUS current
    DESCRIPTION
        "X.721 proposed repair action value for use in 
         notifications and event records.  May be used in 
         a communicationsAlarm, environmentalAlarm, 
         equipmentAlarm, processingErrorAlarm or 
         qualityofServiceAlarm notification, and may appear in 
         AlarmRecordEntry.
         
         Specifies that no repair action is required."
    REFERENCE
        "ITU-T Rec. X.721 (1992) | ISO/IEC 10165-2 : 1992, 
               noActionRequired"
    ::= { arfProposedRepairAction 1 }

repairActionRequired OBJECT-IDENTITY
    STATUS current
    DESCRIPTION
        "X.721 proposed repair action value for use in 
         notifications and event records.  May be used in 
         a communicationsAlarm, environmentalAlarm, 
         equipmentAlarm, processingErrorAlarm or 
         qualityofServiceAlarm notification, and may appear in 
         AlarmRecordEntry.
         
         Specifies that repair action is required."
    REFERENCE
        "ITU-T Rec. X.721 (1992) | ISO/IEC 10165-2 : 1992, 
               repairActionRequired"
    ::= { arfProposedRepairAction 2 }

gnmProbableCause OBJECT IDENTIFIER
    ::= { smiOids 4 }

aIS OBJECT-IDENTITY
    STATUS current
    DESCRIPTION
        "Global value of M.3100 probable cause error for use 
         with communicationsAlarm."
    REFERENCE
        "ITU-T Rec. M.3100 (1992) : aIS"
    ::= { gnmProbableCause 1 }

callSetUpFailure OBJECT-IDENTITY
    STATUS current
    DESCRIPTION
        "Global value of M.3100 probable cause error for use 
         with communicationsAlarm."
    REFERENCE
        "ITU-T Rec. M.3100 (1992) : callSetUpFailure"
    ::= { gnmProbableCause 2 }

degradedSignalGnm OBJECT-IDENTITY
    STATUS current
    DESCRIPTION
        "Global value of M.3100 probable cause error for use 
         with communicationsAlarm."
    REFERENCE
        "ITU-T Rec. M.3100 (1992) : degradedSignal"
    ::= { gnmProbableCause 3 }

farEndReceiverFailure OBJECT-IDENTITY
    STATUS current
    DESCRIPTION
        "Global value of M.3100 probable cause error for use 
         with communicationsAlarm."
    REFERENCE
        "ITU-T Rec. M.3100 (1992) : farEndReceiverFailure"
    ::= { gnmProbableCause 4 }

framingErrorGnm OBJECT-IDENTITY
    STATUS current
    DESCRIPTION
        "Global value of M.3100 probable cause error for use 
         with communicationsAlarm.  The original name conflicts 
         with the ITU-T Rec. X.721 probable cause of the same 
         name."
    REFERENCE
        "ITU-T Rec. M.3100 (1992) : framingError"
    ::= { gnmProbableCause 5 }

lossOfFrameGnm OBJECT-IDENTITY
    STATUS current
    DESCRIPTION
        "Global value of M.3100 probable cause error for use 
         with communicationsAlarm.  The original name conflicts 
         with the ITU-T Rec. X.721 probable cause of the same 
         name."
    REFERENCE
        "ITU-T Rec. M.3100 (1992) : lossOfFrame"
    ::= { gnmProbableCause 6 }

lossOfPointer OBJECT-IDENTITY
    STATUS current
    DESCRIPTION
        "Global value of M.3100 probable cause error for use 
         with communicationsAlarm."
    REFERENCE
        "ITU-T Rec. M.3100 (1992) : lossOfPointer"
    ::= { gnmProbableCause 7 }

lossOfSignalGnm OBJECT-IDENTITY
    STATUS current
    DESCRIPTION
        "Global value of M.3100 probable cause error for use 
         with communicationsAlarm.  The original name conflicts 
         with the ITU-T Rec. X.721 probable cause of the same 
         name."
    REFERENCE
        "ITU-T Rec. M.3100 (1992) : lossOfSignal"
    ::= { gnmProbableCause 8 }

payloadTypeMismatch OBJECT-IDENTITY
    STATUS current
    DESCRIPTION
        "Global value of M.3100 probable cause error for use 
         with communicationsAlarm."
    REFERENCE
        "ITU-T Rec. M.3100 (1992) : payloadTypeMismatch"
    ::= { gnmProbableCause 9 }

transmissionError OBJECT-IDENTITY
    STATUS current
    DESCRIPTION
        "Global value of M.3100 probable cause error for use 
         with communicationsAlarm."
    REFERENCE
        "ITU-T Rec. M.3100 (1992) : transmissionError"
    ::= { gnmProbableCause 10 }

remoteAlarmInterface OBJECT-IDENTITY
    STATUS current
    DESCRIPTION
        "Global value of M.3100 probable cause error for use 
         with communicationsAlarm."
    REFERENCE
        "ITU-T Rec. M.3100 (1992) : remoteAlarmInterface"
    ::= { gnmProbableCause 11 }

excessiveBER OBJECT-IDENTITY
    STATUS current
    DESCRIPTION
        "Global value of M.3100 probable cause error for use 
         with communicationsAlarm."
    REFERENCE
        "ITU-T Rec. M.3100 (1992) : excessiveBER"
    ::= { gnmProbableCause 12 }

pathTraceMismatch OBJECT-IDENTITY
    STATUS current
    DESCRIPTION
        "Global value of M.3100 probable cause error for use 
         with communicationsAlarm."
    REFERENCE
        "ITU-T Rec. M.3100 (1992) : pathTraceMismatch"
    ::= { gnmProbableCause 13 }

unavailable OBJECT-IDENTITY
    STATUS current
    DESCRIPTION
        "Global value of M.3100 probable cause error for use 
         with communicationsAlarm."
    REFERENCE
        "ITU-T Rec. M.3100 (1992) : unavailable"
    ::= { gnmProbableCause 14 }

signalLabelMismatch OBJECT-IDENTITY
    STATUS current
    DESCRIPTION
        "Global value of M.3100 probable cause error for use 
         with communicationsAlarm."
    REFERENCE
        "ITU-T Rec. M.3100 (1992) : signalLabelMismatch"
    ::= { gnmProbableCause 15 }

lossOfMultiFrame OBJECT-IDENTITY
    STATUS current
    DESCRIPTION
        "Global value of M.3100 probable cause error for use 
         with communicationsAlarm."
    REFERENCE
        "ITU-T Rec. M.3100 (1992) : lossOfMultiFrame"
    ::= { gnmProbableCause 16 }

backplaneFailure OBJECT-IDENTITY
    STATUS current
    DESCRIPTION
        "Global value of M.3100 probable cause error for use 
         with equipmentAlarm."
    REFERENCE
        "ITU-T Rec. M.3100 (1992) : backplaneFailure"
    ::= { gnmProbableCause 51 }

dataSetProblem OBJECT-IDENTITY
    STATUS current
    DESCRIPTION
        "Global value of M.3100 probable cause error for use 
         with equipmentAlarm."
    REFERENCE
        "ITU-T Rec. M.3100 (1992) : dataSetProblem"
    ::= { gnmProbableCause 52 }

equipmentIdentifierDuplication OBJECT-IDENTITY
    STATUS current
    DESCRIPTION
        "Global value of M.3100 probable cause error for use 
         with equipmentAlarm."
    REFERENCE
        "ITU-T Rec. M.3100 (1992) 
               : equipmentIdentifierDuplication"
    ::= { gnmProbableCause 53 }

externalIFDeviceProblem OBJECT-IDENTITY
    STATUS current
    DESCRIPTION
        "Global value of M.3100 probable cause error for use 
         with equipmentAlarm."
    REFERENCE
        "ITU-T Rec. M.3100 (1992) : externalIFDeviceProblem"
    ::= { gnmProbableCause 54 }

lineCardProblem OBJECT-IDENTITY
    STATUS current
    DESCRIPTION
        "Global value of M.3100 probable cause error for use 
         with equipmentAlarm."
    REFERENCE
        "ITU-T Rec. M.3100 (1992) : lineCardProblem"
    ::= { gnmProbableCause 55 }

multiplexerProblemGnm OBJECT-IDENTITY
    STATUS current
    DESCRIPTION
        "Global value of M.3100 probable cause error for use 
         with equipmentAlarm.  The original name conflicts with 
         the ITU-T Rec. X.721 probable cause of the same name."
    REFERENCE
        "ITU-T Rec. M.3100 (1992) : multiplexerProblem"
    ::= { gnmProbableCause 56 }

nEIdentifierDuplication OBJECT-IDENTITY
    STATUS current
    DESCRIPTION
        "Global value of M.3100 probable cause error for use 
         with equipmentAlarm."
    REFERENCE
        "ITU-T Rec. M.3100 (1992) : nEIdentifierDuplication"
    ::= { gnmProbableCause 57 }

powerProblemGnm OBJECT-IDENTITY
    STATUS current
    DESCRIPTION
        "Global value of M.3100 probable cause error for use 
         with equipmentAlarm.  The original name conflicts with 
         the ITU-T Rec. X.721 probable cause of the same name."
    REFERENCE
        "ITU-T Rec. M.3100 (1992) : powerProblem"
    ::= { gnmProbableCause 58 }

processorProblemGnm OBJECT-IDENTITY
    STATUS current
    DESCRIPTION
        "Global value of M.3100 probable cause error for use 
         with equipmentAlarm.  The original name conflicts with 
         the ITU-T Rec. X.721 probable cause of the same name."
    REFERENCE
        "ITU-T Rec. M.3100 (1992) : processorProblem"
    ::= { gnmProbableCause 59 }

protectionPathFailure OBJECT-IDENTITY
    STATUS current
    DESCRIPTION
        "Global value of M.3100 probable cause error for use 
         with equipmentAlarm."
    REFERENCE
        "ITU-T Rec. M.3100 (1992) : protectionPathFailure"
    ::= { gnmProbableCause 60 }

receiverFailureGnm OBJECT-IDENTITY
    STATUS current
    DESCRIPTION
        "Global value of M.3100 probable cause error for use 
         with equipmentAlarm.  The original name conflicts with 
         the ITU-T Rec. X.721 probable cause of the same name."
    REFERENCE
        "ITU-T Rec. M.3100 (1992) : receiverFailure"
    ::= { gnmProbableCause 61 }

replaceableUnitMissing OBJECT-IDENTITY
    STATUS current
    DESCRIPTION
        "Global value of M.3100 probable cause error for use 
         with equipmentAlarm."
    REFERENCE
        "ITU-T Rec. M.3100 (1992) : replaceableUnitMissing"
    ::= { gnmProbableCause 62 }

replaceableUnitTypeMismatch OBJECT-IDENTITY
    STATUS current
    DESCRIPTION
        "Global value of M.3100 probable cause error for use 
         with equipmentAlarm."
    REFERENCE
        "ITU-T Rec. M.3100 (1992) : replaceableUnitTypeMismatch"
    ::= { gnmProbableCause 63 }

synchronizationSourceMismatch OBJECT-IDENTITY
    STATUS current
    DESCRIPTION
        "Global value of M.3100 probable cause error for use 
         with equipmentAlarm."
    REFERENCE
        "ITU-T Rec. M.3100 (1992) 
               : synchronizationSourceMismatch"
    ::= { gnmProbableCause 64 }

terminalProblem OBJECT-IDENTITY
    STATUS current
    DESCRIPTION
        "Global value of M.3100 probable cause error for use 
         with equipmentAlarm."
    REFERENCE
        "ITU-T Rec. M.3100 (1992) : terminalProblem"
    ::= { gnmProbableCause 65 }

timingProblemGnm OBJECT-IDENTITY
    STATUS current
    DESCRIPTION
        "Global value of M.3100 probable cause error for use 
         with equipmentAlarm.  The original name conflicts with 
         the ITU-T Rec. X.721 probable cause of the same name."
    REFERENCE
        "ITU-T Rec. M.3100 (1992) : timingProblem"
    ::= { gnmProbableCause 66 }

transmitterFailureGnm OBJECT-IDENTITY
    STATUS current
    DESCRIPTION
        "Global value of M.3100 probable cause error for use 
         with equipmentAlarm.  The original name conflicts with 
         the ITU-T Rec. X.721 probable cause of the same name."
    REFERENCE
        "ITU-T Rec. M.3100 (1992) : transmitterFailure"
    ::= { gnmProbableCause 67 }

trunkCardProblem OBJECT-IDENTITY
    STATUS current
    DESCRIPTION
        "Global value of M.3100 probable cause error for use 
         with equipmentAlarm."
    REFERENCE
        "ITU-T Rec. M.3100 (1992) : trunkCardProblem"
    ::= { gnmProbableCause 68 }

replaceableUnitProblem OBJECT-IDENTITY
    STATUS current
    DESCRIPTION
        "Global value of M.3100 probable cause error for use 
         with equipmentAlarm."
    REFERENCE
        "ITU-T Rec. M.3100 (1992) : replaceableUnitProblem"
    ::= { gnmProbableCause 69 }

airCompressorFailure OBJECT-IDENTITY
    STATUS current
    DESCRIPTION
        "Global value of M.3100 probable cause error for use 
         with environmentalAlarm."
    REFERENCE
        "ITU-T Rec. M.3100 (1992) : airCompressorFailure"
    ::= { gnmProbableCause 101 }

airConditioningFailure OBJECT-IDENTITY
    STATUS current
    DESCRIPTION
        "Global value of M.3100 probable cause error for use 
         with environmentalAlarm."
    REFERENCE
        "ITU-T Rec. M.3100 (1992) : airConditioningFailure"
    ::= { gnmProbableCause 102 }

airDryerFailure OBJECT-IDENTITY
    STATUS current
    DESCRIPTION
        "Global value of M.3100 probable cause error for use 
         with environmentalAlarm."
    REFERENCE
        "ITU-T Rec. M.3100 (1992) : airDryerFailure"
    ::= { gnmProbableCause 103 }

batteryDischarging OBJECT-IDENTITY
    STATUS current
    DESCRIPTION
        "Global value of M.3100 probable cause error for use 
         with environmentalAlarm."
    REFERENCE
        "ITU-T Rec. M.3100 (1992) : batteryDischarging"
    ::= { gnmProbableCause 104 }

batteryFailure OBJECT-IDENTITY
    STATUS current
    DESCRIPTION
        "Global value of M.3100 probable cause error for use 
         with environmentalAlarm."
    REFERENCE
        "ITU-T Rec. M.3100 (1992) : batteryFailure"
    ::= { gnmProbableCause 105 }

commercialPowerFailure OBJECT-IDENTITY
    STATUS current
    DESCRIPTION
        "Global value of M.3100 probable cause error for use 
         with environmentalAlarm."
    REFERENCE
        "ITU-T Rec. M.3100 (1992) : commercialPowerFailure"
    ::= { gnmProbableCause 106 }

coolingFanFailure OBJECT-IDENTITY
    STATUS current
    DESCRIPTION
        "Global value of M.3100 probable cause error for use 
         with environmentalAlarm."
    REFERENCE
        "ITU-T Rec. M.3100 (1992) : coolingFanFailure"
    ::= { gnmProbableCause 107 }

engineFailure OBJECT-IDENTITY
    STATUS current
    DESCRIPTION
        "Global value of M.3100 probable cause error for use 
         with environmentalAlarm."
    REFERENCE
        "ITU-T Rec. M.3100 (1992) : engineFailure"
    ::= { gnmProbableCause 108 }

fireDetectorFailure OBJECT-IDENTITY
    STATUS current
    DESCRIPTION
        "Global value of M.3100 probable cause error for use 
         with environmentalAlarm."
    REFERENCE
        "ITU-T Rec. M.3100 (1992) : fireDetectorFailure"
    ::= { gnmProbableCause 109 }

fuseFailure OBJECT-IDENTITY
    STATUS current
    DESCRIPTION
        "Global value of M.3100 probable cause error for use 
         with environmentalAlarm."
    REFERENCE
        "ITU-T Rec. M.3100 (1992) : fuseFailure"
    ::= { gnmProbableCause 110 }

generatorFailure OBJECT-IDENTITY
    STATUS current
    DESCRIPTION
        "Global value of M.3100 probable cause error for use 
         with environmentalAlarm."
    REFERENCE
        "ITU-T Rec. M.3100 (1992) : generatorFailure"
    ::= { gnmProbableCause 111 }

lowBatteryThreshold OBJECT-IDENTITY
    STATUS current
    DESCRIPTION
        "Global value of M.3100 probable cause error for use 
         with environmentalAlarm."
    REFERENCE
        "ITU-T Rec. M.3100 (1992) : lowBatteryThreshold"
    ::= { gnmProbableCause 112 }

pumpFailureGnm OBJECT-IDENTITY
    STATUS current
    DESCRIPTION
        "Global value of M.3100 probable cause error for use 
         with environmentalAlarm.  The original name conflicts 
         with the ITU-T Rec. X.721 probable cause of the same 
         name."
    REFERENCE
        "ITU-T Rec. M.3100 (1992) : pumpFailure"
    ::= { gnmProbableCause 113 }

rectifierFailure OBJECT-IDENTITY
    STATUS current
    DESCRIPTION
        "Global value of M.3100 probable cause error for use 
         with environmentalAlarm."
    REFERENCE
        "ITU-T Rec. M.3100 (1992) : rectifierFailure"
    ::= { gnmProbableCause 114 }

rectifierHighVoltage OBJECT-IDENTITY
    STATUS current
    DESCRIPTION
        "Global value of M.3100 probable cause error for use 
         with environmentalAlarm."
    REFERENCE
        "ITU-T Rec. M.3100 (1992) : rectifierHighVoltage"
    ::= { gnmProbableCause 115 }

rectifierLowVoltage OBJECT-IDENTITY
    STATUS current
    DESCRIPTION
        "Global value of M.3100 probable cause error for use 
         with environmentalAlarm."
    REFERENCE
        "ITU-T Rec. M.3100 (1992) : rectifierLowVoltage"
    ::= { gnmProbableCause 116 }

ventilationsSystemFailure OBJECT-IDENTITY
    STATUS current
    DESCRIPTION
        "Global value of M.3100 probable cause error for use 
         with environmentalAlarm."
    REFERENCE
        "ITU-T Rec. M.3100 (1992) : ventilationsSystemFailure"
    ::= { gnmProbableCause 117 }

enclosureDoorOpenGnm OBJECT-IDENTITY
    STATUS current
    DESCRIPTION
        "Global value of M.3100 probable cause error for use 
         with environmentalAlarm.  The original name conflicts 
         with the ITU-T Rec. X.721 probable cause of the same 
         name."
    REFERENCE
        "ITU-T Rec. M.3100 (1992) : enclosureDoorOpen"
    ::= { gnmProbableCause 118 }

explosiveGas OBJECT-IDENTITY
    STATUS current
    DESCRIPTION
        "Global value of M.3100 probable cause error for use 
         with environmentalAlarm."
    REFERENCE
        "ITU-T Rec. M.3100 (1992) : explosiveGas"
    ::= { gnmProbableCause 119 }

fire OBJECT-IDENTITY
    STATUS current
    DESCRIPTION
        "Global value of M.3100 probable cause error for use 
         with environmentalAlarm."
    REFERENCE
        "ITU-T Rec. M.3100 (1992) : fire"
    ::= { gnmProbableCause 120 }

flood OBJECT-IDENTITY
    STATUS current
    DESCRIPTION
        "Global value of M.3100 probable cause error for use 
         with environmentalAlarm."
    REFERENCE
        "ITU-T Rec. M.3100 (1992) : flood"
    ::= { gnmProbableCause 121 }

highHumidity OBJECT-IDENTITY
    STATUS current
    DESCRIPTION
        "Global value of M.3100 probable cause error for use 
         with environmentalAlarm."
    REFERENCE
        "ITU-T Rec. M.3100 (1992) : highHumidity"
    ::= { gnmProbableCause 122 }

highTemperature OBJECT-IDENTITY
    STATUS current
    DESCRIPTION
        "Global value of M.3100 probable cause error for use 
         with environmentalAlarm."
    REFERENCE
        "ITU-T Rec. M.3100 (1992) : highTemperature"
    ::= { gnmProbableCause 123 }

highWind OBJECT-IDENTITY
    STATUS current
    DESCRIPTION
        "Global value of M.3100 probable cause error for use 
         with environmentalAlarm."
    REFERENCE
        "ITU-T Rec. M.3100 (1992) : highWind"
    ::= { gnmProbableCause 124 }

iceBuildUp OBJECT-IDENTITY
    STATUS current
    DESCRIPTION
        "Global value of M.3100 probable cause error for use 
         with environmentalAlarm."
    REFERENCE
        "ITU-T Rec. M.3100 (1992) : iceBuildUp"
    ::= { gnmProbableCause 125 }

intrusionDetectionGnm OBJECT-IDENTITY
    STATUS current
    DESCRIPTION
        "Global value of M.3100 probable cause error for use 
         with environmentalAlarm.  The original name conflicts 
         with the ITU-T Rec. X.721 probable cause of the same 
         name."
    REFERENCE
        "ITU-T Rec. M.3100 (1992) : intrusionDetection"
    ::= { gnmProbableCause 126 }

lowFuel OBJECT-IDENTITY
    STATUS current
    DESCRIPTION
        "Global value of M.3100 probable cause error for use 
         with environmentalAlarm."
    REFERENCE
        "ITU-T Rec. M.3100 (1992) : lowFuel"
    ::= { gnmProbableCause 127 }

lowHumidity OBJECT-IDENTITY
    STATUS current
    DESCRIPTION
        "Global value of M.3100 probable cause error for use 
         with environmentalAlarm."
    REFERENCE
        "ITU-T Rec. M.3100 (1992) : lowHumidity"
    ::= { gnmProbableCause 128 }

lowCablePressure OBJECT-IDENTITY
    STATUS current
    DESCRIPTION
        "Global value of M.3100 probable cause error for use 
         with environmentalAlarm."
    REFERENCE
        "ITU-T Rec. M.3100 (1992) : lowCablePressure"
    ::= { gnmProbableCause 129 }

lowTemperature OBJECT-IDENTITY
    STATUS current
    DESCRIPTION
        "Global value of M.3100 probable cause error for use 
         with environmentalAlarm."
    REFERENCE
        "ITU-T Rec. M.3100 (1992) : lowTemperature"
    ::= { gnmProbableCause 130 }

lowWater OBJECT-IDENTITY
    STATUS current
    DESCRIPTION
        "Global value of M.3100 probable cause error for use 
         with environmentalAlarm."
    REFERENCE
        "ITU-T Rec. M.3100 (1992) : lowWater"
    ::= { gnmProbableCause 131 }

smoke OBJECT-IDENTITY
    STATUS current
    DESCRIPTION
        "Global value of M.3100 probable cause error for use 
         with environmentalAlarm."
    REFERENCE
        "ITU-T Rec. M.3100 (1992) : smoke"
    ::= { gnmProbableCause 132 }

toxicGas OBJECT-IDENTITY
    STATUS current
    DESCRIPTION
        "Global value of M.3100 probable cause error for use 
         with environmentalAlarm."
    REFERENCE
        "ITU-T Rec. M.3100 (1992) : toxicGas"
    ::= { gnmProbableCause 133 }

storageCapacityProblemGnm OBJECT-IDENTITY
    STATUS current
    DESCRIPTION
        "Global value of M.3100 probable cause error for use 
         with processingErrorAlarm.  The original name conflicts 
         with the ITU-T Rec. X.721 probable cause of the same 
         name."
    REFERENCE
        "ITU-T Rec. M.3100 (1992) : storageCapacityProblem"
    ::= { gnmProbableCause 151 }

memoryMismatchGnm OBJECT-IDENTITY
    STATUS current
    DESCRIPTION
        "Global value of M.3100 probable cause error for use 
         with processingErrorAlarm.  The original name conflicts 
         with the ITU-T Rec. X.721 probable cause of the same 
         name."
    REFERENCE
        "ITU-T Rec. M.3100 (1992) : memoryMismatch"
    ::= { gnmProbableCause 152 }

corruptDataGnm OBJECT-IDENTITY
    STATUS current
    DESCRIPTION
        "Global value of M.3100 probable cause error for use 
         with processingErrorAlarm.  The original name conflicts 
         with the ITU-T Rec. X.721 probable cause of the same 
         name."
    REFERENCE
        "ITU-T Rec. M.3100 (1992) : corruptData"
    ::= { gnmProbableCause 153 }

outOfCPUCycles OBJECT-IDENTITY
    STATUS current
    DESCRIPTION
        "Global value of M.3100 probable cause error for use 
         with processingErrorAlarm."
    REFERENCE
        "ITU-T Rec. M.3100 (1992) : outOfCPUCycles"
    ::= { gnmProbableCause 154 }

sfwrEnvironmentProblem OBJECT-IDENTITY
    STATUS current
    DESCRIPTION
        "Global value of M.3100 probable cause error for use 
         with processingErrorAlarm."
    REFERENCE
        "ITU-T Rec. M.3100 (1992) : sfwrEnvironmentProblem"
    ::= { gnmProbableCause 155 }

sfwrDownloadFailure OBJECT-IDENTITY
    STATUS current
    DESCRIPTION
        "Global value of M.3100 probable cause error for use 
         with processingErrorAlarm."
    REFERENCE
        "ITU-T Rec. M.3100 (1992) : sfwrDownloadFailure"
    ::= { gnmProbableCause 156 }

smiGroups OBJECT IDENTIFIER
    ::= { smiMIB 5 }

attributeValueChange NOTIFICATION-TYPE
    OBJECTS     { 
        tmnObjectInstance, tmnAttributeValueChangeDefinition }
    STATUS current
    DESCRIPTION
        "This notification type is used to report changes to the 
         attribute such as addition or deletion of members to 
         one or more set valued attributes, replacement of the 
         value of one or more attributes and setting attribute 
         values to their defaults.
         
         The attribute value changes specification in TMN is 
         a complicated thing.  Here it is required that the 
         issuer of the notification include the attributes whose 
         values have changed, first the attribute with the old 
         value and next the attribute with the new value for 
         each attribute reported."
    REFERENCE
        "ITU-T Rec. X.721 (1992) | ISO/IEC 10165-2 : 1992 
               attributeValueChange NOTIFICATION."
    ::= { smiNotifications 1 }

communicationsAlarm NOTIFICATION-TYPE
    OBJECTS     { 
        tmnObjectInstance, tmnProbableCause, 
        tmnPerceivedSeverity }
    STATUS current
    DESCRIPTION
        "This notification type is used to report when the 
         object detects a communications error.
         
         This is one of two mechanisms of providing 
         communications alarms corresponding to TMN alarms.  One 
         method is to provide a single notification which is 
         parameterized in a similar fashion to TMN.  The other 
         method is providing indepdendent notifications for each 
         cause.  The advantages of providing a single 
         notification for communications alarms is that the 
         management station need only monitor a single trap to 
         receive all alarm indications.  On a managed system 
         with thousands of unique alarms, this has scale 
         benefits.
         
         The communicationsAlarm is modelled on the TMN 
         notification of the same name.  TMN too has the ability 
         to provide independent notifications and chose 
         a similar unified alarm notification.
         
         The first parameter of the communicationsAlarm is the 
         probable cause, which is an object identifier defined 
         with the OBJECT-IDENTITY macro.  The probable cause 
         identifies the alarm.  The third parameter (second 
         object in SNMP) is the perceived severity.  Following 
         the PerceivedSeverity textual convention, this 
         parameter indicates when the alarm has onset or 
         cleared, and when indicating onset, the relative 
         severity in telecommunications terms (warning, minor, 
         major, critical).  The second parameter (optional 
         additional object in SNMP) is a sequence of specific 
         problems that refined the alarm indication.
         
         Because their values are defined by an OBJECT-IDENTITY 
         macro, the DESCRIPTION clause in that macro defining 
         a probable cause or specific problem should clearly 
         identify the purpose of the alarm, when it is 
         generated, when it is cleared, and how a specific 
         problem refines the probable cause.  This makes this 
         information available to managers via the MIB 
         generating the alarms.  Where a generic value is not 
         used, the probable cause and specific problems should 
         be defined within the MIB module that use them.
         
         State changes and attribute value changes can be 
         reported by simply including the object with the old 
         value and the object with the new value for each object 
         reported."
    REFERENCE
        "ITU-T Rec. X.721 (1992) | ISO/IEC 10165-2 : 1992 
               communicationsAlarm NOTIFICATION."
    ::= { smiNotifications 2 }

environmentalAlarm NOTIFICATION-TYPE
    OBJECTS     { 
        tmnObjectInstance, tmnProbableCause, 
        tmnPerceivedSeverity }
    STATUS current
    DESCRIPTION
        "This notification type is used to report a problem in 
         the environment.
         
         This is similar to the communicationsAlarm. The first 
         parameter is the probable cause which follows the 
         ProbableCause textual convention.  The second parameter 
         is the perceived severity which follows the 
         PerceivedSeverity textual convention.  Additional 
         specificProblems parameters may be added along with 
         other information.  See communicationsAlarm for more 
         information."
    REFERENCE
        "ITU-T Rec. X.721 (1992) | ISO/IEC 10165-2 : 1992 
               environmentalAlarm NOTIFICATION."
    ::= { smiNotifications 3 }

equipmentAlarm NOTIFICATION-TYPE
    OBJECTS     { 
        tmnObjectInstance, tmnProbableCause, 
        tmnPerceivedSeverity }
    STATUS current
    DESCRIPTION
        "This notification type is used to report a failure in 
         the equipment.
         
         This is similar to both the environmentalAlarm and the 
         communicationsAlarm.  The first parameter is the 
         probaable cause which follows the ProbableCause textual 
         convention.  The second parameter is the perceived 
         severity which follows the PerceivedSeverity textual 
         convention.  Additional SpecificProblems parameters may 
         be added along with other information.  See 
         communicationsAlarm for more information."
    REFERENCE
        "ITU-T Rec. X.721 (1992) | ISO/IEC 10165-2 : 1992 
               equipmentAlarm NOTIFICATION."
    ::= { smiNotifications 4 }

integrityViolation NOTIFICATION-TYPE
    OBJECTS     { 
        tmnObjectInstance, tmnSecurityAlarmCause, 
        tmnSecurityAlarmSeverity, tmnSecurityAlarmDetector, 
        tmnServiceUser, tmnServiceProvider }
    STATUS current
    DESCRIPTION
        "This notification is used to report that a potential 
         interruption in information flow has occurred such that 
         information may have been illegally modified, inserted 
         or deleted."
    REFERENCE
        "ITU-T Rec. X.721 (1992) | ISO/IEC 10165-2 : 1992 
               integrityViolation NOTIFICATION."
    ::= { smiNotifications 5 }

objectCreation NOTIFICATION-TYPE
    OBJECTS     { 
        tmnObjectInstance }
    STATUS current
    DESCRIPTION
        "This notification type is used to report the creation 
         of a managed object to another open system.
         
         Note that the reporting agent should include 
         a RowPointer identification of the object instance that 
         has been created."
    REFERENCE
        "ITU-T Rec. X.721 (1992) | ISO/IEC 10165-2 : 1992 
               objectCreation NOTIFICATION."
    ::= { smiNotifications 6 }

objectDeletion NOTIFICATION-TYPE
    OBJECTS     { 
        tmnObjectInstance }
    STATUS current
    DESCRIPTION
        "This notification type is used to report the deletion 
         of a managed object to another open system.
         
         Note that the reporting agent should include 
         a RowPointer identification and all the previous 
         attributes in the notification."
    REFERENCE
        "ITU-T Rec. X.721 (1992) | ISO/IEC 10165-2 : 1992 
               objectDeletion NOTIFICATION."
    ::= { smiNotifications 7 }

operationalViolation NOTIFICATION-TYPE
    OBJECTS     { 
        tmnObjectInstance, tmnSecurityAlarmCause, 
        tmnSecurityAlarmSeverity, tmnSecurityAlarmDetector, 
        tmnServiceUser, tmnServiceProvider }
    STATUS current
    DESCRIPTION
        "This notification is used to report that the provision 
         of the requested service was not possible due to the 
         unavailability, malfunction or incorrect invocation of 
         the service."
    REFERENCE
        "ITU-T Rec. X.721 (1992) | ISO/IEC 10165-2 : 1992 
               operationalViolation NOTIFICATION."
    ::= { smiNotifications 8 }

physicalViolation NOTIFICATION-TYPE
    OBJECTS     { 
        tmnObjectInstance, tmnSecurityAlarmCause, 
        tmnSecurityAlarmSeverity, tmnSecurityAlarmDetector, 
        tmnServiceUser, tmnServiceProvider }
    STATUS current
    DESCRIPTION
        "This notification is used to report that a physical 
         resource has been violated in a way that indicates 
         a potential security attack."
    REFERENCE
        "ITU-T Rec. X.721 (1992) | ISO/IEC 10165-2 : 1992 
               physicalViolation NOTIFICATION."
    ::= { smiNotifications 9 }

processingErrorAlarm NOTIFICATION-TYPE
    OBJECTS     { 
        tmnObjectInstance, tmnProbableCause, 
        tmnPerceivedSeverity }
    STATUS current
    DESCRIPTION
        "This notification type is used to report processing 
         failure in a managed object.
         
         The agent should include the identification of the row 
         or variable generating the alarm."
    REFERENCE
        "ITU-T Rec. X.721 (1992) | ISO/IEC 10165-2 : 1992 
               processingErrorAlarm NOTIFICATION."
    ::= { smiNotifications 10 }

qualityofServiceAlarm NOTIFICATION-TYPE
    OBJECTS     { 
        tmnObjectInstance, tmnProbableCause, 
        tmnPerceivedSeverity }
    STATUS current
    DESCRIPTION
        "This notification type is used to report a failure in 
         the quality of service of the managed object."
    REFERENCE
        "ITU-T Rec. X.721 (1992) | ISO/IEC 10165-2 : 1992 
               qualityofServiceAlarm NOTIFICATION."
    ::= { smiNotifications 11 }

relationshipChange NOTIFICATION-TYPE
    OBJECTS     { 
        tmnObjectInstance, tmnRelationshipChangeDefinition }
    STATUS current
    DESCRIPTION
        "This notification type is used to report the change in 
         the value of one or more relationship attributes of 
         a managed object, that result through either internal 
         operation of the managed object or via management 
         operation."
    REFERENCE
        "ITU-T Rec. X.721 (1992) | ISO/IEC 10165-2 : 1992 
               relationshipChange NOTIFICATION."
    ::= { smiNotifications 12 }

securityServiceOrMechanismViolation NOTIFICATION-TYPE
    OBJECTS     { 
        tmnObjectInstance, tmnSecurityAlarmCause, 
        tmnSecurityAlarmSeverity, tmnSecurityAlarmDetector, 
        tmnServiceUser, tmnServiceProvider }
    STATUS current
    DESCRIPTION
        "This notification is used to report that a security 
         attack has been detected by a security service or 
         mechanism."
    REFERENCE
        "ITU-T Rec. X.721 (1992) | ISO/IEC 10165-2 : 1992 
               securityServiceOrMechanismViolation 
               NOTIFICATION."
    ::= { smiNotifications 13 }

stateChange NOTIFICATION-TYPE
    OBJECTS     { 
        tmnObjectInstance, tmnStateChangeDefinition }
    STATUS current
    DESCRIPTION
        "This notification type is used to report the change in 
         the value of one or more state attributes of a managed 
         object, that result through either internal operation 
         of the managed object or via management operation.
         
         The stateChangeDefinition in TMN is a complicated 
         thing.  Here the issuer of this norification should 
         include the old value of the attribute followed by the 
         new value of the attribute for each attribute 
         reported."
    REFERENCE
        "ITU-T Rec. X.721 (1992) | ISO/IEC 10165-2 : 1992 
               stateChange NOTIFICATION."
    ::= { smiNotifications 14 }

timeDomainViolation NOTIFICATION-TYPE
    OBJECTS     { 
        tmnObjectInstance, tmnSecurityAlarmCause, 
        tmnSecurityAlarmSeverity, tmnSecurityAlarmDetector, 
        tmnServiceUser, tmnServiceProvider }
    STATUS current
    DESCRIPTION
        "This notification is used to report that an event has 
         occurred at an unexpected or prohibited time."
    REFERENCE
        "ITU-T Rec. X.721 (1992) | ISO/IEC 10165-2 : 1992 
               timeDomainViolation NOTIFICATION."
    ::= { smiNotifications 15 }

communicationsInformation NOTIFICATION-TYPE
    OBJECTS     { 
        tmnObjectInstance, tmnInformationType }
    STATUS current
    DESCRIPTION
        "This notification may be used to report the occurrence 
         of events pertaining to the normal operation of 
         a managed object.  These are informational events; 
         important enough to report, but not requiring any 
         further action by a manager.  Faults and abnormal 
         conditions (which may require manager action) shall be 
         reported using the event types defined in CCITT Rec.  
         X.733 (1992) | ISO/IEC 10164-4:1992.
         
         The communicationsInformation notification is modelled 
         on the TMN notification of the same name.
         
         The first paraemter of the communicationInformation 
         notification is the information type, which is an 
         object identifier defined with the OBJECT-IDENTITY 
         macro.  The information type identifies the event.
         
         Beacuse its value is defined by an OBJECT-IDENTITY 
         macro, the DESCRIPTION clause in that macro defining an 
         information type should clearly identify the purpose of 
         the event notification, when it is geenrtated, ahd how 
         any information data refines the information type.  
         This makes this information available to managers via 
         the MIB generating the alarms.  When a generic value is 
         not used, the information type should be defined within 
         the MIB module that issues them."
    REFERENCE
        "ITU-T Recommendation X.723 (1993) | ISO/IEC 10165-5 
               : 1993, communicationInformation"
    ::= { smiNotifications 16 }

smiMandatoryParametersGroup OBJECT-GROUP
    OBJECTS     { 
        tmnObjectInstance, tmnNotificationIdentifier, 
        tmnCorrelatedNotifications, tmnProbableCause, 
        tmnSpecificProblems, tmnPerceivedSeverity, 
        tmnBackedUpStatus, tmnBackUpObject, tmnTrendIndication, 
        tmnThresholdInfo, tmnStateChangeDefinition, 
        tmnMonitoredAttributes, tmnProposedRepairActions, 
        tmnSourceIndicator, tmnAttributeIdentifierList, 
        tmnAttributeValueChangeDefinition, tmnAdditionalText, 
        tmnAdditionalInformation }
    STATUS current
    DESCRIPTION
        "A collection of mandatory notification parameters."
    ::= { smiGroups 1 }

smiConditionalParametersGroup OBJECT-GROUP
    OBJECTS     { 
        tmnSecurityAlarmCause, tmnSecurityAlarmSeverity, 
        tmnSecurityAlarmDetector, tmnServiceUser, 
        tmnServiceProvider, tmnAttributeList, 
        tmnRelationshipChangeDefinition }
    STATUS current
    DESCRIPTION
        "A collection of conditional notification parameters."
    ::= { smiGroups 2 }

smiOptionalParametersGroup OBJECT-GROUP
    OBJECTS     { 
        tmnInformationType, tmnInformationData }
    STATUS current
    DESCRIPTION
        "A collection of optional notification parameters."
    ::= { smiGroups 3 }

smiMandatoryNotificationsGroup NOTIFICATION-GROUP
    NOTIFICATIONS { attributeValueChange, communicationsAlarm, 
                  objectCreation, objectDeletion, 
                  processingErrorAlarm, qualityofServiceAlarm, 
                  relationshipChange, stateChange }
    STATUS current
    DESCRIPTION
        "A collection of mandatory notifications."
    ::= { smiGroups 4 }

smiConditionalNotificationsGroup NOTIFICATION-GROUP
    NOTIFICATIONS { environmentalAlarm, equipmentAlarm, 
                  integrityViolation, operationalViolation, 
                  physicalViolation, 
                  securityServiceOrMechanismViolation, 
                  timeDomainViolation }
    STATUS current
    DESCRIPTION
        "A collection of conditional notifications."
    ::= { smiGroups 5 }

smiOptionalNotificationsGroup NOTIFICATION-GROUP
    NOTIFICATIONS { communicationsInformation }
    STATUS current
    DESCRIPTION
        "A collection of optional notifications."
    ::= { smiGroups 6 }

smiDiscriminatorGroup OBJECT-GROUP
    OBJECTS     { 
        discriminatorConstruct, 
        discriminatorAdministrativeState, 
        discriminatorOperationalState, 
        discriminatorAvailabilityStatus, discriminatorStartTime, 
        discriminatorStopTime, discriminatorIntervalsOfDay, 
        discriminatorWeekMask, discriminatorSchedulerName, 
        discriminatorEntryStatus }
    STATUS current
    DESCRIPTION
        "Objects required to implement the discriminatorTable."
    ::= { smiGroups 10 }

smiEventForwardingDiscriminatorGroup OBJECT-GROUP
    OBJECTS     { 
        destination, activeDestination, backUpDestinationList, 
        confirmedMode, eventForwardingDiscriminatorEntryStatus }
    STATUS current
    DESCRIPTION
        "Objects required to implement the 
         eventForwardingDiscriminatorTable."
    ::= { smiGroups 11 }

smiLogGroup OBJECT-GROUP
    OBJECTS     { 
        logDiscriminatorConstruct, logAdministrativeState, 
        logOperationalState, logAvailabilityStatus, 
        logFullAction, maxLogSize, currentLogSize, 
        numberOfRecords, capacityAlarmThreshold, logStartTime, 
        logStopTime, logIntervalsOfDay, logWeekMask, 
        logSchedulerName, logEntryStatus }
    STATUS current
    DESCRIPTION
        "Objects required to implement the logTable."
    ::= { smiGroups 12 }

smiLogRecordGroup OBJECT-GROUP
    OBJECTS     { 
        loggingTime, logRecordEntryStatus }
    STATUS current
    DESCRIPTION
        "Objects required to implement the logRecordTable."
    ::= { smiGroups 13 }

smiEventLogRecordGroup OBJECT-GROUP
    OBJECTS     { 
        managedObjectClass, managedObjectInstance, eventType, 
        eventTimes, eventNotificationIdentifier, 
        eventCorrelatedNotifications, eventAdditionalText, 
        eventAdditionalInformation }
    STATUS current
    DESCRIPTION
        "Objects required to implement the logRecordTable."
    ::= { smiGroups 14 }

smiAlarmRecordGroup OBJECT-GROUP
    OBJECTS     { 
        alarmRecordProbableCause, alarmRecordPerceivedSeverity, 
        alarmRecordSpecificProblems, alarmRecordBackedUpStatus, 
        alarmRecordBackUpObject, alarmRecordTrendIndication, 
        alarmRecordThresholdInfo, 
        alarmRecordStateChangeDefinition, 
        alarmRecordMonitoredAttributes, 
        alarmRecordProposedRepairActions }
    STATUS current
    DESCRIPTION
        "Objects required to implement the logRecordTable."
    ::= { smiGroups 15 }

smiAttributeValueChangeRecordGroup OBJECT-GROUP
    OBJECTS     { 
        attributeValueChangeRecordDefinition, 
        attributeValueChangeSourceIndicator, 
        attributeValueChangeAttributeIdentifierList }
    STATUS current
    DESCRIPTION
        "Objects required to implement the logRecordTable."
    ::= { smiGroups 16 }

smiObjectCreationRecordGroup OBJECT-GROUP
    OBJECTS     { 
        objectCreationSourceIndicator, 
        objectCreationAttributeIdentifierList }
    STATUS current
    DESCRIPTION
        "Objects required to implement the logRecordTable."
    ::= { smiGroups 17 }

smiObjectDeletionRecordGroup OBJECT-GROUP
    OBJECTS     { 
        objectDeletionSourceIndicator, 
        objectDeletionAttributeIdentifierList }
    STATUS current
    DESCRIPTION
        "Objects required to implement the logRecordTable."
    ::= { smiGroups 18 }

smiRelationshipChangeRecordGroup OBJECT-GROUP
    OBJECTS     { 
        relationshipChangeRecordDefinition, 
        relationshipChangeSourceIndicator, 
        relationshipChangeAttributeIdentifierList }
    STATUS current
    DESCRIPTION
        "Objects required to implement the logRecordTable."
    ::= { smiGroups 19 }

smiSecurityAlarmReportRecordGroup OBJECT-GROUP
    OBJECTS     { 
        securityAlarmRecordCause, securityAlarmRecordSeverity, 
        securityAlarmRecordDetector, securityServiceUser, 
        securityServiceProvider }
    STATUS current
    DESCRIPTION
        "Objects required to implement the logRecordTable."
    ::= { smiGroups 20 }

smiStateChangeRecordGroup OBJECT-GROUP
    OBJECTS     { 
        stateChangeRecordDefinition, stateChangeSourceIndicator, 
        stateChangeAttributeIdentifierList }
    STATUS current
    DESCRIPTION
        "Objects required to implement the logRecordTable."
    ::= { smiGroups 21 }

createDeleteNotificationsPackage NOTIFICATION-GROUP
    NOTIFICATIONS { objectCreation, objectDeletion }
    STATUS current
    DESCRIPTION
        "A collection of notifications for object createion and 
         deleteion."
    ::= { smiGroups 22 }

attributeValueChangeNotificationPackage NOTIFICATION-GROUP
    NOTIFICATIONS { attributeValueChange }
    STATUS current
    DESCRIPTION
        "A collection of notifications for attribute value 
         changes."
    ::= { smiGroups 23 }

communicationsAlarmPackage NOTIFICATION-GROUP
    NOTIFICATIONS { communicationsAlarm }
    STATUS current
    DESCRIPTION
        "A collection of notifications for communications 
         alarms."
    REFERENCE
        "ITU-T Rec. Q.751.1 (1997), ANSI T1.116.1 (2000), 
               communicationsAlarmPackage ."
    ::= { smiGroups 24 }

smiCompliances OBJECT IDENTIFIER
    ::= { smiMIB 6 }

smiCompliance MODULE-COMPLIANCE
    STATUS current
    DESCRIPTION
        "Provides the module compliance requirements for the SMI 
         MIB."

    MODULE -- this module

        MANDATORY-GROUPS { 
            smiMandatoryParametersGroup, 
            smiMandatoryNotificationsGroup, 
            smiDiscriminatorGroup, smiLogGroup, 
            smiLogRecordGroup }

        GROUP smiConditionalParametersGroup
        DESCRIPTION
              "Conditional items when some alarms are 
               implemented."

        GROUP smiConditionalNotificationsGroup
        DESCRIPTION
              "Conditional items when some alarms are 
               implemented."

        GROUP smiEventForwardingDiscriminatorGroup
        DESCRIPTION
              "Conditional items when some alarms are 
               implemented."

        GROUP smiOptionalParametersGroup
        DESCRIPTION
              "Optional iterms when some alarms are implemented 
               and logged."

        GROUP smiOptionalNotificationsGroup
        DESCRIPTION
              "Optional iterms when some alarms are implemented 
               and logged."

        GROUP smiEventLogRecordGroup
        DESCRIPTION
              "Optional iterms when some alarms are implemented 
               and logged."

        GROUP smiAlarmRecordGroup
        DESCRIPTION
              "Optional iterms when some alarms are implemented 
               and logged."

        GROUP smiAttributeValueChangeRecordGroup
        DESCRIPTION
              "Optional iterms when some alarms are implemented 
               and logged."

        GROUP smiObjectCreationRecordGroup
        DESCRIPTION
              "Optional iterms when some alarms are implemented 
               and logged."

        GROUP smiObjectDeletionRecordGroup
        DESCRIPTION
              "Optional iterms when some alarms are implemented 
               and logged."

        GROUP smiRelationshipChangeRecordGroup
        DESCRIPTION
              "Optional iterms when some alarms are implemented 
               and logged."

        GROUP smiSecurityAlarmReportRecordGroup
        DESCRIPTION
              "Optional iterms when some alarms are implemented 
               and logged."

        GROUP smiStateChangeRecordGroup
        DESCRIPTION
              "Optional iterms when some alarms are implemented 
               and logged."

    ::= { smiCompliances 1 }

END -- end of module OPENSS7-SMI-MIB.

-- =============================================================================
-- vim: ft=mib comments=\f\b\:\"ITU\-T,\f\b\:ITU\-T,\f\:\",\b\:\-\-,\:\-\-,\f\b\:\- fo+=tcqlornw12 tw=64 ai nocin nosi sts=4 sw=4 et
