-- vim: ft=mib comments=\f\:\",\b\:\-\-,\:\-\-,\f\b\:- fo+=tcqlornw tw=72 nocin nosi sts=4 sw=4
-- =============================================================================
-- 
-- @(#) $RCSfile: OPENSS7-CDR2-MIB.mib,v $ $Name:  $($Revision: 0.9.2.7 $) $Date: 2009-01-10 17:09:24 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-10 17:09:24 $ by $Author: brian $
--
-- -----------------------------------------------------------------------------
--
-- $Log: OPENSS7-CDR2-MIB.mib,v $
-- Revision 0.9.2.7  2009-01-10 17:09:24  brian
-- - updated agents
--
-- Revision 0.9.2.6  2009-01-03 10:51:08  brian
-- - updated agent
--
-- Revision 0.9.2.5  2008-12-14 12:55:56  brian
-- - working up mibs
--
-- Revision 0.9.2.4  2008-04-29 07:11:21  brian
-- - updating headers for release
--
-- Revision 0.9.2.3  2008/01/24 17:40:55  brian
-- - updated mibs
--
-- Revision 0.9.2.2  2008/01/14 16:55:12  brian
-- - updated mibs
--
-- Revision 0.9.2.1  2008/01/13 00:12:53  brian
-- - added updated CDR mib
--
-- =============================================================================

OPENSS7-CDR2-MIB DEFINITIONS ::= BEGIN

IMPORTS
    openss7Q825
        FROM OPENSS7-SMI
    SimpleNameType, logId, logRecordId
        FROM OPENSS7-SMI-MIB
    NetworkPointCode
        FROM OPENSS7-SS7-MIB
    controlObjectId
        FROM OPENSS7-UMC-MIB
    MODULE-COMPLIANCE, NOTIFICATION-GROUP, OBJECT-GROUP
        FROM SNMPv2-CONF
    Counter64, Integer32, MODULE-IDENTITY, NOTIFICATION-TYPE, 
    OBJECT-TYPE, Opaque, Unsigned32
        FROM SNMPv2-SMI
    DisplayString, RowStatus, StorageType, TEXTUAL-CONVENTION, 
    TimeInterval, TruthValue
        FROM SNMPv2-TC;

cdr2MIB MODULE-IDENTITY
    LAST-UPDATED "200801110032Z"
    ORGANIZATION 
        "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         E-mail: bidulock@openss7.org"
    DESCRIPTION 
        "This is an enhanced MIB module providing definition of a wide 
         array of CDR data objects within the IUT-T Rec. Q.825 (1998) 
         Call Detail Recording framework."
    REVISION    "200801110032Z"
    DESCRIPTION 
        "First release of this module."
    ::= { openss7Q825 2 }


StartDateTime ::= TEXTUAL-CONVENTION
    DISPLAY-HINT "1x1x-1x-1x 1x:1x:1x.1x"
    STATUS      current
    DESCRIPTION 
        "The date and time coded YYYYMMDDHHmmSSCC (Year, Month, Day, 
         Hour, Minute, Second, Centisecond), each field one digit, two 
         digits per octet, the digits 0 through 9 encoded as '0000'B to 
         '1001'B, first digit in the most significant 4 bits."
    REFERENCE   
        "ITU-T Rec. Q.825, Q825-CDR-ASN1Module.StartDateTime."
    SYNTAX      OCTET STRING (SIZE(0 | 8))

Number ::= TEXTUAL-CONVENTION
    DISPLAY-HINT "1x:1x:3x-3x-4x"
    STATUS      current
    DESCRIPTION 
        "This type is used to represent a number for addressing 
         purposes. It is composed of:
         
         a) one octet for odd/even indicator and nature of address 
         indicator:
         
            bits 8: Odd/even indicator
             0 even number of address signals
             1 odd number of address signals
            bits 7654321: Nature of address indicator
             0000000 spare
             0000001 subscriber number
             0000010 unknown
             0000011 national (significant) number
             0000100 international number
             0000101 (
             to      ( spare
             1101111 (
             1110000 (
             to      ( reserved for national use
             1111110 (
             1111111 spare
         
         b) one octet for numbering plan indicator:
         
            bits 765: numbering plan indicator
             000 spare
             001 ISDN (Telephony) Number Plan (ITU-T Rec. 
         	 E.164)
             010 spare
             011 data numbering plan (ITU-T Rec. X.121)
             100 telex numbering plan (ITU-T Rec. F.69)
             101 reserved for national use
             110 reserved for national use
             111 spare
         
         c) digits of the address encoded as TBCD String:
             The following octets representing digits of an address 
             encoded as a TBCD-STRING.
         
             TBCD-STRING ::= OCTETSTRING
         
             This type (Telephony Binary Coded Decimal String) is used 
             to represent dig its from 0 through 9, *, #, a, b, c, two 
             digits per octet, each digit encoded 0000 to 1001 (0 to 9), 
             1010 (*) 1011(#), 1100 (a), 1101 (b) or 1110 (c); 1111 (end 
         	  of pulsing signal-ST); 0000 is used as a filler when 
         	  there is an odd number of digits.  The most 
         	  significant address signal is sent first. Subsequent 
         	  address signals are sent in successive 4-bit fields."
    REFERENCE   
        "ITU-T Rec. Q.825, Q825-CDR-ASN1Module.Number."
    SYNTAX      OCTET STRING (SIZE(1..15))

DialledDigits ::= TEXTUAL-CONVENTION
    STATUS      current
    DESCRIPTION 
        "This type is used to represent digits input by the subscriber.  
         It is composed of:
         
         a) one octet for odd/even indicator:
         
            bits 8: Odd/even indicator
         	0 even number of address signals
         	1 odd number of address signals
         
         b) digits of the address encoded as TBCD String
            The following octets representing the received digits 
            encoded as a TBCD-STRING.
         
            TBCD-STRING ::= OCTET STRING
         
            This type (Telephony Binary Coded Decimal String) is used to 
            represent digits from 0 through 9, *, #, a, b, c, two digits 
            per octet, each digit encoded 0000 to 1001 (0 to 9), 1010 
            (*), 1011(#), 1100 (a), 1101 (b) or 1110 (c); 1111 (end of 
            pulsing signal-ST); 0000 is used as a filler when there is 
            an odd number of digits.  The most significant address 
            signal is sent first. Subsequent address signals are sent in 
            successive 4-bit fields."
    REFERENCE   
        "ITU-T Rec. Q.825 (1998), 
         Q825-CDR-ASN1Module.ReceivedDigits."
    SYNTAX      OCTET STRING (SIZE(1..18))

BearerServiceCapability ::= TEXTUAL-CONVENTION
    STATUS      current
    DESCRIPTION 
        "The first octet in the string indicates the bearer service 
         capability as follows:
         
         - speech(0), speech;
         
         - audio3dot1kHZ(1), 3.1 kHz audio;
         
         - uni64(2), universal 64 kbps without inband tones and 
           announcements;
         
         - uni64withTA(3), universal 64 kbps with inband tones and 
           announcements;
         
         - multipleRate(4), multirate Nx64 kbpx where N(2..30) is in the 
           second octet;
         
         - packetModeBch(5), B-Channel packet mode.
         
         When the first octet is multipleRate(4), the second octet is 
         present and contains the multiplier (2..30) indicating the 
         number of channels.  Otherwise, the octet string must contain 
         only one octet or the second octet must be coded to one (1)."
    REFERENCE   
        "ITU-T Rec. Q.825, Q825-CDR-ASN1Module.BearerService."
    SYNTAX      OCTET STRING (SIZE(1..2))

ParticipantType ::= TEXTUAL-CONVENTION
    STATUS      current
    DESCRIPTION 
        "Provides a specification of a participant in the call by 
         identifying the number related to the particpant."
    REFERENCE   
        "ITU-T Rec. Q.825 (1998) Q825-CDR-ASN1Module ParticipantType."
    SYNTAX      INTEGER { callingPartyNumber(0), calledPartyNumber(1), 
                    redirectingNumber(2), redirectionNumber(3), 
                    originalCalledNumber(4), 
                    callingPartyNumberNotScreened(5), 
                    operatorSpecific1Number(6), 
                    operatorSpecific2Number(7), 
                    operatorSpecific3Number(8), operator(9), unknown(10) }

CauseAndLocation ::= TEXTUAL-CONVENTION
    DISPLAY-HINT "1x:1x"
    STATUS      current
    DESCRIPTION 
        "Specifies the Q.850 cause code which is a one-octet CauseValue 
         (0..255) and a one octet Location code where the location code 
         can have one of the following values:
         
         - user(0), error occured at the user;
         
         - localUserPrivateNetwork(1), error occured at the local user 
           of a private network;
         
         - localUserPublicNetwork(2), error occured at the local user of 
           a public network;
         
         - transitNetwork(3), error occured in a transit network;
         
         - remoteUserPublicNetwork(4), error occured at the remote user 
           of a private network;
         
         - remoteUsePrivateNetwork(5), error occured at the remote user 
           of a public network;
         
         - internationalNetwork(7), error occured in the international 
           network;
         
         - beyondInterworkPoint(10), error occured beyond an 
           interworking point."
    REFERENCE   
        "ITU-T Rec. Q.825, Q825-CDR-ASN1Module.Cause."
    SYNTAX      OCTET STRING (SIZE(2))

UserIdentifier ::= TEXTUAL-CONVENTION
    DISPLAY-HINT "1x:3x-3x-4x"
    STATUS      current
    DESCRIPTION 
        "This type is used to represent the Personal User Id.  For UMT 
         the Personal User Id is defined according to E.212 as an 
         International Mobile Station Identity (IMSI). Accordingly only 
         numerical characters (0-9) are used.
         
         The PersonalNumber type does however not exclude the use of 
         other formats. These formats can be indicated in the numbering 
         plan indicator.
         
         The type is composed of:
         
         a) one octet for odd/even indicator and numbering plan 
         indicator:
         
            bits 8: Odd/even indicator
             0 even number of address signals
             1 odd number of address signals
         
            bits 765: numbering plan indicator
             000 E.212 (IMSEI)
             001 ISDN (Telephony) Number Plan (ITU-T Rec. 
         	 E.164)
             010 spare
             011 spare
             100 spare
         
         b) digits of the address encoded as TBCD String:
            The following octets representing the personal number 
            encoded as a TBCD-STRING.
         
            TBCD-STRING ::= OCTET STRING
         
            This type (Telephony Binary Coded Decimal String) is used to 
            represent digits from 0 through 9, *, #, a, b, c, two digits 
            per octet, each digit encoded 0000 to 1001 (0 to 9), 1010 
            (*), 1011(#), 1100 (a), 1101 (b) or 1110 (c); 1111 (end of 
            pulsing signal-ST); 0000 is used as a filler when there is 
            an odd number of digits.  The most significant address 
            signal is sent first. Subsequent ad dress signals are sent 
            in successive 4-bit fields."
    SYNTAX      OCTET STRING (SIZE(1..10))

AccountCode ::= TEXTUAL-CONVENTION
    STATUS      current
    DESCRIPTION 
        "This type is used to represent information, which is provided 
         by the subscriber necessary for use by some services.
         
         a) bits 876: Encoding scheme
         
            000 BCD even (even number of digits)
            001 BCD odd (odd number of digits)
            010 IA5 character
            011 Binary coded
            100
            ... spare
            111
         
         b) bits 54321: Type of digits
         
            00000 reserved for account code
            00001 reserved for authorization code
            00010 reserved for private network travelling class mark
            00011 reserved for business communication
            00100
            ... spare for international use
            01111
            10000
            ... spare for national use
            11111
         
         c) Digits:
         
            Coding in accordance to the coding scheme and type of 
            digits."
    REFERENCE   
        "ITU-T Rec. Q.825 (1998), Q825-CDR-ASN1Module.AccountCode."
    SYNTAX      OCTET STRING (SIZE(1..18))

ChargingInformation ::= TEXTUAL-CONVENTION
    STATUS      current
    DESCRIPTION 
        "The first octet determines the contents of the remaining 
         octets.  The first octet may be one of:
         
         - recordedCurrency [0], remaining octets contain a 
           RecordedCurrency;
         
         - recordedUnitsList [1], remaining octets contain a 
           RecordedUnitsList;
         
         - freeOfCharge [2], there are no more octets;
         
         - changeInfoNotAvailable [3], there are no more octets."
    REFERENCE   
        "ITU-T Rec. Q.825 (1998), 
         Q825-CDR-ASN1Module.ChangingInformation."
    SYNTAX      OCTET STRING

ProgressAndLocation ::= TEXTUAL-CONVENTION
    STATUS      current
    DESCRIPTION 
        "Provides a specification of progress.
         
         The first octet contains the ProgressDescription that can be 
         one of the following values:
         
         - notEndToEndISDN(1),
         - nonISDNDestination(2),
         - nonISDNOrigination(3),
         - returnedToISDN(4),
         - interworkingServiceChange(5),
         - inBandInfo(8),
         
         The second onctet contains the Location that can be one of the 
         following values:
         
         - user(0),
         - localUserPrivateNetwork(1),
         - localUserPublicNetwork(2),
         - transitNetwork(3),
         - remoteUserPublicNetwork(4),
         - remoteUsePrivateNetwork(5),
         - internationalNetwork(7),
         - beyondInterworkPoint(10)."
    REFERENCE   
        "ITU-T Rec. Q.825 (1998), Q825-CDR-ASN1Module.Progress."
    SYNTAX      OCTET STRING (SIZE(2))

UserToUserInformation ::= TEXTUAL-CONVENTION
    STATUS      current
    DESCRIPTION 
        "The octet string is a group of 1..3 groups representing the 
         UUxInfo for group 1, 2 and/or 3.  Each group begins with a 
         group number octet (1..3) indicating the group and a length 
         octet (4..16) in multiples of 4 indicating the length of the 
         remaining fields in the group.  The group octet is intepreted 
         as follows:
         
         - uu1Info [0] UUxInfo OPTIONAL;
         - uu2Info [1] UUxInfo OPTIONAL;
         - uu3Info [2] UUxInfo OPTIONAL.
         
         The remaining fields in the group contsist of groupings of 4 
         octets, where the first octet in the group indicates the type 
         of count and the last three octets in the group indicate the 
         count.  The type of count octet is interpreted as follows:
         
         - receivedMessages [0] Count OPTIONAL;
         - transmittedMessages [1] Count OPTIONAL;
         - receivedOctets [2] Count OPTIONAL;
         - transmittedOctets [3] Count OPTIONAL."
    REFERENCE   
        "ITU-T Rec. Q.825 (1998), Q825-CDR-ASN1Module.UUInfo."
    SYNTAX      OCTET STRING (SIZE(0..54))

GeneralizedTime ::= TEXTUAL-CONVENTION
    STATUS      current
    DESCRIPTION 
        "Generalized machine local time zone time formatted as a visible 
         string as YYYYMMDDHHmmSSCC where each field is one IA5 
         character and Y = Year, M = Month, D = Day, H = Hour, m = 
         Minute, S = Second and C = Centisecond.  The centiseconds can 
         be skipped."
    SYNTAX      OCTET STRING (SIZE(0 | 14 | 16))

cdr2Notifications OBJECT IDENTIFIER
    ::= { cdr2MIB 0 }

cdr2Objects OBJECT IDENTIFIER
    ::= { cdr2MIB 1 }

cdr2Scalars OBJECT IDENTIFIER
    ::= { cdr2Objects 1 }

fileName OBJECT-TYPE
    SYNTAX      DisplayString (SIZE(1..128))
    MAX-ACCESS  accessible-for-notify
    STATUS      current
    DESCRIPTION 
        "Provides the file name of a generated file.  Used with the 
         fileCreationNotification INFORM message.
         
         Name of a file.  This should be the name of a file, possibly 
         including the complete path to the file on the managed system, 
         limited to 128 characters."
    REFERENCE   
        "ITU-T Rec. Q.825 (1998), 
         Q825-CDR-ASN1Module.FileName."
    ::= { cdr2Scalars 1 }

reasonForOutput OBJECT-TYPE
    SYNTAX      INTEGER { absoluteTimeEvent(0), maxBlockSizeReached(1), 
                    maxTimeIntervalElapsed(2), 
                    internalSizeLimitReached(3), oSAction(4) }
    MAX-ACCESS  accessible-for-notify
    STATUS      current
    DESCRIPTION 
        "Provides the reason for output for use with notifications.  
         This may be one of:
         
         - absoluteTimeEvent(0), file was generated because the rotation 
           time was reached;
         - maxBlockSizeReached(1), block was generated as a result of 
           the maximum block size being reached on a blockGeneratingLog;
         - maxTimeIntervalElapsed(2), block was generated as a result of 
           the maimum time interval elapsing on a blockGeneratingLog;
         - internalSizeLimitReached(3), block or file was generated as a 
           result of internal size limitations;
         - oSAction(4), block or file was generated at the request of 
           the operations management."
    REFERENCE   
        "ITU-T Rec. Q.825 (1998), Q825-CDR-ASN1Module.ReasonForOutput."
    ::= { cdr2Scalars 2 }

sequenceNumber OBJECT-TYPE
    SYNTAX      Integer32
    MAX-ACCESS  accessible-for-notify
    STATUS      current
    DESCRIPTION 
        "The sequence number of the record block."
    REFERENCE   
        "ITU-T Rec. Q.825 (1998), 
         Q825-CDR-ASN1Module.sequenceNumber."
    ::= { cdr2Scalars 3 }

callRecord OBJECT-TYPE
    SYNTAX      Opaque
    MAX-ACCESS  accessible-for-notify
    STATUS      current
    DESCRIPTION 
        "A packaged call record.  This is used to save varbind space.  
         The package is formatted as follows:
         
         callRecord ::= SEQUENCE {
             sequenceId          [  1] IMPLICIT INTEGER,
             zoneId              [  2] IMPLICIT INTEGER,
             recSeqId            [  3] IMPLICIT INTEGER,
             fileSeqId           [  4] IMPLICIT INTEGER,
             callId              [  5] IMPLICIT VisibleString,
             lastUpdate          [  6] IMPLICIT GeneralizedTime,
             eventOrder          [  7] IMPLICIT VisibleString,
             status              [  8] IMPLICIT INTEGER,
             callType            [  9] IMPLICIT INTEGER OPTIONAL,
             clngPtyNbr          [ 10] IMPLICIT VisibleString OPTIONAL,
             chargeNbr           [ 11] IMPLICIT VisibleString OPTIONAL,
             clldPtyNbr          [ 12] IMPLICIT VisibleString OPTIONAL,
             clldPtyNoa          [ 13] IMPLICIT INTEGER OPTIONAL,
             origLnInfo          [ 14] IMPLICIT VisibleString OPTIONAL,
             ingLrn              [ 15] IMPLICIT VisibleString OPTIONAL,
             ingCic              [ 16] IMPLICIT VisibleString OPTIONAL,
             ingCsi              [ 17] IMPLICIT INTEGER OPTIONAL,
             ingCceId            [ 18] IMPLICIT INTEGER OPTIONAL,
             ingTgProt           [ 19] IMPLICIT INTEGER OPTIONAL,
             ingTgType           [ 20] IMPLICIT INTEGER OPTIONAL,
             ingTgId             [ 21] IMPLICIT INTEGER OPTIONAL,
             ingCallStart        [ 22] IMPLICIT GeneralizedTime OPTIONAL,
             ingGateId           [ 23] IMPLICIT INTEGER OPTIONAL,
             ingCardId           [ 24] IMPLICIT INTEGER OPTIONAL,
             ingSpanId           [ 25] IMPLICIT INTEGER OPTIONAL,
             ingChanId           [ 26] IMPLICIT INTEGER OPTIONAL,
             ingIsdnDChan        [ 27] IMPLICIT INTEGER OPTIONAL,
             ingIsdnCrn          [ 28] IMPLICIT INTEGER OPTIONAL,
             ingCreatConnCplt    [ 29] IMPLICIT GeneralizedTime OPTIONAL,
             ingAddrCplt         [ 30] IMPLICIT GeneralizedTime OPTIONAL,
             ingCallAns          [ 31] IMPLICIT GeneralizedTime OPTIONAL,
             transNbr            [ 32] IMPLICIT VisibleString OPTIONAL,
             termLrn             [ 33] IMPLICIT VisibleString OPTIONAL,
             transCic            [ 34] IMPLICIT VisibleString OPTIONAL,
             ingCallRls          [ 35] IMPLICIT GeneralizedTime OPTIONAL,
             ingRlsCause         [ 36] IMPLICIT INTEGER OPTIONAL,
             egrCceId            [ 37] IMPLICIT INTEGER OPTIONAL,
             egrTgProt           [ 38] IMPLICIT INTEGER OPTIONAL,
             egrTgType           [ 39] IMPLICIT INTEGER OPTIONAL,
             egrTgId             [ 40] IMPLICIT INTEGER OPTIONAL,
             egrCallStart        [ 41] IMPLICIT GeneralizedTime OPTIONAL,
             egrGateId           [ 42] IMPLICIT INTEGER OPTIONAL,
             egrCardId           [ 43] IMPLICIT INTEGER OPTIONAL,
             egrSpanId           [ 44] IMPLICIT INTEGER OPTIONAL,
             egrChanId           [ 45] IMPLICIT INTEGER OPTIONAL,
             egrIsdnDChan        [ 46] IMPLICIT INTEGER OPTIONAL,
             egrIsdnCrn          [ 47] IMPLICIT INTEGER OPTIONAL,
             egrCreatConnCplt    [ 48] IMPLICIT GeneralizedTime OPTIONAL,
             egrAddrCplt         [ 49] IMPLICIT GeneralizedTime OPTIONAL,
             egrCallAns          [ 50] IMPLICIT GeneralizedTime OPTIONAL,
             egrCallRls          [ 51] IMPLICIT GeneralizedTime OPTIONAL,
             egrRlsCause         [ 52] IMPLICIT INTEGER OPTIONAL,
             chkptFirst          [ 53] IMPLICIT GeneralizedTime OPTIONAL,
             chkptLast           [ 54] IMPLICIT GeneralizedTime OPTIONAL,
             ingGateName         [ 55] IMPLICIT VisibleString OPTIONAL,
             egrGateName         [ 56] IMPLICIT VisibleString OPTIONAL,
             ingTgName           [ 57] IMPLICIT VisibleString OPTIONAL,
             egrTgName           [ 58] IMPLICIT VisibleString OPTIONAL,
             origGateIp          [ 59] IMPLICIT VisibleString OPTIONAL,
             termGateIp          [ 60] IMPLICIT VisibleString OPTIONAL,
             h323ConfId          [ 61] IMPLICIT VisibleString OPTIONAL,
             ingCardPort         [ 62] IMPLICIT INTEGER OPTIONAL,
             ingCardPath         [ 63] IMPLICIT INTEGER OPTIONAL,
             egrCardPort         [ 64] IMPLICIT INTEGER OPTIONAL,
             egrCardPath         [ 65] IMPLICIT INTEGER OPTIONAL,
             ingTg               [ 66] IMPLICIT INTEGER OPTIONAL,
             egrTg               [ 67] IMPLICIT INTEGER OPTIONAL,
             dialedNbr           [ 68] IMPLICIT VisibleString OPTIONAL,
             dialedNoa           [ 69] IMPLICIT INTEGER OPTIONAL,
             redirNbr            [ 70] IMPLICIT VisibleString OPTIONAL,
             redirNoa            [ 71] IMPLICIT INTEGER OPTIONAL,
             redirInd            [ 72] IMPLICIT INTEGER OPTIONAL,
             redirRsn            [ 73] IMPLICIT INTEGER OPTIONAL,
             calledNbr           [ 74] IMPLICIT VisibleString OPTIONAL,
             calledNoa           [ 75] IMPLICIT INTEGER OPTIONAL,
             redirRsnOrig        [ 76] IMPLICIT INTEGER OPTIONAL,
             redirCntr           [ 77] IMPLICIT INTEGER OPTIONAL,
             redirPrsntnInd      [ 78] IMPLICIT INTEGER OPTIONAL,
             ingJuris            [ 79] IMPLICIT VisibleString OPTIONAL,
             egrJuris            [ 80] IMPLICIT VisibleString OPTIONAL,
             ingTrunkBearCap     [ 81] IMPLICIT INTEGER OPTIONAL,
             egrTrunkBearCap     [ 82] IMPLICIT INTEGER OPTIONAL,
             transNetSelCarr     [ 83] IMPLICIT VisibleString OPTIONAL,
             clngPtyNoa          [ 84] IMPLICIT INTEGER OPTIONAL,
             ingRlsCauseIntrnl   [ 85] IMPLICIT VisibleString OPTIONAL,
             egrRlsCauseIntrnl   [ 86] IMPLICIT VisibleString OPTIONAL,
             egrClldNbr          [ 87] IMPLICIT VisibleString OPTIONAL,
             egrClldNoa          [ 88] IMPLICIT INTEGER OPTIONAL,
             egrCnndNbr          [ 89] IMPLICIT VisibleString OPTIONAL,
             egrCnndNoa          [ 90] IMPLICIT INTEGER OPTIONAL,
             clngPtyPrsntnInd    [ 91] IMPLICIT INTEGER OPTIONAL,
             ingIri              [ 92] IMPLICIT INTEGER OPTIONAL,
             egrOri              [ 93] IMPLICIT INTEGER OPTIONAL,
             ingCallidExtrnl     [ 94] IMPLICIT VisibleString OPTIONAL,
             egrCallidExtrnl     [ 95] IMPLICIT VisibleString OPTIONAL,
             ingChargeInfo       [ 96] IMPLICIT VisibleString OPTIONAL,
             egrChargeInfo       [ 97] IMPLICIT VisibleString OPTIONAL,
             ingPrtlInd          [ 98] IMPLICIT VisibleString OPTIONAL,
             ingNatfwdCliblkInd  [ 99] IMPLICIT INTEGER OPTIONAL,
             ingNatfwdNtaInd     [100] IMPLICIT INTEGER OPTIONAL,
             ingLastDvrtLnDigs   [101] IMPLICIT VisibleString OPTIONAL,
             ingLastDvrtLnNoa    [102] IMPLICIT INTEGER OPTIONAL,
             j7IngAddlPtyCat     [103] IMPLICIT VisibleString OPTIONAL,
             j7IngChgAreaInfo    [104] IMPLICIT VisibleString OPTIONAL,
             j7IngFwdCallInd     [105] IMPLICIT VisibleString OPTIONAL,
             j7EgrAddlPtyCat     [106] IMPLICIT VisibleString OPTIONAL,
             j7EgrChgAreaInfo    [107] IMPLICIT VisibleString OPTIONAL,
             j7EgrBkwCallInd     [108] IMPLICIT VisibleString OPTIONAL,
             j7CarrInfoXfer      [109] IMPLICIT VisibleString OPTIONAL,
             ingSs7GnrcParm      [110] IMPLICIT VisibleString OPTIONAL,
             egrSs7GnrcParm      [111] IMPLICIT VisibleString OPTIONAL,
             ingPktsSent         [112] IMPLICIT INTEGER OPTIONAL,
             ingPktsRcvd         [113] IMPLICIT INTEGER OPTIONAL,
             ingPktsLost         [114] IMPLICIT INTEGER OPTIONAL,
             ingPktsXfer         [115] IMPLICIT INTEGER OPTIONAL,
             ingJitter           [116] IMPLICIT INTEGER OPTIONAL,
             ingLtncy            [117] IMPLICIT INTEGER OPTIONAL,
             egrPktsSent         [118] IMPLICIT INTEGER OPTIONAL,
             egrPktsRcvd         [119] IMPLICIT INTEGER OPTIONAL,
             egrPktsLost         [120] IMPLICIT INTEGER OPTIONAL,
             egrPktsXfer         [121] IMPLICIT INTEGER OPTIONAL,
             egrJitter           [122] IMPLICIT INTEGER OPTIONAL,
             egrLtncy            [123] IMPLICIT INTEGER OPTIONAL,
             ingCrctId           [124] IMPLICIT INTEGER OPTIONAL,
             egrCrctId           [125] IMPLICIT INTEGER OPTIONAL,
             ingCodec            [126] IMPLICIT INTEGER OPTIONAL,
             egrCodec            [127] IMPLICIT INTEGER OPTIONAL,
             ingLocGateId        [128] IMPLICIT INTEGER OPTIONAL,
             egrLocGateId        [129] IMPLICIT INTEGER OPTIONAL,
             ingCasCrctSzr       [130] IMPLICIT GeneralizedTime OPTIONAL,
             egrCasCrctSzr       [131] IMPLICIT GeneralizedTime OPTIONAL,
             ingZz               [132] IMPLICIT VisibleString OPTIONAL,
             egrZz               [133] IMPLICIT VisibleString OPTIONAL,
             ingCtryAddrType     [134] IMPLICIT VisibleString OPTIONAL,
             egrCtryAddrType     [135] IMPLICIT VisibleString OPTIONAL,
             ingPartition        [136] IMPLICIT INTEGER OPTIONAL,
             egrPartition        [137] IMPLICIT INTEGER OPTIONAL,
             ingClngPtyCat       [138] IMPLICIT INTEGER OPTIONAL,
             ingRlsCauseLctn     [139] IMPLICIT INTEGER OPTIONAL,
             egrRlsCauseLctn     [140] IMPLICIT INTEGER OPTIONAL,
             clldPtyCat          [141] IMPLICIT INTEGER OPTIONAL,
             callDuration        [142] IMPLICIT INTEGER OPTIONAL,
             ingRlsDrctn         [143] IMPLICIT INTEGER OPTIONAL,
             egrRlsDrctn         [144] IMPLICIT INTEGER OPTIONAL,
             ingAnsLctim         [145] IMPLICIT GeneralizedTime OPTIONAL,
             egrAnsLctim         [146] IMPLICIT GeneralizedTime OPTIONAL,
             ingHlcChrsId        [147] IMPLICIT INTEGER OPTIONAL,
             egrHlcChrsId        [148] IMPLICIT INTEGER OPTIONAL,
             ingLlcXferCap       [149] IMPLICIT INTEGER OPTIONAL,
             egrLlcXferCap       [150] IMPLICIT INTEGER OPTIONAL,
             routeList           [151] IMPLICIT VisibleString OPTIONAL,
             ingPointCode        [152] IMPLICIT INTEGER OPTIONAL,
             egrPointCode        [153] IMPLICIT INTEGER OPTIONAL
         }"
    REFERENCE   
        "ITU-T Rec. Q.825 (1998), Q825-CDR-ASN1Module.CallRecord."
    ::= { cdr2Scalars 4 }

callDetailData OBJECT IDENTIFIER
    ::= { cdr2Objects 2 }

callDetailDataTable OBJECT-TYPE
    SYNTAX      SEQUENCE OF CallDetailDataEntry
    MAX-ACCESS  not-accessible
    STATUS      current
    DESCRIPTION 
        "This managed object class emits the CDR notifications for 
         telecommunications events slected by the control object.  The 
         selection is made based on either one or a the combination of 
         the simpleUsageMeteringControl object and 
         configurableSimpleUsageMeteringControl object.  No management 
         operations are permitted on this object class.  A CDR 
         notification is sent out if one of the following events occur:
         
         - termination of a service;
         - change of servce, e.g, due to change of charging conditions;
         - reaching a volumn threshold;
         - at regular intervals during a practical service transaction;
         - supplementary service input.
         
         Additional conditions than can cause detail record measurement, 
         fraud detectin or traffic management are:
         
         - denial of service;
         - change of observed service quality;
         - reaching a quality threashold;
         - call failures."
    REFERENCE   
        "ITU-T Rec. Q825 (1998), callDetailData MO."
    ::= { callDetailData 1 }

callDetailDataEntry OBJECT-TYPE
    SYNTAX      CallDetailDataEntry
    MAX-ACCESS  not-accessible
    STATUS      current
    DESCRIPTION 
        "callDetailData objects are created and deleted implicitly, that 
         is, they are created and deleted upon the occurrence of defined 
         trigger events and are not explicitly manipulated by a managing 
         system; i.e. a manager cannot perform any operations on 
         instances of this object class. To support recording data in a 
         callDetailData object two sets of triggers coming from the 
         control objects are defined:
         
         - Creation Triggers: events that cause creation of a 
           callDetailData object, these triggers are defined as part of 
           the control object.
         
         - Termination Triggers: events that cause deletion of a 
           callDetailData object.  Currently the termination is implicit 
           as part of the data object behaviour.  Deletion occurs upon 
           completion of usage data collection for that instance of 
           service.
         
         CDR notifications are emitted in response to reporting triggers 
         (ITU-T Rec. X.742) that are also defined as part of 
         the control objects.
         
         Entries in this table generate a callDetailRecordNotification 
         when a reporting trigger has fired."
    REFERENCE   
        "ITU-T Rec. Q825 (1998), callDetailData MOC."
    INDEX       { callDetailDataId }
    ::= { callDetailDataTable 1 }

CallDetailDataEntry ::= SEQUENCE {
    callDetailDataId    SimpleNameType
}

callDetailDataId OBJECT-TYPE
    SYNTAX      SimpleNameType
    MAX-ACCESS  read-only
    STATUS      current
    DESCRIPTION 
        "An index for call detail data."
    ::= { callDetailDataEntry 1 }

simpleUsageMeteringControl OBJECT IDENTIFIER
    ::= { cdr2Objects 3 }

simpleUsageMeteringControlTable OBJECT-TYPE
    SYNTAX      SEQUENCE OF SimpleUsageMeteringControlEntry
    MAX-ACCESS  not-accessible
    STATUS      current
    DESCRIPTION 
        "simpleUsageMeteringControl object class allows the definition 
         of different types of triggers for usage metering recording.  
         One of the defined reporting triggers requires periodic 
         reporting and can be used to transfer partial service usage 
         data to a log or remote OS for long duration service usage.  
         Another type of trigger is determined by the occurrence of a 
         particular event during usage of the service, e.g. completion 
         of usage. This object class fully supports the requirements for 
         usage metering. If only Usage Metering application is required, 
         then simpleUsageMeteringControl object class shall be used.  
         This object class controls the generation of CDRs in the NE.  
         CDRs are actually produced if the transaction fulfils the 
         conditions defined in the creationTriggerList attribute.  If 
         the creationTriggerList is empty, no CDR will be generated.  
         The value of the time period in reportingTriggers defines the 
         time interval between partial records. No attribute value 
         change notification is sent by this object when data object 
         reference list is changed and no attribute change value 
         reflects this data object reference list."
    REFERENCE   
        "ITU-T Rec. Q.825 (1998) simpleUsageMeteringControl MO."
    ::= { simpleUsageMeteringControl 1 }

simpleUsageMeteringControlEntry OBJECT-TYPE
    SYNTAX      SimpleUsageMeteringControlEntry
    MAX-ACCESS  not-accessible
    STATUS      current
    DESCRIPTION 
        "Entries in this table are derived from entries in the 
         usageMeteringControlObjectTable in the OPENSS7-UMC-MIB module 
         with the same index of the controlObjectId.
         
         When deleted, the associated entry in the 
         usageMeteringControlObjectTable and the referenced data objects 
         in the dataObjectReferenceTable of the OPENSS7-UMC-MIB module 
         are also deleted.
         
         Note that the associated usageMeteringControlObjectTable 
         entries do not normally support actions taken on data objects 
         and starting, suspending and resuming call detail records one 
         an individual data object by data object basis would be 
         nonsensical.   Suspending CDRs on all data objects for all 
         accontable object references might make sense in some 
         circumstances.
         
         Periodic triggering of CDR reporting from the 
         usageMeteringControlObjectTable has special value for cutting 
         partial records for long-duration calls.  Induced report 
         triggering due to a change in operational state is also 
         possible.  Event driver report triggering can determine at what 
         points in the call a CDR wil be generated.  The controlObject- 
         ReportingTriggersEvent is set valued and may contain:
         
         - registration(0), reporting is triggered upon off-hook or 
           seizure;
         
         - request(1), reporting is triggered when the first digit is 
           received from the origination;
         
         - accept(2), reporting is triggerd when the ACM (last digit) is 
           received;
         
         - complete(3), reporting is triggered when the call is 
           completed and terminating data is available;
         
         - corresponding(4), reporting is triggered when additional data 
           corresponding to the call is available;
         
         - bulk(5), reporting is triggered when bulk data is available 
           (such as mid-call during long-duration calls);
         
         - interruption(6), reporting is triggered whenever an error or 
           an exception occurs (e.g. abnormal release, circuit reset or 
           hardware blocking)."
    REFERENCE   
        "ITU-T Rec. Q.825 (1998) simpleUsageMeteringControl MOC."
    INDEX       { controlObjectId }
    ::= { simpleUsageMeteringControlTable 1 }

SimpleUsageMeteringControlEntry ::= SEQUENCE {
    creationTriggerList                     BITS,
    simpleUsageMeteringControlEntryStatus   RowStatus
}

creationTriggerList OBJECT-TYPE
    SYNTAX      BITS { seizure(0), firstDigitReceived(1), aCMReceived(2), 
                    aNMReceived(3), supplementaryServiceInvocation(4), 
                    supplementaryServiceInput(5) }
    MAX-ACCESS  read-write
    STATUS      current
    DESCRIPTION 
        "This attribute consists of a list of values that specify the 
         conditions that will lead to the creation of Call Detail data 
         objects.  Triggers can be call related (Seizure or first digit 
         or ACM received or ANM received) and non-call related 
         (supplementary service invocation and/or input). When multiple 
         triggers are present, the recording process is activated by the 
         first recordable event.  Note that this mask controls creation 
         and does not control reporting.  The controlObjectReporting-
         Triggers in the UsageMeteringControlObjectTable at the 
         coresponding controlObjectId index is responsible for reporting 
         triggers.
         
         The creation mask provides a specification of a set of triggers 
         for creating usage meter data objects.  The object is 
         set-valued and may contain the following:
         
         - seizure(0), when present, trigger call detail recording 
           creation when the originating trunk is siezed (unless this 
           value is included in the set, seizure time will not be 
           collected);
         
         - firstDigitReceived(1), when present, trigger call detail 
           recording creation when the first digit is received from the 
           origination (unless this value or earlier values are is 
           included in the set, IAM times and associated transient 
           information (e.g. COT) will not be collected);
         
         - aCMReceived(2), when present, trigger call detail recording 
           creation when the ACM (last digit) is received (unless this 
           value or earlier values are included in the set, ACM times 
           and associated transient information will not be collected;
         
         - aNMReceived(3), when present, trigger call detail recording 
           creation when an ANM is received from the termination (unless 
           this value or earlier values are included in the set, ANM 
           times and associated transient information will not be 
           collected);
         
         - supplementaryServiceInvocation(4), when present, trigger call 
           detail recording creation whenever a supplementary service is 
           invoked (unless this value or earlier values are included in 
           the set, supplementary service invocation and any transient 
           data associated with such invocation will not be collected);
         
         - supplementaryServiceInput(5), when present, trigger call 
           detail recording creation whenever a supplementary service 
           input occurs.
         
         aCMreceived(2) is defined as the receipt of ACM for an external 
         call. In the case of a terminating exchange the event ACM 
         received will occur when the ACM is normally generated. This is 
         either when a B-subscriber port is free (early ACM) or when a 
         B-subscriber terminal is free (late ACM).  The choice between 
         early and late ACM is a network option in the terminating 
         network.  For local calls a corresponding time shall be used.
         
         For trunks that have no seizure event (such as SS7 ISUP trunks 
         which only have an IAM or first digit event) the earliest event 
         at which the CDR can be create is at firstDigitReceived(1).  
         Setting seizure(0) on trunks with no seizure has no effect."
    REFERENCE   
        "ITU-T Rec. Q.825 (1998) creationTriggerList attribute."
    ::= { simpleUsageMeteringControlEntry 1 }

simpleUsageMeteringControlEntryStatus OBJECT-TYPE
    SYNTAX      RowStatus
    MAX-ACCESS  read-write
    STATUS      current
    DESCRIPTION 
        "Managment stations may delete entries in this table but may not 
         create them.  All of the contained mesaures are deleted when 
         the entry is deleted."
    REFERENCE   
        "STD 58, SNMPv2-TC, RowStatus"
    ::= { simpleUsageMeteringControlEntry 2 }

configurableSimpleUsageMeteringControl OBJECT IDENTIFIER
    ::= { cdr2Objects 4 }

configurableSimpleUsageMeteringControlTable OBJECT-TYPE
    SYNTAX      SEQUENCE OF ConfigurableSimpleUsageMeteringControlEntry
    MAX-ACCESS  not-accessible
    STATUS      current
    DESCRIPTION 
        "This object class is used if Analysis function is required.  
         configurableSimpleUsageMeteringControl object allows sampling 
         rate and allows configuration of all the optional parameters, 
         as defined by configurationMask, to be included in the Call 
         Detail Notification. The object class controls the creation of 
         call Detail Data objects based on the creationTriggerList, and 
         the samplingRate. The configurationMask together will control 
         the additional data to be included in the CDR notification 
         emitted by the CDR object for QoS, Fraud and Traffic Network 
         Management purpose. The characteristic additional is with 
         reference to the data already included in the notification for 
         the purpose of usage metering"
    REFERENCE   
        "ITU-T Rec. Q.825 (1998) 
         configurableSimpleUsageMeteringControl MOC."
    ::= { configurableSimpleUsageMeteringControl 1 }

configurableSimpleUsageMeteringControlEntry OBJECT-TYPE
    SYNTAX      ConfigurableSimpleUsageMeteringControlEntry
    MAX-ACCESS  not-accessible
    STATUS      current
    DESCRIPTION 
        "The configurable simple usage metering control is derived from 
         and has all of the functionality of the simple usage metering 
         control, but adds some configuration.  Because the simple usage 
         metering control is in turn derived from the usage metering 
         control object (of the OPENSS7-UMC-MIB module), they all shared 
         the same index, the controlObjectId."
    REFERENCE   
        "ITU-T Rec. Q.825 (1998) 
         configurableSimpleUsageMeteringControl MO."
    INDEX       { controlObjectId }
    ::= { configurableSimpleUsageMeteringControlTable 1 }

ConfigurableSimpleUsageMeteringControlEntry ::= SEQUENCE {
    samplingRate            Integer32,
    configurationMask       BITS,
    configurationRowStatus  RowStatus
}

samplingRate OBJECT-TYPE
    SYNTAX      Integer32
    UNITS       "calls"
    MAX-ACCESS  read-create
    STATUS      current
    DESCRIPTION 
        "This attribute indicates that every n-th callDetailData object 
         created will be flagged for analysis purpose and all subsequent 
         CDRs emitted will indicate Analysis in the cDRPurpose field of 
         the call detail report and call detail record notifications."
    REFERENCE   
        "ITU-T Rec. Q.825 (1998) samplingRate attribute."
    ::= { configurableSimpleUsageMeteringControlEntry 1 }

configurationMask OBJECT-TYPE
    SYNTAX      BITS { exchangeInfo(0), relatedCallNumber(1), 
                    additionalParticipantInfo(2), 
                    callingPartyCategory(3), callingPartyType(4), 
                    progress(5), accessDelivery(6), 
                    trunkGroupOutgoing(7), trunkGroupIncoming(8), 
                    teleservice(9), standardExtensions(10), 
                    recordExtensions(11), bPartyCategory(12), 
                    iSUPPrefferred(13), networkManagementControls(14), 
                    glare(15) }
    MAX-ACCESS  read-create
    STATUS      current
    DESCRIPTION 
        "This object specifies the additional information to be included 
         in the Call Detail Notification.  The configuraiton mask will 
         control the additional data to be included in the CDR 
         notification emitted by the CDR object for QoS, Fraud and 
         Traffic Network Management purpose.  The characteristic 
         'additional' is with reference to the data already included in 
         the notification for the purpose of usage metering.
         
         The syntax of this object provides specification of a 
         configuration mask that determines which additional data will 
         be included in the CDR notification emitted by the CDR object 
         for QoS, Fraud and Traffic Network Management purpose.  The 
         characteristic 'additional' is with reference to the data 
         already included in the notification for the purpose of usage 
         metering.
         
         The mask is set-valued and may contain the following: 
         
         - exchangeInfo(0), the exchange Info object is included in the 
           notification;
         - relatedCallNumber(1), the releated Call Number object is 
           included in the notification;
         - additionalParticipantInfo(2), the physical Line Code, 
           received Digits, operator Specific 1 Additional Number, 
           operator Specific 2 Additional Number and operator Specific 3 
           Additional Number objects are included in the notification; 
         - callingPartyCategory(3), the calling Party Category object is 
           included in the notification;
         - callingPartyType(4), the calling Party Type object is 
           included in the notification;
         - progress(5), the progress object is included in the 
           notification;
         - accessDelivery(6), the access Delivery object is included in 
           the notification;
         - trunkGroupOutgoing(7), the trunk Group Outgoing object is 
           included in the notification;
         - trunkGroupIncoming(8), the trunk Group Incoming object is 
           included in the notification;
         - teleservice(9), the teleservice object is included in the 
           notification;
         - standard Extensions(10), the standard Extensions object is 
           included in the notification; record 
         - Extensions(11), the record Extensions object is included in 
           the notification;
         - bPartyCategory(12), the b Party Category object is included 
           in the notification;
         - iSUPPrefferred(13), the iSUP Preferred object is included in 
           the notification; 
         - networkManagementControls(14), the network Management 
           Controls object is included in the notification;
         - glare(15), the glare object is included in the notification."
    REFERENCE   
        "ITU-T Rec. Q.825 (1998) configurationMask attribute.
         ITU-T Rec. Q.825 (1998), Q825-CDR-ASN1Module.ConfigurationMask"
    ::= { configurableSimpleUsageMeteringControlEntry 2 }

configurationRowStatus OBJECT-TYPE
    SYNTAX      RowStatus
    MAX-ACCESS  read-create
    STATUS      current
    DESCRIPTION 
        "Provides a mechanism whereby management stations may delete 
         entries in this table."
    REFERENCE   
        "STD58, SNMPv2-TC, RowStatus"
    ::= { configurableSimpleUsageMeteringControlEntry 3 }

blockGeneratingLog OBJECT IDENTIFIER
    ::= { cdr2Objects 5 }

blockGeneratingLogTable OBJECT-TYPE
    SYNTAX      SEQUENCE OF BlockGeneratingLogEntry
    MAX-ACCESS  not-accessible
    STATUS      current
    DESCRIPTION 
        "This log is considered to be infinite and therefore it does not 
         have to instantiate the finite-log size package from its 
         superclass log. The blocking-log stores all records that 
         satisfy its discriminator construct. The log provides the value 
         (sequence number) for the 'recordId' (field of CDR). An 
         instance of this log emits the block record notification when 
         any of the following events occurs:
         
         - the number of records in the log becomes equal to the maximum 
           block size,
         
         - the time interval elapsed since the first record currently 
           contained in the log exceeds the value maxTimeInterval 
           attribute,
         
         - an internal system limitation has been exceeded, including 
           the blocking log itself overflowing.
         
         Upon emitting the block record notification all records stored 
         in the blocking log are deleted and the log is ready to store 
         new records. Because of the self-emptying nature of this log, 
         any log-full action may be selected and the behavior of the log 
         will not change."
    REFERENCE   
        "ITU-T Rec. Q.825 (1998), blockGeneratingLog MOC."
    ::= { blockGeneratingLog 1 }

blockGeneratingLogEntry OBJECT-TYPE
    SYNTAX      BlockGeneratingLogEntry
    MAX-ACCESS  not-accessible
    STATUS      current
    DESCRIPTION 
        "Entries in this table are derivates of entries in the logTable 
         contained in the OPENSS7-SMI-MIB module, and so uses the same 
         logId index that is used by the logTable.  Entries that exist 
         in this table also exist in the logTable.  Entries deleted from 
         the logTable are also deleted from this table.
         
         Entries in this table generate a blockRecordNotification."
    REFERENCE   
        "ITU-T Rec. Q.825 (1998), blockGeneratingLog MO."
    INDEX       { logId }
    ::= { blockGeneratingLogTable 1 }

BlockGeneratingLogEntry ::= SEQUENCE {
    blockGeneratingLogMaxBlockSize      Integer32,
    blockGeneratingLogMaxTimeInterval   Integer32,
    blockGeneratingLogStorageType       StorageType,
    blockGeneratingLogRowStatus         RowStatus
}

blockGeneratingLogMaxBlockSize OBJECT-TYPE
    SYNTAX      Integer32 (0..32767)
    MAX-ACCESS  read-create
    STATUS      current
    DESCRIPTION 
        "The value of this attribute specifies the maximum number of 
         CDRs that may be contained in the blockRecordNotification 
         emitted by the blockGeneratingLog. If the value '0' is entered, 
         it means that this output trigger is not used.
         
         Note that the underlying SNMP event notification protocol 
         transport mapping may impose its own limitations on the 
         maximum size of the block in terms of the maximum number of 
         messages or octets that can be placed in an underlying 
         transport PDU."
    REFERENCE   
        "ITU-T Rec. Q.825 (1998) maxBlockSize attribute."
    ::= { blockGeneratingLogEntry 1 }

blockGeneratingLogMaxTimeInterval OBJECT-TYPE
    SYNTAX      Integer32 (0..32767)
    MAX-ACCESS  read-create
    STATUS      current
    DESCRIPTION 
        "The value of this attribute specifies the maximum time interval 
         that may elapse from receipt of the first record currently in 
         the log to the time at which a blockRecordNotification must be 
         emitted. This value, therefore, specifies the maximum latency 
         with which near-real-time CDR data will be transmitted to the 
         upstream system. If the value '0' is entered, it means that 
         this output trigger is not used."
    REFERENCE   
        "ITU-T Rec. Q.825 (1998) maxTimeInteval attribute."
    ::= { blockGeneratingLogEntry 2 }

blockGeneratingLogStorageType OBJECT-TYPE
    SYNTAX      StorageType
    MAX-ACCESS  read-create
    STATUS      current
    DESCRIPTION 
        "Specifies whether the log is transient or permanent:
         
         - volatile - transient logs may be defined for performing 
           specific studies and if the agent system reboots the study 
           should not be reapplied (it may have been the cause of the 
           reboot);
         
         - nonVolatile - permanent logs are for normal CDR generation 
           for the purposes of billing or permanent usage studies."
    REFERENCE   
        "STD 58, SNMPv2-TC StorageType."
    ::= { blockGeneratingLogEntry 3 }

blockGeneratingLogRowStatus OBJECT-TYPE
    SYNTAX      RowStatus
    MAX-ACCESS  read-create
    STATUS      current
    DESCRIPTION 
        "Provides a mechanism whereby management stations may create or 
         delete entries in this table.  Entries cannot be created in 
         this table unless a corresponding entry alredy exists in the 
         logTable for the corresponding logId."
    REFERENCE   
        "STD 58, SNMPv2-TC RowStatus."
    ::= { blockGeneratingLogEntry 4 }

fileGeneratingLog OBJECT IDENTIFIER
    ::= { cdr2Objects 6 }

fileGeneratingLogTable OBJECT-TYPE
    SYNTAX      SEQUENCE OF FileGeneratingLogEntry
    MAX-ACCESS  not-accessible
    STATUS      current
    DESCRIPTION 
        "This log is used to create files that can be exchanged using an 
         appropriate file transfer protocol. The log provides the value 
         (sequence number) for the precordId (field of the CDR). The 
         action create file is used to generate the file to be 
         exchanged. The file created consists of a concatenation of the 
         content of the call detail records; i.e. the call detail 
         records without the record overhead (Record Id, Managed Object 
         Class and Instance and Logging Time).  To avoid duplication of 
         CDRs, logging of blockedRecord notifications emitted by the 
         blocking log should be excluded by configuration of the file 
         generating loggs discriminator construct.  Files may also be 
         created due to internal trigger events. One such internal 
         trigger is based on time of day. The records are deleted after 
         successful copying of the records to the file."
    REFERENCE   
        "ITU-T Rec. Q.825 (1998) fileGeneratingLog MO."
    ::= { fileGeneratingLog 1 }

fileGeneratingLogEntry OBJECT-TYPE
    SYNTAX      FileGeneratingLogEntry
    MAX-ACCESS  not-accessible
    STATUS      current
    DESCRIPTION 
        "Creating may use automatic instance naming.  Deleting a log 
         deletes its contents."
    REFERENCE   
        "ITU-T Rec. Q.825 (1998) fileGeneratingLog MO."
    INDEX       { logId }
    ::= { fileGeneratingLogTable 1 }

FileGeneratingLogEntry ::= SEQUENCE {
    timesOfDay                      OCTET STRING,
    periodicTrigger                 Integer32,
    fileGeneratingLogStorageType    StorageType,
    fileGeneratingLogEntryStatus    RowStatus
}

timesOfDay OBJECT-TYPE
    SYNTAX      OCTET STRING (SIZE(0 | 2))
    MAX-ACCESS  read-create
    STATUS      current
    DESCRIPTION 
        "This attribute specifies the times at which the log will 
         automatically generate a file.  When specified as the null 
         octet string, the file will not be generated daily.
         
         This object provides a specification of the time of day at 
         which the log will be rotated daily.  HHmm (Hours, Minutes) 
         each field one digit, two digits per octet, the digits 0 
         through 9 encoded as 
         0000 to 1001 'hstring', 1st digit in the LSB."
    REFERENCE   
        "ITU-T Recommneation Q.825 (1998) timesOfDay attribute.
         ITU-T Rec. Q.825 (1998), Q825-CDR-ASN1Module.TimesOfDay."
    DEFVAL      { }
    ::= { fileGeneratingLogEntry 1 }

periodicTrigger OBJECT-TYPE
    SYNTAX      Integer32 (0..512)
    MAX-ACCESS  read-create
    STATUS      current
    DESCRIPTION 
        "This attribute defines the periodic interval at which the file 
         should be created.  If specified as zero (0), the file will not 
         be created periodically.
         
         This object provides a specification of a period by indicating 
         the elapsed time in minutes."
    REFERENCE   
        "ITU-T Recommneation Q.825 (1998) periodicTrigger attribute."
    DEFVAL      { 0 }
    ::= { fileGeneratingLogEntry 2 }

fileGeneratingLogStorageType OBJECT-TYPE
    SYNTAX      StorageType
    MAX-ACCESS  read-create
    STATUS      current
    DESCRIPTION 
        "Provides a specification of whether the fileGeneratingLog entry 
         is volatile or nonVolatile.  volatile file generating logs may 
         be useful for generating logs for analysis based on usage 
         detail."
    REFERENCE   
        "STD 58, SNMPv2-TC, StorageType."
    DEFVAL      { nonVolatile }
    ::= { fileGeneratingLogEntry 3 }

fileGeneratingLogEntryStatus OBJECT-TYPE
    SYNTAX      RowStatus
    MAX-ACCESS  read-create
    STATUS      current
    DESCRIPTION 
        "Provides a mechanism whereby management station may create or 
         delete entries in this table.  Entries for the same logId index 
         must already exist in the logTable before the entry may be 
         created in this table.  When entries are deleted, all contained 
         logRecords are deleted."
    REFERENCE   
        "STD 58, SNMPv2-TC, RowStatus."
    ::= { fileGeneratingLogEntry 4 }

callDetailLogRecord OBJECT IDENTIFIER
    ::= { cdr2Objects 7 }

callDetailLogRecordTable OBJECT-TYPE
    SYNTAX      SEQUENCE OF CallDetailLogRecordEntry
    MAX-ACCESS  not-accessible
    STATUS      current
    DESCRIPTION 
        "This object class describes the layout of a log record created 
         for each single call detail record notification."
    REFERENCE   
        "ITU-T Rec. Q.825 (1998), callDetailLogRecord MOC."
    ::= { callDetailLogRecord 1 }

callDetailLogRecordEntry OBJECT-TYPE
    SYNTAX      CallDetailLogRecordEntry
    MAX-ACCESS  not-accessible
    STATUS      current
    DESCRIPTION 
        "Each entry in this table is derived from an entry in the 
         logTable which is part of the OPENSS7-SMI-MIB module.  Because 
         of this, this table and the logTable in the OPENSS7-SMI-MIB 
         share the same indices."
    REFERENCE   
        "ITU-T Rec. Q.825 (1998), callDetailLogRecord MOC."
    INDEX       { logId, logRecordId }
    ::= { callDetailLogRecordTable 1 }

CallDetailLogRecordEntry ::= SEQUENCE {
    networkProviderId                       DisplayString,
    recordType                              INTEGER,
    seizureTime                             StartDateTime,
    answerTime                              StartDateTime,
    partialTime                             StartDateTime,
    eventTime                               StartDateTime,
    callingPartyNumber                      Number,
    calledPartyNumber                       Number,
    redirectingNumber                       Number,
    redirectionNumber                       Number,
    originalCalledNumber                    Number,
    callingPartyNumberNotScreened           Number,
    operatorSpecific1Number                 Number,
    operatorSpecific2Number                 Number,
    operatorSpecific3Number                 Number,
    bearerService                           BearerServiceCapability,
    participantServiceUser                  ParticipantType,
    callIdentificationNumber                OCTET STRING,
    supplementaryServices                   OCTET STRING,
    immediateNotificationForUsageMetering   TruthValue,
    cause                                   CauseAndLocation,
    personalUserId                          UserIdentifier,
    chargedParticipant                      ParticipantType,
    chargedDirectoryNumber                  Number,
    percentageToBeBilled                    Integer32,
    accountCodeInput                        AccountCode,
    iNServiceCode                           OCTET STRING,
    queueTimeStamp                          StartDateTime,
    queueDuration                           TimeInterval,
    serviceSpecificINInformation            OCTET STRING,
    partialRecordNumber                     Integer32,
    partialRecordReason                     INTEGER,
    exchangeInfo                            OCTET STRING,
    relatedCallNumber                       OCTET STRING,
    cDRPurpose                              BITS,
    physicalLineCode                        OCTET STRING,
    receivedDigits                          DialledDigits,
    operatorSpecific1AdditionalNumber       OCTET STRING,
    operatorSpecific2AdditionalNumber       OCTET STRING,
    operatorSpecific3AdditionalNumber       OCTET STRING,
    callingPartyCategory                    OCTET STRING,
    callingPartyType                        INTEGER,
    chargeInformation                       ChargingInformation,
    progress                                ProgressAndLocation,
    accessDelivery                          BITS,
    trunkGroupOutgoing                      SimpleNameType,
    trunkGroupIncoming                      SimpleNameType,
    fallbackBearerService                   BearerServiceCapability,
    teleservice                             OCTET STRING,
    conversationTime                        TimeInterval,
    durationTimeACM                         TimeInterval,
    durationTimeBAnswer                     TimeInterval,
    durationTimeNoBAnswer                   TimeInterval,
    uUInfo                                  UserToUserInformation,
    standardExtensions                      OCTET STRING,
    recordExtensions                        OCTET STRING,
    bPartyCategory                          OCTET STRING,
    iSUPPreferred                           INTEGER,
    networkManagementControls               INTEGER,
    glare                                   INTEGER,
    recordId                                Integer32,
    dataValidity                            INTEGER,
    callStatus                              INTEGER,
    carrierId                               OCTET STRING,
    dPC                                     NetworkPointCode,
    oPC                                     NetworkPointCode
}

networkProviderId OBJECT-TYPE
    SYNTAX      DisplayString (SIZE(0..11))
    MAX-ACCESS  read-only
    STATUS      current
    DESCRIPTION 
        "Provides the network provider identifier as an administrative 
         string.  If there is only one network provider, this string is 
         null."
    REFERENCE   
        "ITU-T Rec. Q.825 (1998), attribute networkProviderId
         ITU-T Rec. Q.825 (1998), Q825-CDR-ASN1Module.NetworkProviderId."
    ::= { callDetailLogRecordEntry 1 }

recordType OBJECT-TYPE
    SYNTAX      INTEGER { call(0), supplServiceInputRecord(1) }
    MAX-ACCESS  read-only
    STATUS      current
    DESCRIPTION 
        "This information element indicates the type of the CDR and it 
         also indicates the way some of the CDR elements are used.
         
         Provides a specification of the type of CRD record.  The type 
         can be one of the following values:
         
         - call(0), the CDR record is a call record;
         - supplServiceInputRecord(1), the CDR record is a supplementary 
           service input record."
    REFERENCE   
        "ITU-T Rec. Q.825 (1998), attribute recordType
         ITU-T Rec. Q.825, Q825-CDR-ASN1Module.RecordType."
    ::= { callDetailLogRecordEntry 2 }

seizureTime OBJECT-TYPE
    SYNTAX      StartDateTime
    MAX-ACCESS  read-only
    STATUS      current
    DESCRIPTION 
        "Provides the seizure time.  This is the time at which the 
         origination was seized (off-hook, trunk seizure), when the 
         exchange is ready to receive digits.  For transit calls the 
         start time stamp (seizure) will relate to the first message 
         received (e.g. IAM or SAM).
         
         Date and time values shall be derived from the exchange clock.  
         This attribute includes year, month, day, hour minute and 
         second and centisecond."
    REFERENCE   
        "ITU-T Rec. Q.825 (1998), 
         Q825-CDR-ASN1Module.StartTimeStamp.seizureTime."
    ::= { callDetailLogRecordEntry 3 }

answerTime OBJECT-TYPE
    SYNTAX      StartDateTime
    MAX-ACCESS  read-only
    STATUS      current
    DESCRIPTION 
        "Provides the answer time.  This is the time at which the call 
         was answered (e.g. ANM received).  If no B-Answer is received, 
         the value will be the null string.
         
         Date and time values shall be derived from the exchange clock.  
         This attribute includes year, month, day, hour minute and 
         second and centisecond."
    REFERENCE   
        "ITU-T Rec. Q.825 (1998), 
         Q825-CDR-ASN1Module.StartTimeStamp.answerTime."
    ::= { callDetailLogRecordEntry 4 }

partialTime OBJECT-TYPE
    SYNTAX      StartDateTime
    MAX-ACCESS  read-only
    STATUS      current
    DESCRIPTION 
        "Provides the partial record start time.  This is the same as 
         the end time (reporting time) of the previous partial CDR.
         
         Date and time values shall be derived from the exchange clock.  
         This attribute includes year, month, day, hour minute and 
         second and centisecond.
         
         For partial outputs the start date time is the end time when 
         the previous output was made."
    REFERENCE   
        "ITU-T Rec. Q.825 (1998), 
         Q825-CDR-ASN1Module.StartTimeStamp.partialTime."
    ::= { callDetailLogRecordEntry 5 }

eventTime OBJECT-TYPE
    SYNTAX      StartDateTime
    MAX-ACCESS  read-only
    STATUS      current
    DESCRIPTION 
        "Provides the event time for a supplementary service record.  
         When the CDR is generated by an event concerning a 
         supplementary service not related to a call, then this object 
         contains the time stamp for the event.  Otherwise, this  object 
         contains a null string.
         
         Date and time values shall be derived from the exchange clock.  
         This attribute includes year, month, day, hour minute and 
         second and centisecond."
    REFERENCE   
        "ITU-T Rec. Q.825 (1998), 
         Q825-CDR-ASN1Module.StartTimeStamp.eventTime."
    ::= { callDetailLogRecordEntry 6 }

callingPartyNumber OBJECT-TYPE
    SYNTAX      Number
    MAX-ACCESS  read-only
    STATUS      current
    DESCRIPTION 
        "This attribute contains the telephone number of the calling 
         party.
         
         The calling party will, for non-UPT calls, be identical to the 
         calling party user. For call type calls and when subscribing to 
         either MSN or DDI the information element indicates the 
         screened and verified number for transfer towards the called 
         subscriber. This attribute contains the default number if the 
         exchange is requested to use that number for transfer towards 
         the called subscriber. If the CDR is generated due to an event 
         concerning a supplementary service then this attribute contains 
         the telephone number of the subscriber that caused the event.
         
         It should be noted that in the case of an exchange with a 
         diverted call, the subscriber for which the CDR is generated is 
         indicated by the redirecting number."
    ::= { callDetailLogRecordEntry 7 }

calledPartyNumber OBJECT-TYPE
    SYNTAX      Number
    MAX-ACCESS  read-only
    STATUS      current
    DESCRIPTION 
        "This attribute contains the telephone number of the called 
         subscriber if the CDR is generated due to a call.
         
         If the CDR is generated due to activation or invocation of the 
         diversion supplementary service, then attribute contains the 
         telephone number of the diverted-to number. In special cases 
         this attribute may contain the translated number. This would be 
         the case when abbreviated dialling is used. As an option, this 
         information element may also include information to indicate 
         the Numbering Plan Identification (NPI) and the Type Of Number 
         (TON) of the called party number."
    ::= { callDetailLogRecordEntry 8 }

redirectingNumber OBJECT-TYPE
    SYNTAX      Number
    MAX-ACCESS  read-only
    STATUS      current
    DESCRIPTION 
        "This attribute contains the telephone number of the party who 
         has redirected the call. This is the information, when using 
         ISUP, that is sent in the forward direction when a call is 
         redirected, indicating the number from which the call was 
         diverted. This number is identical to the original called 
         number for a single diversion. In the case of a diverted call 
         the Service User will be indicated by the redirecting number."
    ::= { callDetailLogRecordEntry 9 }

redirectionNumber OBJECT-TYPE
    SYNTAX      Number
    MAX-ACCESS  read-only
    STATUS      current
    DESCRIPTION 
        "This attribute contains the telephone number of the party that 
         the call must be forwarded to. This is the information, when 
         using ISUP, that is sent in the backward direction indicating 
         the number towards which the call must be re-routed or has been 
         forwarded. The redirection number is identical to the 
         diverted-to number which can be either a forwarded to number or 
         a deflected to number."
    ::= { callDetailLogRecordEntry 10 }

originalCalledNumber OBJECT-TYPE
    SYNTAX      Number
    MAX-ACCESS  read-only
    STATUS      current
    DESCRIPTION 
        "This information element shall contain the telephone number of 
         the original called party. This is the information, when using 
         ISUP, that is sent in the forward direction when a call is 
         redirected and identifies the original called party."
    ::= { callDetailLogRecordEntry 11 }

callingPartyNumberNotScreened OBJECT-TYPE
    SYNTAX      Number
    MAX-ACCESS  read-only
    STATUS      current
    DESCRIPTION 
        "This attribute contains an additional user-provided, not 
         screened telephone number of the calling party if the CDR is 
         generated due to a call.
         
         This attribute is relevant in connection with users subscribing 
         to the special arrangement according to e.g. the CLIP 
         supplementary service."
    ::= { callDetailLogRecordEntry 12 }

operatorSpecific1Number OBJECT-TYPE
    SYNTAX      Number
    MAX-ACCESS  read-only
    STATUS      current
    DESCRIPTION 
        "This attribute contains operator defined participant 
         information and is used when the elements defined elsewhere are 
         not adequate."
    ::= { callDetailLogRecordEntry 13 }

operatorSpecific2Number OBJECT-TYPE
    SYNTAX      Number
    MAX-ACCESS  read-only
    STATUS      current
    DESCRIPTION 
        "This attribute contains operator defined participant 
         information and is used when the elements defined elsewhere are 
         not adequate."
    ::= { callDetailLogRecordEntry 14 }

operatorSpecific3Number OBJECT-TYPE
    SYNTAX      Number
    MAX-ACCESS  read-only
    STATUS      current
    DESCRIPTION 
        "This attribute contains operator defined participant 
         information and is used when the elements defined elsewhere are 
         not adequate."
    ::= { callDetailLogRecordEntry 15 }

bearerService OBJECT-TYPE
    SYNTAX      BearerServiceCapability
    MAX-ACCESS  read-only
    STATUS      current
    DESCRIPTION 
        "This attribute contains the bearer capability information for a 
         call or an event concerning a supplementary service. This 
         attribute exists only for ISDN calls."
    REFERENCE   
        "ITU-T Rec. Q.825 (1998) bearerService attribute."
    ::= { callDetailLogRecordEntry 16 }

participantServiceUser OBJECT-TYPE
    SYNTAX      ParticipantType
    MAX-ACCESS  read-only
    STATUS      current
    DESCRIPTION 
        "This attribute provides information of the party whose use of 
         resources has been accounted for. The information provided in 
         this element is a pointer to the party number provided 
         elsewhere in the record. In the case where e.g. the CDR is 
         generated on a transit exchange and no calling party number is 
         available, this element will indicate that the service user is 
         unknown."
    REFERENCE   
        "ITU-T Rec. Q.825 (1998) serviceUser attribute."
    ::= { callDetailLogRecordEntry 17 }

callIdentificationNumber OBJECT-TYPE
    SYNTAX      OCTET STRING
    MAX-ACCESS  read-only
    STATUS      current
    DESCRIPTION 
        "An identification number that identifies the call. All records 
         produced for the same call have the same call identification 
         number.
         
         With the call identification number it is possible to link 
         partial outputs, outputs due to supplementary services during 
         the call and to discriminate between simultaneous call 
         establishments. If a global call reference is received through 
         signalling, this can be used as call identification number thus 
         allowing the correlation of CDRs generated for the same call in 
         different NEs. If no global call reference is signalled in the 
         network, the call identification will only have local 
         significance."
    REFERENCE   
        "ITU-T Rec. Q.825 (1998) callIdentificationNumber attribute."
    ::= { callDetailLogRecordEntry 18 }

supplementaryServices OBJECT-TYPE
    SYNTAX      OCTET STRING (SIZE(4..256))
    MAX-ACCESS  read-only
    STATUS      current
    DESCRIPTION 
        "An octet string representing a list of supplementary services.  
         This is a list of concetenations of a single octet length 
         indicator and a SupplementaryService octet string.
         
         This attribute contains information about the use of one or 
         more supplementary services. Information about the use of one 
         or more supplementary service is only possible in connection 
         with a call record type. Each supplementary service is included 
         as a SEQUENCE OF SupplementaryService.
         
         Each SupplementaryService construct contains relevant 
         information about the use of a supplementary service.  The 
         attribute contains a service code identifying the supplementary 
         service and an addition information about the action taken. An 
         optional time stamp is provided for time dependent charging of 
         supplementary services.  The time stamp is a duration time 
         relative to the startTimeStamp and is recorded in centisecond.
         
         For each service code information is provided indicating the 
         action taken. The following actions are defined:
         
         - Provision of supplementary service;
         - Withdrawal of supplementary service;
         - Registration of supplementary service;
         - Erasure of supplementary service;
         - Activation of supplementary service;
         - Deactivation of supplementary service;
         - Invocation of supplementary service;
         - Disabling of supplementary service;
         - Interrogation of supplementary service;
         
         If provided by the network, actions can be made on 
         supplementary service by the operator. In such a case the 
         service user element in the CDR will indicate the operator as 
         the initiator of the action.
         
         In the case of functional signalling on ISDN further 
         information of the supplementary service usage is provided by 
         the optional functional information field.  This field contains 
         a set of 'management extensions' as defined by ITU-T 
         Rec. X.721."
    REFERENCE   
        "ITU-T Rec. Q.825 (1998) supplementaryServices attribute."
    ::= { callDetailLogRecordEntry 19 }

immediateNotificationForUsageMetering OBJECT-TYPE
    SYNTAX      TruthValue
    MAX-ACCESS  read-only
    STATUS      current
    DESCRIPTION 
        "This attribute shall contain an indication that the record 
         requires immediate data transfer to the OS. This standard does 
         not specify if this indication is due to a subscriber action or 
         contained in the user data. This attribute may be used to 
         define the filter of an event forwarding discriminator."
    REFERENCE   
        "ITU-T Rec. Q.825 (1998) immediateNotificationForUsageMetering 
         attribute."
    ::= { callDetailLogRecordEntry 20 }

cause OBJECT-TYPE
    SYNTAX      CauseAndLocation
    MAX-ACCESS  read-only
    STATUS      current
    DESCRIPTION 
        "This attribute indicates the cause and location value for the 
         termination of the call. For ISDN/ISUP, it will contain ITU-T 
         Rec. Q.850 cause values (sent or received). For 
         analogue call, or intra-switch call, the agent will provide the 
         best mapping corresponding to the cause value of Q.850."
    REFERENCE   
        "ITU-T Rec. Q.825 (1998) cause attribute."
    ::= { callDetailLogRecordEntry 21 }

personalUserId OBJECT-TYPE
    SYNTAX      UserIdentifier
    MAX-ACCESS  read-only
    STATUS      current
    DESCRIPTION 
        "This element has only relevance when UPT calls are made. It is 
         a network requirement that the provided international personal 
         User Identity is unique and verified by the network."
    REFERENCE   
        "ITU-T Rec. Q.825 (1998) cause iNServiceInfo attribute, 
         personalUserId component."
    ::= { callDetailLogRecordEntry 22 }

chargedParticipant OBJECT-TYPE
    SYNTAX      ParticipantType
    MAX-ACCESS  read-only
    STATUS      current
    DESCRIPTION 
        "This information element shall contain the participant, i.e.  
         calling, called, redirecting, redirection or original called 
         party, to be charged for the usage."
    REFERENCE   
        "ITU-T Rec. Q.825 (1998) cause iNServiceInfo attribute, 
         chargedParticpant component."
    ::= { callDetailLogRecordEntry 23 }

chargedDirectoryNumber OBJECT-TYPE
    SYNTAX      Number
    MAX-ACCESS  read-only
    STATUS      current
    DESCRIPTION 
        "This information element shall contain the charged directory 
         number in the case where the number cannot be indicated by the 
         charged participant element."
    REFERENCE   
        "ITU-T Rec. Q.825 (1998) cause iNServiceInfo attribute, 
         chargedDirectoryNumber component."
    ::= { callDetailLogRecordEntry 24 }

percentageToBeBilled OBJECT-TYPE
    SYNTAX      Integer32 (0..99)
    MAX-ACCESS  read-only
    STATUS      current
    DESCRIPTION 
        "This information element shall contain the percentage to be 
         billed in the case where normal billing rules are not 
         followed.
         
         Provides a specification of the percentage to be billed to a 
         specified participant.  The value ranges from 0 to 99 percent.  
         The field is not necessary if 100% is being billed to a party."
    ::= { callDetailLogRecordEntry 25 }

accountCodeInput OBJECT-TYPE
    SYNTAX      AccountCode
    MAX-ACCESS  read-only
    STATUS      current
    DESCRIPTION 
        "This information element shall contain the code to which 
         accounting is to be referred and input by the subscriber.  
         Examples of use are authorisation code, PI, bank account, PV 
         code or credit card number to be used for billing."
    ::= { callDetailLogRecordEntry 26 }

iNServiceCode OBJECT-TYPE
    SYNTAX      OCTET STRING (SIZE(0 | 2))
    MAX-ACCESS  read-only
    STATUS      current
    DESCRIPTION 
        "Provides the IN service code.  Specifies a two-octet service 
         code for an IN service."
    REFERENCE   
        "ITU-T Q.825 (1998) iNServiceCode attribute."
    ::= { callDetailLogRecordEntry 27 }

queueTimeStamp OBJECT-TYPE
    SYNTAX      StartDateTime
    MAX-ACCESS  read-only
    STATUS      current
    DESCRIPTION 
        "Provides a time stamp of the time that the call enterered a 
         queue."
    REFERENCE   
        "ITU-T Q.825 (1998) queueInfo attribute."
    ::= { callDetailLogRecordEntry 28 }

queueDuration OBJECT-TYPE
    SYNTAX      TimeInterval
    MAX-ACCESS  read-only
    STATUS      current
    DESCRIPTION 
        "Provides the duration of time that the call spent in the queue."
    REFERENCE   
        "ITU-T Q.825 (1998) queueInfo attribute."
    ::= { callDetailLogRecordEntry 29 }

serviceSpecificINInformation OBJECT-TYPE
    SYNTAX      OCTET STRING
    MAX-ACCESS  read-only
    STATUS      current
    DESCRIPTION 
        "Provides IN service specific information."
    REFERENCE   
        "ITU-T Q.825 (1998),
         Q825-CDR-ASN1Module.ServiceSpecificINInformation."
    ::= { callDetailLogRecordEntry 30 }

partialRecordNumber OBJECT-TYPE
    SYNTAX      Integer32 (0..255)
    MAX-ACCESS  read-only
    STATUS      current
    DESCRIPTION 
        "Note that in Q.825 this field is the 'number' subfield of the 
         partialGeneration component of the cdrRecord.
         
         Provides specification of a partial record number in the range 
         from (0..255) indicating the partial record generated for the 
         same call."
    REFERENCE   
        "ITU-T Rec. Q.825 (1998), partialGeneration attribute.
         ITU-T Rec. Q.825 (1998), Q825-CDR-ASN1Module.PartialGeneration."
    ::= { callDetailLogRecordEntry 31 }

partialRecordReason OBJECT-TYPE
    SYNTAX      INTEGER { timeLimit(0), serviceChange(1), overflow(2), 
                    networkInternalReasons(3), lastCDR(4), timeChange(5) }
    MAX-ACCESS  read-only
    STATUS      current
    DESCRIPTION 
        "Note that in Q.825 this field is the 'reason' subfield of the 
         partialGeneration component of the cdrRecord.
         
         Provides specifications of the reason for generation of a 
         partial record, and has a value of:
         
         - timeLimit(0), used for long duration calls;
         
         - serviceChange(1), generated because a service aspect has 
           changed;
         
         - overflow(2), generated because of overflow;
         
         - networkInternalReasons(3), generated due to internal network 
           conditions;
         
         - lastCDR(4), generated because it is a closing (the last) CDR;
         
         - timeChange(5), generated because of a changed in the system 
           clock."
    REFERENCE   
        "ITU-T Rec. Q.825 (1998), partialGeneration attribute."
    ::= { callDetailLogRecordEntry 32 }

exchangeInfo OBJECT-TYPE
    SYNTAX      OCTET STRING (SIZE(0..24))
    MAX-ACCESS  read-only
    STATUS      current
    DESCRIPTION 
        "This attribute contains the exchange identity. By means of the 
         exchange identity it is always possible to identify the 
         exchange where a specific CDR was generated. In addition to the 
         identity of the exchange, additional information can be added 
         to indicate the program version of the originator. This 
         information is provided to assist in interpreting the CDR when 
         new software releases, that affect the CDR format, are 
         introduced in the network. When all records to be transferred 
         originate from the same exchange, this information can 
         optionally be provided in the file header.
         
         This is a display string containing an ExchangeID string 
         SIZE(1..11) not conntaining a colon ':', followed by an 
         optional colon ':' and SoftwareVersion string SIZE(1..12).  The 
         colon ':' is not present if the SoftwareVersion string is not 
         present and must be present when the SoftwareVersion string is 
         present."
    REFERENCE   
        "ITU-T Rec. Q.825 (1998) exchangeInfo attribute.
         ITU-T Rec. Q.825 (1998), Q825-CDR-ASN1Module.ExchangeInfo."
    ::= { callDetailLogRecordEntry 33 }

relatedCallNumber OBJECT-TYPE
    SYNTAX      OCTET STRING
    MAX-ACCESS  read-only
    STATUS      current
    DESCRIPTION 
        "This attribute contains the Call identification number of an 
         associated call record. This number is used for associating 
         different call records generated in the same exchange."
    REFERENCE   
        "ITU-T Rec. Q.825 (1998) relatedCallNumber attribute."
    ::= { callDetailLogRecordEntry 34 }

cDRPurpose OBJECT-TYPE
    SYNTAX      BITS { usagemetering(0), analysis(1) }
    MAX-ACCESS  read-only
    STATUS      current
    DESCRIPTION 
        "This attribute provides information to the OS on the reason for 
         triggering of the record. In most networks the OS will be aware 
         of the triggering conditions of the network and hence this 
         information will not be required.
         
         Provides a specification of the purpose for generating a CDR."
    REFERENCE   
        "ITU-T Rec. Q.825 (1998) cDRPurpose attribute.
         ITU-T Rec. Q.825 (1998), Q825-CDR-ASN1Module.CDRPurpose."
    ::= { callDetailLogRecordEntry 35 }

physicalLineCode OBJECT-TYPE
    SYNTAX      OCTET STRING
    MAX-ACCESS  read-only
    STATUS      current
    DESCRIPTION 
        "This information element shall be used to identify the physical 
         line used by the calling subscriber. This element is used for 
         customer care purposes and is only relevant in the case where 
         multiple lines are used by a common directory number."
    REFERENCE   
        "ITU-T Rec. Q.825 (1998) physicalLineCode attribute."
    ::= { callDetailLogRecordEntry 36 }

receivedDigits OBJECT-TYPE
    SYNTAX      DialledDigits
    MAX-ACCESS  read-only
    STATUS      current
    DESCRIPTION 
        "This attribute contains the digits dialled by the subscriber or 
         sent by the subscriber terminal. Normally this information is 
         only included for customer care purposes. It should however be 
         noted that the use of functional signalling in ISDN as well as 
         requirements to restrict this information will require operator 
         or manufacturer specific coding of this element.  Alternatively 
         functional information should be included in the supplementary 
         service field."
    REFERENCE   
        "ITU-T Rec. Q.825 (1998) receivedDigits attribute."
    ::= { callDetailLogRecordEntry 37 }

operatorSpecific1AdditionalNumber OBJECT-TYPE
    SYNTAX      OCTET STRING
    MAX-ACCESS  read-only
    STATUS      current
    DESCRIPTION 
        "This attribute contains operator defined additional participant 
         information and is used when the elements defined elsewhere are 
         not adequate."
    REFERENCE   
        "ITU-T Rec. Q.825 (1998) 
         operatorSpecifc1AdditioanlNumber attribute."
    ::= { callDetailLogRecordEntry 38 }

operatorSpecific2AdditionalNumber OBJECT-TYPE
    SYNTAX      OCTET STRING
    MAX-ACCESS  read-only
    STATUS      current
    DESCRIPTION 
        "This attribute contains operator defined additional participant 
         information and is used when the elements defined elsewhere are 
         not adequate."
    REFERENCE   
        "ITU-T Rec. Q.825 (1998) 
         operatorSpecifc2AdditioanlNumber attribute."
    ::= { callDetailLogRecordEntry 39 }

operatorSpecific3AdditionalNumber OBJECT-TYPE
    SYNTAX      OCTET STRING
    MAX-ACCESS  read-only
    STATUS      current
    DESCRIPTION 
        "This attribute contains operator defined additional participant 
         information and is used when the elements defined elsewhere are 
         not adequate."
    REFERENCE   
        "ITU-T Rec. Q.825 (1998) 
         operatorSpecifc3AdditioanlNumber attribute."
    ::= { callDetailLogRecordEntry 40 }

callingPartyCategory OBJECT-TYPE
    SYNTAX      OCTET STRING (SIZE(1))
    MAX-ACCESS  read-only
    STATUS      current
    DESCRIPTION 
        "This attribute contains the calling subscriber category. This 
         information may also be related to the redirecting party for a 
         forwarded call.
         
         A single octet containing the party category as coded  in ITU-T 
         Rec. Q.763 or ANSI T1.116.3."
    REFERENCE   
        "ITU-T Rec. Q.825 (1998) callingPartyCategory 
         attribute."
    ::= { callDetailLogRecordEntry 41 }

callingPartyType OBJECT-TYPE
    SYNTAX      INTEGER { analogue(0), customerLink(1), basicAccess(2), 
                    primaryRateAccess(3) }
    MAX-ACCESS  read-only
    STATUS      current
    DESCRIPTION 
        "This information element shall contain the calling subscriber 
         type. This information may also be related to the redirecting 
         party for a forwarded call.
         
         The Calling party Type is defined as:
         
         - analogue(0), Analogue;
         
         - customerLink(1), T1 or E1 PSTN digital access;
         
         - basicAccess(2), Basic Access;
         
         - primaryRateAccess(3), Primary Rate Access."
    REFERENCE   
        "ITU-T Rec. Q.825 (1998) callingPartyType attribute."
    ::= { callDetailLogRecordEntry 42 }

chargeInformation OBJECT-TYPE
    SYNTAX      ChargingInformation
    MAX-ACCESS  read-only
    STATUS      current
    DESCRIPTION 
        "This attribute contains the charging information generated by 
         an NE which is capable of charging. This information can either 
         be passed on to the billing application or in the case where 
         the NE calculates charging information for presentation to the 
         user, this information can be used to compare the values 
         generated by the off-line charging application. The attribute 
         contains the charged amount either in recorded currency or call 
         charge units."
    REFERENCE   
        "ITU-T Rec. Q.825 (1998) chargingInformation 
         attribute."
    ::= { callDetailLogRecordEntry 43 }

progress OBJECT-TYPE
    SYNTAX      ProgressAndLocation
    MAX-ACCESS  read-only
    STATUS      current
    DESCRIPTION 
        "This attribute describes an event which has occurred during the 
         life of a call.  The attribute contains a location value as 
         well as the progress description.  Progress information can be 
         used e.g. for determining whether the subscriber shall be 
         charged for the use of a supplementary service towards a non- 
         ISDN user. Only the Progress indicator received from the far 
         end is of relevance and should be used. In the case where more 
         than one value is received only the last Progress indicator is 
         used."
    REFERENCE   
        "ITU-T Rec. Q.825 (1998) progress attribute."
    ::= { callDetailLogRecordEntry 44 }

accessDelivery OBJECT-TYPE
    SYNTAX      BITS { setupMessageGenerated(0) }
    MAX-ACCESS  read-only
    STATUS      current
    DESCRIPTION 
        "This attribute contains the Access delivery information which 
         indicates if the call has been delivered to the called 
         subscriber. Normally the value is derived from the ISUP 
         signalling. In the case of local calls, where no ISUP 
         signalling is used, a similar value shall be adopted. Access 
         delivery can be used for statistical purposes or to determine 
         whether the charged subscriber should be charged with call 
         attempt charge or not.
         
         Provides a specification of the access delivery method:
         
         - setupMessageGenerated(0), when present indicates the a set-up 
           message was generated; otherwise, no set-up message was 
           generated."
    REFERENCE   
        "ITU-T Rec. Q.825 (1998) accessDelivery attribute.
         ITU-T Rec. Q.825 (1998), Q825-CDR-ASN1Module.AccessDelivery."
    ::= { callDetailLogRecordEntry 45 }

trunkGroupOutgoing OBJECT-TYPE
    SYNTAX      SimpleNameType
    MAX-ACCESS  read-only
    STATUS      current
    DESCRIPTION 
        "This attribute contains the symbolic name of the trunk that is 
         used by the outgoing call as seen from the NE.  If the called 
         subscriber is a local subscriber then this information is not 
         relevant."
    REFERENCE   
        "ITU-T Rec. Q.825 (1998) trunkGroupOutgoing 
         attribute."
    ::= { callDetailLogRecordEntry 46 }

trunkGroupIncoming OBJECT-TYPE
    SYNTAX      SimpleNameType
    MAX-ACCESS  read-only
    STATUS      current
    DESCRIPTION 
        "This attribute contains the symbolic name of the trunk that is 
         used by the incoming call as seen by the NE. If the calling 
         subscriber is a local subscriber then this information element 
         is not relevant."
    REFERENCE   
        "ITU-T Rec. Q.825 (1998) trunkGroupIncoming 
         attribute."
    ::= { callDetailLogRecordEntry 47 }

fallbackBearerService OBJECT-TYPE
    SYNTAX      BearerServiceCapability
    MAX-ACCESS  read-only
    STATUS      current
    DESCRIPTION 
        "This attribute contains the fallback bearer capability 
         information for a call or an event concerning a supplementary 
         service. This indicator is only provided when, in the case of 
         fallback, the bearer service is not identical to the initial 
         requested service."
    REFERENCE   
        "ITU-T Rec. Q.825 (1998) fallbackBearerService 
         attribute."
    ::= { callDetailLogRecordEntry 48 }

teleservice OBJECT-TYPE
    SYNTAX      OCTET STRING (SIZE(1))
    MAX-ACCESS  read-only
    STATUS      current
    DESCRIPTION 
        "This information element shall contain the high layer 
         compatibility information for a call or an event concerning a 
         supplementary service.
         
         This information element is only relevant in connection with 
         ISDN.
         
         Provides a speicfiication of the Teleservice according to ITU-T 
         Rec. Q.763 or ANSI T1.116.3 coding."
    REFERENCE   
        "ITU-T Rec. Q.825 (1998) teleservice attribute.
         ITU-T Rec. Q.825 (1998), Q825-CDR-ASN1Module.Teleservice."
    ::= { callDetailLogRecordEntry 49 }

conversationTime OBJECT-TYPE
    SYNTAX      TimeInterval
    MAX-ACCESS  read-only
    STATUS      current
    DESCRIPTION 
        "This attribute contains the time consumption from B-answer or 
         equivalent. The call is considered terminated when 
         communication between the parties is no longer possible."
    REFERENCE   
        "ITU-T Rec. Q.825 (1998) conversationTime attribute."
    ::= { callDetailLogRecordEntry 50 }

durationTimeACM OBJECT-TYPE
    SYNTAX      TimeInterval
    MAX-ACCESS  read-only
    STATUS      current
    DESCRIPTION 
        "This attribute contains the time consumption from seizure time 
         until received ACM. This attribute is only included if ACM is 
         received."
    REFERENCE   
        "ITU-T Rec. Q.825 (1998) durationTimeACM attribute."
    ::= { callDetailLogRecordEntry 51 }

durationTimeBAnswer OBJECT-TYPE
    SYNTAX      TimeInterval
    MAX-ACCESS  read-only
    STATUS      current
    DESCRIPTION 
        "This attribute contains the time consumption from the seizure 
         time until received BAnswer. This attribute is included if 
         B-Answer is received."
    REFERENCE   
        "ITU-T Rec. Q.825 (1998) durationTimeB-Answer 
         attribute."
    ::= { callDetailLogRecordEntry 52 }

durationTimeNoBAnswer OBJECT-TYPE
    SYNTAX      TimeInterval
    MAX-ACCESS  read-only
    STATUS      current
    DESCRIPTION 
        "This attribute contains the time consumption from the seizure 
         time to termination time when no B-Answer is received."
    REFERENCE   
        "ITU-T Rec. Q.825 (1998) durationTimeNoB-Answer 
         attribute."
    ::= { callDetailLogRecordEntry 53 }

uUInfo OBJECT-TYPE
    SYNTAX      UserToUserInformation
    MAX-ACCESS  read-only
    STATUS      current
    DESCRIPTION 
        "This attribute shall contain the User-to-User info data 
         counter. The counter shall indicate the total number of octets 
         or elements transmitted or received by the subscriber using the 
         User-to-user signalling supplementary service. Separate 
         counters can be assigned to the 3 different User-to-user 
         signalling services."
    REFERENCE   
        "ITU-T Rec. Q.825 (1998) uUInfo attribute."
    ::= { callDetailLogRecordEntry 54 }

standardExtensions OBJECT-TYPE
    SYNTAX      OCTET STRING
    MAX-ACCESS  read-only
    STATUS      current
    DESCRIPTION 
        "This attribute shall contain standardized extensions that are 
         added to the standard usage metering record.  This field 
         contains a set of 'management extensions' as defined in ITU-T 
         Rec. X.721.
         
         Standards extensions in opaque form."
    REFERENCE   
        "ITU-T Rec. Q.825 (1998) standardExtensions attribute.
         ITU-T Rec. Q.825 (1998), Q825-CDR-ASN1Module.StandardExtensions."
    ::= { callDetailLogRecordEntry 55 }

recordExtensions OBJECT-TYPE
    SYNTAX      OCTET STRING
    MAX-ACCESS  read-only
    STATUS      current
    DESCRIPTION 
        "This attribute shall contain information elements that network 
         operators and/or manufacturers have added to the standard usage 
         metering record. This information element contains a set of 
         'management extensions' as defined in ITU-T Rec. 
         X.721.
         
         Record extensions in opaque form."
    REFERENCE   
        "ITU-T Rec. Q.825 (1998) recordExtensions attribute.
         ITU-T Rec. Q.825 (1998), Q825-CDR-ASN1Module.RecordExtensions."
    ::= { callDetailLogRecordEntry 56 }

bPartyCategory OBJECT-TYPE
    SYNTAX      OCTET STRING (SIZE(1))
    MAX-ACCESS  read-only
    STATUS      current
    DESCRIPTION 
        "This attribute contains the called subscriber category.
         
         A single octet containing the party category as coded  in ITU-T 
         Rec. Q.763 or ANSI T1.116.3."
    REFERENCE   
        "ITU-T Rec. Q.825 (1998) b-PartyCategory attribute."
    ::= { callDetailLogRecordEntry 57 }

iSUPPreferred OBJECT-TYPE
    SYNTAX      INTEGER { preferred(0), notrequired(1), required(2), 
                    notapplicable(3) }
    MAX-ACCESS  read-only
    STATUS      current
    DESCRIPTION 
        "This attribute indicates if an ISUP preference was requested.  
         For ISUP, this attribute contains the ISUP Preference Indicator 
         field of Forwarding Call Call Indicator parameter defined in 
         ITU-T Rec. Q.763. If ISUP is not used this attribute 
         is set not applicable.
         
         Provides a specification of a preference for the use of ISUP 
         signalling."
    REFERENCE   
        "ITU-T Rec. Q.825 (1998) iSUPPreferred attribute.
         ITU-T Rec. Q.825 (1998), Q825-CDR-ASN1Module.ISUPPreferred."
    ::= { callDetailLogRecordEntry 58 }

networkManagementControls OBJECT-TYPE
    SYNTAX      INTEGER { acc(0), adc(1), cancelFrom(2), 
                    cancelRerouted(3), cancelTo(4), 
                    destinationCodeControl(5), scr(6), skip(7), 
                    tarfrom(8), tarto(9) }
    MAX-ACCESS  read-only
    STATUS      current
    DESCRIPTION 
        "This attribute indicates which Traffic Network Management 
         control has affected the call. This means that calls which are 
         blocked by a traffic control will be taken into account. A call 
         is affected by a Traffic Network Management control if the 
         normal call routing process has been altered by a Traffic 
         Network Management control.
         
         Provides a specification of the Traffic Network Management 
         control that has been applied to a call."
    REFERENCE   
        "ITU-T Rec. Q.825 (1998) networkManagementControls attribute.
         ITU-T Rec. Q.825 (1998), Q825-CDR-ASN1Module.NetworkManagementControls."
    ::= { callDetailLogRecordEntry 59 }

glare OBJECT-TYPE
    SYNTAX      INTEGER { absent(0), present(1) }
    MAX-ACCESS  read-only
    STATUS      current
    DESCRIPTION 
        "This attribute indicates if a glare condition was encountered 
         even if it does not cause the call to fail.
         
         Provides a specification of the presence or absence of glare 
         condition."
    REFERENCE   
        "ITU-T Rec. Q.825 (1998) glare attribute.
         ITU-T Rec. Q.825 (1998), Q825-CDR-ASN1Module.Glare."
    ::= { callDetailLogRecordEntry 60 }

recordId OBJECT-TYPE
    SYNTAX      Integer32 (0..16777215)
    MAX-ACCESS  read-only
    STATUS      current
    DESCRIPTION 
        "This attribute is used for audit trail purposes to check if all 
         logged CDRs are transferred to the OS. It is a sequential 
         number.
         
         The record Id is a sequence number that is incremented for each 
         logged CDR, it is generated by the log."
    REFERENCE   
        "ITU-T Rec. Q.825 (1998) recordId attribute.
         ITU-T Rec. Q.825 (1998), Q825-CDR-ASN1Module.RecordId."
    ::= { callDetailLogRecordEntry 61 }

dataValidity OBJECT-TYPE
    SYNTAX      INTEGER { possibleduplicated(0), requireddatamissing(1), 
                    other(2) }
    MAX-ACCESS  read-only
    STATUS      current
    DESCRIPTION 
        "This attribute indicates that the NE is having problems and 
         that the content of the generated CDR is not reliable. This 
         indication enables the OS to take the necessary actions on the 
         collected CDRs.
         
         Provides a mechanism whereby NEs can specify that a problem was 
         encountered in the generation of the CDR and can have one of 
         the following values:
         
         - possibleduplicated(0), the CDR is possibly duplicated;
         - requireddatamissing(1), the CDR is missing some required 
           data;
         - other(2), another problem has occurred making the CDR 
           suspsect."
    REFERENCE   
        "ITU-T Rec. Q.825 (1998) dataValidity attribute.
         ITU-T Rec. Q.825 (1998), Q825-CDR-ASN1Module.DataValidity."
    ::= { callDetailLogRecordEntry 62 }

callStatus OBJECT-TYPE
    SYNTAX      INTEGER { answered(0), notanswered(1) }
    MAX-ACCESS  read-only
    STATUS      current
    DESCRIPTION 
        "This attribute identifies whether the call is answered or not.  
         A call is considered answered if ANM or its equivalent has been 
         received.
         
         Provides a specification of whether a call was answered or 
         not."
    REFERENCE   
        "ITU-T Rec. Q.825 (1998) callStatus attribute.
         ITU-T Rec. Q.825 (1998), Q825-CDR-ASN1Module.CallStatus."
    ::= { callDetailLogRecordEntry 63 }

carrierId OBJECT-TYPE
    SYNTAX      OCTET STRING (SIZE(1..11))
    MAX-ACCESS  read-only
    STATUS      current
    DESCRIPTION 
        "This attribute contains the carrier Id to which the call is 
         sent.
         
         This is a DisplayString of 1..11 octets in length that 
         specifies the identity of the selected carrier."
    REFERENCE   
        "ITU-T Rec. Q.825 (1998) carrierId attribute.
         ITU-T Rec. Q.825 (1998), Q825-CDR-ASN1Module.CarrierId."
    ::= { callDetailLogRecordEntry 64 }

dPC OBJECT-TYPE
    SYNTAX      NetworkPointCode
    MAX-ACCESS  read-only
    STATUS      current
    DESCRIPTION 
        "This attribute is used for analysis purpose. It contains the 
         destination point code."
    REFERENCE   
        "ITU-T Rec. Q.825 (1998) dPC attribute."
    ::= { callDetailLogRecordEntry 65 }

oPC OBJECT-TYPE
    SYNTAX      NetworkPointCode
    MAX-ACCESS  read-only
    STATUS      current
    DESCRIPTION 
        "This attribute is used for analysis purpose. It contains the 
         originating point code of the failed call."
    REFERENCE   
        "ITU-T Rec. Q.825 (1998) oPC attribute."
    ::= { callDetailLogRecordEntry 66 }

configurableSimpleUsageMeteringControlR2 OBJECT IDENTIFIER
    ::= { cdr2Objects 8 }

configurableSimpleUsageMeteringControlR2Table OBJECT-TYPE
    SYNTAX      SEQUENCE OF ConfigurableSimpleUsageMeteringControlR2Entry
    MAX-ACCESS  not-accessible
    STATUS      current
    DESCRIPTION 
        "This object class is used if Analysis function is required.  
         configurableSimpleUsageMeteringControl object allows sampling 
         rate and allows configuration of all the optional parameters, 
         as defined by configurationMask, to be included in the Call 
         Detail Notification. The object class controls the creation of 
         call Detail Data objects based on the creationTriggerList, and 
         the samplingRate. The configurationMask together will control 
         the additional data to be included in the CDR notification 
         emitted by the CDR object for QoS, Fraud and Traffic Network 
         Management purpose. The characteristic additional is with 
         reference to the data already included in the notification for 
         the purpose of usage metering"
    REFERENCE   
        "ITU-T Rec. Q.825 (1998), configurableSimpleUsageMeteringControl MOC."
    ::= { configurableSimpleUsageMeteringControlR2 1 }

configurableSimpleUsageMeteringControlR2Entry OBJECT-TYPE
    SYNTAX      ConfigurableSimpleUsageMeteringControlR2Entry
    MAX-ACCESS  not-accessible
    STATUS      current
    DESCRIPTION 
        "The configurable simple usage metering control revision 2 
         augments the configurableSimpleUsageMeteringControl entry by 
         adding a revision 2 configuration Mask which is aimed at 
         controlling the included fields in the revision 2 CDR format  
         Otherwise the operation of the augmented entry is the same as 
         before."
    REFERENCE   
        "ITU-T Rec. Q.825 (1998), configurableSimpleUsageMeteringControl MO."
    AUGMENTS    { configurableSimpleUsageMeteringControlEntry }
    ::= { configurableSimpleUsageMeteringControlR2Table 1 }

ConfigurableSimpleUsageMeteringControlR2Entry ::= SEQUENCE {
    configurationR2Mask     BITS,
    configurationR2Status   RowStatus
}

configurationR2Mask OBJECT-TYPE
    SYNTAX      BITS { none(0) }
    MAX-ACCESS  read-create
    STATUS      current
    DESCRIPTION 
        "This object specifies the additional information to be included 
         in the Call Detail Notification revision 2.  The configuration 
         mask will control the additional data to be included in the CDR 
         notification emitted by the CDR object for QoS, Fraud and 
         Traffic Network Management purpose.  The characteristic 
         'additional' is with reference to the data already included in 
         the notification for the purpose of usage metering.
         
         The syntax of this object provides specification of a 
         configuration mask that determines which additional data will 
         be included in the CDR notification emitted by the CDR object 
         for QoS, Fraud and Traffic Network Mangement purpose.  The 
         characteristic 'additional' is with reference to the data 
         already included in the notification for the purpose of usage 
         metering.
         
         The mask is set-valued and may contain the following:
         
         When an component is added to the set, the corresponding 
         call data is populated in the optional fields of the 
         notification when CDR data is reported."
    REFERENCE   
        "ITU-T Rec. Q.825 (1998) configurationMask attribute.
         ITU-T Rec. Q.825 (1998), Q825-CDR-ASN1Module.ConfigurationMask"
    ::= { configurableSimpleUsageMeteringControlR2Entry 1 }

configurationR2Status OBJECT-TYPE
    SYNTAX      RowStatus
    MAX-ACCESS  read-create
    STATUS      current
    DESCRIPTION 
        "Provides a mechanism whereby management stations may delete 
         entries in this table."
    REFERENCE   
        "STD58, SNMPv2-TC, RowStatus"
    ::= { configurableSimpleUsageMeteringControlR2Entry 2 }

blockGeneratingLogR2 OBJECT IDENTIFIER
    ::= { cdr2Objects 10 }

blockGeneratingLogR2Table OBJECT-TYPE
    SYNTAX      SEQUENCE OF BlockGeneratingLogR2Entry
    MAX-ACCESS  not-accessible
    STATUS      current
    DESCRIPTION 
        "This table augments the blockGeneratingLogTable and adds a new 
         field which can be used to to set the protcol version of 
         notifications issued by the blockGeneratingLog."
    ::= { blockGeneratingLogR2 1 }

blockGeneratingLogR2Entry OBJECT-TYPE
    SYNTAX      BlockGeneratingLogR2Entry
    MAX-ACCESS  not-accessible
    STATUS      current
    DESCRIPTION 
        "This table augments the entry in the blockGeneratingLogEntry."
    AUGMENTS    { blockGeneratingLogEntry }
    ::= { blockGeneratingLogR2Table 1 }

BlockGeneratingLogR2Entry ::= SEQUENCE {
    blockGeneratingLogVersion   INTEGER
}

blockGeneratingLogVersion OBJECT-TYPE
    SYNTAX      INTEGER { version1(1), version2(2) }
    MAX-ACCESS  read-write
    STATUS      current
    DESCRIPTION 
        "Provides for selecting of the new version 2 CDR block record 
         format versus the previous version 1 format."
    DEFVAL      { version1 }
    ::= { blockGeneratingLogR2Entry 1 }

callDetailLogRecordR2 OBJECT IDENTIFIER
    ::= { cdr2Objects 11 }

callDetailLogRecordR2Table OBJECT-TYPE
    SYNTAX      SEQUENCE OF CallDetailLogRecordR2Entry
    MAX-ACCESS  not-accessible
    STATUS      current
    DESCRIPTION 
        "This object class describes the layout of a Revision 2 log 
         record created for each single call detail record 
         notification."
    REFERENCE   
        "ITU-T Rec. Q.825 (1998), callDetailLogRecord MOC."
    ::= { callDetailLogRecordR2 1 }

callDetailLogRecordR2Entry OBJECT-TYPE
    SYNTAX      CallDetailLogRecordR2Entry
    MAX-ACCESS  not-accessible
    STATUS      current
    DESCRIPTION 
        "Each entry in this table is derived from an entry in the 
         logTable which is part of the OPENSS7-SMI-MIB module.  Because 
         of this, this table and the logTable in the OPENSS7-SMI-MIB 
         share the same indices."
    REFERENCE   
        "ITU-T Rec. Q.825 (1998), callDetailLogRecord MO."
    INDEX       { logId, logRecordId }
    ::= { callDetailLogRecordR2Table 1 }

CallDetailLogRecordR2Entry ::= SEQUENCE {
    sequenceId          Counter64,
    zoneId              Counter64,
    recSeqId            Counter64,
    fileSeqId           Counter64,
    callId              DisplayString,
    lastUpdate          GeneralizedTime,
    eventOrder          DisplayString,
    status              Integer32,
    callType            Integer32,
    clngPtyNbr          DisplayString,
    chargeNbr           DisplayString,
    clldPtyNbr          DisplayString,
    clldPtyNoa          Integer32,
    origLnInfo          DisplayString,
    ingLrn              DisplayString,
    ingCic              DisplayString,
    ingCsi              Integer32,
    ingCceId            Unsigned32,
    ingTgProt           Integer32,
    ingTgType           Integer32,
    ingTgId             Unsigned32,
    ingCallStart        GeneralizedTime,
    ingGateId           Unsigned32,
    ingCardId           Unsigned32,
    ingSpanId           Unsigned32,
    ingChanId           Unsigned32,
    ingIsdnDChan        Unsigned32,
    ingIsdnCrn          Unsigned32,
    ingCreatConnCplt    GeneralizedTime,
    ingAddrCplt         GeneralizedTime,
    ingCallAns          GeneralizedTime,
    transNbr            DisplayString,
    termLrn             DisplayString,
    transCic            DisplayString,
    ingCallRls          GeneralizedTime,
    ingRlsCause         Unsigned32,
    egrCceId            Unsigned32,
    egrTgProt           Integer32,
    egrTgType           Integer32,
    egrTgId             Unsigned32,
    egrCallStart        GeneralizedTime,
    egrGateId           Unsigned32,
    egrCardId           Unsigned32,
    egrSpanId           Unsigned32,
    egrChanId           Unsigned32,
    egrIsdnDChan        Unsigned32,
    egrIsdnCrn          Unsigned32,
    egrCreatConnCplt    GeneralizedTime,
    egrAddrCplt         GeneralizedTime,
    egrCallAns          GeneralizedTime,
    egrCallRls          GeneralizedTime,
    egrRlsCause         Unsigned32,
    chkptFirst          GeneralizedTime,
    chkptLast           GeneralizedTime,
    ingGateName         DisplayString,
    egrGateName         DisplayString,
    ingTgName           DisplayString,
    egrTgName           DisplayString,
    origGateIp          DisplayString,
    termGateIp          DisplayString,
    h323ConfId          DisplayString,
    ingCardPort         Unsigned32,
    ingCardPath         Unsigned32,
    egrCardPort         Unsigned32,
    egrCardPath         Unsigned32,
    ingTg               Unsigned32,
    egrTg               Unsigned32,
    dialedNbr           DisplayString,
    dialedNoa           Integer32,
    redirNbr            DisplayString,
    redirNoa            Integer32,
    redirInd            Integer32,
    redirRsn            Integer32,
    calledNbr           DisplayString,
    calledNoa           Integer32,
    redirRsnOrig        Integer32,
    redirCntr           Unsigned32,
    redirPrsntnInd      Integer32,
    ingJuris            DisplayString,
    egrJuris            DisplayString,
    ingTrunkBearCap     Integer32,
    egrTrunkBearCap     Integer32,
    transNetSelCarr     DisplayString,
    clngPtyNoa          Unsigned32,
    ingRlsCauseIntrnl   DisplayString,
    egrRlsCauseIntrnl   DisplayString,
    egrClldNbr          DisplayString,
    egrClldNoa          Integer32,
    egrCnndNbr          DisplayString,
    egrCnndNoa          Integer32,
    clngPtyPrsntnInd    Integer32,
    ingIri              Integer32,
    egrOri              Integer32,
    ingCallidExtrnl     DisplayString,
    egrCallidExtrnl     DisplayString,
    ingChargeInfo       DisplayString,
    egrChargeInfo       DisplayString,
    ingPrtlInd          DisplayString,
    ingNatfwdCliblkInd  Integer32,
    ingNatfwdNtaInd     Integer32,
    ingLastDvrtLnDigs   DisplayString,
    ingLastDvrtLnNoa    Integer32,
    j7IngAddlPtyCat     DisplayString,
    j7IngChgAreaInfo    DisplayString,
    j7IngFwdCallInd     DisplayString,
    j7EgrAddlPtyCat     DisplayString,
    j7EgrChgAreaInfo    DisplayString,
    j7EgrBkwCallInd     DisplayString,
    j7CarrInfoXfer      DisplayString,
    ingSs7GnrcParm      DisplayString,
    egrSs7GnrcParm      DisplayString,
    ingPktsSent         Unsigned32,
    ingPktsRcvd         Unsigned32,
    ingPktsLost         Unsigned32,
    ingPktsXfer         Unsigned32,
    ingJitter           Unsigned32,
    ingLtncy            Unsigned32,
    egrPktsSent         Unsigned32,
    egrPktsRcvd         Unsigned32,
    egrPktsLost         Unsigned32,
    egrPktsXfer         Unsigned32,
    egrJitter           Unsigned32,
    egrLtncy            Unsigned32,
    ingCrctId           Unsigned32,
    egrCrctId           Unsigned32,
    ingCodec            Unsigned32,
    egrCodec            Unsigned32,
    ingLocGateId        Unsigned32,
    egrLocGateId        Unsigned32,
    ingCasCrctSzr       GeneralizedTime,
    egrCasCrctSzr       GeneralizedTime,
    ingZz               DisplayString,
    egrZz               DisplayString,
    ingCtryAddrType     DisplayString,
    egrCtryAddrType     DisplayString,
    ingPartition        Unsigned32,
    egrPartition        Unsigned32,
    ingClngPtyCat       Unsigned32,
    ingRlsCauseLctn     Unsigned32,
    egrRlsCauseLctn     Unsigned32,
    clldPtyCat          Unsigned32,
    callDuration        Unsigned32,
    ingRlsDrctn         Unsigned32,
    egrRlsDrctn         Unsigned32,
    ingAnsLctim         GeneralizedTime,
    egrAnsLctim         GeneralizedTime,
    ingHlcChrsId        Unsigned32,
    egrHlcChrsId        Unsigned32,
    ingLlcXferCap       Unsigned32,
    egrLlcXferCap       Unsigned32,
    routeList           DisplayString,
    ingPointCode        Unsigned32,
    egrPointCode        Unsigned32
}

sequenceId OBJECT-TYPE
    SYNTAX      Counter64
    MAX-ACCESS  read-only
    STATUS      current
    DESCRIPTION 
        "CDR Sequence Number"
    ::= { callDetailLogRecordR2Entry 1 }

zoneId OBJECT-TYPE
    SYNTAX      Counter64
    MAX-ACCESS  read-only
    STATUS      current
    DESCRIPTION 
        "Zone id"
    ::= { callDetailLogRecordR2Entry 2 }

recSeqId OBJECT-TYPE
    SYNTAX      Counter64
    MAX-ACCESS  read-only
    STATUS      current
    DESCRIPTION 
        "Record Sequence Identifier"
    ::= { callDetailLogRecordR2Entry 3 }

fileSeqId OBJECT-TYPE
    SYNTAX      Counter64
    MAX-ACCESS  read-only
    STATUS      current
    DESCRIPTION 
        "File Sequence Identifier"
    ::= { callDetailLogRecordR2Entry 4 }

callId OBJECT-TYPE
    SYNTAX      DisplayString (SIZE(22))
    MAX-ACCESS  read-only
    STATUS      current
    DESCRIPTION 
        "Global Call Identifier"
    ::= { callDetailLogRecordR2Entry 5 }

lastUpdate OBJECT-TYPE
    SYNTAX      GeneralizedTime
    MAX-ACCESS  read-only
    STATUS      current
    DESCRIPTION 
        "Last Received Update Timestamp"
    ::= { callDetailLogRecordR2Entry 6 }

eventOrder OBJECT-TYPE
    SYNTAX      DisplayString (SIZE(0..100))
    MAX-ACCESS  read-only
    STATUS      current
    DESCRIPTION 
        "Event Order"
    ::= { callDetailLogRecordR2Entry 7 }

status OBJECT-TYPE
    SYNTAX      Integer32 (0..255)
    MAX-ACCESS  read-only
    STATUS      current
    DESCRIPTION 
        "CDR Status references oss7Status(oss7StatusId)"
    ::= { callDetailLogRecordR2Entry 8 }

callType OBJECT-TYPE
    SYNTAX      Integer32 (0..255)
    MAX-ACCESS  read-only
    STATUS      current
    DESCRIPTION 
        "Call Type references oss7Calltypes(oss7CalltypeId)"
    ::= { callDetailLogRecordR2Entry 9 }

clngPtyNbr OBJECT-TYPE
    SYNTAX      DisplayString (SIZE(0..24))
    MAX-ACCESS  read-only
    STATUS      current
    DESCRIPTION 
        "Calling Party Number"
    ::= { callDetailLogRecordR2Entry 10 }

chargeNbr OBJECT-TYPE
    SYNTAX      DisplayString (SIZE(0..24))
    MAX-ACCESS  read-only
    STATUS      current
    DESCRIPTION 
        "Charge Number"
    ::= { callDetailLogRecordR2Entry 11 }

clldPtyNbr OBJECT-TYPE
    SYNTAX      DisplayString (SIZE(0..24))
    MAX-ACCESS  read-only
    STATUS      current
    DESCRIPTION 
        "Called Party Number"
    ::= { callDetailLogRecordR2Entry 12 }

clldPtyNoa OBJECT-TYPE
    SYNTAX      Integer32 (0..127)
    MAX-ACCESS  read-only
    STATUS      current
    DESCRIPTION 
        "Nature of Address for Called Party Number references 
         oss7Noa(oss7NoaId)"
    ::= { callDetailLogRecordR2Entry 13 }

origLnInfo OBJECT-TYPE
    SYNTAX      DisplayString (SIZE(0..24))
    MAX-ACCESS  read-only
    STATUS      current
    DESCRIPTION 
        "Originating Line Information"
    ::= { callDetailLogRecordR2Entry 14 }

ingLrn OBJECT-TYPE
    SYNTAX      DisplayString (SIZE(0..24))
    MAX-ACCESS  read-only
    STATUS      current
    DESCRIPTION 
        "Ingress Local Routing Number"
    ::= { callDetailLogRecordR2Entry 15 }

ingCic OBJECT-TYPE
    SYNTAX      DisplayString (SIZE(0..24))
    MAX-ACCESS  read-only
    STATUS      current
    DESCRIPTION 
        "Ingress Carrier Identification Code"
    ::= { callDetailLogRecordR2Entry 16 }

ingCsi OBJECT-TYPE
    SYNTAX      Integer32 (0..255)
    MAX-ACCESS  read-only
    STATUS      current
    DESCRIPTION 
        "Ingress Carrier Selection Information"
    ::= { callDetailLogRecordR2Entry 17 }

ingCceId OBJECT-TYPE
    SYNTAX      Unsigned32
    MAX-ACCESS  read-only
    STATUS      current
    DESCRIPTION 
        "Ingress Call Control Element ID (OpenSS7 Server ID)"
    ::= { callDetailLogRecordR2Entry 18 }

ingTgProt OBJECT-TYPE
    SYNTAX      Integer32 (0..127)
    MAX-ACCESS  read-only
    STATUS      current
    DESCRIPTION 
        "Ingress Trunk Group Media Protocol references 
         oss7ProtocolType(oss7ProtocolTypeId)"
    ::= { callDetailLogRecordR2Entry 19 }

ingTgType OBJECT-TYPE
    SYNTAX      Integer32 (0..255)
    MAX-ACCESS  read-only
    STATUS      current
    DESCRIPTION 
        "Ingress Trunk Group Type references oss7TgTypes(oss7TgTypesId)"
    ::= { callDetailLogRecordR2Entry 20 }

ingTgId OBJECT-TYPE
    SYNTAX      Unsigned32
    MAX-ACCESS  read-only
    STATUS      current
    DESCRIPTION 
        "Ingress Trunk Group ID"
    ::= { callDetailLogRecordR2Entry 21 }

ingCallStart OBJECT-TYPE
    SYNTAX      GeneralizedTime
    MAX-ACCESS  read-only
    STATUS      current
    DESCRIPTION 
        "Ingress Signal Start Timestamp"
    ::= { callDetailLogRecordR2Entry 22 }

ingGateId OBJECT-TYPE
    SYNTAX      Unsigned32
    MAX-ACCESS  read-only
    STATUS      current
    DESCRIPTION 
        "Ingress Gateway ID"
    ::= { callDetailLogRecordR2Entry 23 }

ingCardId OBJECT-TYPE
    SYNTAX      Unsigned32
    MAX-ACCESS  read-only
    STATUS      current
    DESCRIPTION 
        "Ingress Card ID"
    ::= { callDetailLogRecordR2Entry 24 }

ingSpanId OBJECT-TYPE
    SYNTAX      Unsigned32
    MAX-ACCESS  read-only
    STATUS      current
    DESCRIPTION 
        "Ingress Span ID"
    ::= { callDetailLogRecordR2Entry 25 }

ingChanId OBJECT-TYPE
    SYNTAX      Unsigned32
    MAX-ACCESS  read-only
    STATUS      current
    DESCRIPTION 
        "Ingress Channel Number"
    ::= { callDetailLogRecordR2Entry 26 }

ingIsdnDChan OBJECT-TYPE
    SYNTAX      Unsigned32
    MAX-ACCESS  read-only
    STATUS      current
    DESCRIPTION 
        "Ingress ISDN D Channel Number"
    ::= { callDetailLogRecordR2Entry 27 }

ingIsdnCrn OBJECT-TYPE
    SYNTAX      Unsigned32
    MAX-ACCESS  read-only
    STATUS      current
    DESCRIPTION 
        "Ingress ISDN Call Reference Number"
    ::= { callDetailLogRecordR2Entry 28 }

ingCreatConnCplt OBJECT-TYPE
    SYNTAX      GeneralizedTime
    MAX-ACCESS  read-only
    STATUS      current
    DESCRIPTION 
        "Ingress Create Connection Complete Timestamp"
    ::= { callDetailLogRecordR2Entry 29 }

ingAddrCplt OBJECT-TYPE
    SYNTAX      GeneralizedTime
    MAX-ACCESS  read-only
    STATUS      current
    DESCRIPTION 
        "Ingress Address Complete Timestamp"
    ::= { callDetailLogRecordR2Entry 30 }

ingCallAns OBJECT-TYPE
    SYNTAX      GeneralizedTime
    MAX-ACCESS  read-only
    STATUS      current
    DESCRIPTION 
        "Ingress Call Answer Timestamp"
    ::= { callDetailLogRecordR2Entry 31 }

transNbr OBJECT-TYPE
    SYNTAX      DisplayString (SIZE(0..24))
    MAX-ACCESS  read-only
    STATUS      current
    DESCRIPTION 
        "Translated Number"
    ::= { callDetailLogRecordR2Entry 32 }

termLrn OBJECT-TYPE
    SYNTAX      DisplayString (SIZE(0..24))
    MAX-ACCESS  read-only
    STATUS      current
    DESCRIPTION 
        "Terminating LRN"
    ::= { callDetailLogRecordR2Entry 33 }

transCic OBJECT-TYPE
    SYNTAX      DisplayString (SIZE(0..24))
    MAX-ACCESS  read-only
    STATUS      current
    DESCRIPTION 
        "Translated Carrier Identification Code"
    ::= { callDetailLogRecordR2Entry 34 }

ingCallRls OBJECT-TYPE
    SYNTAX      GeneralizedTime
    MAX-ACCESS  read-only
    STATUS      current
    DESCRIPTION 
        "Ingress Call Release Timestamp"
    ::= { callDetailLogRecordR2Entry 35 }

ingRlsCause OBJECT-TYPE
    SYNTAX      Unsigned32
    MAX-ACCESS  read-only
    STATUS      current
    DESCRIPTION 
        "Ingress Release Cause Code"
    ::= { callDetailLogRecordR2Entry 36 }

egrCceId OBJECT-TYPE
    SYNTAX      Unsigned32
    MAX-ACCESS  read-only
    STATUS      current
    DESCRIPTION 
        "Egress Call Control Element ID"
    ::= { callDetailLogRecordR2Entry 37 }

egrTgProt OBJECT-TYPE
    SYNTAX      Integer32 (0..127)
    MAX-ACCESS  read-only
    STATUS      current
    DESCRIPTION 
        "Egress Trunk Group Protocol references 
         oss7ProtocolType(oss7ProtocolTypeId)"
    ::= { callDetailLogRecordR2Entry 38 }

egrTgType OBJECT-TYPE
    SYNTAX      Integer32 (0..127)
    MAX-ACCESS  read-only
    STATUS      current
    DESCRIPTION 
        "Egress Trunk Group Type references oss7TgType(oss7TgTypeId)"
    ::= { callDetailLogRecordR2Entry 39 }

egrTgId OBJECT-TYPE
    SYNTAX      Unsigned32
    MAX-ACCESS  read-only
    STATUS      current
    DESCRIPTION 
        "Egress Trunk Group ID"
    ::= { callDetailLogRecordR2Entry 40 }

egrCallStart OBJECT-TYPE
    SYNTAX      GeneralizedTime
    MAX-ACCESS  read-only
    STATUS      current
    DESCRIPTION 
        "Egress Call Start Timestamp"
    ::= { callDetailLogRecordR2Entry 41 }

egrGateId OBJECT-TYPE
    SYNTAX      Unsigned32
    MAX-ACCESS  read-only
    STATUS      current
    DESCRIPTION 
        "Egress Gateway ID"
    ::= { callDetailLogRecordR2Entry 42 }

egrCardId OBJECT-TYPE
    SYNTAX      Unsigned32
    MAX-ACCESS  read-only
    STATUS      current
    DESCRIPTION 
        "Egress Card ID"
    ::= { callDetailLogRecordR2Entry 43 }

egrSpanId OBJECT-TYPE
    SYNTAX      Unsigned32
    MAX-ACCESS  read-only
    STATUS      current
    DESCRIPTION 
        "Egress Span ID"
    ::= { callDetailLogRecordR2Entry 44 }

egrChanId OBJECT-TYPE
    SYNTAX      Unsigned32
    MAX-ACCESS  read-only
    STATUS      current
    DESCRIPTION 
        "Egress Channel Number"
    ::= { callDetailLogRecordR2Entry 45 }

egrIsdnDChan OBJECT-TYPE
    SYNTAX      Unsigned32
    MAX-ACCESS  read-only
    STATUS      current
    DESCRIPTION 
        "Egress ISDN D Channel Number"
    ::= { callDetailLogRecordR2Entry 46 }

egrIsdnCrn OBJECT-TYPE
    SYNTAX      Unsigned32
    MAX-ACCESS  read-only
    STATUS      current
    DESCRIPTION 
        "Egress ISDN Call Reference Number"
    ::= { callDetailLogRecordR2Entry 47 }

egrCreatConnCplt OBJECT-TYPE
    SYNTAX      GeneralizedTime
    MAX-ACCESS  read-only
    STATUS      current
    DESCRIPTION 
        "Egress Create Connection Complete Timestamp"
    ::= { callDetailLogRecordR2Entry 48 }

egrAddrCplt OBJECT-TYPE
    SYNTAX      GeneralizedTime
    MAX-ACCESS  read-only
    STATUS      current
    DESCRIPTION 
        "Egress Address Complete Timestamp"
    ::= { callDetailLogRecordR2Entry 49 }

egrCallAns OBJECT-TYPE
    SYNTAX      GeneralizedTime
    MAX-ACCESS  read-only
    STATUS      current
    DESCRIPTION 
        "Egress Call Answer Timestamp"
    ::= { callDetailLogRecordR2Entry 50 }

egrCallRls OBJECT-TYPE
    SYNTAX      GeneralizedTime
    MAX-ACCESS  read-only
    STATUS      current
    DESCRIPTION 
        "Egress Call Release Timestamp"
    ::= { callDetailLogRecordR2Entry 51 }

egrRlsCause OBJECT-TYPE
    SYNTAX      Unsigned32
    MAX-ACCESS  read-only
    STATUS      current
    DESCRIPTION 
        "Egress Release Cause Code"
    ::= { callDetailLogRecordR2Entry 52 }

chkptFirst OBJECT-TYPE
    SYNTAX      GeneralizedTime
    MAX-ACCESS  read-only
    STATUS      current
    DESCRIPTION 
        "First Checkpoint Timestamp"
    ::= { callDetailLogRecordR2Entry 53 }

chkptLast OBJECT-TYPE
    SYNTAX      GeneralizedTime
    MAX-ACCESS  read-only
    STATUS      current
    DESCRIPTION 
        "Last Checkpoint Timestamp"
    ::= { callDetailLogRecordR2Entry 54 }

ingGateName OBJECT-TYPE
    SYNTAX      DisplayString (SIZE(0..50))
    MAX-ACCESS  read-only
    STATUS      current
    DESCRIPTION 
        "Ingress Gateway Access ID (gateway name)"
    ::= { callDetailLogRecordR2Entry 55 }

egrGateName OBJECT-TYPE
    SYNTAX      DisplayString (SIZE(0..50))
    MAX-ACCESS  read-only
    STATUS      current
    DESCRIPTION 
        "Egress Gateway Access ID (gateway name)"
    ::= { callDetailLogRecordR2Entry 56 }

ingTgName OBJECT-TYPE
    SYNTAX      DisplayString (SIZE(0..50))
    MAX-ACCESS  read-only
    STATUS      current
    DESCRIPTION 
        "Ingress Trunk Group Name"
    ::= { callDetailLogRecordR2Entry 57 }

egrTgName OBJECT-TYPE
    SYNTAX      DisplayString (SIZE(0..50))
    MAX-ACCESS  read-only
    STATUS      current
    DESCRIPTION 
        "Egress Trunk Group Name"
    ::= { callDetailLogRecordR2Entry 58 }

origGateIp OBJECT-TYPE
    SYNTAX      DisplayString (SIZE(0..23))
    MAX-ACCESS  read-only
    STATUS      current
    DESCRIPTION 
        "Originating Gateway IP Address and port"
    ::= { callDetailLogRecordR2Entry 59 }

termGateIp OBJECT-TYPE
    SYNTAX      DisplayString (SIZE(0..23))
    MAX-ACCESS  read-only
    STATUS      current
    DESCRIPTION 
        "Terminating Gateway IP Address and port"
    ::= { callDetailLogRecordR2Entry 60 }

h323ConfId OBJECT-TYPE
    SYNTAX      DisplayString (SIZE(0..32))
    MAX-ACCESS  read-only
    STATUS      current
    DESCRIPTION 
        "H323 Conference ID"
    ::= { callDetailLogRecordR2Entry 61 }

ingCardPort OBJECT-TYPE
    SYNTAX      Unsigned32
    MAX-ACCESS  read-only
    STATUS      current
    DESCRIPTION 
        "Ingress Card Port Number"
    ::= { callDetailLogRecordR2Entry 62 }

ingCardPath OBJECT-TYPE
    SYNTAX      Unsigned32
    MAX-ACCESS  read-only
    STATUS      current
    DESCRIPTION 
        "Ingress Card Path Number"
    ::= { callDetailLogRecordR2Entry 63 }

egrCardPort OBJECT-TYPE
    SYNTAX      Unsigned32
    MAX-ACCESS  read-only
    STATUS      current
    DESCRIPTION 
        "Egress Card Port Number"
    ::= { callDetailLogRecordR2Entry 64 }

egrCardPath OBJECT-TYPE
    SYNTAX      Unsigned32
    MAX-ACCESS  read-only
    STATUS      current
    DESCRIPTION 
        "Egress Card Path Number"
    ::= { callDetailLogRecordR2Entry 65 }

ingTg OBJECT-TYPE
    SYNTAX      Unsigned32
    MAX-ACCESS  read-only
    STATUS      current
    DESCRIPTION 
        "Ingress Trunk Group Number"
    ::= { callDetailLogRecordR2Entry 66 }

egrTg OBJECT-TYPE
    SYNTAX      Unsigned32
    MAX-ACCESS  read-only
    STATUS      current
    DESCRIPTION 
        "Egress Trunk Group Number"
    ::= { callDetailLogRecordR2Entry 67 }

dialedNbr OBJECT-TYPE
    SYNTAX      DisplayString (SIZE(0..24))
    MAX-ACCESS  read-only
    STATUS      current
    DESCRIPTION 
        "Original Dialed Number"
    ::= { callDetailLogRecordR2Entry 68 }

dialedNoa OBJECT-TYPE
    SYNTAX      Integer32 (0..127)
    MAX-ACCESS  read-only
    STATUS      current
    DESCRIPTION 
        "Original Dialed Number Nature of Address references 
         oss7Noa(oss7NoaId)"
    ::= { callDetailLogRecordR2Entry 69 }

redirNbr OBJECT-TYPE
    SYNTAX      DisplayString (SIZE(0..24))
    MAX-ACCESS  read-only
    STATUS      current
    DESCRIPTION 
        "Redirecting Number"
    ::= { callDetailLogRecordR2Entry 70 }

redirNoa OBJECT-TYPE
    SYNTAX      Integer32 (0..127)
    MAX-ACCESS  read-only
    STATUS      current
    DESCRIPTION 
        "Redirecting Number Nature of Address references 
         oss7Noa(oss7NoaId)"
    ::= { callDetailLogRecordR2Entry 71 }

redirInd OBJECT-TYPE
    SYNTAX      Integer32 (0..255)
    MAX-ACCESS  read-only
    STATUS      current
    DESCRIPTION 
        "Redirecting Indicator references oss7RedirInd(oss7RedirIndId)"
    ::= { callDetailLogRecordR2Entry 72 }

redirRsn OBJECT-TYPE
    SYNTAX      Integer32 (0..255)
    MAX-ACCESS  read-only
    STATUS      current
    DESCRIPTION 
        "Redirecting Reason references oss7RedirRsn(oss7RedirRsnId)"
    ::= { callDetailLogRecordR2Entry 73 }

calledNbr OBJECT-TYPE
    SYNTAX      DisplayString (SIZE(0..24))
    MAX-ACCESS  read-only
    STATUS      current
    DESCRIPTION 
        "Original Called Number"
    ::= { callDetailLogRecordR2Entry 74 }

calledNoa OBJECT-TYPE
    SYNTAX      Integer32 (0..127)
    MAX-ACCESS  read-only
    STATUS      current
    DESCRIPTION 
        "Original Called Number Nature of Address references 
         oss7Noa(oss7NoaId)"
    ::= { callDetailLogRecordR2Entry 75 }

redirRsnOrig OBJECT-TYPE
    SYNTAX      Integer32 (0..255)
    MAX-ACCESS  read-only
    STATUS      current
    DESCRIPTION 
        "Original Redirecting Reason references 
         oss7RedirRsnOrig(oss7RedirRsnOrigId)"
    ::= { callDetailLogRecordR2Entry 76 }

redirCntr OBJECT-TYPE
    SYNTAX      Unsigned32
    MAX-ACCESS  read-only
    STATUS      current
    DESCRIPTION 
        "Redirection Counter"
    ::= { callDetailLogRecordR2Entry 77 }

redirPrsntnInd OBJECT-TYPE
    SYNTAX      Integer32 (0..255)
    MAX-ACCESS  read-only
    STATUS      current
    DESCRIPTION 
        "Presentation Indicator for Redirecting Number references 
         oss7PrsntnInd(oss7PrsntnIndId)"
    ::= { callDetailLogRecordR2Entry 78 }

ingJuris OBJECT-TYPE
    SYNTAX      DisplayString (SIZE(0..32))
    MAX-ACCESS  read-only
    STATUS      current
    DESCRIPTION 
        "Ingress Jurisdiction Parameter"
    ::= { callDetailLogRecordR2Entry 79 }

egrJuris OBJECT-TYPE
    SYNTAX      DisplayString (SIZE(0..32))
    MAX-ACCESS  read-only
    STATUS      current
    DESCRIPTION 
        "Egress Jurisdiction Parameter"
    ::= { callDetailLogRecordR2Entry 80 }

ingTrunkBearCap OBJECT-TYPE
    SYNTAX      Integer32 (0..255)
    MAX-ACCESS  read-only
    STATUS      current
    DESCRIPTION 
        "Ingress Trunk Bearer Capability references 
         oss7BearCap(oss7BearCapId)"
    ::= { callDetailLogRecordR2Entry 81 }

egrTrunkBearCap OBJECT-TYPE
    SYNTAX      Integer32 (0..255)
    MAX-ACCESS  read-only
    STATUS      current
    DESCRIPTION 
        "Egress Trunk Bearer Capability references 
         oss7BearCap(oss7BearCapId)"
    ::= { callDetailLogRecordR2Entry 82 }

transNetSelCarr OBJECT-TYPE
    SYNTAX      DisplayString (SIZE(0..24))
    MAX-ACCESS  read-only
    STATUS      current
    DESCRIPTION 
        "Transit Network Selection Carrier Code"
    ::= { callDetailLogRecordR2Entry 83 }

clngPtyNoa OBJECT-TYPE
    SYNTAX      Unsigned32
    MAX-ACCESS  read-only
    STATUS      current
    DESCRIPTION 
        "Nature of Address of Calling Party Number"
    ::= { callDetailLogRecordR2Entry 84 }

ingRlsCauseIntrnl OBJECT-TYPE
    SYNTAX      DisplayString (SIZE(0..60))
    MAX-ACCESS  read-only
    STATUS      current
    DESCRIPTION 
        "Ingress Internal Release Cause"
    ::= { callDetailLogRecordR2Entry 85 }

egrRlsCauseIntrnl OBJECT-TYPE
    SYNTAX      DisplayString (SIZE(0..60))
    MAX-ACCESS  read-only
    STATUS      current
    DESCRIPTION 
        "Egress Internal Release Cause"
    ::= { callDetailLogRecordR2Entry 86 }

egrClldNbr OBJECT-TYPE
    SYNTAX      DisplayString (SIZE(0..24))
    MAX-ACCESS  read-only
    STATUS      current
    DESCRIPTION 
        "Egress Called Number"
    ::= { callDetailLogRecordR2Entry 87 }

egrClldNoa OBJECT-TYPE
    SYNTAX      Integer32 (0..127)
    MAX-ACCESS  read-only
    STATUS      current
    DESCRIPTION 
        "Egress Called Number Nature of Address references 
         oss7NoaGnrc(oss7NoaGnrcId)"
    ::= { callDetailLogRecordR2Entry 88 }

egrCnndNbr OBJECT-TYPE
    SYNTAX      DisplayString (SIZE(0..24))
    MAX-ACCESS  read-only
    STATUS      current
    DESCRIPTION 
        "Egress Connected Number"
    ::= { callDetailLogRecordR2Entry 89 }

egrCnndNoa OBJECT-TYPE
    SYNTAX      Integer32 (0..127)
    MAX-ACCESS  read-only
    STATUS      current
    DESCRIPTION 
        "Egress Connected Number Nature of Address references 
         oss7NoaGnrc(oss7NoaGnrcId)"
    ::= { callDetailLogRecordR2Entry 90 }

clngPtyPrsntnInd OBJECT-TYPE
    SYNTAX      Integer32 (0..255)
    MAX-ACCESS  read-only
    STATUS      current
    DESCRIPTION 
        "Presentation Indicator for Calling Party Number"
    ::= { callDetailLogRecordR2Entry 91 }

ingIri OBJECT-TYPE
    SYNTAX      Integer32 (0..255)
    MAX-ACCESS  read-only
    STATUS      current
    DESCRIPTION 
        "Ingress IRI (ISUPSingapore)"
    ::= { callDetailLogRecordR2Entry 92 }

egrOri OBJECT-TYPE
    SYNTAX      Integer32 (0..255)
    MAX-ACCESS  read-only
    STATUS      current
    DESCRIPTION 
        "Egress ORI (ISUPSingapore)"
    ::= { callDetailLogRecordR2Entry 93 }

ingCallidExtrnl OBJECT-TYPE
    SYNTAX      DisplayString (SIZE(0..256))
    MAX-ACCESS  read-only
    STATUS      current
    DESCRIPTION 
        "Ingress External Call ID (SIP/H323)"
    ::= { callDetailLogRecordR2Entry 94 }

egrCallidExtrnl OBJECT-TYPE
    SYNTAX      DisplayString (SIZE(0..256))
    MAX-ACCESS  read-only
    STATUS      current
    DESCRIPTION 
        "Egress External Call ID (SIP/H323)"
    ::= { callDetailLogRecordR2Entry 95 }

ingChargeInfo OBJECT-TYPE
    SYNTAX      DisplayString (SIZE(0..600))
    MAX-ACCESS  read-only
    STATUS      current
    DESCRIPTION 
        "Ingress Charge Info"
    ::= { callDetailLogRecordR2Entry 96 }

egrChargeInfo OBJECT-TYPE
    SYNTAX      DisplayString (SIZE(0..600))
    MAX-ACCESS  read-only
    STATUS      current
    DESCRIPTION 
        "Egress Charge Info"
    ::= { callDetailLogRecordR2Entry 97 }

ingPrtlInd OBJECT-TYPE
    SYNTAX      DisplayString (SIZE(0..24))
    MAX-ACCESS  read-only
    STATUS      current
    DESCRIPTION 
        "Incoming Partial Call Indicator"
    ::= { callDetailLogRecordR2Entry 98 }

ingNatfwdCliblkInd OBJECT-TYPE
    SYNTAX      Integer32 (0..255)
    MAX-ACCESS  read-only
    STATUS      current
    DESCRIPTION 
        "National Forward Call Indicator CLI blocking indicator (ISUPUK) 
         references oss7CliblkInd(oss7CliblkIndId)"
    ::= { callDetailLogRecordR2Entry 99 }

ingNatfwdNtaInd OBJECT-TYPE
    SYNTAX      Integer32 (0..255)
    MAX-ACCESS  read-only
    STATUS      current
    DESCRIPTION 
        "National Forward Call Indicator Network Translated Address 
         Indicator (ISUPUK) references oss7NetTransAddr(oss7NetTra"
    ::= { callDetailLogRecordR2Entry 100 }

ingLastDvrtLnDigs OBJECT-TYPE
    SYNTAX      DisplayString (SIZE(0..24))
    MAX-ACCESS  read-only
    STATUS      current
    DESCRIPTION 
        "Last Diverting Line Identity Digits (ISUPUK)"
    ::= { callDetailLogRecordR2Entry 101 }

ingLastDvrtLnNoa OBJECT-TYPE
    SYNTAX      Integer32 (0..127)
    MAX-ACCESS  read-only
    STATUS      current
    DESCRIPTION 
        "Last Diverting Line Identity Nature of Address (ISUPUK)"
    ::= { callDetailLogRecordR2Entry 102 }

j7IngAddlPtyCat OBJECT-TYPE
    SYNTAX      DisplayString (SIZE(0..150))
    MAX-ACCESS  read-only
    STATUS      current
    DESCRIPTION 
        "Ingress Additional Party Category (J7)"
    ::= { callDetailLogRecordR2Entry 103 }

j7IngChgAreaInfo OBJECT-TYPE
    SYNTAX      DisplayString (SIZE(0..60))
    MAX-ACCESS  read-only
    STATUS      current
    DESCRIPTION 
        "Ingress Charge Area Info (J7)"
    ::= { callDetailLogRecordR2Entry 104 }

j7IngFwdCallInd OBJECT-TYPE
    SYNTAX      DisplayString (SIZE(0..180))
    MAX-ACCESS  read-only
    STATUS      current
    DESCRIPTION 
        "Ingress Forward Call Indicator (J7)"
    ::= { callDetailLogRecordR2Entry 105 }

j7EgrAddlPtyCat OBJECT-TYPE
    SYNTAX      DisplayString (SIZE(0..150))
    MAX-ACCESS  read-only
    STATUS      current
    DESCRIPTION 
        "Egress Additional Party Category (J7)"
    ::= { callDetailLogRecordR2Entry 106 }

j7EgrChgAreaInfo OBJECT-TYPE
    SYNTAX      DisplayString (SIZE(0..60))
    MAX-ACCESS  read-only
    STATUS      current
    DESCRIPTION 
        "Egress Charge Area Info (J7)"
    ::= { callDetailLogRecordR2Entry 107 }

j7EgrBkwCallInd OBJECT-TYPE
    SYNTAX      DisplayString (SIZE(0..180))
    MAX-ACCESS  read-only
    STATUS      current
    DESCRIPTION 
        "Egress Backward Call Indicator (J7)"
    ::= { callDetailLogRecordR2Entry 108 }

j7CarrInfoXfer OBJECT-TYPE
    SYNTAX      DisplayString (SIZE(0..700))
    MAX-ACCESS  read-only
    STATUS      current
    DESCRIPTION 
        "Carrier Info Transfer (J7)"
    ::= { callDetailLogRecordR2Entry 109 }

ingSs7GnrcParm OBJECT-TYPE
    SYNTAX      DisplayString (SIZE(0..700))
    MAX-ACCESS  read-only
    STATUS      current
    DESCRIPTION 
        "Ingress SS7 Generic Parameter"
    ::= { callDetailLogRecordR2Entry 110 }

egrSs7GnrcParm OBJECT-TYPE
    SYNTAX      DisplayString (SIZE(0..700))
    MAX-ACCESS  read-only
    STATUS      current
    DESCRIPTION 
        "Egress SS7 Generic Parameter"
    ::= { callDetailLogRecordR2Entry 111 }

ingPktsSent OBJECT-TYPE
    SYNTAX      Unsigned32
    MAX-ACCESS  read-only
    STATUS      current
    DESCRIPTION 
        "Ingress Packets Sent"
    ::= { callDetailLogRecordR2Entry 112 }

ingPktsRcvd OBJECT-TYPE
    SYNTAX      Unsigned32
    MAX-ACCESS  read-only
    STATUS      current
    DESCRIPTION 
        "Ingress Packets Received"
    ::= { callDetailLogRecordR2Entry 113 }

ingPktsLost OBJECT-TYPE
    SYNTAX      Unsigned32
    MAX-ACCESS  read-only
    STATUS      current
    DESCRIPTION 
        "Ingress Packets Lost"
    ::= { callDetailLogRecordR2Entry 114 }

ingPktsXfer OBJECT-TYPE
    SYNTAX      Unsigned32
    MAX-ACCESS  read-only
    STATUS      current
    DESCRIPTION 
        "Ingress Packets Transferred"
    ::= { callDetailLogRecordR2Entry 115 }

ingJitter OBJECT-TYPE
    SYNTAX      Unsigned32
    MAX-ACCESS  read-only
    STATUS      current
    DESCRIPTION 
        "Ingress Jitter in milliseconds"
    ::= { callDetailLogRecordR2Entry 116 }

ingLtncy OBJECT-TYPE
    SYNTAX      Unsigned32
    MAX-ACCESS  read-only
    STATUS      current
    DESCRIPTION 
        "Ingress Latency in milliseconds"
    ::= { callDetailLogRecordR2Entry 117 }

egrPktsSent OBJECT-TYPE
    SYNTAX      Unsigned32
    MAX-ACCESS  read-only
    STATUS      current
    DESCRIPTION 
        "Egress Packets Sent"
    ::= { callDetailLogRecordR2Entry 118 }

egrPktsRcvd OBJECT-TYPE
    SYNTAX      Unsigned32
    MAX-ACCESS  read-only
    STATUS      current
    DESCRIPTION 
        "Egress Packets Received"
    ::= { callDetailLogRecordR2Entry 119 }

egrPktsLost OBJECT-TYPE
    SYNTAX      Unsigned32
    MAX-ACCESS  read-only
    STATUS      current
    DESCRIPTION 
        "Egress Packets Lost"
    ::= { callDetailLogRecordR2Entry 120 }

egrPktsXfer OBJECT-TYPE
    SYNTAX      Unsigned32
    MAX-ACCESS  read-only
    STATUS      current
    DESCRIPTION 
        "Egress Packets Transferred"
    ::= { callDetailLogRecordR2Entry 121 }

egrJitter OBJECT-TYPE
    SYNTAX      Unsigned32
    MAX-ACCESS  read-only
    STATUS      current
    DESCRIPTION 
        "Egress Jitter in milliseconds"
    ::= { callDetailLogRecordR2Entry 122 }

egrLtncy OBJECT-TYPE
    SYNTAX      Unsigned32
    MAX-ACCESS  read-only
    STATUS      current
    DESCRIPTION 
        "Egress Latency in milliseconds"
    ::= { callDetailLogRecordR2Entry 123 }

ingCrctId OBJECT-TYPE
    SYNTAX      Unsigned32
    MAX-ACCESS  read-only
    STATUS      current
    DESCRIPTION 
        "Ingress Circuit Identification Code"
    ::= { callDetailLogRecordR2Entry 124 }

egrCrctId OBJECT-TYPE
    SYNTAX      Unsigned32
    MAX-ACCESS  read-only
    STATUS      current
    DESCRIPTION 
        "Egress Circuit Identification Code"
    ::= { callDetailLogRecordR2Entry 125 }

ingCodec OBJECT-TYPE
    SYNTAX      Unsigned32
    MAX-ACCESS  read-only
    STATUS      current
    DESCRIPTION 
        "Ingress Codec"
    ::= { callDetailLogRecordR2Entry 126 }

egrCodec OBJECT-TYPE
    SYNTAX      Unsigned32
    MAX-ACCESS  read-only
    STATUS      current
    DESCRIPTION 
        "Egress Codec"
    ::= { callDetailLogRecordR2Entry 127 }

ingLocGateId OBJECT-TYPE
    SYNTAX      Unsigned32
    MAX-ACCESS  read-only
    STATUS      current
    DESCRIPTION 
        "Ingress Local Gateway ID"
    ::= { callDetailLogRecordR2Entry 128 }

egrLocGateId OBJECT-TYPE
    SYNTAX      Unsigned32
    MAX-ACCESS  read-only
    STATUS      current
    DESCRIPTION 
        "Egress Local Gateway ID"
    ::= { callDetailLogRecordR2Entry 129 }

ingCasCrctSzr OBJECT-TYPE
    SYNTAX      GeneralizedTime
    MAX-ACCESS  read-only
    STATUS      current
    DESCRIPTION 
        "Ingress CAS Circuit Seizure Time"
    ::= { callDetailLogRecordR2Entry 130 }

egrCasCrctSzr OBJECT-TYPE
    SYNTAX      GeneralizedTime
    MAX-ACCESS  read-only
    STATUS      current
    DESCRIPTION 
        "Egress CAS Circuit Seizure Time"
    ::= { callDetailLogRecordR2Entry 131 }

ingZz OBJECT-TYPE
    SYNTAX      DisplayString (SIZE(0..4))
    MAX-ACCESS  read-only
    STATUS      current
    DESCRIPTION 
        "Ingress ZZ Code (CAS)"
    ::= { callDetailLogRecordR2Entry 132 }

egrZz OBJECT-TYPE
    SYNTAX      DisplayString (SIZE(0..4))
    MAX-ACCESS  read-only
    STATUS      current
    DESCRIPTION 
        "Egress ZZ Code (CAS)"
    ::= { callDetailLogRecordR2Entry 133 }

ingCtryAddrType OBJECT-TYPE
    SYNTAX      DisplayString (SIZE(0..4))
    MAX-ACCESS  read-only
    STATUS      current
    DESCRIPTION 
        "Ingress Country Address Type (CAS)"
    ::= { callDetailLogRecordR2Entry 134 }

egrCtryAddrType OBJECT-TYPE
    SYNTAX      DisplayString (SIZE(0..4))
    MAX-ACCESS  read-only
    STATUS      current
    DESCRIPTION 
        "Egress Country Address Type (CAS)"
    ::= { callDetailLogRecordR2Entry 135 }

ingPartition OBJECT-TYPE
    SYNTAX      Unsigned32
    MAX-ACCESS  read-only
    STATUS      current
    DESCRIPTION 
        "Ingress Partition Number"
    ::= { callDetailLogRecordR2Entry 136 }

egrPartition OBJECT-TYPE
    SYNTAX      Unsigned32
    MAX-ACCESS  read-only
    STATUS      current
    DESCRIPTION 
        "Egress Partition Number"
    ::= { callDetailLogRecordR2Entry 137 }

ingClngPtyCat OBJECT-TYPE
    SYNTAX      Unsigned32
    MAX-ACCESS  read-only
    STATUS      current
    DESCRIPTION 
        "Ingress Calling Party Category"
    ::= { callDetailLogRecordR2Entry 138 }

ingRlsCauseLctn OBJECT-TYPE
    SYNTAX      Unsigned32
    MAX-ACCESS  read-only
    STATUS      current
    DESCRIPTION 
        "Ingress Release Cause Location"
    ::= { callDetailLogRecordR2Entry 139 }

egrRlsCauseLctn OBJECT-TYPE
    SYNTAX      Unsigned32
    MAX-ACCESS  read-only
    STATUS      current
    DESCRIPTION 
        "Egress Release Cause Location"
    ::= { callDetailLogRecordR2Entry 140 }

clldPtyCat OBJECT-TYPE
    SYNTAX      Unsigned32
    MAX-ACCESS  read-only
    STATUS      current
    DESCRIPTION 
        "Called Party Category"
    ::= { callDetailLogRecordR2Entry 141 }

callDuration OBJECT-TYPE
    SYNTAX      Unsigned32
    MAX-ACCESS  read-only
    STATUS      current
    DESCRIPTION 
        "Call TimeInterval in seconds"
    ::= { callDetailLogRecordR2Entry 142 }

ingRlsDrctn OBJECT-TYPE
    SYNTAX      Unsigned32
    MAX-ACCESS  read-only
    STATUS      current
    DESCRIPTION 
        "Ingress Release Direction"
    ::= { callDetailLogRecordR2Entry 143 }

egrRlsDrctn OBJECT-TYPE
    SYNTAX      Unsigned32
    MAX-ACCESS  read-only
    STATUS      current
    DESCRIPTION 
        "Egress Release Direction"
    ::= { callDetailLogRecordR2Entry 144 }

ingAnsLctim OBJECT-TYPE
    SYNTAX      GeneralizedTime
    MAX-ACCESS  read-only
    STATUS      current
    DESCRIPTION 
        "Ingress Answer Time (local)"
    ::= { callDetailLogRecordR2Entry 145 }

egrAnsLctim OBJECT-TYPE
    SYNTAX      GeneralizedTime
    MAX-ACCESS  read-only
    STATUS      current
    DESCRIPTION 
        "Egress Answer Time (local)"
    ::= { callDetailLogRecordR2Entry 146 }

ingHlcChrsId OBJECT-TYPE
    SYNTAX      Unsigned32
    MAX-ACCESS  read-only
    STATUS      current
    DESCRIPTION 
        "Ingress HLC Characteristics Identification"
    ::= { callDetailLogRecordR2Entry 147 }

egrHlcChrsId OBJECT-TYPE
    SYNTAX      Unsigned32
    MAX-ACCESS  read-only
    STATUS      current
    DESCRIPTION 
        "Egress HLC Characteristics Identification"
    ::= { callDetailLogRecordR2Entry 148 }

ingLlcXferCap OBJECT-TYPE
    SYNTAX      Unsigned32
    MAX-ACCESS  read-only
    STATUS      current
    DESCRIPTION 
        "Ingress LLC Transfer Capability"
    ::= { callDetailLogRecordR2Entry 149 }

egrLlcXferCap OBJECT-TYPE
    SYNTAX      Unsigned32
    MAX-ACCESS  read-only
    STATUS      current
    DESCRIPTION 
        "Egress LLC Transfer Capability"
    ::= { callDetailLogRecordR2Entry 150 }

routeList OBJECT-TYPE
    SYNTAX      DisplayString (SIZE(0..120))
    MAX-ACCESS  read-only
    STATUS      current
    DESCRIPTION 
        "Ordered list of trunk group numbers received from Least Cost 
         Routing (call-by-call) server"
    ::= { callDetailLogRecordR2Entry 151 }

ingPointCode OBJECT-TYPE
    SYNTAX      Unsigned32
    MAX-ACCESS  read-only
    STATUS      current
    DESCRIPTION 
        "Origin Point Code"
    ::= { callDetailLogRecordR2Entry 152 }

egrPointCode OBJECT-TYPE
    SYNTAX      Unsigned32
    MAX-ACCESS  read-only
    STATUS      current
    DESCRIPTION 
        "Destination Point Code"
    ::= { callDetailLogRecordR2Entry 153 }

cdr2Conformance OBJECT IDENTIFIER
    ::= { cdr2MIB 2 }

cdr2Compliances OBJECT IDENTIFIER
    ::= { cdr2Conformance 1 }

cdr2Groups OBJECT IDENTIFIER
    ::= { cdr2Conformance 2 }

blockRecordNotification NOTIFICATION-TYPE
    OBJECTS     { exchangeInfo, sequenceNumber, reasonForOutput, 
                  recordType, bearerService, participantServiceUser, 
                  callIdentificationNumber }
    STATUS      current
    DESCRIPTION 
        "This notification is emitted whenever one of the triggering 
         events described in the object class template occurs. The 
         notification consists of a concatenation of the content of the 
         call detail records currently contained in the blockingLog; 
         i.e. the call detail records without the record overhead (Log 
         Record Id, Managed Object Class and Instance and Logging Time).
         
         
         The block header consists of the following mandatory fields:
         
            exchangeInfo, sequenceNumber, reasonForOutput.
         
         These are followed by at least one set of:
         
            recordType, bearerService, participantServiceUser, 
            callIdentificationNumber;
         
         followed be additional fields described under the 
         callDetailRecordNotification.  Additional records can be 
         appended beginning with the recordType of the next record."
    REFERENCE   
        "ITU-T Rec. Q.825 (1998) : blockRecordNotification"
    ::= { cdr2Notifications 1 }

callDetailRecordNotification NOTIFICATION-TYPE
    OBJECTS     { recordType, bearerService, participantServiceUser, 
                  callIdentificationNumber }
    STATUS      current
    DESCRIPTION 
        "This notification is issued to transmit a call detail record.  
         The immediate notification may be used by the Event Forwarding 
         Discriminator to select records requiring real time handling by 
         the OS. Remaining attributes can be used to further filter the 
         information in the record content.
         
         Mandatory objects are:
         
            recordType, bearerService, participantServiceUser, 
            callIdentificationNumber.
         
         When marked for immediate forwarding, the following should be 
         present:
         
            immediateNotificationForUsageMetering.
         
         These objects are followed by all of the following that are 
         available:
         
            callingPartyNumber, calledPartyNumber, redirectingNumber, 
            originalCalledNumber, callingPartyNumberNotScreened, 
            operatorSpecific1Number, operatorSpecific2Number, 
            operatorSpecific3Number.
         
         For complete Call Records - the following are included:
         
            seizureTime, answerTime.
         
         For partial Call Records - the following are included:
         
            partialTime, partialRecordNumber, partialRecordReason.
         
         Supplementary Service Input Recoreds - the following are 
         included:
         
            eventTime, supplementaryServices.
         
         For all records, the following are included when available and 
         requested:
         
            supplementaryServices, personalUserId, chargedParticipant, 
            chargedDirectoryNumber, percentageToBeBilled, 
            accountCodeInput, iNServiceCode, queueTimeStamp, 
            queueDuration.
         
         The notification may include whenever available, requested and 
         applicable:
         
            cause, exchangeInfo, relatedCallNumber, cDRPurpose, 
            physicalLineCode, receivedDigits, 
            operatorSpecific1AdditionalNumber, 
            operatorSpecific2AdditionalNumber, 
            operatorSpecific3AdditionalNumber, callingPartyCategory, 
            callingPartyType, chargeInformation, progress, 
            accessDelivery, trunkGroupOutgoing, trunkGroupIncoming, 
            fallbackBearerService, teleservice, conversationTime, 
            durationTimeACM, durationTimeBAnswer, durationTimeNoBAnswer, 
            uUInfo, bPartyCategory, iSUPPreferred, 
            networkManagementControls, glare, recordId, dataValidity, 
            callStatus, carrierId, dPC, oPC.
         
         Two extension fields are available for additional extensions 
         and may be included in any record:
         
            standardExtensions, recordExtensions.
         
         See the descriptions for each of the fields for more 
         information."
    REFERENCE   
        "ITU-T Rec. Q.825 (1998) : fileCreationNotification"
    ::= { cdr2Notifications 2 }

fileCreationNotification NOTIFICATION-TYPE
    OBJECTS     { fileName, reasonForOutput }
    STATUS      current
    DESCRIPTION 
        "This notification is emitted whenever the fileGenerating Log 
         creates a new file in order to let the managing system know 
         that the file is available for retrieval.  It provides the file 
         name on the managed system and the reason for output."
    REFERENCE   
        "ITU-T Rec. Q.825 (1998) : fileCreationNotification"
    ::= { cdr2Notifications 3 }

blockRecordNotificationR2 NOTIFICATION-TYPE
    OBJECTS     { exchangeInfo, sequenceNumber, reasonForOutput, 
                  callRecord }
    STATUS      current
    DESCRIPTION 
        "The notification includes header information that precedes the 
         packed call records and then is followed by one or more call 
         records in packed ASN.1 format."
    REFERENCE   
        "ITU-T Rec. Q.825 (1998) : blockRecordNotification"
    ::= { cdr2Notifications 4 }

callDetailRecordNotificationR2 NOTIFICATION-TYPE
    OBJECTS     { sequenceId, zoneId, recSeqId, fileSeqId, callId, 
                  lastUpdate, eventOrder, status }
    STATUS      current
    DESCRIPTION 
        "The notification includes the mandatory fields that form the 
         header of the notification followed by any of the other 145 
         fields.  Only one call record is contained in a notification."
    REFERENCE   
        "ITU-T Rec. Q.825 (1998) : fileCreationNotification"
    ::= { cdr2Notifications 5 }

cdrParameterGroup OBJECT-GROUP
    OBJECTS     { fileName, reasonForOutput, sequenceNumber, callRecord, 
                  exchangeInfo, recordType, bearerService, 
                  participantServiceUser, callIdentificationNumber }
    STATUS      current
    DESCRIPTION 
        "A set of parameters for notificaitons."
    ::= { cdr2Groups 1 }

cdrNotificationGroup NOTIFICATION-GROUP
    NOTIFICATIONS { fileCreationNotification }
    STATUS      current
    DESCRIPTION 
        "File creation notification always implemented."
    ::= { cdr2Groups 2 }

cdr1NotificationGroup NOTIFICATION-GROUP
    NOTIFICATIONS { blockRecordNotification, 
                  callDetailRecordNotification }
    STATUS      current
    DESCRIPTION 
        "Notifications in format CDR1."
    ::= { cdr2Groups 3 }

cdr2NotificationGroup NOTIFICATION-GROUP
    NOTIFICATIONS { blockRecordNotificationR2, 
                  callDetailRecordNotificationR2 }
    STATUS      current
    DESCRIPTION 
        "Notifications in format CDR2."
    ::= { cdr2Groups 4 }

cdr2MandatoryCallRecordFields OBJECT-GROUP
    OBJECTS     { sequenceId, zoneId, recSeqId, fileSeqId, callId, 
                  lastUpdate, eventOrder, status }
    STATUS      current
    DESCRIPTION 
        "Mandatory CDR2 call record fields."
    ::= { cdr2Groups 5 }

cdrMandatoryGroups OBJECT-GROUP
    OBJECTS     { creationTriggerList, 
                  simpleUsageMeteringControlEntryStatus, samplingRate, 
                  blockGeneratingLogMaxBlockSize, 
                  blockGeneratingLogMaxTimeInterval, 
                  blockGeneratingLogStorageType, 
                  blockGeneratingLogRowStatus, timesOfDay, 
                  periodicTrigger, fileGeneratingLogStorageType, 
                  fileGeneratingLogEntryStatus }
    STATUS      current
    DESCRIPTION 
        "Common mandatory CDR table fields."
    ::= { cdr2Groups 6 }

cdr1ConditionalGroups OBJECT-GROUP
    OBJECTS     { configurationMask, configurationRowStatus }
    STATUS      current
    DESCRIPTION 
        "Mandatory groups for CDR1, optional for CDR2 format."
    ::= { cdr2Groups 7 }

cdr2MandatoryGroups OBJECT-GROUP
    OBJECTS     { configurationR2Mask, configurationR2Status, 
                  blockGeneratingLogVersion }
    STATUS      current
    DESCRIPTION 
        "Mandatory groups for CDR2 format."
    ::= { cdr2Groups 8 }

cd1RecordFormatGroup OBJECT-GROUP
    OBJECTS     { networkProviderId, seizureTime, answerTime, 
                  partialTime, eventTime, callingPartyNumber, 
                  calledPartyNumber, redirectingNumber, 
                  redirectionNumber, originalCalledNumber, 
                  callingPartyNumberNotScreened, operatorSpecific1Number, 
                  operatorSpecific2Number, operatorSpecific3Number, 
                  supplementaryServices, 
                  immediateNotificationForUsageMetering, cause, 
                  personalUserId, chargedParticipant, 
                  chargedDirectoryNumber, percentageToBeBilled, 
                  accountCodeInput, iNServiceCode, queueTimeStamp, 
                  queueDuration, serviceSpecificINInformation, 
                  partialRecordNumber, partialRecordReason, 
                  relatedCallNumber, cDRPurpose, physicalLineCode, 
                  receivedDigits, operatorSpecific1AdditionalNumber, 
                  operatorSpecific2AdditionalNumber, 
                  operatorSpecific3AdditionalNumber, 
                  callingPartyCategory, callingPartyType, 
                  chargeInformation, progress, accessDelivery, 
                  trunkGroupOutgoing, trunkGroupIncoming, 
                  fallbackBearerService, teleservice, conversationTime, 
                  durationTimeACM, durationTimeBAnswer, 
                  durationTimeNoBAnswer, uUInfo, standardExtensions, 
                  recordExtensions, bPartyCategory, iSUPPreferred, 
                  networkManagementControls, glare, recordId, 
                  dataValidity, callStatus, carrierId, dPC, oPC }
    STATUS      current
    DESCRIPTION 
        "Provides for the CDR1 formatted call record."
    ::= { cdr2Groups 9 }

cdr2ConditionalFieldsGroup OBJECT-GROUP
    OBJECTS     { callType, clngPtyNbr, chargeNbr, clldPtyNbr, 
                  clldPtyNoa, origLnInfo, ingLrn, ingCic, ingCsi, 
                  ingCceId, ingTgProt, ingTgType, ingTgId, ingCallStart, 
                  ingGateId, ingCardId, ingSpanId, ingChanId, 
                  ingIsdnDChan, ingIsdnCrn, ingCreatConnCplt, 
                  ingAddrCplt, ingCallAns, transNbr, termLrn, transCic, 
                  ingCallRls, ingRlsCause, egrCceId, egrTgProt, 
                  egrTgType, egrTgId, egrCallStart, egrGateId, egrCardId, 
                  egrSpanId, egrChanId, egrIsdnDChan, egrIsdnCrn, 
                  egrCreatConnCplt, egrAddrCplt, egrCallAns, egrCallRls, 
                  egrRlsCause, chkptFirst, chkptLast, ingGateName, 
                  egrGateName, ingTgName, egrTgName, origGateIp, 
                  termGateIp, h323ConfId, ingCardPort, ingCardPath, 
                  egrCardPort, egrCardPath, ingTg, egrTg, dialedNbr, 
                  dialedNoa, redirNbr, redirNoa, redirInd, redirRsn, 
                  calledNbr, calledNoa, redirRsnOrig, redirCntr, 
                  redirPrsntnInd, ingJuris, egrJuris, ingTrunkBearCap, 
                  egrTrunkBearCap, transNetSelCarr, clngPtyNoa, 
                  ingRlsCauseIntrnl, egrRlsCauseIntrnl, egrClldNbr, 
                  egrClldNoa, egrCnndNbr, egrCnndNoa, clngPtyPrsntnInd, 
                  ingIri, egrOri, ingCallidExtrnl, egrCallidExtrnl, 
                  ingChargeInfo, egrChargeInfo, ingPrtlInd, 
                  ingNatfwdCliblkInd, ingNatfwdNtaInd, ingLastDvrtLnDigs, 
                  ingLastDvrtLnNoa, j7IngAddlPtyCat, j7IngChgAreaInfo, 
                  j7IngFwdCallInd, j7EgrAddlPtyCat, j7EgrChgAreaInfo, 
                  j7EgrBkwCallInd, j7CarrInfoXfer, ingSs7GnrcParm, 
                  egrSs7GnrcParm, ingPktsSent, ingPktsRcvd, ingPktsLost, 
                  ingPktsXfer, ingJitter, ingLtncy, egrPktsSent, 
                  egrPktsRcvd, egrPktsLost, egrPktsXfer, egrJitter, 
                  egrLtncy, ingCrctId, egrCrctId, ingCodec, egrCodec, 
                  ingLocGateId, egrLocGateId, ingCasCrctSzr, 
                  egrCasCrctSzr, ingZz, egrZz, ingCtryAddrType, 
                  egrCtryAddrType, ingPartition, egrPartition, 
                  ingClngPtyCat, ingRlsCauseLctn, egrRlsCauseLctn, 
                  clldPtyCat, callDuration, ingRlsDrctn, egrRlsDrctn, 
                  ingAnsLctim, egrAnsLctim, ingHlcChrsId, egrHlcChrsId, 
                  ingLlcXferCap, egrLlcXferCap, routeList, ingPointCode, 
                  egrPointCode }
    STATUS      current
    DESCRIPTION 
        "Conditional fields of the CDR2 format."
    ::= { cdr2Groups 10 }

cdr2Conformances MODULE-COMPLIANCE
    STATUS      current
    DESCRIPTION 
        "Provides compliance for this module."

    MODULE      -- this module

        MANDATORY-GROUPS        { cdrParameterGroup, 
                  cdrNotificationGroup, cdrMandatoryGroups, 
                  cdr2NotificationGroup, cdr2MandatoryGroups, 
                  cdr2MandatoryCallRecordFields, 
                  cdr2ConditionalFieldsGroup }

        GROUP   cdr1NotificationGroup
        DESCRIPTION   
              "Optional to also support CDR 1 format."

        GROUP   cdr1ConditionalGroups
        DESCRIPTION   
              "Optional to also support CDR 1 format."

        GROUP   cd1RecordFormatGroup
        DESCRIPTION   
              "Optional to also support CDR 1 format."

    ::= { cdr2Groups 11 }

END -- end of module OPENSS7-CDR2-MIB.

-- =============================================================================
-- vim: ft=mib comments=\f\:\",\b\:\-\-,\:\-\-,\f\b\:- fo+=tcqlornw tw=72 nocin nosi sts=4 sw=4
