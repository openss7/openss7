-- vim: ft=mib comments=\f\:\",\b\:\-\-,\:\-\-,\f\b\:- fo+=tcqlornw tw=64 nocin nosi sts=4 sw=4 et
-- =============================================================================
-- 
-- @(#) $RCSfile: OPENSS7-X400P-MIB.mib,v $ $Name:  $($Revision: 0.9.2.19 $) $Date: 2009-01-19 18:25:37 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-19 18:25:37 $ by $Author: brian $
--
-- -----------------------------------------------------------------------------
--
-- $Log: OPENSS7-X400P-MIB.mib,v $
-- Revision 0.9.2.19  2009-01-19 18:25:37  brian
-- - corrections
--
-- Revision 0.9.2.18  2009-01-19 16:41:39  brian
-- - rationalized mibs
--
-- Revision 0.9.2.17  2009-01-14 14:30:09  brian
-- - working up agents
--
-- Revision 0.9.2.16  2009-01-14 09:38:25  brian
-- - typos
--
-- Revision 0.9.2.15  2009-01-14 09:08:46  brian
-- - mib updates
--
-- Revision 0.9.2.14  2009-01-12 12:09:48  brian
-- - mib updates
--
-- Revision 0.9.2.13  2009-01-11 11:46:38  brian
-- - updates
--
-- Revision 0.9.2.12  2009-01-10 17:09:28  brian
-- - updated agents
--
-- Revision 0.9.2.11  2008-12-24 13:08:29  brian
-- - building ss7confd
--
-- Revision 0.9.2.10  2008-12-14 12:55:57  brian
-- - working up mibs
--
-- Revision 0.9.2.9  2008-10-11 04:34:40  brian
-- - cleanup MIBs
--
-- Revision 0.9.2.8  2008-04-29 07:11:23  brian
-- - updating headers for release
--
-- Revision 0.9.2.6  2008/01/10 19:55:44  brian
-- - updating mibs
--
-- Revision 0.9.2.5  2007/12/29 21:57:41  brian
-- - updates
--
-- Revision 0.9.2.4  2007/12/15 20:19:14  brian
-- - updates
--
-- Revision 0.9.2.3  2007/11/06 09:47:06  brian
-- - updated mibs
--
-- Revision 0.9.2.2  2007/10/15 01:14:28  brian
-- - updated MIBs
--
-- Revision 0.9.2.1  2007/09/29 14:31:39  brian
-- - added new mib files
--
-- =============================================================================

OPENSS7-X400P-MIB DEFINITIONS ::= BEGIN

IMPORTS
    MODULE-IDENTITY, OBJECT-IDENTITY, OBJECT-TYPE, Counter32, Integer32, 
    Unsigned32
        FROM SNMPv2-SMI
    TEXTUAL-CONVENTION, AutonomousType, DateAndTime, DisplayString, 
    RowPointer, RowStatus, StorageType, TimeInterval, TimeStamp, 
    TruthValue
        FROM SNMPv2-TC
    MODULE-COMPLIANCE, OBJECT-GROUP
        FROM SNMPv2-CONF
    SnmpAdminString
        FROM SNMP-FRAMEWORK-MIB
    PerfCurrentCount, PerfIntervalCount, PerfTotalCount
        FROM PerfHist-TC-MIB
    HCPerfValidIntervals, HCPerfInvalidIntervals, HCPerfTimeElapsed,
    HCPerfIntervalThreshold, HCPerfCurrentCount, HCPerfIntervalCount,
    HCPerfTotalCount
        FROM HC-PerfHist-TC-MIB
    StreamsModuleName
        FROM OPENSS7-STREAMS-MIB
    CommonLanguageName
        FROM OPENSS7-TC
    AdministrativeState, AlarmStatus, AvailabilityStatus, ControlStatus, 
    OperationalState, ProceduralStatus, SimpleNameType, StandbyStatus, 
    UnknownStatus, UsageState
        FROM OPENSS7-SMI-MIB
    openss7Modules
        FROM OPENSS7-SMI;

x400pMIB MODULE-IDENTITY
    LAST-UPDATED        "200901191603Z"
    ORGANIZATION
        "The OpenSS7 Project"
    CONTACT-INFO
        "Brian Bidulock
         OpenSS7 Corporation
         1469 Jefferys Crescent
         Edmonton AB  T6L 6T1
         CANADA
         Tel: +1 780 490 1141
         Fax: +1 780 490 1241
         Mob: +1 780 953 0557
         E-Mail: bidulock@openss7.org"
    DESCRIPTION
        "MIB Module for the X400P Drivers and Cards.  Note that, 
         unlike the OPENSS7-X400P-MX-MIB module, this module 
         includes span and channel configuration and is intended 
         on being used with the older X400P-SL SS7 drivers.

         This module is depreceated, use the OPENSS7-MX-MIB 
         instead."
    REVISION    "200901191603Z"
    DESCRIPTION
        "Rationalized OPENSS7-X400P-MIB abd OPENSS7-X400-MX-MIB.  
         Both these modules are deprecated now.  Use the 
         OPENSS7-MX-MIB instead."
    REVISION    "200901141143Z"
    DESCRIPTION
        "Added driver table to the MIB."
    REVISION    "200901111019Z"
    DESCRIPTION
        "Latest update of this module, mostly comments and file 
         formatting."
    REVISION    "200812222303Z"
    DESCRIPTION
        "Rationalized to OPENSS7-X400P-MX-MIB."
    REVISION    "200709290553Z"
    DESCRIPTION
        "First release of this module."
    ::= { openss7Modules 400 }

-- ====================================================================
-- TEXUTAL CONVENTIONS
-- ====================================================================

SpanIdentity ::= TEXTUAL-CONVENTION
    DISPLAY-HINT "1d:"
    STATUS      current
    DESCRIPTION
        "Provides a specification of a span identifier amoungst 
         all of the spans available on all cards in the system.  
         The octet string is coded as follows: the first two 
         octets is the module identity number of the device 
         driver, most significant octet first, the third octet 
         is the card number; and the fourth octet is the span 
         number on the card."
    SYNTAX      OCTET STRING (SIZE(0 | 4))

SpanNumber ::= TEXTUAL-CONVENTION
    DISPLAY-HINT "d-0"
    STATUS      current
    DESCRIPTION
        "Provides a specification of a span relative to a span 
         group.  This is a small ordinal number from 1 to 32.  
         The number zero (0) indicates no span or an entire span 
         group. The values 1..3 are used for E2; 1..4 for T1; 
         1..21 for E3; and 1..28 for T3."
    SYNTAX      Unsigned32 (0..32)

ChannelNumber ::= TEXTUAL-CONVENTION
    DISPLAY-HINT "d-0"
    STATUS      current
    DESCRIPTION
        "Provides a specification of a channel relative to a 
         span.  This is a small ordinal number from 1 to 24 for 
         T1 spans and 1 to 31 for E1 spans.  The number is the 
         same as the time slot number for the span.  The number 
         zero (0) indicates no chanel or an entire span."
    SYNTAX      Unsigned32 (0..31)

ChannelSet ::= TEXTUAL-CONVENTION
    STATUS      current
    DESCRIPTION
        "Provides a specificiation of a set of channels within a 
         span.  This is bit mask of the channels included in the 
         set (channels 1 through 24 for T1 and 1 through 31 for 
         E1)."
    SYNTAX      BITS {
        ch1(0), ch2(1), ch3(2), ch4(3), ch5(4), ch6(5), ch7(6), 
        ch8(7), ch9(8), ch10(9), ch11(10), ch12(11), ch13(12), 
        ch14(13), ch15(14), ch16(15), ch17(16), ch18(17), 
        ch19(18), ch20(19), ch21(20), ch22(21), ch23(22), 
        ch24(23), ch25(24), ch26(25), ch27(26), ch28(27), 
        ch29(28), ch30(29), ch31(30) }

PhysicalPointOfAppearance ::= TEXTUAL-CONVENTION
    STATUS      current
    DESCRIPTION
        "Provides a specification of a physical point of 
         appearance (e.g. card and port) that corresponds to a 
         trace termination point of a network arc (network 
         interface).  The PPA is coded as two octets, where the 
         first octet is the most significant 8 bits of the PPA 
         and the second octet is the least significant 8 bits of 
         the PPA."
    SYNTAX      OCTET STRING (SIZE(2))

x400pNotifications OBJECT IDENTIFIER
    ::= { x400pMIB 0 }

x400pObjects OBJECT IDENTIFIER
    ::= { x400pMIB 1 }

-- ====================================================================
-- TABLES
-- ====================================================================

x400pTables OBJECT IDENTIFIER
    ::= { x400pObjects 1 }

x400pSync OBJECT IDENTIFIER
    ::= { x400pTables 1 }

x400pSyncTable OBJECT-TYPE
    SYNTAX      SEQUENCE OF X400pSyncEntry
    MAX-ACCESS  not-accessible
    STATUS      current
    DESCRIPTION
        "The synchronization table is a table of synchronization 
         groups.  Equipped cards that are configured for 
         automatic synchronzation are assigned to a 
         synchronization group."
    ::= { x400pSync 1 }

x400pSyncEntry OBJECT-TYPE
    SYNTAX      X400pSyncEntry
    MAX-ACCESS  not-accessible
    STATUS      current
    DESCRIPTION
        "Each entry in the synchronization table represents a 
         synchronization source to be used for automatic 
         synchronization within each group in the order of the 
         index.  Rows may be created and deleted explicitly by 
         management stations.  Rows may be deleted implicitly as 
         a part of system operation when a card is disassociated 
         with a synchroniation group."
    INDEX       {
        x400pSyncGroup,
        x400pSyncIndex
    }
    ::= { x400pSyncTable 1 }

X400pSyncEntry ::= SEQUENCE {
    x400pSyncGroup
        Unsigned32,
    x400pSyncIndex
        Unsigned32,
    x400pSyncSpanId
        SpanIdentity,
    x400pSyncRowStatus
        RowStatus
}

x400pSyncGroup OBJECT-TYPE
    SYNTAX      Unsigned32 (1..16)
    MAX-ACCESS  not-accessible
    STATUS      current
    DESCRIPTION
        "Specifies the group number of the entry.  A 
         synchronization group is a group of cards which share a 
         common timing bus.  Membership in the group is the 
         cards which have an synchronization group value equal 
         to this index and a synchronization source setting of 
         syncAuto(6)."
    ::= { x400pSyncEntry 1 }

x400pSyncIndex OBJECT-TYPE
    SYNTAX      Unsigned32 (1..8)
    MAX-ACCESS  not-accessible
    STATUS      current
    DESCRIPTION
        "Specifies the index of the entry and the priority at 
         which the entry will be used for synchronization of the 
         card.  Index value 1 is the highest priority and index 
         value 8 is the lowest priority."
    ::= { x400pSyncEntry 2 }

x400pSyncSpanId OBJECT-TYPE
    SYNTAX      SpanIdentity
    MAX-ACCESS  read-create
    STATUS      current
    DESCRIPTION
        "Specifies the card and span to be used as a card 
         synchronization source at the priority of the 
         corresponding index.  Cards 1..16 and spans 1..4 can be 
         specified in accordance with the SpanIdentity textual 
         convention.  However, the card number specified must 
         belong to the same synchronization group as the indexed 
         group.  That is, the card must have its synchronization 
         group set to the index of this entry, and the card 
         synchronization source must be set to syncAuto(6)."
    ::= { x400pSyncEntry 3 }

x400pSyncRowStatus OBJECT-TYPE
    SYNTAX      RowStatus
    MAX-ACCESS  read-create
    STATUS      current
    DESCRIPTION
        "Provides a mechanism whereby management stations may 
         create or delete rows in this table.

         Rows may be created or deleted explicitly by management 
         stations or implicitly as a part of system oepration.  
         When a card is removed from a synchronization group (by 
         having its sychronization group number changed or 
         having its synchronization source set to other than 
         syncAuto(6)), the system may automatically delete rows 
         from this table."
    REFERENCE
        "STD 58, SNMPv2-TC RowStatus."
    ::= { x400pSyncEntry 4 }


x400pDriv OBJECT IDENTIFIER
    ::= { x400pTables 2 }

x400pDrivTable OBJECT-TYPE
    SYNTAX      SEQUENCE OF X400pDrivEntry
    MAX-ACCESS  not-accessible
    STATUS      current
    DESCRIPTION
        "The driver table is a table of device drivers.  Each 
         driver that provides support for hardware cards is 
         represented in this table."
    ::= { x400pDriv 1 }

x400pDrivEntry OBJECT-TYPE
    SYNTAX      X400pDrivEntry
    MAX-ACCESS  not-accessible
    STATUS      current
    DESCRIPTION
        "Each entry in the driver table represents a software 
         device driver that supports objects in this MIB.  Rows 
         in this table are generated automatically by the agent.  
         Additional rows may be added (but not removed) by a 
         management station."
    INDEX       {
        x400pDrivName
    }
    ::= { x400pDrivTable 1 }

X400pDrivEntry ::= SEQUENCE {
    x400pDrivName
        StreamsModuleName,
    x400pDrivIdnum
        Unsigned32,
    x400pDrivMajor
        Unsigned32,
    x400pDrivDescription
        SnmpAdminString,
    x400pDrivRevision
        SnmpAdminString,
    x400pDrivCopyright
        SnmpAdminString,
    x400pDrivSupportedDevice
        SnmpAdminString,
    x400pDrivContact
        SnmpAdminString,
    x400pDrivLicense
        INTEGER,
    x400pDrivDate
        DateAndTime,
    x400pDrivRowStatus
        RowStatus
}

x400pDrivName OBJECT-TYPE
    SYNTAX      StreamsModuleName
    MAX-ACCESS  not-accessible
    STATUS      current
    DESCRIPTION
        "Provides the STREAMS driver name associated with the 
         device driver.  This is equivalent to the strModName 
         entry in the OPENSS7-STREAMS-MIB.  This driver name 
         also describes the path to the device driver for the 
         agent to use in accessing the driver (e.g. 
         /dev/streams/mxDrivName/0)."
    ::= { x400pDrivEntry 1 }

x400pDrivIdnum OBJECT-TYPE
    SYNTAX      Unsigned32 (0..16383)
    MAX-ACCESS  read-only
    STATUS      current
    DESCRIPTION
        "Provides the STREAMS module identification number 
         associated with the device driver.  This is equivalent 
         to the strModIdnum  entry in the OPENSS7-STREAMS-MIB."
    ::= { x400pDrivEntry 2 }

x400pDrivMajor OBJECT-TYPE
    SYNTAX      Unsigned32 (0..16383)
    MAX-ACCESS  read-only
    STATUS      current
    DESCRIPTION
        "Provides the STREAMS driver major device number 
         associated with the device driver.  This is equivalent 
         to the strModMajor entry in the OPENSS7-STREAMS-MIB."
    ::= { x400pDrivEntry 3 }

x400pDrivDescription OBJECT-TYPE
    SYNTAX      SnmpAdminString
    MAX-ACCESS  read-only
    STATUS      current
    DESCRIPTION
        "Provides a brief one line description of the device 
         driver."
    ::= { x400pDrivEntry 4 }

x400pDrivRevision OBJECT-TYPE
    SYNTAX      SnmpAdminString
    MAX-ACCESS  read-only
    STATUS      current
    DESCRIPTION
        "Provides a brief one line description of the device 
         driver version and revision."
    ::= { x400pDrivEntry 5 }

x400pDrivCopyright OBJECT-TYPE
    SYNTAX      SnmpAdminString
    MAX-ACCESS  read-only
    STATUS      current
    DESCRIPTION
        "Provides a brief one line copyright statement."
    ::= { x400pDrivEntry 6 }

x400pDrivSupportedDevice OBJECT-TYPE
    SYNTAX      SnmpAdminString
    MAX-ACCESS  read-only
    STATUS      current
    DESCRIPTION
        "Provides a brief one line text description of the 
         supported devices.  This is the 
         MODULE_SUPPORTED_DEVICE() field associated with the 
         kernel module."
    ::= { x400pDrivEntry 7 }

x400pDrivContact OBJECT-TYPE
    SYNTAX      SnmpAdminString
    MAX-ACCESS  read-only
    STATUS      current
    DESCRIPTION
        "Provides the contact information (e.g. email address) 
         of the author or other contact for the device driver.  
         This is the MODULE_AUTHOR() field associated with the 
         kernel module."
    ::= { x400pDrivEntry 8 }

x400pDrivLicense OBJECT-TYPE
    SYNTAX      INTEGER {
        proprietary(0), gpl(1), gplV2(2), gplPlus(3), 
        dualBsdGpl(4), dualMitGpl(5), dualMplGpl(6) }
    MAX-ACCESS  read-only
    STATUS      current
    DESCRIPTION
        "Provides the Linux kernel license applicable to the 
         kernel module representing the device driver.  This 
         object is single-valued and can assume one of the 
         following values:

         - proprietary(0), non-free products;
         - gpl(1), GNU Public License v2 or later;
         - gplV2(2), GNU Public License v2;
         - gplPlus(3), GNU Public License v2 rights and more 
           (e.g. LGPL);
         - dualBsdGpl(4), GNU Public License v2 or BSD license 
           choice;
         - dualMitGpl(4), GNU Public License v2 or MIT license 
           choice;
         - dualMplGpl(4), GNU Public License v2 or MPL license 
           choice.

         This is the MODULE_LICENSE() field associated with the 
         kernel module."
    ::= { x400pDrivEntry 9 }

x400pDrivDate OBJECT-TYPE
    SYNTAX      DateAndTime
    MAX-ACCESS  read-only
    STATUS      current
    DESCRIPTION
        "Provides the date of the device driver."
    ::= { x400pDrivEntry 10 }

x400pDrivRowStatus OBJECT-TYPE
    SYNTAX      RowStatus
    MAX-ACCESS  read-create
    STATUS      current
    DESCRIPTION
        "Provides a mechanism whereby management stations may 
         create or delete rows in this table.  Rows added by 
         management stations persist across an agent reboot.  
         Management stations must provide a valid value for the 
         x400pDrivName field that corresponds to a device driver 
         in the managed system.  The agent will populate other 
         fields accordingly.  Invalid, unsupported or 
         non-existent device drivers will cause the row creation 
         request to be rejected with an inconsistent name.  
         Requests to destroy rows in this table that are 
         referenced in other tables will be likewise refused."
    ::= { x400pDrivEntry 11 }


x400pCard OBJECT IDENTIFIER
    ::= { x400pTables 3 }

x400pCardNextIndex OBJECT-TYPE
    SYNTAX      Unsigned32
    MAX-ACCESS  read-only
    STATUS      current
    DESCRIPTION
        "Provides the next available index into the 
         x400pCardTable for use by management stations when 
         adding rows to the table."
    REFERENCE
        "STD 58"
    ::= { x400pCard 1 }

x400pCardTable OBJECT-TYPE
    SYNTAX      SEQUENCE OF X400pCardEntry
    MAX-ACCESS  not-accessible
    STATUS      current
    DESCRIPTION
        "Provides the card table which indexes each card in the 
         managed element.  The Card Table provides an entry for 
         each of the equipped cards in the system."
    ::= { x400pCard 2 }

x400pCardEntry OBJECT-TYPE
    SYNTAX      X400pCardEntry
    MAX-ACCESS  not-accessible
    STATUS      current
    DESCRIPTION
        "Provides an entry in the card table.  Each entry in the 
         table indexes a card in the managed element.  Cards are 
         not intended on being added to or removed from this 
         table by management stations.  Physical insertion and 
         removal of cards is required and as these cards do not 
         support PCI hotplug, the system needs to be rebooted in 
         which case the cards will appear in this table on 
         reboot.  Therefore there is no NextIndex scalar or 
         RowStatus column for this table.

         Rows are neither created nor deleted explicity by 
         mangement stations but are present inherently as a part 
         of system operation.  Each entry in the table 
         corresponds to an existing and installed card."
    INDEX       {
        x400pDrivName,  -- shared index
        x400pCardIndex
    }
    ::= { x400pCardTable 1 }

X400pCardEntry ::= SEQUENCE {
    x400pCardIndex
        Unsigned32,
    x400pCardType
        AutonomousType,
    x400pCardIdentifier
        INTEGER,
    x400pCardRevision
        DisplayString,
    x400pCardChipType
        AutonomousType,
    x400pCardChipRevision
        DisplayString,
    x400pCardPciBus
        Unsigned32,
    x400pCardPciSlot
        Unsigned32,
    x400pCardPciIrq
        Unsigned32,
    x400pCardSpanType
        INTEGER,
    x400pCardMode
        BITS,
    x400pCardSyncMaster
        INTEGER,
    x400pCardSyncSource
        INTEGER,
    x400pCardSyncGroup
        Unsigned32,
    x400pCardAdministrativeState
        AdministrativeState,
    x400pCardOperationalState
        OperationalState,
    x400pCardUsageState
        UsageState,
    x400pCardAlarmStatus
        AlarmStatus,
    x400pCardProceduralStatus
        ProceduralStatus,
    x400pCardAvailabilityStatus
        AvailabilityStatus,
    x400pCardControlStatus
        ControlStatus,
    x400pCardUnknownStatus
        UnknownStatus,
    x400pCardStandbyStatus
        StandbyStatus,
    x400pCardSyncSpanId
        SpanIdentity,
    x400pCardSyncTransitions
        Counter32,
    x400pCardName
        CommonLanguageName,
    x400pCardStatus
        RowStatus
}

x400pCardIndex OBJECT-TYPE
    SYNTAX      Unsigned32 (1..16)
    MAX-ACCESS  not-accessible -- index
    STATUS      current
    DESCRIPTION
        "Provides an index for the card in the managed element.  
         This is the ordinal value of the card number and is 
         used as a handle to refer to this card.  This is a 
         small ordinal number beginning with a 1 and enumerating 
         as many as 16 cards."
    ::= { x400pCardEntry 1 }

x400pCardType OBJECT-TYPE
    SYNTAX      AutonomousType
    MAX-ACCESS  read-only
    STATUS      current
    DESCRIPTION
        "Indicates the card type for the entry using an 
         AutonomousType.  Following are some examples (some of 
         these example card types are obsolete):

         - zeroDotZero,
         - x400pCardTypePLX9030,
         - x400pCardTypePLXDevelopmentBoard,
         - x400pCardTypeX400P,
         - x400pCardTypeE400P,
         - x400pCardTypeT400P,
         - x400pCardTypeX400P-SS7,
         - x400pCardTypeE400P-SS7,
         - x400pCardTypeT400P-SS7,
         - x400pCardTypeV400PE,
         - x400pCardTypeV400PT,
         - x400pCardTypeV401PE,
         - x400pCardTypeV401PT,
        "
    ::= { x400pCardEntry 2 }

x400pCardIdentifier OBJECT-TYPE
    SYNTAX      INTEGER (SIZE(2))
    MAX-ACCESS  read-only
    STATUS      current
    DESCRIPTION
        "This is a 2 octet card identifier that is written to 
         the card to identify it regardless of the slot 
         position."
    ::= { x400pCardEntry 3 }

x400pCardRevision OBJECT-TYPE
    SYNTAX      DisplayString (SIZE(1))
    MAX-ACCESS  read-only
    STATUS      current
    DESCRIPTION
        "Indicates a single character revision (e.g. Rev. A) 
         indicating the board revision number.  It is typically 
         a single character beginning an A and working up.  That 
         is, the first revision of a board is Rev. A, the second 
         revision, Rev. B, an so on."
    ::= { x400pCardEntry 4 }

x400pCardChipType OBJECT-TYPE
    SYNTAX      AutonomousType
    MAX-ACCESS  read-only
    STATUS      current
    DESCRIPTION
        "Indicates the type of framer chip found in the device 
         using an autonomous type.  An example of values for 
         Dallas framer chips follow:

         - zeroDotZero, indicates that the equipment is either 
           absent, not configured or failed.

         - x400pChipTypeDS2152, the DS2152 T1 chip.
         - x400pChipTypeDS21352, the DS21352 T1 chip.
         - x400pChipTypeDS21552, the DS21552 T1 chip.

         - x400pChipTypeDS2154, the DS2154 E1 chip.
         - x400pChipTypeDS21354, the DS21354 E1 chip.
         - x400pChipTypeDS21554, the DS21554 E1 chip.

         - x400pChipTypeDS2155, the DS2155 E1/T1/J1 chip.
         - x400pChipTypeDS2156, the DS2156 E1/T1/J1 chip.

         The DS2152, DS21352, DS21552 are T1-only chips; the 
         DS2154, DS21354, DS21554 are E1-only chips; the DS2155 
         and DS2156 are E1/T1/J1 chips."
    ::= { x400pCardEntry 5 }

x400pCardChipRevision OBJECT-TYPE
    SYNTAX      DisplayString (SIZE(1))
    MAX-ACCESS  read-only
    STATUS      current
    DESCRIPTION
        "Indicates a single character revision (e.g. Rev. A) 
         indicate the chipset revision number.  It is typically 
         a single character beginning at A and working up.  That 
         is, the first revision of a chipset is Rev. A, the 
         second revision, Rev. B, and so on."
    ::= { x400pCardEntry 6 }

x400pCardPciBus OBJECT-TYPE
    SYNTAX      Unsigned32 (0..16)
    MAX-ACCESS  read-only
    STATUS      current
    DESCRIPTION
        "Indicates the PCI bus number for the PCI bus on which 
         the card is located.  The value zero (0) means that the 
         card is not on a bus (i.e. the card is unequiped)."
    ::= { x400pCardEntry 7 }

x400pCardPciSlot OBJECT-TYPE
    SYNTAX      Unsigned32 (0..16)
    MAX-ACCESS  read-only
    STATUS      current
    DESCRIPTION
        "Indicates the PCI bus slot number in which the card is 
         located.  The value zero (0) means that the card is not 
         in a slot (i.e.  the card is unequipped)."
    ::= { x400pCardEntry 8 }

x400pCardPciIrq OBJECT-TYPE
    SYNTAX      Unsigned32 (0..1024)
    MAX-ACCESS  read-only
    STATUS      current
    DESCRIPTION
        "Indicates the PCI IRQ that is assigned to the card.  
         The value zero (0) means that no IRQ is currently 
         assigned (i.e. the card is unequipped or is not 
         configured at the system level)."
    ::= { x400pCardEntry 9 }

x400pCardSpanType OBJECT-TYPE
    SYNTAX      INTEGER {
        none(1), t1(2), e1(3), j1(4) }
    MAX-ACCESS  read-create
    STATUS      current
    DESCRIPTION
        "Specifies or indicates the span type for the indexed 
         card.  Some cards and chipsets support mutliple span 
         types, in which case, this column sets the default span 
         type.  Some cards and chipsets only support a single 
         span type, in which case, this column is read-only and 
         provides the span type for all spans on the card.  The 
         value can be:

         - none(1), unknown or unspecified.

         - t1(2), the default is T1 operation.

         - e1(3), the default is E1 operation.

         - j1(4), the default is J1 operation.

         The value none(1) can be read but not written.  When 
         read, the value none(1) indicates that the equipment is 
         either absent, not configured or failed.

         Note that not all values are applicable to all card 
         types and chipsets.  Also, not all cards or chipsets 
         will allow all values to be set."
    ::= { x400pCardEntry 10 }

x400pCardMode OBJECT-TYPE
    SYNTAX      BITS { remoteLoopback(0), localLoopback(1) }
    MAX-ACCESS  read-create
    STATUS      current
    DESCRIPTION
        "Specifies the loopback mode for the entire card.  The 
         value may contain:

         - remoteLoopback(0), RSER is looped back on TSER for 
           all spans; that is, all received bits are looped back 
           to the transmit between the elastic store and the 
           system bus.  This is equivalent to a per-span payload 
           loopback, but is performed through the elastic store 
           and on a card basis.

         - localLoopback(1), RxBuf is driven by TxBuf; that is, 
           all transmitted data bits are passed to the 
           corresponding receive data bits between the elastic 
           store and the system bus.

         These modes are only useful for specialized testing and 
         the card must have a control status of subjectToTest(0) 
         or reservedForTest(2) before either of these values may 
         be added to the set."
    ::= { x400pCardEntry 11 }

x400pCardSyncMaster OBJECT-TYPE
    SYNTAX      INTEGER { slave(0), master(1) }
    MAX-ACCESS  read-create
    STATUS      current
    DESCRIPTION
        "Specifies whether the card is a slave or a master on 
         the external timing bus.  The value can be one of:

         - slave(0), the external timing bus may be used as a 
           synchronization source for the card by setting the 
           card synchronization source to syncExtern(5).  Spans 
           that use the external timing source should have their 
           span clocking set to slave(6).

         - master(1), the card drives the external timing bus 
           and the synchronization source may not also be set to 
           syncExtern(5)."
    ::= { x400pCardEntry 12 }

x400pCardSyncSource OBJECT-TYPE
    SYNTAX      INTEGER {
        syncSelf(0), sync1(1), sync2(2), sync3(3), sync4(4), 
        syncExtern(5), syncAuto(6) }
    MAX-ACCESS  read-create
    STATUS      current
    DESCRIPTION
        "Specifies the synchronization source for the entire 
         card (the synchronization applied to the TCLK pin on 
         all spans).  The synchronization source may be one of:

         - syncSelf(0), the internal clock will be used as a 
           synchronization source for the card.

         - sync1(1), sync2(2), sync3(3) or sync4(4), the 
           corresponding span RCLK output will be used as the 
           TCLK input for all spans on the card.

         - syncExtern(5), the TCLK input for all spans will be 
           taken from the external timing bus.

         - syncAuto(6), the driver will use the spans specified 
           in the x400pSyncTable side-table for the card as 
           synchronization sources.

         Note that the card synchronization source only affects 
         spans that are set for internal(2) or slave(6) span 
         clocking."
    ::= { x400pCardEntry 13 }

x400pCardSyncGroup OBJECT-TYPE
    SYNTAX      Unsigned32 (1..16)
    MAX-ACCESS  read-create
    STATUS      current
    DESCRIPTION
        "Specifies the synchronization group to which this card 
         belongs.  This value is only significant when the 
         synchronization source is set to syncAuto(6).  A 
         synchronization group is a group of cards, including 
         the current card in the set, that are connected 
         together with a timing cable and therefore share the 
         same timing bus.  The order of cards and spans that 
         will be used for timing are specified against the 
         synchronization group that has an group index of the 
         same value as this column."
    ::= { x400pCardEntry 14 }

x400pCardAdministrativeState OBJECT-TYPE
    SYNTAX      AdministrativeState
    MAX-ACCESS  read-create
    STATUS      current
    DESCRIPTION
        "Provides the administrative state of the card following 
         the AdministrativeState textual convention of the 
         OPENSS7-SMI-MIB module in accordance with the 
         administrativeState attribute of ITU-T Rec. X.721 | 
         ISO/IEC 10165-2.  The administrative state can have one 
         of the following values:

         - locked(0), the card is administratively prohibited 
           from providing service to users: no user will be 
           permitted to access a channel on the card.

         - unlocked(1), the card is administratively permitted 
           to provide service to users: users will be permitted 
           to access channels on the card.

         - shuttingDown(2), the card will continue to provider 
           service to existing users but will reject new users.  
           Once there are no more users of the card, the card 
           will move to the locked(1) state: no new users will 
           be permitted to access channels on the card, however, 
           existing users will be allowed to continue using 
           channels until they are released by the user."
    REFERENCE
        "OPENSS7-SMI-MIB, ITU-T Rec. X.721 | ISO/IEC 10165-2, 
         administrativeState."
    DEFVAL      { locked }
    ::= { x400pCardEntry 15 }

x400pCardOperationalState OBJECT-TYPE
    SYNTAX      OperationalState
    MAX-ACCESS  read-only
    STATUS      current
    DESCRIPTION
        "Provides the operational state of the card following 
         the OperationalState textual convention of the 
         OPENSS7-SMI-MIB module in accordance with the 
         operationalState attribute of ITU-T Rec. X.721 | 
         ISO/IEC 10165-2.  The operational state can have one of 
         the following values:

         - disabled(0), the card is inoperable and unable to 
           provide service to users;

         - enabled(1), it is partially or fully operable and 
           available for use."
    REFERENCE
        "OPENSS7-SMI-MIB, ITU-T Rec. X.721 | ISO/IEC 10165-2, 
         operationalState."
    DEFVAL      { disabled }
    ::= { x400pCardEntry 16 }

x400pCardUsageState OBJECT-TYPE
    SYNTAX      UsageState
    MAX-ACCESS  read-only
    STATUS      current
    DESCRIPTION
        "Provides the usage state of the card following the 
         UsageState textual convention of the OPENSS7-SMI-MIB 
         module in accordance with the usageState attribute of 
         ITU-T Rec. X.721 | ISO/IEC 10165-2.

         The usage state can be one of the following:

         - idle(0), the card is not curently in use; no channels 
           are in use.

         - active(1), the card is in use and has sufficient 
           operating capacity to provide for additional users 
           simultaneously (i.e.  some channel in some span is 
           idle(0)); some channels are in use.

         - busy(2), the card is in use and has no spare capacity 
           (i.e.  all spanse are busy(2)): all spans and 
           channels are in use."
    REFERENCE
        "OPENSS7-SMI-MIB, ITU-T Rec. X.721 | ISO/IEC 10165-2, 
         usageState."
    DEFVAL      { idle }
    ::= { x400pCardEntry 17 }

x400pCardAlarmStatus OBJECT-TYPE
    SYNTAX      AlarmStatus
    MAX-ACCESS  read-create
    STATUS      current
    DESCRIPTION
        "Provides the alarm status for the card following the 
         AlarmStatus textual convention of the OPENSS7-SMI-MIB 
         module in accordance with the alarmStatus attribute of 
         ITU-T Rec. X.721 | ISO/IEC 10165-2.  The alarm status 
         is set-valued and may contain:

         - underRepair(0), the card is marked as under repair 
           either locally or by a management station; the card 
           is currently being repaired, the operational state is 
           disabled(0).

         - critical(1), one or more critical faults were 
           detected for which alarms are oustanding; does not 
           occur.

         - major(2), one or more major faults were detected for 
           which alarms are oustanding; does not occur.

         - minor(3), one or more minor faults were detected for 
           which alarms are outstanding; indicates that one or 
           more minor alarms indicating a faults have been 
           detected in the resource, and have not yet been 
           cleared, the operational status is enabled(1).

         - alarmOutstanding(4), one more more alarms are 
           outstanding; indicates that one or more alarms have 
           been detected in the resource, and have not yet been 
           cleared, the condition of which may be disabling.  
           When alarmOutstanding(4) is set, and the operational 
           state is enabled(1), other status and state 
           attributes provide additional information, 
           particularly the carrier alarm related columns.

         The alarm status for the card is not directly 
         associated with the alarm status of the spans provided 
         by the card.  Alarm notifications associated with the 
         card occur when synchronization is lost the span 
         currently used as a synchronization source and the card 
         is searching for another synchronization source."
    REFERENCE
        "OPENSS7-SMI-MIB, ITU-T Rec. X.721 | ISO/IEC 10165-2, 
         alarmStatus."
    DEFVAL      { '00000'B }
    ::= { x400pCardEntry 18 }

x400pCardProceduralStatus OBJECT-TYPE
    SYNTAX      ProceduralStatus
    MAX-ACCESS  read-only
    STATUS      current
    DESCRIPTION
        "Provides the procedural status of the card following 
         the ProceduralStatus textual convention of the 
         OPENSS7-SMI-MIB module in accordance with the 
         proceduralStatus attribute of ITU-T Rec. X.721 | 
         ISO/IEC 10165-2.  The procedural status is set-valued 
         and may contain the following:

         - initializationRequired(0), the card requires 
           initialization by the management station before it 
           can perform normal functions and this procedure has 
           not been initiated.  The operational state is 
           disabled; a driver has not been loaded against this 
           card or the card has not been configured for 
           operation; the operational state is disabled(0).

         - notInitialized(1), the card requires initialization 
           before it can perform its normal functions and this 
           procedure has not been initiated.  The card 
           initializes itself autonomously; the operational 
           state is disabled; a driver has been loaded against 
           the card and the card has been configured for 
           operation; however, spans still require configuration 
           before the channels on the card are usable; the 
           operational state is disabled(1).

         - initializing(2), the card requires initialization 
           before it can perform its normal functions and this 
           procedure has been initiated but is not yet complete; 
           when present, the initialization requried condition 
           is absent; the operational state is disabled; spans 
           are being initialized; the operational state is 
           enabled(1).

         - reporting(3), the card is reporting the results of a 
           procedure; this condition is not applicable;

         - terminating(4), the card is in a termination phase; 
           if the resource does not initialize itself 
           autonomously, the initialization required condition 
           is also present and operational state is disabled; 
           the resource is in a termination phase and the driver 
           is being unloaded; the operational state is 
           disabled(0).
        "
    REFERENCE
        "OPENSS7-SMI-MIB, ITU-T Rec. X.721 | ISO/IEC 10165-2, 
         proceduralStatus."
    DEFVAL      { '00000'B }
    ::= { x400pCardEntry 19 }

x400pCardAvailabilityStatus OBJECT-TYPE
    SYNTAX      AvailabilityStatus
    MAX-ACCESS  read-only
    STATUS      current
    DESCRIPTION
        "Provides the availability status of the card following 
         the AvailabilityStatus textual convention of the 
         OPENSS7-SMI-MIB module in accordance with the 
         availabilityStatus attribute of ITU-T Rec. X.721 | 
         ISO/IEC 10165-2.  The availability status is set-valued 
         and may contain the following:

         - inTest(0), the card is undergoing a test procedure.  
           The administrative state is locked(0) and the 
           operational state is disabled(1).  This condition 
           exists while the card is powering up or is being 
           reset.  Not applicable.  The card is not tested as a 
           whole.

         - failed(1), the card has an internal fault that 
           prevents it from operating.  The operational state is 
           disabled.  Some cards fail when firmware cannot be 
           loaded, or the card cannot be configured for 
           operation, or some aspect of the hardware is 
           incompatible with a driver.  The operational state is 
           disabled.  An alarm will have been generated.

         - powerOff(2), the card requires power to be applied 
           and is not powered on.  For example, power 
           managements may have removed power from the device.  
           Not applicable.  Some cards do not support power 
           management.

         - offLine(3), the card requires a routing operation to 
           be performed to place it online an make it available 
           for use.  The operation may be manual or automatic, 
           or both.  The operational state is disabled.  When 
           the card is configured for use but the transmitters 
           and receivers have been powered down, the card is 
           considered offline.

         - offDuty(4), the card has been made inactve by an 
           internal control process in accordance with a 
           predetermined time schedule.  Under normal 
           conditions, the control process can be expected to 
           reactivate the card at some scheduled time.

         - dependency(5), the card cannot operate because some 
           other resource on which it depends is unavailable.  
           Some cards have the dependency that spans and 
           channels must at least be partially configured before 
           they are available for use.  This value is reflected 
           until at least one span and one channel are 
           configured.

         - degraded(6), the card is operating with degraded 
           performance.  This is the case when the card is 
           searching for a new synchronization source and a 
           yellow or red alarm condition has occurred on the 
           current synchronization source.  Some cards are 
           degraded when thier spans or circuits are degraded.

         - notInstalled(7), the card is not present in the 
           system or is incomplete.  The card does not exist in 
           the system, or the card exists in the system but is 
           not loaded with a driver.  The operational state is 
           diabled(0).

         - logFull(8), not used.  Not applicable."
    REFERENCE
        "OPENSS7-SMI-MIB, ITU-T Rec. X.721 | ISO/IEC 10165-2, 
         availabilityStatus."
    DEFVAL      { '000000000'B }
    ::= { x400pCardEntry 20 }

x400pCardControlStatus OBJECT-TYPE
    SYNTAX      ControlStatus
    MAX-ACCESS  read-create
    STATUS      current
    DESCRIPTION
        "Provides the control status of the card following the 
         ControlStatus textual convention of the OPENSS7-SMI-MIB 
         module and in accordance with the controlStatus 
         attribute of ITU-T Rec. X.721 | ISO/IEC 10165-2.  The 
         control status is set-valued and may contain:

         - subjectToTest(0), the card is available to normal 
           users but tests may be conducted on it simultaneously 
           at unpredicatble times, which may cause it to exhibit 
           unusual characteristics to users.  Not applicable.

         - partOfServicesLocked(1), when present, a manager has 
           administratively locked some part of the card.  The 
           card may exhibit this value when the card is 
           unlocked(1), but one or more of its spans or channels 
           is locked(1).

         - reservedForTest(2), when present, the card is 
           undergoing a test procedures and is unavailable to 
           users.  Not applicable.

         - suspended(3), when present, service has been 
           administratively suspended to users.  Not 
           applicable."
    REFERENCE
        "OPENSS7-SMI-MIB, ITU-T Rec. X.721 | ISO/IEC 10165-2, 
         controlStatus."
    DEFVAL      { '0000'B }
    ::= { x400pCardEntry 21 }

x400pCardUnknownStatus OBJECT-TYPE
    SYNTAX      UnknownStatus
    MAX-ACCESS  read-only
    STATUS      current
    DESCRIPTION
        "Provides the unknown status of the card following the 
         UnknownStatus textual convention of the OPENSS7-SMI-MIB 
         module in accordance with the unknownStatus attribute 
         of ITU-T Rec.  X.721 | ISO/IEC 10165-2.  It indicates 
         whether the values of other state and status objects 
         for this row are known or not.

         - false(0), the status of the objects is not unknown.
         - true(1), the status of the objects is unknown.
        "
    REFERENCE
        "OPENSS7-SMI-MIB, ITU-T Rec. X.721 | ISO/IEC 10165-2, 
         unknownStatus."
    DEFVAL      { false }
    ::= { x400pCardEntry 22 }

x400pCardStandbyStatus OBJECT-TYPE
    SYNTAX      StandbyStatus
    MAX-ACCESS  read-only
    STATUS      current
    DESCRIPTION
        "Provides the standby status of the card according to 
         the StandbyStatus textual convention.  This status 
         returns a standby status when the card has been 
         configured in the system to act as a backup unit for 
         another card providing service to the same span.  This 
         is performed by placing the receivers into high 
         impedance mode, and powering down the transmitters.

         - hotStandby(0), The receivers are in high impedance 
           mode and are monitoring the T1/E1/J1 spans, however, 
           the transmitters are open-circuited.  In this case, 
           the card is syncrhonized to the incoming frames and 
           ready to be brought into service by merely powering 
           up the transmitters.

         - coldStandby(1), Both the receives and the 
           transmitters are open-circuited, or are connected to 
           a separate facility via a DACCS or other 
           cross-connect system which will be connected when a 
           changeover occurs.

         - providingService(2), Both the receivers and 
           transmitters are connects and powered up.  The spans 
           on the card are passing data to and from the wire.

         There are a number of backup arrangements possible with 
         this card, however, have an entire card act as a backup 
         for another entire card is the only way that line 
         synchronization can be made the same for both cards."
    REFERENCE
        "OPENSS7-SMI-MIB, ITU-T Rec. X.721 | ISO/IEC 10165-2, 
         standbyStatus."
    DEFVAL      { providingService }
    ::= { x400pCardEntry 23 }

x400pCardSyncSpanId OBJECT-TYPE
    SYNTAX      SpanIdentity
    MAX-ACCESS  read-only
    STATUS      current
    DESCRIPTION
        "Indicates which card and span is being used as the 
         current synchronization source for the indexed card.  
         When the synchronization source is set to syncSelf(0) 
         or syncExtern(5), this value will be the null octet 
         string.  When the synchronization source is set to 
         sync1(1), sync2(2), sync3(3) or sync4(4), the value 
         will always ben the same as the identifier of span 1, 
         2, 3 or 4, respectively, for the indexed card.  When 
         the synchronization source is set to syncAuto(6), the 
         value reflectes the identifier of the span currently 
         providing the synchronization source, or the null octet 
         string if no span is providing the synchroniation 
         source."
    ::= { x400pCardEntry 24 }

x400pCardSyncTransitions OBJECT-TYPE
    SYNTAX      Counter32
    MAX-ACCESS  read-only
    STATUS      current
    DESCRIPTION
        "Indicates the number of times since the last 
         discontinuity that the synchronization span has 
         transitioned."
    ::= { x400pCardEntry 25 }

x400pCardName OBJECT-TYPE
    SYNTAX      CommonLanguageName
    MAX-ACCESS  read-only
    STATUS      current
    DESCRIPTION
        "Provides the name of the card using COMMON LANGUAGE 
         procedures and the CommonLanguageName textual 
         convention."
    REFERENCE
        "OPENSS7-TC"
    ::= { x400pCardEntry 26 }

x400pCardStatus OBJECT-TYPE
    SYNTAX      RowStatus
    MAX-ACCESS  read-only
    STATUS      current
    DESCRIPTION
        "Provides management stations with the ability to add 
         and delete rows from the x400pCardTable.  All written 
         columns in all rows are persistent across agent reboot.  
         Management stations may add to this table but may not 
         add to the subordinate tables.  Entries in subordinate 
         tables are established automatically by the agent when 
         a row is created in this table.

         The primary purpose for allowing management stations to 
         add to this table is to permit management station to 
         configure cards that have not yet been installed in the 
         system.

         Rows cannot be deleted that correspond to physical 
         cards."
    ::= { x400pCardEntry 27 }


x400pSpan OBJECT IDENTIFIER
    ::= { x400pTables 4 }

x400pSpanTable OBJECT-TYPE
    SYNTAX      SEQUENCE OF X400pSpanEntry
    MAX-ACCESS  not-accessible
    STATUS      current
    DESCRIPTION
        "The Span Table provides an entry for each of the 
         equipped spans in the system."
    ::= { x400pSpan 1 }

x400pSpanEntry OBJECT-TYPE
    SYNTAX      X400pSpanEntry
    MAX-ACCESS  not-accessible
    STATUS      current
    DESCRIPTION
        "Rows are neither created nor deleted explicitly by 
         management stations but are present inherently as a 
         part of system operation.  Each entry in the table 
         corresponds to a equipped and installed span."
    INDEX       {
        x400pDrivName,  -- shared index
        x400pCardIndex, -- shared index
        x400pSpanIndex
    }
    ::= { x400pSpanTable 1 }

X400pSpanEntry ::= SEQUENCE {
    x400pSpanIndex
        Unsigned32,
    x400pSpanName
        CommonLanguageName,
    x400pSpanDevice
        RowPointer,
    x400pSpanEquipmentId
        PhysicalPointOfAppearance,
    x400pSpanType
        INTEGER,
    x400pSpanNumber
        SpanNumber,
    x400pSpanRate
        INTEGER,
    x400pSpanMode
        BITS,
    x400pSpanCrc
        INTEGER,
    x400pSpanClocking
        INTEGER,
    x400pSpanPriority
        Unsigned32,
    x400pSpanCoding
        INTEGER,
    x400pSpanFraming
        INTEGER,
    x400pSpanLineImpedance
        INTEGER,
    x400pSpanLineMode
        INTEGER,
    x400pSpanLineLength
        INTEGER,
    x400pSpanLineAttenuation
        INTEGER,
    x400pSpanLineGain
        INTEGER,
    x400pSpanLineDelay
        Unsigned32,
    x400pSpanTxLevel
        INTEGER,
    x400pSpanRxLevel
        INTEGER,
    x400pSpanAlarmSettleTime
        TimeInterval,
    x400pSpanLineCodeTime
        TimeInterval,
    x400pSpanPrimary
        Unsigned32,
    x400pSpanDataLink
        BITS,
    x400pSpanLineCode
        INTEGER,
    x400pSpanAlarmSeverityMappingProfile
        RowPointer,
    x400pSpanAdministrativeState
        AdministrativeState,
    x400pSpanOperationalState
        OperationalState,
    x400pSpanUsageState
        UsageState,
    x400pSpanAlarmStatus
        AlarmStatus,
    x400pSpanProceduralStatus
        ProceduralStatus,
    x400pSpanAvailabilityStatus
        AvailabilityStatus,
    x400pSpanControlStatus
        ControlStatus,
    x400pSpanStandbyStatus
        StandbyStatus,
    x400pSpanUnknownStatus
        UnknownStatus,
    x400pSpanSap
        RowPointer,
    x400pSpanLoopbackStatus
        BITS,
    x400pSpanLineStatus
        BITS,
    x400pSpanAlarms
        BITS,
    x400pSpanEvents
        BITS,
    x400pSpanReceiveLevel
        Unsigned32,
    x400pSpanReceiveThreshold
        Unsigned32,
    x400pSpanRowStatus
        RowStatus
}

x400pSpanIndex OBJECT-TYPE
    SYNTAX      Unsigned32 (0..4)
    MAX-ACCESS  not-accessible
    STATUS      current
    DESCRIPTION
        "Provides an index by card of the span.  This is a small 
         integer from (0..4), where 1 through 4 indicates 
         spans 1 through 4 on the card, and the special index 0 
         indicates defaults or settings for the entire card.  
         Active rows corresponding to spans can only be added to 
         this table by the agent.  Management stations can add 
         notinservice rows and control or configure the span by 
         accessing the read-create columns for each span entry."
    ::= { x400pSpanEntry 1 }

x400pSpanName OBJECT-TYPE
    SYNTAX      CommonLanguageName
    MAX-ACCESS  read-create
    STATUS      current
    DESCRIPTION
        "Provides an optional administrative COMMON LANGUAGE 
         NAME for the span using the CommonLanguageName textual 
         convention of the OPENSS7-TC module and in accordance 
         with Telcordia procedures.  This name, when provided, 
         must uniquely identify a row in this table.  Management 
         station creation requests with names that have already 
         been assigned to an existing row will be refused as 
         having an inconsistent value."
    DEFVAL      { '' }
    ::= { x400pSpanEntry 2 }

x400pSpanDevice OBJECT-TYPE
    SYNTAX      RowPointer
    MAX-ACCESS  read-create
    STATUS      current
    DESCRIPTION
        "Specifies a row in a table that models the device or 
         driver that provides the span.  In some implementations 
         this may model a pseudo-device driver rather than a 
         hardware device (equipment) or real device driver.  
         This identifier must be specified on row creation (by 
         agent or management station) and must be a valid device 
         identifier.  For example, for the x400p driver modelled 
         by the OPENSS7-X400P-MX-MIB, this is a RowPointer to 
         the x400pCardEntry in the x400pCardTable that 
         corresponds to the hardware card that provides the 
         span."
    DEFVAL      { { zeroDotZero } }
    ::= { x400pSpanEntry 3 }

x400pSpanEquipmentId OBJECT-TYPE
    SYNTAX      PhysicalPointOfAppearance
    MAX-ACCESS  read-create
    STATUS      current
    DESCRIPTION
        "Provides the equipment identifier that identifies the 
         span within the device, driver or system.  This 
         equipment identifier must be specified on row creation 
         and must be a valid equipment identifier."
    ::= { x400pSpanEntry 4 }

x400pSpanType OBJECT-TYPE
    SYNTAX      INTEGER {
        none(0), t1(1), e1(2), j1(3), e2(4), e3(5), t3(6) }
    MAX-ACCESS  read-create
    STATUS      current
    DESCRIPTION
        "Provides the group interface type for the span and the 
         span type.  This object is single-valued and can have 
         one of the following values:

         - none(0), unknown or unspecified (this value cannot be 
           set); the interface is capable of being placed in any 
           of the modes and has not yet been configured for one 
           of them;

         - t1(1), the span is a T1 or DSX1 span;

         - e1(2), the span is an E1 span;

         - j1(3), the span is a J1 or DSX1 span;

         - e2(4), the span is an E1 span in an E2 facility;

         - e3(5), the span is an E1 span in an E3 facility;

         - t3(6), the span is a T1 span in a T3 facility.

         The value none(0) can be read but not written.  When 
         read, the value none(0) indicates that the equipment is 
         either absent, not configured, or failed.

         For some implementations this might be a read-only 
         field.  The default value if unspecified on row 
         creation is implementation specific."
    DEFVAL      { none }
    ::= { x400pSpanEntry 5 }

x400pSpanNumber OBJECT-TYPE
    SYNTAX      SpanNumber
    MAX-ACCESS  read-create
    STATUS      current
    DESCRIPTION
        "Specifies the span number within an E2, E3 or T3 
         facility.  For simple span types this value is zero.  
         The agent may supply a default based on the 
         x400pSpanEquipmentId, or may require that this value be 
         set upon creation."
    ::= { x400pSpanEntry 6 }

x400pSpanRate OBJECT-TYPE
    SYNTAX      INTEGER (0|1544|2048)
    UNITS       "kilobits per second"
    MAX-ACCESS  read-only
    STATUS      current
    DESCRIPTION
        "Provides the span unframed syncrhonous bit rate in 
         kilobits per second.  This is either the T1/J1 rate 
         (1544 kbps) when configured for T1 or J1, or the E1 
         rate (2048) when for E1.  Returns zero (0) when the 
         hardware has not yet been configured for any interface 
         type."
    DEFVAL      { 0 }
    ::= { x400pSpanEntry 7 }

x400pSpanMode OBJECT-TYPE
    SYNTAX      BITS {
        local(0), remote(1), framer(2), payload(3) }
    MAX-ACCESS  read-create
    STATUS      current
    DESCRIPTION
        "Specifies the loopback to apply.  This object may 
         include the following values:

         - local(0), payload bits for tranmission from the host 
           interface are looped back on receive payload bits 
           (data may be transmitted as normal but the received 
           payload is discarded);

         - remote(1), the received serial bit stream is looped 
           back after the line interface unit to the transmitted 
           serial bit stream (transmit data from the host is 
           ignored, but received data may be delivered to the 
           host);

         - framer(2), the transmitted serial bit stream is 
           looped back at the framer to the receive serial bit 
           stream (unframed all ones is transmittted to the line 
           interface and received information is ignored);

         - payload(3), the received payload bits are looped back 
           to the tranmit payload bits at the framer 
           (transmitted data from the host is ignored, but 
           received data may be delivered to the host).

         Only one of framer(2) or payload(3) may be present.  
         Only one of local(0) and remote(1) may be present.  
         local(0) and framer(2) are only useful for specialized 
         testing.  The span must have a control status of 
         subjectToTest(0) or reservedForTest(2) before any 
         values may be added to the set by a management station.

         These values represent the loopback condition that has 
         been set by a management station or locallly as a part 
         of system operations.  The current loppback condition 
         is reported in the x400pSpanLoopbackStatus object.

         To request or remote a loopback at the far end, use the 
         x400pSpanLineCode object."
    DEFVAL      { '0000'B }
    ::= { x400pSpanEntry 8 }

x400pSpanCrc OBJECT-TYPE
    SYNTAX      INTEGER {
        none(0), crc4(1), crc5(2), crc6(3), crc6j(4) }
    MAX-ACCESS  read-create
    STATUS      current
    DESCRIPTION
        "Provides the cyclic redundancy check code calculation 
         that is performed on the framing and the policy for the 
         span.  This object is single-valued and can assume one 
         of the following values:

         - none(0), the span has not yet been configured for a 
           CRC calculation and the hardware has not yet been 
           enabled;

         - crc4(1), the span is configured for CRC4 calculation 
           (E1); CRC4 is used for MF alignment in addition to 
           CRC5 for errored frames on E1 spans;

         - crc5(2), the span is configured for CRC5 calculation 
           (E1); CRC4 is not used for MF alignment, only CRC5 is 
           used for errored frames on E1 spans (default for E1);

         - crc6(3), the span is configured for CRC6 calculation 
           (T1); CRC6 is used on T1 spans;

         - crc6j(4), the span is configured for CRC6J 
           calculation (J1); CRC6J is used on J1 spans.

         Not all values are valid for all span types.  The agent 
         may refuse settings that conflict with the span type.  
         It may be necessary for the span to be in a disabled 
         operational state, in a locked administrative state, or 
         not in service via the row status, for the agent to 
         permit changing this value.  The value may be changed 
         autonomously by the agent when the interface type is 
         changed.

         The value none(0) can be read but not written.  When 
         read, the value none(0) indicates that the equipment is 
         either absent, not configured, or failed."
    DEFVAL      { none }
    ::= { x400pSpanEntry 9 }

x400pSpanClocking OBJECT-TYPE
    SYNTAX      INTEGER {
        none(0), loop(1), local(2), internal(3), external(4), 
        adaptive(5) }
    MAX-ACCESS  read-create
    STATUS      current
    DESCRIPTION
        "Provides the clock source for the span.  This object is 
         single-valued and can assume one of the following 
         values:

         - none(0), the default clocking for the span, or the 
           span has not yet been configured for clocking, the 
           value is unknown or unspecified (the span might not 
           be operational while this value is present);

         - loop(1), loop clocking: the clock is recovered from 
           the receive line (e.g. using digital PLL) and used to 
           drive the transmit clock for the span;

         - local(2), the timing source is internal to the device 
           (e.g.  provided by a crystal oscillator);

         - internal(3), internal clocking: the span receives its 
           clocking from an internal source (i.e. whatever is 
           defined for the device);

         - external(4), external clocking: the span receives its 
           clocking from an external source (e.g. an external 
           timing bus or timing input);

         - adaptive(5), clocking is adpated to the DSU side 
           system or serial bus;

         Not all values are applicable to all card types.  Not 
         all chip sets are capable of setting all values.  The 
         agent will refuse any value that is not possible given 
         the hardware or is inconsistent with the span type.

         The value none(0) can be read but not written.  When 
         read, the value none(0) indicates that the equipment is 
         either absent, not configured, or failed."
    ::= { x400pSpanEntry 10 }

x400pSpanPriority OBJECT-TYPE
    SYNTAX      Unsigned32
    MAX-ACCESS  read-create
    STATUS      current
    DESCRIPTION
        "Specifies or indicates the priority of this span as a 
         timing source.  When zero(0), this span will not be 
         used as a timing source.  When non-zero, the recovered 
         receive clock of this span will be used as the timing 
         source with the priority given."
    ::= { x400pSpanEntry 11 }

x400pSpanCoding OBJECT-TYPE
    SYNTAX      INTEGER {
        none(0), ami(1), b6zs(2), b8zs(3), hdb3(4), jbzs(5), 
        zbtsi(6) }
    MAX-ACCESS  read-create
    STATUS      current
    DESCRIPTION
        "Provides the span line coding for the PCM signal.  This 
         object is single-valued and can assume one of the 
         following values:

         - none(0), the value is unknown or unspecified (the 
           span might not be operational while this value is 
           present);

         - ami(1), Alternate Mark Inversion (AMI), applicable to 
           all span types;

         - b6zs(2), Bipolar with 6 Zero Substitution (B6ZS), 
           applicable to DS3 span types, not used;

         - b8zs(3), Bipolar with 8 Zero Substitution (B8ZS), 
           applicable to, and the default for, T1 and J1 spans;

         - hdb3(4), High-Density Bipolar 3 (HDB3), applicable 
           to, and the default for, E1 spans;

         - jbzs(5), Jammed Bit Zero Suppression (JBZS), 
           applicable to T1 clear channel and E1 CCS spans;

         - zbtsi(6), Zero Byte Time Slot Interchange (ZBTSI), 
           not used.

         Not all values are applicable to all span types.  Not 
         all chip sets are capable of setting all values.  The 
         agent will refuse any value that is not possible given 
         the hardware or is inconsistent with the span type.

         The value none(0) can be read but not written.  When 
         read, the value none(0), indicates that the equipment 
         is either absent, not configured, or failed."
    ::= { x400pSpanEntry 12 }

x400pSpanFraming OBJECT-TYPE
    SYNTAX      INTEGER {
        none(0), ccs(1), cas(2), sf(3), d4(4), esf(5) }
    MAX-ACCESS  read-create
    STATUS      current
    DESCRIPTION
        "Provides the framing for the span.  This object is 
         single-valued and can assume one of the following 
         values:

         - none(0), the framing is unknown or unspecified;

         - ccs(1), common channel signalling framing for E1 
           spans (CCS signalling on TS16 without CAS MF); 
           setting this value causes the CRC setting to default 
           to crc5(2);

         - cas(2), channel associated signalling framing for E1 
           spans (CAS signalling on TS16 with CAS MF); setting 
           this value causes the CRC setting to default to 
           crc4(1);

         - sf(3), super-frame (SF) framing for T1 spans;

         - d4(4), D4 framing for T1 spans;

         - esf(5), extended super-frame framing for T1 or J1 
           spans.

         Not all values are applicable to all span types.  Not 
         all chip sets are capable of setting all values.  The 
         agent will refuse any value that is not possible given 
         the hardware or is inconsistent with the span type.

         The value none(0) can be read but not written.  When 
         read, the value none(0) indicates that the equipment is 
         either absent, not configured, or failed."
    ::= { x400pSpanEntry 13 }

x400pSpanLineImpedance OBJECT-TYPE
    SYNTAX      INTEGER {
        none(0), unbalanced75ohm(1), balanced100ohm(2), 
        balanced120ohm(3) }
    MAX-ACCESS  read-create
    STATUS      current
    DESCRIPTION
        "Specifies and indicates the line impedance of the span.  
         The object can have one of the following values:

         - none(0), unknown or unspecified;

         - unbalanced75ohm(1), unbalanced 75 Ohms, for E1 spans;

         - balanced100ohm(2), balanced 100 Ohms, for T1 or J1 
           spans;

         - balanced120ohm(3), balanced 120 Ohms, for E1 spans.

         The value none(0) can be read but not written.  When 
         read, the value none(0) indicates that the equipment is 
         either absent, not configured, or failed."
    ::= { x400pSpanEntry 14 }

x400pSpanLineMode OBJECT-TYPE
    SYNTAX      INTEGER {
        none(0), dsu(1), csu(2), monitor(3) }
    MAX-ACCESS  read-create
    STATUS      current
    DESCRIPTION
        "Provides the span line mode.  The object can have one 
         of the following values:

         - none(0), unknown or unspecified;

         - dsu(1), data service unit (DSU) application 
           (short-haul E1 and limited long-haul, DSX, T1/J1 
           spans);

         - csu(2), channel service unit (CSU) application 
           (long-haul E1 or T1/J1 span);

         - monitor(3), high-impedance line monitoring of the 
           span.

         The value none(0) can be read but not written.  When 
         read, the value none(0) indicates that the equipment is 
         either absent, not configured, or failed."
    DEFVAL      { none }
    ::= { x400pSpanEntry 15 }

x400pSpanLineLength OBJECT-TYPE
    SYNTAX      INTEGER {
        none(0), dsx133ft(1), dsx266ft(2), dsx399ft(3), 
        dsx533ft(4), dsx666ft(5) }
    MAX-ACCESS  read-create
    STATUS      current
    DESCRIPTION
        "Provides the line length for T1 DSX operation.  The 
         object can have one of the following values:

         - none(0), unknown, unspecified or not applicable;

         - dsx133ft(1), DSX-1 0 to 133 feet;

         - dsx266ft(2), DSX-1 133 to 266 feet;

         - dsx399ft(3), DSX-1 266 to 399 feet;

         - dsx533ft(4), DSX-1 399 to 533 feet;

         - dsx666ft(5), DSX-1 533 to 666 feet.

         The value none(0) can be read but not written.  When 
         read, the value none(0) indicates that the span is 
         either absent, not configured or failed.

         The value is only significant when x400pSpanLineMode is 
         set to dsu(1) for T1 spans."
    DEFVAL      { dsx133ft }
    ::= { x400pSpanEntry 16 }

x400pSpanLineAttenuation OBJECT-TYPE
    SYNTAX      INTEGER {
        none(0), csu0dB(1), csu8dB(2), csu15dB(3), csu23db(4) }
    MAX-ACCESS  read-create
    STATUS      current
    DESCRIPTION
        "Provides the line attenuation for T1 CSU operation.  
         The object can have one of the following values:

         - none(0), unknown, unspecified or not applicable;

         - csu0dB(1), CSU 0 dB;

         - csu8dB(2), CSU -7.5 dB;

         - csu15dB(3), CSU -15 dB;

         - csu23db(4), CSU -22.5 dB.

         The value none(0) can be read but not written.  When 
         read, the value none(0) indicates that the span is 
         either absent, not configured, or failed.

         The value is only significant when x400pSpanLineMode is 
         set to csu(2) for T1 spans."
    DEFVAL      { none }
    ::= { x400pSpanEntry 17 }

x400pSpanLineGain OBJECT-TYPE
    SYNTAX      INTEGER {
        none(0), mon0dB(1), mon12dB(2), mon20dB(3), mon26dB(4), 
        mon30dB(5), mon32dB(6) }
    MAX-ACCESS  read-create
    STATUS      current
    DESCRIPTION
        "Specifies and indicates the line gain for monitoring 
         operation.  The object can have one of the following 
         values:

         - none(0), unknown, unspecified or not applicable;

         - mon0dB(1), 0 dB linear monitoring gain;

         - mon12dB(2), 12 dB linear monitoring gain;

         - mon20dB(3), 20 dB linear monitoring gain;

         - mon26dB(4), 26 dB linear monitoring gain;

         - mon30dB(5), 30 dB linear monitoring gain;

         - mon32dB(6), 32 dB linear monitoring gain.

         The value none(0) can be read but not written.  When 
         read, the value none(0) indicates that the span is 
         either absent, not configured, or failed.

         The value is only significant when x400pSpanLineMode is 
         set to monitor(3)."
    DEFVAL      { none }
    ::= { x400pSpanEntry 18 }

x400pSpanLineDelay OBJECT-TYPE
    SYNTAX      Unsigned32
    UNITS       "microseconds"
    MAX-ACCESS  read-create
    STATUS      current
    DESCRIPTION
        "Specifies and indicates the line delay in microseconds.  
         This can be measured and by maangement stations for the 
         use of users of the span or channel within the span.

         When the value is zero (0) it indicates that the loop 
         delay is unknown."
    DEFVAL      { 0 }
    ::= { x400pSpanEntry 19 }

x400pSpanTxLevel OBJECT-TYPE
    SYNTAX      INTEGER {
        open(0), off(1), on(2) }
    MAX-ACCESS  read-create
    STATUS      current
    DESCRIPTION
        "Specifies whether the transmitters for the span are 
         enabled or disabled.

         - open(0), the transmitters are open-circuited.

         - off(1), the transmitters are disabled.

         - on(2), the transmitters are enabled.

         Disabling transmitters is often performed in monitoring 
         modes.  Also, when a span wired as a backup for another 
         span, the receivers are high-impeadance but the 
         transmitters are directly connected.  Disabling the 
         transmitters places the span in hot standby and the 
         span becomes active when the transmitters are enabled.

         All chip sets are capable of disabling the 
         transmitters."
    DEFVAL      { open }
    ::= { x400pSpanEntry 20 }

x400pSpanRxLevel OBJECT-TYPE
    SYNTAX      INTEGER {
        open(0), off(1), on(2) }
    MAX-ACCESS  read-create
    STATUS      current
    DESCRIPTION
        "Specifies whether the receivers for the span are 
         enabled or disabled.

         - open(1), the receiver is open-circuited.

         - off(1), the receiver is disabled.

         - on(2), the receiver is enabled.

         Disabling of receives does not serve much purpose 
         except to avoid alarms on spans that are not being 
         used.

         All chip sets are capable of disabling the receivers."
    DEFVAL      { open }
    ::= { x400pSpanEntry 21 }

x400pSpanAlarmSettleTime OBJECT-TYPE
    SYNTAX      TimeInterval
    UNITS       "centiseconds"
    MAX-ACCESS  read-create
    STATUS      current
    DESCRIPTION
        "After local alarm conditions clear, the driver will 
         continue to transmit a yellow alarm (T1/J1) or RAI (E1) 
         to the remote terminal until the local alarm conditions 
         have remained clear for this period of time.  The 
         default is 5 seconds (500 centiseconds).  This column 
         may be read-only for some systems."
    DEFVAL      { 500 } -- 5 seconds
    ::= { x400pSpanEntry 22 }

x400pSpanLineCodeTime OBJECT-TYPE
    SYNTAX      TimeInterval
    UNITS       "centiseconds"
    MAX-ACCESS  read-create
    STATUS      current
    DESCRIPTION
        "The period of time for which to transmit or expect to 
         receive a loop-up, loop-down, or spare code.  This 
         value is only significant for T1 or J1 operation.  The 
         default value is 5 seconds (500 centiseconds).  This 
         column may be read-only for some systems."
    DEFVAL      { 500 } -- 5 seconds
    ::= { x400pSpanEntry 23 }

x400pSpanPrimary OBJECT-TYPE
    SYNTAX      Unsigned32
    MAX-ACCESS  read-create
    STATUS      current
    DESCRIPTION
        "Provides the primary span index of the span in the 
         system to which this span is acting as a backup.  When 
         the span is not acting as a backup (it is a primary 
         span, the default), the index is set to the null 
         string, an invalid span index. Only one span in the 
         system may act as a backup to any other span in the 
         system.  The span index specified must be a primary 
         span (that is, the primay span must not be backing up 
         another span and its corrresponding value in this 
         column must be the null string.

         The state of the backup span is indicated by the 
         standby status of the span.  Only the primary span 
         index can be referenced directly by a service access 
         point."
    ::= { x400pSpanEntry 24 }

x400pSpanDataLink OBJECT-TYPE
    SYNTAX      BITS {
        ansiT1403(0), aTT54016(1), other(2) }
    MAX-ACCESS  read-create
    STATUS      current
    DESCRIPTION
        "Provides for the use of a facility data link.  This set 
         may contain:

         - ansiT1403(0), present when the ANSI T1.403 protocol 
           issued on the FDL;

         - aTT54016(1), present when the AT&T TR54016 protocol 
           is used on the FDL;

         - other(2), present when another protocol is used.

         When the set is empty, no FDL is used."
    ::= { x400pSpanEntry 25 }

x400pSpanLineCode OBJECT-TYPE
    SYNTAX      INTEGER {
        noCode(1), lineCode(2), payloadCode(3), resetCode(4), 
        testCode(5), unframedAllOnes(6), unframedOneAndZero(7) }
    MAX-ACCESS  read-create
    STATUS      current
    DESCRIPTION
        "Specifies the line code being tranmitted.  The object 
         can have values:

         - noCode(1), no code is being tranmitted: normal or 
           loopback data is being transmitted if the 
           transmitters are enabled;

         - lineCode(2), the loop-up line code is being 
           transmitted;

         - payloadCode(3), the loop-up payload code is being 
           transmitted;

         - resetCode(4), the loop-down code is being 
           transmitted;

         - testCode(5), a BERT code or test pattern is being 
           transmitted;

         - unframedAllOnes(6), unframed all ones pattern 
           ('11111111'B), 'out of service indication', is being 
           transmitted;

         - unframedOneAndZero(7), unframed alternating one and 
           zero pattern ('10101010'B), 'customer disconnect 
           indication signal', is being transmitted.

         The linkCode(2), payloadCode(3) and resetCode(4) 
         settings will only persist for 5 seconds.  Other 
         settings will persist until reset."
    DEFVAL      { noCode }
    ::= { x400pSpanEntry 26 }

x400pSpanAlarmSeverityMappingProfile OBJECT-TYPE
    SYNTAX      RowPointer
    MAX-ACCESS  read-create
    STATUS      current
    DESCRIPTION
        "Provides the name of an alarm severity mapping profile 
         to be used when generating alarm notifications.  When 
         this is the null string, or when a mapping does not 
         exist, the default values will be used."
    DEFVAL      { { zeroDotZero } }
    ::= { x400pSpanEntry 27 }

x400pSpanAdministrativeState OBJECT-TYPE
    SYNTAX      AdministrativeState
    MAX-ACCESS  read-create
    STATUS      current
    DESCRIPTION
        "Provides the administrative state of the span following 
         the AdministrativeState textual convention of the 
         OPENSS7-SMI-MIB module in accordance with ITU-T Rec. 
         X.721 | ISO/IEC 10165-2.

         - locked(0), the span is administratively prohibited 
           from providing service; no user may use the span;

         - unlocked(1), the span is administratively permitted 
           to provide service; users may use the span;

         - shuttingDown(2), the span will be locked(0) once all 
           of its circuits are no longer in use; existing users 
           can complete using the span before it is shut down, 
           but no new users may use the span.

         The administrative state will transition from 
         shuttingDown(2) to locked(0)."
    REFERENCE
        "OPENSS7-SMI-MIB, ITU-T Rec. X.721 | ISO/IEC 10165-2, 
         administrativeState."
    DEFVAL      { locked }
    ::= { x400pSpanEntry 28 }

x400pSpanOperationalState OBJECT-TYPE
    SYNTAX      OperationalState
    MAX-ACCESS  read-only
    STATUS      current
    DESCRIPTION
        "Provides the operational state of the span following 
         the OperationalState textual convention of the 
         OPENSS7-SMI-MIB module in accordance with ITU-T Rec. 
         X.721 | ISO/IEC 10165-2.

         The operational state is single-valued and may assume 
         one of the following values:

         - disabled(0), the span is (and all its circuits are) 
           inoperable and unable to provide service to users;

         - enabled(1), the span is partially or fully operable 
           and available for, or in, use (some or all of its 
           circuits are operable)."
    REFERENCE
        "OPENSS7-SMI-MIB, ITU-T Rec. X.721 | ISO/IEC 10165-2, 
         operationalState."
    ::= { x400pSpanEntry 29 }

x400pSpanUsageState OBJECT-TYPE
    SYNTAX      UsageState
    MAX-ACCESS  read-only
    STATUS      current
    DESCRIPTION
        "Provides the usage state of the circuit following the 
         UsageState textual convention of the OPENSS7-SMI-MIB in 
         accordance with ITU-T Rec. X.721 | ISO/IEC 10165-2.  
         The usage state is single-valued and may assume one of 
         the following values:

         - idle(0), neither the span (nor its circuits) are 
           currently in use; no data is being transferred in the 
           span or its circuits;

         - active(1), the span is in use and has sufficient 
           operating capacity to provide for additional users 
           simultanteously (e.g. some channels are available);

         - busy(2), the span is in use and has no spare capacity 
           (i.e.  all channels are in use).

         If the driver does not support the independent use of 
         channels, only the values idle(0) and busy(2) are 
         returned."
    REFERENCE
        "OPENSS7-SMI-MIB, ITU-T Rec. X.721 | ISO/IEC 10165-2, 
         usageState."
    ::= { x400pSpanEntry 30 }

x400pSpanAlarmStatus OBJECT-TYPE
    SYNTAX      AlarmStatus
    MAX-ACCESS  read-create
    STATUS      current
    DESCRIPTION
        "Provides the alarm status of the span following the 
         AlarmStatus textual convention of the OPENSS7-SMI-MIB 
         module in accordance with ITU-T Rec. X.721 | ISO/IEC 
         10165-2.  This object is set-valued and can contain 
         zero or more of the following values:

         - underRepair(0), the span is under repair;

         - critical(1), a critical alarm is outstanding: one or 
           more critical alarms indicating a fault have been 
           detected and have not been cleared.

         - major(2), a major alarm is outstanding: one or more 
           major alarms indicating a fault have been detected 
           and have not been cleared.

         - minor(3), a minor alarm is outstanding: one or more 
           minor alarms indicating a fault have beem detected 
           and have not been cleared.

         - alarmOutstanding(4), an alarm is outstanding: one or 
           more alarms have been detected, the condition of 
           which may or may not be disabling.

         The presence or absence of an alarm state condition 
         does not affect the generation of future fault related 
         notifications.  Only underRepair(0) may be added to the 
         set by management stations.  The remaining alarm 
         statuses can only be removed from the set by management 
         stations and has the effect of a manual clearing 
         action, particularly for those alarm conditions that do 
         not have clearing events."
    REFERENCE
        "OPENSS7-SMI-MIB, ITU-T Rec. X.721 | ISO/IEC 10165-2, 
         alarmStatus."
    DEFVAL      { '00000'B }
    ::= { x400pSpanEntry 31 }

x400pSpanProceduralStatus OBJECT-TYPE
    SYNTAX      ProceduralStatus
    MAX-ACCESS  read-only
    STATUS      current
    DESCRIPTION
        "Provides the procedural status of the span following 
         the ProceduralStatus textual convention of the 
         OPENSS7-SMI-MIB module in accordance with the 
         proceduralStatus attribute of ITU-T Rec. X.721 | 
         ISO/IEC 10165-2.  The procedural status is set-valued 
         and can contain zero or more of the following values:

         - initializationRequired(0), the span requires 
           initialization by the management station before it 
           can perform normal functions and this procedure has 
           not been initiated.  The operational state is 
           disabled.

         - notInitialized(1), the span requires initialization 
           before it can perform its normal functions and this 
           procedure has not been initiated.  The span 
           initializes itself autonomously.  The operational 
           state is disabled.

         - initializing(2), the span requires initialization 
           before it can perform its normal functions and this 
           procedure has been initiated but is not yet complete.  
           When this condition is present, the initialization 
           requried condition is absent.  The operational state 
           is disabled.

         - reporting(3), the span is reporting the results of a 
           procedure.  This condition is applicable to test 
           procedures.

         - terminating(4), the span is in a termination phase.  
           If the resource does not initialize itself 
           autonomously, the initialization required condition 
           is also present and operational state is disabled."
    REFERENCE
        "OPENSS7-SMI-MIB, ITU-T Rec. X.721 | ISO/IEC 10165-2, 
         proceduralStatus."
    ::= { x400pSpanEntry 32 }

x400pSpanAvailabilityStatus OBJECT-TYPE
    SYNTAX      AvailabilityStatus
    MAX-ACCESS  read-only
    STATUS      current
    DESCRIPTION
        "Provides the availability status of the span following 
         the AvailabilityStatus textual convention of the 
         OPENSS7-SMI-MIB module in accordance with the 
         availabilityStatus attribute of ITU-T Rec. X.721 | 
         ISO/IEC 10165-2.  The availability status is set-valued 
         and can contain zero or more of the following values:

         - inTest(0), the span is undergoing a test procedure.  
           If the administrative state is locked or shutting 
           down then normal users are precluded from using the 
           resource and the control status attribute has the 
           value reservedForTest(2).  Tests that do not exclude 
           additional uses can be present in any operational or 
           administrative state but the reservedForTest(2) 
           condition should not be present.  This condition is 
           present when the span is in one of the loopback or 
           test modes.

         - failed(1), the span has an internal fault that 
           prevents it from operating (e.g. blue alarm).  The 
           operational state is disabled.

         - powerOff(2), the resource requires power to be 
           applied and is not powered on.  For example, a fuse 
           or other protection devices is known to have removed 
           power or a low voltage condition has been detected.  
           The operational state is disabled.

         - offLine(3), the resource requires a routine operation 
           to be performed to place it online and make it 
           available for use.  The operation may be manual or 
           automatic, or both.  The operational state is 
           disabled.

         - offDuty(4), the resource has been made inactive by an 
           internal control process in accordance with a 
           predetermined time schedule.  Under normal conditions 
           the control process can be expected to reactivate the 
           resource at some scheduled time.  The operational 
           state is enabled or disabled.

         - dependency(5), the resource cannot operate because of 
           some other resource on which it depends is 
           unavailable (e.g. the card is not operational).  The 
           operational state is disabled.

         - degraded(6), the service available from the resource 
           is degraded in some respect, such as in speed or 
           operating capacity.  However, the resource remains 
           available for service, either because some services 
           are satisfactory or because degraded service is 
           preferrable to no service at all.  This is the cause 
           for yellow and red alarm conditions on the carrier.  
           The operational state is enabled.

         - notInstalled(7), the resource represented is not 
           present, or is incomplete.  For example, a card is 
           missing or a span is not provided by a card.

         - logFull(8), indicate a log full condition.  This is 
           not applicable to spans."
    REFERENCE
        "OPENSS7-SMI-MIB, ITU-T Rec. X.721 | ISO/IEC 10165-2, 
         availabilityStatus."
    ::= { x400pSpanEntry 33 }

x400pSpanControlStatus OBJECT-TYPE
    SYNTAX      ControlStatus
    MAX-ACCESS  read-create
    STATUS      current
    DESCRIPTION
        "Provides the control status of the span following the 
         ControlStatus textual convention of the OPENSS7-SMI-MIB 
         module in accordance with the controlStatus attribute 
         of ITU-T Rec.  X.721 | ISO/IEC 10165-2.  The controls 
         status is single-valued and can assume one of the 
         following values:

         - subjectToTest(0), the span is available for use but 
           may be subject to test at unpredictable times and may 
           cause it to exhibit unusual characteristics to users; 
           the adminitrative state is unlocked(1).

         - partOfServicesLocked(1), although the administrative 
           is unlocked(1), some part of the service is locked 
           (such as specific channels).

         - reservedForTest(2), the span is unavailable to normal 
           users because it is undergoing a test procedure; the 
           administrative state is locked(0).

         - suspended(3), service has been administratively 
           suspsended to users of the resource and does not 
           resume performing services until the suspended 
           condition is revoked; the administrative state is 
           unlocked(1)."
    REFERENCE
        "OPENSS7-SMI-MIB, ITU-T Rec. X.721 | ISO/IEC 10165-2, 
         controlStatus."
    ::= { x400pSpanEntry 34 }

x400pSpanStandbyStatus OBJECT-TYPE
    SYNTAX      StandbyStatus
    MAX-ACCESS  read-only
    STATUS      current
    DESCRIPTION
        "Provides the standby status of the span following the 
         StandbyStatus textual convention of the OPENSS7-SMI-MIB 
         module in accordance with the standbyStatus attribute 
         of ITU-T Rec.  X.721 | ISO/IEC 10165-2.  The standby 
         status is single-valued and may assume one of the 
         following values:

         - hotStandby(0), the card is synchronizing with the 
           receive stream but is not providing service (i.e. the 
           transmitters are off or open-circuited).  Writing 
           this value for a backup span results in the span 
           assuming a hot standby role.

         - coldStandby(1), the card has both receiver and 
           transmitters off.  Writing this value for a backup 
           span results in the span assuming a cold standby 
           role.

         - providingService(2), the card responsible for 
           providing service as a back-up, or is a primary or 
           solitary resource.  This value cannot be written.

         This value cannot be written for primary or solitary 
         spans.  For backup spans, any value may be written, but 
         the value read reflects the current state of the backup 
         span.

         The value will transition from the hotStandby(0) or 
         coldStandby(1) value to the providingService(2) value 
         should the primary span to which this span is a backup 
         experiences a disabling fault condition or is otherwise 
         disabled by a management station.

         There are normally two ways that a span can be wired as 
         a standby: either the receivers are in high-impedance 
         mode and are tapped onto the same receive line as the 
         primary and the transmitters are turned off; or the 
         span is on a drop-down arrangement (through a DCCS) but 
         is receiving OOS signal (blue alarm)."
    REFERENCE
        "OPENSS7-SMI-MIB, ITU-T Rec. X.721 | ISO/IEC 10165-2, 
         standbyStatus."
    DEFVAL      { providingService }
    ::= { x400pSpanEntry 35 }

x400pSpanUnknownStatus OBJECT-TYPE
    SYNTAX      UnknownStatus
    MAX-ACCESS  read-only
    STATUS      current
    DESCRIPTION
        "Provides the unknown status of the span following the 
         UnknownStatus textual convention of the OPENSS7-SMI-MIB 
         module in accordance with the unknownStatus attribute 
         of ITU-T Rec.  X.721 | ISO/IEC 10165-2.  It indicates 
         whether the other status attributes are known or not.

         - false(0), the status is known and other status 
           attributes are valid; the value of the other TMN 
           state and status textual conventions may not reflect 
           the actual state of the span.

         - true(1), the status is unknown and other status 
           attributes may be invalid; the value of the other TMN 
           state and status textual conventions reflects the 
           actual state of the span."
    REFERENCE
        "OPENSS7-SMI-MIB, ITU-T Rec. X.721 | ISO/IEC 10165-2, 
         unknownStatus."
    ::= { x400pSpanEntry 36 }

x400pSpanSap OBJECT-TYPE
    SYNTAX      RowPointer
    MAX-ACCESS  read-only
    STATUS      current
    DESCRIPTION
        "Indicates the name of the service access point that 
         represents the user of the entire span.   When the 
         value is the null string, it indicates that there is no 
         user of the entire span."
    ::= { x400pSpanEntry 37 }

x400pSpanLoopbackStatus OBJECT-TYPE
    SYNTAX      BITS {
        nearEndInward(0), nearEndLine(1), nearEndFramer(2), 
        nearEndPayload(3), farEndLine(4), farEndPayload(5) }
    MAX-ACCESS  read-only
    STATUS      current
    DESCRIPTION
        "Provides the current (versus the desired) loopback 
         status of the span.  This object may contain the 
         following values:

         - nearEndInward(0), payload bits for transmission 
           overwrite the receive payload bits;

         - nearEndLine(1), the received serial bit stream is 
           copied to the transmit serial bit stream;

         - nearEndFramer(2), the transmit serial bit stream is 
           copied to the receive serial bit stream;

         - nearEndPayload(3), the received payload bits 
           overwrite the transmit payload bits;

         - farEndLine(4), the far end is in line loopback;

         - farEndPayload(5), the far end is in payload loopback.

         When the object contains no values, the loopback status 
         is either unknown or no loopback is present.  The two 
         conditions can be distinguished using the 
         x400pSpanUnknownStatus object in the same row."
    ::= { x400pSpanEntry 38 }

x400pSpanLineStatus OBJECT-TYPE
    SYNTAX      BITS {
        none(0), rcvFarEndLOF(1), xmtFarEndLOF(2), rcvAIS(3), 
        xmtAIS(4), lossOfFrame(5), lossOfSignal(6), 
        loopbackState(7), t16AIS(8), rcvFarEndLOMF(9), 
        xmtFarEndLOMF(10), rcvTestCode(11), otherFailure(12), 
        uavailSigState(13), netEquipOOS(14), rcvPayloadAIS(15), 
        perfThreshold(16) }
    MAX-ACCESS  read-only
    STATUS      current
    DESCRIPTION
        "Provides the line status for the span.  This object is 
         set-valued and can contain the following values:

         - none(0), only present when no other status is 
           present;

         - rcvFarEndLOF(1), receiving a far end loss of frame 
           indication (receiving yellow alarm/RAI);

         - xmtFarEndLOF(2), transmitting a far end loss of frame 
           indication (transmitting yellow alarm/RAI);

         - rcvAIS(3), receiving an AIS indication (receiving 
           blue alarm/AIS);

         - xmtAIS(4), transmitting an AIS indication 
           (transmitting blue alarm/AIS);

         - lossOfFrame(5), experiencing a receive loss of frame 
           condition;

         - lossOfSignal(6), experiencing a receive loss of 
           signal condition;

         - loopbackState(7), in a loopback state;

         - t16AIS(8), receiving an AIS indication in TS16;

         - rcvFarEndLOMF(9), receiving a far end loss of 
           multiframe indication (receiving E-bits);

         - xmtFarEndLOMF(10), transmitting a far end loss of 
           multiframe indication (transmitting E-bits);

         - rcvTestCode(11), receiving a test code;

         - otherFailure(12), other failure (e.g. transitter open 
           circuit, transmitter short circuit);

         - uavailSigState(13), in an unavailable signalling 
           state;

         - netEquipOOS(14), associated network equipment is out 
           of service;

         - rcvPayloadAIS(15), receiving a payload AIS;

         - perfThreshold(16), performance threshold exceeded."
    DEFVAL      { '00000000000000000'B }
    ::= { x400pSpanEntry 39 }

x400pSpanAlarms OBJECT-TYPE
    SYNTAX      BITS {
        yellow(0), red(1), blue(2), recovery(3) }
    MAX-ACCESS  read-only
    STATUS      current
    DESCRIPTION
        "Indicates the current span alarms.  The may contain:

         - yellow(0), a yellow alarm (T1/J1) or RAI (E1) 
           condition exists, present while a received yellow 
           alarm or RAI condition perists;

         - red(1), a red alarm condition exists, present while a 
           receive loss of sync or receive carrier loss 
           condition persists;

         - blue(2), a blue alarm (T1/J1) or AIS (E1) condition 
           exists, present while a received unframed all-ones 
           condition persists;

         - recovery(3), after a read or blue/AIS alarm condition 
           has cleared, the driver waits for an alarm recovery 
           period (x400pSpanAlarmSettleTime) before clearing the 
           sending of yellow alarm (T1/J1) or RAI condition 
           (E1), present after the red or blue/AIS alarms clear 
           while waiting for the alarm recovery period."
    DEFVAL      { '0000'B }
    ::= { x400pSpanEntry 40 }

x400pSpanEvents OBJECT-TYPE
    SYNTAX      BITS {
        rlos(0), frcl(1), rual(2), ryel(3), rra(4), rdma(5), 
        v52lnk(6), lorc(7), lotc(8), lup(9), ldn(10), 
        lspare(11), tocd(12), tcle(13) }
    MAX-ACCESS  read-only
    STATUS      current
    DESCRIPTION
        "Indicates the current span detected events.  This may 
         contain the following:

         - rlos(0), receiver loss of synchronization, present 
           while the framer is not synchronized to the receive 
           data stream;

         - frcl(1), framer receive carrier loss, present when a 
           frame (or second) of consecutive zeros has been 
           detected;

         - rua1(2), receive unframed all ones, T1 blue alarm, E1 
           AIS, present when an unframed all one's code is 
           received;

         - ryel(3), receive yellow alarm condition, T1 yellow 
           alarm, present when a yellow alarm is received;

         - rra(4), receive remote alarm condition, E1 only, 
           present when a remote alarm is received.

         - rdma(5), receive distant multiframe alarm condition, 
           E1 only, present when bit 6 of time slot 16 in frame 
           0 has been set for two consecutive mutliframes.

         - v52lnk(6), V5.2 link detected condition, E1 only, 
           present on detection of a V5.2 link identification 
           signal (G.965).

         - lorc(7), loss of receive clock condition, present 
           when the receive clock has not transitioned for one 
           channel time.

         - lotc(8), loss of transmit clock condition, present 
           when the TCLK pin has not transitioned for one 
           channel time.

         - lup(9), loop-up code detected condition, T1 only, 
           present when the loop-up code is being received.

         - ldn(10), loop-down code detected condition, T1 only, 
           present when the loop-down code is being received.

         - lspare(11), spare code detected condition, T1 only, 
           present when the spare code is being received.

         - tocd(12), transmit open circuit detected, present 
           when an open circuit on the transmit leads is 
           detected.

         - tcle(13), transmit current limite exceeded, present 
           when the 50mA short circuit current limiter is in 
           effect.

         Note that some of these conditions are only applicable 
         to T1 operation and some are only applicable to E1 
         operation.  Not all devices will report all conditions.  
         Some conditions may also cause alarm conditions and 
         notifications."
    DEFVAL      { '0000000000000'B }
    ::= { x400pSpanEntry 41 }

x400pSpanReceiveLevel OBJECT-TYPE
    SYNTAX      Unsigned32 (0..600)
    UNITS       "negative tenths of a decibel"
    MAX-ACCESS  read-only
    STATUS      current
    DESCRIPTION
        "Indicates the receive level in increments of -0.1 dB.  
         The level indicated is only within the range detected 
         by the device."
    ::= { x400pSpanEntry 42 }

x400pSpanReceiveThreshold OBJECT-TYPE
    SYNTAX      Unsigned32 (0..600)
    UNITS       "negative tenths of a decibel"
    MAX-ACCESS  read-create
    STATUS      current
    DESCRIPTION
        "Specifies or indicates the lowest receive level 
         threshold in increments of -0.1 dB.  The level 
         indicated by the x400pSpanReceiveLevel is only within 
         the range from 0 to this value.  When this value 
         returns zero (0), the device is incapable of providing 
         the receive level."
    ::= { x400pSpanEntry 43 }

x400pSpanRowStatus OBJECT-TYPE
    SYNTAX      RowStatus
    MAX-ACCESS  read-create
    STATUS      current
    DESCRIPTION
        "Provides a mechanism whereby management stations may 
         create or destroy rows in this table.

         The primary purpose is to permit management stations to 
         configure cards that have not yet been installed.  
         Installed cards will have their rows populated 
         automatically by the agent.  Management stations may 
         not delete rows that correspond to installed equipment.  
         Management stations may not activate rows that do not 
         correspond to installed equipment."
    ::= { x400pSpanEntry 44 }


x400pBert OBJECT IDENTIFIER
    ::= { x400pTables 5 }

x400pBertTable OBJECT-TYPE
    SYNTAX      SEQUENCE OF X400pBertEntry
    MAX-ACCESS  not-accessible
    STATUS      current
    DESCRIPTION
        "The X400P BERT table provides a mechanism whereby BERT 
         testing  can be performed on a span by span basis."
    ::= { x400pBert 1 }

x400pBertEntry OBJECT-TYPE
    SYNTAX      X400pBertEntry
    MAX-ACCESS  not-accessible
    STATUS      current
    DESCRIPTION
        "Each entry in the table provides an interface to BERT 
         testing for the span.  Entries exist in this table as a 
         part of system configuration.  A span whose device 
         hardware or driver does not support any BERT testing 
         will not have a corresponding entry in this table."
    INDEX       {
        x400pDrivName,  -- shared index
        x400pCardIndex, -- shared index
        x400pSpanIndex  -- shared index
    }
    ::= { x400pBertTable 1 }

X400pBertEntry ::= SEQUENCE {
    x400pBertMode
        INTEGER,
    x400pBertSelect
        INTEGER,
    x400pBertPattern
        OCTET STRING,
    x400pBertOperationalState
        OperationalState,
    x400pBertProceduralStatus
        ProceduralStatus,
    x400pBertBitCount
        Counter32,
    x400pBertErrorCount
        Counter32
}

x400pBertMode OBJECT-TYPE
    SYNTAX      INTEGER {
        none(0), span(1), channel(2), fbit(3) }
    MAX-ACCESS  read-write
    STATUS      current
    DESCRIPTION
        "Specifies the BERT testing for the span on span types 
         and span equipment that supports the selected BERT 
         testing.  This object can have one of the following 
         values:

         - none(0), no testing will be performed;

         - span(1), BERT testing will be peformed on the entire 
           span;

         - channel(2), BERT testing will be performed on the 
           channels that have been marked for test;

         - fbit(3), testing will be performed using the F-bit.

         The value fbit(3) can only be set for T1 or J1 mode 
         spans with supporting span equipment.  To set span(1), 
         because it disrupts the entire span, the span must be 
         idle.  To set channel(2), because it disrupts the 
         selected channels, selected channels must be idle.

         Not all values are supported by all spans, and not all 
         values are supported by all span equipment."
    DEFVAL      { none }
    ::= { x400pBertEntry 1 }

x400pBertSelect OBJECT-TYPE
    SYNTAX      INTEGER {
        none(0), pre2E7minus1(1), pre2E9minus1(2), 
        pre2E11minus1(3), pre2E15minus1(4), qrss(5), daly(6), 
        repeating(7), alternating(8) }
    MAX-ACCESS  read-write
    STATUS      current
    DESCRIPTION
        "Specifies the BERT test pattern selected.  The value 
         can be one of:

         - none(0), the test pattern selected is unknown or 
           unspecified;

         - pre2E7minus1(1), a pseudorandom 127-bit pattern;

         - pre2E9minus1(2), a pseudorandom 511-bit pattern.

         - pre2E11minus1(3), a pseudorandom 2047-bit pattern;

         - pre2E15minus1(4), a pesudorandom 16383-bit pattern;

         - qrss(5), a pseudorandom QRSS 1048575-bit pattern;

         - daly(6), a 55-octet (440-bit) daly (ATIS T1.TR25) 
           pattern;

         - repeating(7), a repeating bit pattern between one and 
           32 bits long;

         - alternating(8), an alternating word pattern with 1 to 
           255 repetitions of one 16-bit word followed by the 
           same number of repetitions of a second 16-bit word.

         Not all values are supported by all span types and not 
         all values are supported by all span equipment."
    DEFVAL      { none }
    ::= { x400pBertEntry 2 }

x400pBertPattern OBJECT-TYPE
    SYNTAX      OCTET STRING (SIZE(0..33))
    MAX-ACCESS  read-write
    STATUS      current
    DESCRIPTION
        "Specifies the BERT pattern to use when the BERT test 
         pattern selected is repeating(7) or alternating(8).  

         When the BERT test pattern selected is repeating(7), 
         the first octet provides the bit length of the pattern 
         (1..32) and the remaining octets provide the bit 
         pattern itself beginning with the first bit of the 
         first octet.  The first octet will be treated modulo 
         32, with zero (0) mapping to 32, should the value be 
         outside the valid range (1..32).  For example, the 
         value 129 will be treated as the length 1.  Bits 
         specified beyond the number of bits indicated by the 
         bit length are ignored.

         When the BERT test pattern selected is alternating(8), 
         the first octet provides the number of times to repeat 
         each word (1..255), the second and third octets 
         provides the first word to alternate, and the fourth 
         and fifth octets provides the second word to alternate.

         Note that this value is of no significance when the 
         BERT pattern selected is other than repeating(7) or 
         alternating(8)."
    DEFVAL      { '10FFFFFFFF'X }
    ::= { x400pBertEntry 3 }

x400pBertOperationalState OBJECT-TYPE
    SYNTAX      OperationalState
    MAX-ACCESS  read-only
    STATUS      current
    DESCRIPTION
        "Specifies the operational state of the test following 
         the OperationalState textual convention of the 
         OPENSS7-TMN-TC module in accordance with the 
         operationalState attribute of ITU-T Rec. X.721 | 
         ISO/IEC 10165-2.

         The operational state is one of:

         - disabled(0), the test is unable to provide service to 
           users;

         - enabled(1), it is partially or fully operable and 
           available for use."
    REFERENCE
        "OPENSS7-TMN-TC, ITU-T Rec. X.721 | ISO/IEC 10165-2 
         operationalState."
    ::= { x400pBertEntry 4 }

x400pBertProceduralStatus OBJECT-TYPE
    SYNTAX      ProceduralStatus
    MAX-ACCESS  read-only
    STATUS      current
    DESCRIPTION
        "Indicates the procedure status of BERT testing 
         following the ProceduralStatus textual convention of 
         the OPENSS7-TMN-TC module in accordance with the 
         proceduralStatus attribute of ITU-T Rec. X.721 | 
         ISO/IEC 10165-2.

         The procedural status is set-valued and may contain the 
         following:

         - initializationRequired(0), the test requires 
           initialization by the management station before it 
           can perform test functions and this procedure has not 
           been initiated.  The operational state of the test is 
           disabled.

         - notInitialized(1), the test requires initialization 
           before it can perform its test functions and this 
           procedure has not been initiated.  The test 
           initializes itself autonomously.  The operational 
           state of the test is disabled.

         - initializing(2), the test requires initialization 
           before it can perform its test functions and this 
           procedure has been initiated but is not yet complete.  
           When this condition is present, the initialization 
           required condition is absent.  The operational state 
           of the test is disabled.

         - reporting(3), the test is reporting the results of a 
           procedure.  The results counts are valid while this 
           value is present.

         - terminating(4), the test is in a termination phase.  
           If the test does not initialize itself autonomously, 
           the initialization required condition is also present 
           and operational state of the test is disabled."
    REFERENCE
        "OPENSS7-TMN-TC, ITU-T Rec. X.721 | ISO/IEC 10165-2 
         proceduralStatus."
    ::= { x400pBertEntry 5 }

x400pBertBitCount OBJECT-TYPE
    SYNTAX      Counter32
    MAX-ACCESS  read-only
    STATUS      current
    DESCRIPTION
        "Indicates the count of the number of bits tested.  At a 
         minimum, this counter will wrap every 30 minutes.  This 
         counter only increments while the BERT receiver is 
         synchronized on the test pattern."
    ::= { x400pBertEntry 6 }

x400pBertErrorCount OBJECT-TYPE
    SYNTAX      Counter32
    MAX-ACCESS  read-only
    STATUS      current
    DESCRIPTION
        "Indicates the count of the number of bits in error.  At 
         a minimum, this counter will wrap every 30 minutes.  
         This counter only increments while the BERT receiver is 
         synchronized on the test pattern."
    ::= { x400pBertEntry 7 }

x400pChan OBJECT IDENTIFIER
    ::= { x400pTables 6 }

x400pChanTable OBJECT-TYPE
    SYNTAX      SEQUENCE OF X400pChanEntry
    MAX-ACCESS  not-accessible
    STATUS      current
    DESCRIPTION
        "The channel table provides an entry for each of the 
         channels for each card and span in the system."
    ::= { x400pChan 1 }

x400pChanEntry OBJECT-TYPE
    SYNTAX      X400pChanEntry
    MAX-ACCESS  not-accessible
    STATUS      current
    DESCRIPTION
        "For T1 spans, there can be 24 channels numbered 1 
         through 24.  For E1 spans there can be 31 channels 
         numbered 1 through 31.  Channels are neither created 
         nor deleted by managemention stations but exist 
         inherently as a part of system operation.

         Rows are neither created nor deleted explicitly by 
         management stations but are present inherently as a 
         part of system operation.  Each entry in the table 
         corresponds to a channel of an equipped span."
    INDEX       {
        x400pDrivName,  -- shared index
        x400pCardIndex, -- shared index
        x400pSpanIndex, -- shared index
        x400pChanIndex
    }
    ::= { x400pChanTable 1 }

X400pChanEntry ::= SEQUENCE {
    x400pChanIndex
        Unsigned32,
    x400pChanType
        INTEGER,
    x400pChanFormat
        INTEGER,
    x400pChanRate
        INTEGER,
    x400pChanMode
        BITS,
    x400pChanSap
        RowPointer,
    x400pChanAdministrativeState
        AdministrativeState,
    x400pChanOperationalState
        OperationalState,
    x400pChanUsageState
        UsageState,
    x400pChanAvailabilityStatus
        AvailabilityStatus,
    x400pChanControlStatus
        ControlStatus,
    x400pChanProceduralStatus
        ProceduralStatus,
    x400pChanAlarmStatus
        AlarmStatus,
    x400pChanStandbyStatus
        StandbyStatus
}

x400pChanIndex OBJECT-TYPE
    SYNTAX      Unsigned32 (1..31)
    MAX-ACCESS  not-accessible
    STATUS      current
    DESCRIPTION
        "Provides a time slot index for the channel.  For T1 and 
         J1 spans, the time slots 1..24 index the corresponding  
         time slot in the span.  For E1 spans, the time slot 
         indices 1..31 index the corresponding time slot in the  
         span.

         For E1 operation, TS0 is unusable and does not appear 
         in this table.  For E1 CAS operation, TS16 is not 
         available to users for payload but continues to appear 
         in this table.

         Special semantics channel 0 refers to the 
         characteristics of all the other channels statistically 
         multiplexed together into a single virtual channel.  
         However, this used is deprecated.

         Management stations do not add or delete rows from this 
         table, only agents, and then only at boot time."
    ::= { x400pChanEntry 1 }

x400pChanType OBJECT-TYPE
    SYNTAX      INTEGER {
        none(0), cas(1), ccs(2) }
    MAX-ACCESS  read-write
    STATUS      current
    DESCRIPTION
        "Specifies whether the channel has channel associated 
         signalling or common channel signalling.  For T1 or J1 
         spans, channel associated signalling implies 56kbps 
         DS0A operation within the channel; otherwise, 64kbps 
         DS0 operation within the channel is indicated.  The 
         default is ccs(1).  For E1 CAS operation, channel 17 
         (timeslot 16) is unavailable for use."
    DEFVAL      { ccs }
    ::= { x400pChanEntry 2 }

x400pChanFormat OBJECT-TYPE
    SYNTAX      INTEGER {
        none(1), ds0a(2), ds0(3), t1(4), j1(5), e1(6) }
    MAX-ACCESS  read-write
    STATUS      current
    DESCRIPTION
        "
         - none(1), no specific channel type;
         - ds0a(2), the channel is a DS0-A channel;
         - ds0(3), the channel is a DS0 channel;
         - t1(4), the channel is a full T1 span;
         - j1(5), the channel is a full J1 span;
         - e1(6), the channel is a full E1 span.
        "
    ::= { x400pChanEntry 3 }

x400pChanRate OBJECT-TYPE
    SYNTAX      INTEGER {
        variable(0), kbits56(56), kbits64(64), kbits1536(1536), 
        kbits1984(1984) }
    UNITS       "kilobits per second"
    MAX-ACCESS  read-write
    STATUS      current
    DESCRIPTION
        "Indicates the bit rate of the channel.  Channels 1..24 
         for T1 and J1 can be 56 or 64 kbps.  Channels 1..31 for 
         E1 are 64 kbps but can be artificially placed into 56 
         kbps mode.  The default is 64kbps for E1 and T1 ccs(3) 
         channels; 56kbps for T1 cas(2) channels.

         - variable(0), the channel bit rate is variable;

         - kbits56(56000), the channel bit rate is 56 kbits per 
           second;

         - kbits64(64000), the channel bit rate is 65 kbits per 
           second;

         - kbits1536(1536000), the channel bit rate is 1536 
           kbits per second;

         - kbits1984(1984000), the channel bit rate is 1984 
           kbits per second.
        "
    ::= { x400pChanEntry 4 }

x400pChanMode OBJECT-TYPE
    SYNTAX      BITS {
        remoteLoopback(0), localLoopback(1), test(2), 
        loopbackEcho(3) }
    MAX-ACCESS  read-write
    STATUS      current
    DESCRIPTION
        "Provides the channel mode.  This object is set-valued 
         and may contain zero or more of the following values:

         - remoteLoopback(0), the channel is in remote loopback 
           mode; the receive data in the channel is looped back 
           to replace the transmit data for the channel.  This 
           may either be accomplished within the host or using 
           the per-channel loopback capability of the chip sets.

         - localLoopback(1), the channel is in local loopback 
           mode; the transmit data for the channel is looped 
           back to replace the receive data for the channel.  
           This may is accomplished within the host.

         - test(2), the channel is marked for BERT testing.  
           When BERT testing for the span is enabled on a 
           channel basis, this channel will be included in the 
           channels upon which the BERT test pattern is 
           transmitted.

         - loopbackEcho(3), the channel is in local loopback and 
           echo mode;

         Because these tests are disruptive, no value can be 
         added to this set unless the channel has a control 
         status of subjectToTest(0) or reservedForTest(2)."
    ::= { x400pChanEntry 5 }

x400pChanSap OBJECT-TYPE
    SYNTAX      RowPointer
    MAX-ACCESS  read-only
    STATUS      current
    DESCRIPTION
        "Indicates the name of the service access point that 
         represents the user of the channel.  When the value is 
         the null string, it indicates that there is no user of 
         the channel."
    ::= { x400pChanEntry 6 }

x400pChanAdministrativeState OBJECT-TYPE
    SYNTAX      AdministrativeState
    MAX-ACCESS  read-write
    STATUS      current
    DESCRIPTION
        "Provides the administrative state of the channel 
         following the AdministrativeState textual convention of 
         the OPENSS7-SMI-MIB module in accordance with the 
         administrativeState attribute of ITU-T Rec. X.721 | 
         ISO/IEC 10165-2.  The state can be one of the 
         following:

         - locked(0), the channel is administratively prohibited 
           from providing service to users;

         - unlocked(1), the channel is administratively 
           permitted to provide service to users;

         - shuttingDown(2), the channel is shutting down and 
           will move to the locked state once is it idle: the 
           channel will continue to provide service to existing 
           users but will reject new users: once there are no 
           more users of the channel, the channel will move to 
           the locked state.

         The administrative state can be changed to 
         shuttingDown(2) or locked(0) by a management station 
         (either NMS or EMS)."
    REFERENCE
        "OPENSS7-SMI-MIB, ITU-T Rec. X.721 | ISO/IEC 10165-2, 
         administrativeState."
    DEFVAL      { locked }
    ::= { x400pChanEntry 7 }

x400pChanOperationalState OBJECT-TYPE
    SYNTAX      OperationalState
    MAX-ACCESS  read-only
    STATUS      current
    DESCRIPTION
        "Provides the operational state of the channel following 
         the OperationalState textual convention of the 
         OPENSS7-SMI-MIB and ITU-T Rec. X.721 | ISO/IEC 10165-2.  
         The state can be one of the following:

         - disabled(0), the channel is not operational;
         - enabled(1), the channel is operational.

         The operational state of the channel is changed only by 
         the managed system."
    REFERENCE
        "OPENSS7-SMI-MIB, ITU-T Rec. X.721 | ISO/IEC 10165-2, 
         operationalState."
    DEFVAL      { 0 } -- disabled
    ::= { x400pChanEntry 8 }

x400pChanUsageState OBJECT-TYPE
    SYNTAX      UsageState
    MAX-ACCESS  read-only
    STATUS      current
    DESCRIPTION
        "Provides the usage state of the channel following the 
         UsageState textual convention of the OPENSS7-SMI-MIB 
         module in accordances with the usageState attribute of  
         ITU-T Rec. X.721 | ISO/IEC 10165-2.  The state can be 
         one of the following:

         - idle(0), the channel is not currently in use;

         - active(1), the channel is in use and has sufficient 
           operating capacity to provide for additional users 
           simultaneously (e.g.  a half-channel is used);

         - busy(2), the channel is in use and has no spare 
           capacity (i.e. the full channel is in use).

         If partial channels are not supported, only the values 
         idle(0) and busy(2) are returned.

         The usage state of the channel is changed only by the 
         managed system."
    REFERENCE
        "OPENSS7-SMI-MIB, ITU-T Rec. X.721 | ISO/IEC 10165-2, 
         usageState."
    ::= { x400pChanEntry 9 }

x400pChanAvailabilityStatus OBJECT-TYPE
    SYNTAX      AvailabilityStatus
    MAX-ACCESS  read-only
    STATUS      current
    DESCRIPTION
        "Provides the availability status of the channel 
         following the AvailabilityStatus textual convention of 
         the OPENSS7-SMI-MIB module in accordance with the 
         availabilityStatus attribute of ITU-T Rec. X.721 | 
         ISO/IEC 10165-2.  The availability status is set-valued 
         and may contain the following values:

         - inTest(0), the channel is undergoing a test 
           procedure.  The administrative state is locked(0) and 
           the operational state is disabled(1).  This condition 
           exists while the span is in test in a manner 
           diruptive to the channel, or when the channel is in 
           loopback or test mode.

         - failed(1), the channel has an internal fault that 
           prevents it from operating.  The operational state is 
           disabled.  This value is present when the same value 
           is present in the span availability status.

         - powerOff(2), the channel requires power to be applied 
           and is not powered on.  For example, power 
           managements may have removed power from the device.  
           This value is present when the same value is present 
           in the span availability status.

         - offLine(3), the channel requires a routing operation 
           to be performed to place it online and make it 
           available for use.  The operation may be manual or 
           automatic, or both.  The operational state is 
           disabled.  This value is present when the same value 
           is present in the span availability status.

         - offDuty(4), the channel has been made inactive by an 
           internal control process in accordance with a 
           predetermined time schedule.  Under normal 
           conditions, the control process can be expected to 
           reactivate the channel at some scheduled time.

         - dependency(5), the channel cannot operate because 
           some other resource on which it depends is 
           unavailable (e.g. the span).

         - degraded(6), the channel is operating with degraded 
           performance.  This value is present when the same 
           value is present in the span availability status.

         - notInstalled(7), the channel is not present in the 
           system or is incomplete.

         - logFull(8), not used.

         The availabiltiy status of the channel is changed only 
         by the managed system."
    REFERENCE
        "OPENSS7-SMI-MIB, ITU-T Rec. X.721 | ISO/IEC 10165-2, 
         availabilityStatus."
    ::= { x400pChanEntry 10 }

x400pChanControlStatus OBJECT-TYPE
    SYNTAX      ControlStatus
    MAX-ACCESS  read-write
    STATUS      current
    DESCRIPTION
        "Provides the control status of the channel following 
         the ControlStatus textual convention of the 
         OPENSS7-SMI-MIB module in accordance with the 
         controlStatus attribute of ITU-T Rec.  X.721 | ISO/IEC 
         10165-2.  The control status is set-valued and 
         read-write and may contain the following values:

         - subjectToTest(0), the channel is available to normal 
           users, but tests may be conducted on it 
           simultaneously at unpredictable times, which may 
           cause it to exhibit unusual characteristics to users;

         - partOfServicesLocked(1), when present, a manager has 
           administratively locked some part of the channel;

         - reservedForTest(2), the channel has been made 
           administratively unavailable to normal users because 
           it is undergoing a test procedure (e.g. BERT 
           testing): the administrative state is locked;

         - suspended(3), service by the channel is suspended but 
           the administrative state is unlocked: the resource 
           may remember the user of the resource; for channels 
           this has the effect of temporarily disconnecting the 
           channel.

         On of the primary uses of the control status is to 
         permit management stations to mark channels as subject 
         to test or reserved for test so that when a BERT test 
         is activated on the span, the channels marked for test 
         are included in the BERT test."
    REFERENCE
        "OPENSS7-SMI-MIB, ITU-T Rec. X.721 | ISO/IEC 10165-2, 
         controlStatus."
    ::= { x400pChanEntry 11 }

x400pChanProceduralStatus OBJECT-TYPE
    SYNTAX      ProceduralStatus
    MAX-ACCESS  read-only
    STATUS      current
    DESCRIPTION
        "Provides the procedural status of the channel following 
         the ProceduralStatus textual convention of the 
         OPENSS7-SMI-MIB and ITU-T Rec. X.721 | ISO/IEC 10165-2.  
         The status can contain zero or more of the following:

         - initializationRequired(0),
         - notInitialized(1),
         - initializing(2),
         - reporting(3),
         - terminating(4),

         The procedural status of the channel is changed only by 
         the managed system."
    REFERENCE
        "OPENSS7-SMI-MIB, ITU-T Rec. X.721 | ISO/IEC 10165-2, 
         proceduralStatus."
    ::= { x400pChanEntry 12 }

x400pChanAlarmStatus OBJECT-TYPE
    SYNTAX      AlarmStatus
    MAX-ACCESS  read-write
    STATUS      current
    DESCRIPTION
        "Provides the alarm state of the channel following the 
         AlarmStatus textual convention of the OPENSS7-SMI-MIB 
         and ITU-T Rec. X.721 | ISO/IEC 10165-2.  The status can 
         contain zero or more of the following:

         - underRepair(0), the channel is under repair;
         - critical(1), a critical alarm is oustanding;
         - major(2), a major alarm is outstanding;
         - minor(3), a minor alarm is outstanding;
         - alarmOutstanding(4), an alarm is outstanding.

         Management stations can set underRepair(0) or clear an 
         alarm."
    REFERENCE
        "OPENSS7-SMI-MIB, ITU-T Rec. X.721 | ISO/IEC 10165-2, 
         alarmStatus."
    ::= { x400pChanEntry 13 }

x400pChanStandbyStatus OBJECT-TYPE
    SYNTAX      StandbyStatus
    MAX-ACCESS  read-only
    STATUS      current
    DESCRIPTION
        "
         - hotStandby(0),
         - coldStandby(1),
         - providingService(2),
        "
    REFERENCE
        "OPENSS7-SMI-MIB, ITU-T Rec. X.721 | ISO/IEC 10165-2, 
         standbyStatus."
    DEFVAL      { providingService }
    ::= { x400pChanEntry 14 }

x400pXcon OBJECT IDENTIFIER
    ::= { x400pTables 7 }

x400pXconTable OBJECT-TYPE
    SYNTAX      SEQUENCE OF X400pXconEntry
    MAX-ACCESS  not-accessible
    STATUS      current
    DESCRIPTION
        "The cross-connect table provides a 1-1 and 0-0 cross 
         connect capability."
    ::= { x400pXcon 1 }

x400pXconEntry OBJECT-TYPE
    SYNTAX      X400pXconEntry
    MAX-ACCESS  not-accessible
    STATUS      current
    DESCRIPTION
        "Each entry in the cross-connect table describes either 
         a 1-1 cross-connect or a 0-0 cross-connect.  When the 
         channel indices are both zero, the entry describes a 
         1-1 cross-connect; when both non-zero, a 0-0 
         cross-connect.  When the both span and both channel 
         indices are the same, the entry describes either a 1-1 
         loopback or a 0-0 loopback.

         Entries in the table can be created and deleted by 
         management stations.  Entries may also be created or 
         delete autonomously as a part of system operation.  
         Management stations may only create and delete entries 
         that correspond to permanent or semi-permanent 
         connections.  As a part of system operation, permanent, 
         semi-permanent, or switched connections may be created 
         or deleted autonomously.

         Entries created or deleted by management stations 
         typically survive an agent and system reboot, however, 
         the storage type can be used to alter this behaviour."
    INDEX       {
        x400pDrivName,  -- shared index
        x400pCardIndex, -- shared index
        x400pSpanIndex, -- shared index
        x400pChanIndex  -- shared index
    }
    ::= { x400pXconTable 1 }

X400pXconEntry ::= SEQUENCE {
    x400pXconCardIndex
        Unsigned32,
    x400pXconSpanIndex
        Unsigned32,
    x400pXconChanIndex
        Unsigned32,
    x400pXconType
        INTEGER,
    x400pXconStorageType
        StorageType,
    x400pXconRowStatus
        RowStatus
}

x400pXconCardIndex OBJECT-TYPE
    SYNTAX      Unsigned32 (1..16)
    MAX-ACCESS  read-create
    STATUS      current
    DESCRIPTION
        "Provides the index of the card to which the 
         cross-connected span belongs."
    ::= { x400pXconEntry 1 }

x400pXconSpanIndex OBJECT-TYPE
    SYNTAX      Unsigned32 (1..4)
    MAX-ACCESS  read-create
    STATUS      current
    DESCRIPTION
        "Provides the index of the span which is cross-connected 
         to the indexed span."
    ::= { x400pXconEntry 2 }

x400pXconChanIndex OBJECT-TYPE
    SYNTAX      Unsigned32 (0..31)
    MAX-ACCESS  read-create
    STATUS      current
    DESCRIPTION
        "Provides the channel number of the channel to which the 
         indexed span and channel is cross-connected."
    ::= { x400pXconEntry 3 }

x400pXconType OBJECT-TYPE
    SYNTAX      INTEGER {
        switched(1), semiPermanent(2), permanent(3) }
    MAX-ACCESS  read-create
    STATUS      current
    DESCRIPTION
        "Specifies and indicates the type of connection.  The 
         value may be one of:

         - switched(1), connection is a switch connection;

         - semiPermanent(2), connection is a semi-permanent 
           connection;

         - permanent(3), connection is a permanent connection.

         Switched connections cannot be created by management 
         stations (but the agent may support management station 
         deletion of switch connections).  Management stations 
         may create and delete semi-permanent and permanent 
         connections."
    DEFVAL      { permanent }
    ::= { x400pXconEntry 4 }

x400pXconStorageType OBJECT-TYPE
    SYNTAX      StorageType
    MAX-ACCESS  read-create
    STATUS      current
    DESCRIPTION
        "Provides the memory realization of a conceptual row.  
         Possible values are:

         - volatile(2), the row is lost upon reboot, applicable 
           to switched, semi-permanent and permanent 
           connections;

         - nonVolatile(3), the row is not lost upon reboot, 
           applicable to semi-permanent and permanent 
           connections."
    DEFVAL      { nonVolatile }
    ::= { x400pXconEntry 5 }

x400pXconRowStatus OBJECT-TYPE
    SYNTAX      RowStatus
    MAX-ACCESS  read-create
    STATUS      current
    DESCRIPTION
        "Provides a mechanism whereby management stations can 
         explicitly create and delete rows in this table.  
         Management stations cannot explicitly create a switched 
         connection type but may explicitly delete all 
         connection types.  Rows may be created or deleted 
         implicitly as a part of system operations.  Rows cannot 
         be created that would form a connection to a span and 
         channel which is already engaged in another connection, 
         the other connection must first be deleted.  Rows may 
         not be taken out of service."
    ::= { x400pXconEntry 6 }


-- ====================================================================
-- SCALARS
-- ====================================================================

x400pScalars OBJECT IDENTIFIER
    ::= { x400pObjects 2 }

x400pDiscontinuityTime OBJECT-TYPE
    SYNTAX      TimeStamp
    MAX-ACCESS  read-only
    STATUS      current
    DESCRIPTION
        "Provides the uptime of the last discontinuity."
    ::= { x400pScalars 1 }


x400pNotifs OBJECT IDENTIFIER
    ::= { x400pObjects 3 }

x400pOids OBJECT IDENTIFIER
    ::= { x400pObjects 4 }

-- ====================================================================
-- CARD TYPES
-- ====================================================================
--
-- Cards can largely be identifier by their PCI information in 
-- Chip numbers, but theses are some autonomous types that 
-- permit the MIB to be extended without changing it when a new 
-- card comes along.
--

x400pCardTypes OBJECT IDENTIFIER
    ::= { x400pOids 1 }

x400pCardTypePLX9030 OBJECT-IDENTITY
    STATUS      current
    DESCRIPTION
        "This the the PLX 90303 board resulting from finding 
         '9030'X in the PCI id.  This is a card that has not has 
         the correct PCI Id burnt into it."
    ::= { x400pCardTypes 1 }

x400pCardTypePLXDevelopmentBoard OBJECT-IDENTITY
    STATUS      current
    DESCRIPTION
        "This is a PLX development board as identified by the 
         PCI Id '3001'X."
    ::= { x400pCardTypes 2 }

x400pCardTypeX400P OBJECT-IDENTITY
    STATUS      current
    DESCRIPTION
        "This is an old Digium X400P card as identified by its 
         PCI Id 'D00D'X.  The next position below this arc 
         identifies whether it is a T1 card or an E1 card.  If 
         there is nothing below this arc, the card supports both 
         E1 and T1 modes.  These cards were discontinued when 
         Digium decided to force upgrade everyone to a TE410 
         card."
    ::= { x400pCardTypes 3 }

x400pCardTypeE400P OBJECT-IDENTITY
    STATUS      current
    DESCRIPTION
        "This is an old Digium E400P card as identifier by its 
         PCI Id 'D00D'X.  The card reports a DS2154, DS21354, 
         DS21554 Dallas chip indicating that this is an E1 card.  
         This card does not support a T1 mode. It also does not 
         support some of the snazzier features.  These cards 
         were discontinued when Digium decided to force upgrade 
         everyone to a TE410 card."
    ::= { x400pCardTypeX400P 1 }

x400pCardTypeT400P OBJECT-IDENTITY
    STATUS      current
    DESCRIPTION
        "This is the old Digium T400P card as identified by its 
         PCI Id 'D00D'X.  The card reporets a DS2152, DS21352, 
         DS21552 Dallas chip indicating that this ia a T1 card.  
         This card does not support an E1 mode. It also does not 
         support some of the snazzier features.  These cards 
         were discontinued when Digium decided to force upgrade 
         everyone to a TE410 card."
    ::= { x400pCardTypeX400P 2 }

x400pCardTypeX400P-SS7 OBJECT-IDENTITY
    STATUS      current
    DESCRIPTION
        "This is an old OpenSS7 X400P-SS7 card as identified by 
         its PCI Id '0557'X. The next position below this arc 
         identifies whether this is a T1 card or an E1 card.  If 
         there is nothing below this arc, the card supports both 
         E1 and T1.  These cards were discontinued when Digium 
         decided to force upgrade everyone to a TE410 card."
    ::= { x400pCardTypes 4 }

x400pCardTypeE400P-SS7 OBJECT-IDENTITY
    STATUS      current
    DESCRIPTION
        "This is an old OpenSS7 E400P-SS7 card as identified by 
         its PCI Id '0557'X.  These are electically equivalent 
         to the E400P card.  The card reports a DS2154, DS21354 
         or DS21554 Dallas chip indicating that this is an E1 
         card.  This card does not support a T1 mode.  It also 
         does not support some othe snazzier features.  These 
         cards were discontinued when Digium decided to force 
         upgrade everyone to a TE410 card."
    ::= { x400pCardTypeX400P-SS7 1 }

x400pCardTypeT400P-SS7 OBJECT-IDENTITY
    STATUS      current
    DESCRIPTION
        "This is an old OpenSS7 T400P-SS7 card as identified by 
         its PCI Id '0557'X.  These are electically equivalent 
         to the T400P card.  The card reports a DS2152, DS21352 
         or DS21552 Dallas chip indicating that this is a T1 
         card.  This card does not support an E1 mode.  It also 
         does not support some othe snazzier features.  These 
         cards were discontinued when Digium decided to force 
         upgrade everyone to a TE410 card."
    ::= { x400pCardTypeX400P-SS7 2 }

x400pCardTypeV400P OBJECT-IDENTITY
    STATUS      current
    DESCRIPTION
        "This is a old Varion V400P card as identified by its 
         PCI id '4000'X.  The next position below this arc 
         identifies whether this is a T1 card or an E1 card.  If 
         there is nothing below this arc, the card supports both 
         E1 and T1.  These cards were discontinued by Varion due 
         to excessive lead content compared to newer European 
         standards."
    ::= { x400pCardTypes 5 }

x400pCardTypeV400PE OBJECT-IDENTITY
    STATUS      current
    DESCRIPTION
        "This is an old Varion V400PE card as identified by its 
         PCI id '4000'X.  These cards sometimes have a E1 only 
         chip and sometimes have a chip that does both E1 and 
         T1.  Some of the E1/T1 chips can be configured for J1.  
         These cards are treated as E1 only.  These cards were 
         discontinued by Varion due to excessive lead content 
         compared to newer European standards."
    ::= { x400pCardTypeV400P 1 }

x400pCardTypeV400PT OBJECT-IDENTITY
    STATUS      current
    DESCRIPTION
        "This is an old Varion V400PT card as identified by its 
         PCI id '4000'X.  These cards sometimes have a T1 only 
         chip and sometimes have a chip that does both E1 and 
         T1.  Some of the E1/T1 chips can be configured for J1.  
         These cards are treated as T1 only.  These cards were 
         discontinued by Varion due to excessive lead content 
         compared to newer European standards."
    ::= { x400pCardTypeV400P 2 }

x400pCardTypeV401PE OBJECT-IDENTITY
    STATUS      current
    DESCRIPTION
        "This is a current Varion V401PE card as identified by 
         its PCI id 'D33D'X.  Unfortunately, even though it 
         reports itself as an E1 card, most of these cards are 
         electrically identical to the T1 card, just reporting a 
         different PCI Id.  The chips support E1/T1/J1 and can 
         be configured for any mode of operation, typically on a 
         card by card basis and sometimes on a span by span 
         basis."
    ::= { x400pCardTypes 6 }

x400pCardTypeV401PT OBJECT-IDENTITY
    STATUS      current
    DESCRIPTION
        "This is a current Varion V401PT card as identified by 
         its PCI id 'D44D'X.  Unfortunately, even though it 
         reports itself as a T1 card, most of these cards are 
         electrically identical to the E1 card, just reporting a 
         different PCI Id.  The chips support E1/T1/J1 and can 
         be configured for any mode of operation, typically on a 
         card by card basis and sometimes on a span by span 
         basis."
    ::= { x400pCardTypes 7 }

-- ====================================================================
-- CHIP TYPES
-- ====================================================================

x400pChipTypes OBJECT IDENTIFIER
    ::= { x400pOids 2 }

x400pChipTypeDS2152 OBJECT-IDENTITY
    STATUS      current
    DESCRIPTION
        "The Dallas DS2152 T1 framer chip."
    ::= { x400pChipTypes 1 }

x400pChipTypeDS21352 OBJECT-IDENTITY
    STATUS      current
    DESCRIPTION
        "The Dallas DS21352 Quad T1 framer chip."
    ::= { x400pChipTypes 2 }

x400pChipTypeDS21552 OBJECT-IDENTITY
    STATUS      current
    DESCRIPTION
        "The Dallas DS21552 Quad T1 framer chip."
    ::= { x400pChipTypes 3 }

x400pChipTypeDS2154 OBJECT-IDENTITY
    STATUS      current
    DESCRIPTION
        "The Dallas DS2154 E1 framer chip."
    ::= { x400pChipTypes 4 }

x400pChipTypeDS21354 OBJECT-IDENTITY
    STATUS      current
    DESCRIPTION
        "The Dallas DS21354 Quad T1 framer chip."
    ::= { x400pChipTypes 5 }

x400pChipTypeDS21554 OBJECT-IDENTITY
    STATUS      current
    DESCRIPTION
        "The Dallas DS21554 Quad T1 framer chip."
    ::= { x400pChipTypes 6 }

x400pChipTypeDS2155 OBJECT-IDENTITY
    STATUS      current
    DESCRIPTION
        "The Dallas DS2155 E1/T1/J1 framer chip."
    ::= { x400pChipTypes 7 }

x400pChipTypeDS2156 OBJECT-IDENTITY
    STATUS      current
    DESCRIPTION
        "The Dallas DS2156 E1/T1/J1 framer chip."
    ::= { x400pChipTypes 8 }


x400pStats OBJECT IDENTIFIER
    ::= { x400pObjects 5 }

x400pNearEndStats OBJECT IDENTIFIER
    ::= { x400pStats 1 }

x400pNearEndCurrent OBJECT IDENTIFIER
    ::= { x400pNearEndStats 1 }

x400pNearEndCurrentTable OBJECT-TYPE
    SYNTAX      SEQUENCE OF X400pNearEndCurrentEntry
    MAX-ACCESS  not-accessible
    STATUS      current
    DESCRIPTION
        "Provides a table of near end current statistic."
    ::= { x400pNearEndCurrent 1 }

x400pNearEndCurrentEntry OBJECT-TYPE
    SYNTAX      X400pNearEndCurrentEntry
    MAX-ACCESS  not-accessible
    STATUS      current
    DESCRIPTION
        "Each entry in this table provides the current 
         accumulation of near end performance statistics for a 
         given span.  Spans that do not support the far end 
         reporting of performance measurements will not have an 
         associated entry in this table."
    INDEX       {
        x400pDrivName,  -- shared index
        x400pCardIndex, -- shared index
        x400pSpanIndex  -- shared index
    }
    ::= { x400pNearEndCurrentTable 1 }

X400pNearEndCurrentEntry ::= SEQUENCE {
    x400pNearEndCurrentTimeElapsed
        HCPerfTimeElapsed,
    x400pNearEndCurrentESs
        PerfCurrentCount,
    x400pNearEndCurrentSESs
        PerfCurrentCount,
    x400pNearEndCurrentSEFSs
        PerfCurrentCount,
    x400pNearEndCurrentUASs
        PerfCurrentCount,
    x400pNearEndCurrentCSSs
        PerfCurrentCount,
    x400pNearEndCurrentPCVs
        PerfCurrentCount,
    x400pNearEndCurrentLESs
        PerfCurrentCount,
    x400pNearEndCurrentBESs
        PerfCurrentCount,
    x400pNearEndCurrentDMs
        PerfCurrentCount,
    x400pNearEndCurrentLCVs
        PerfCurrentCount
}

x400pNearEndCurrentTimeElapsed OBJECT-TYPE
    SYNTAX      HCPerfTimeElapsed
    UNITS       "seconds"
    MAX-ACCESS  read-only
    STATUS      current
    DESCRIPTION
        "The number of seconds that have elapsed in the current 
         measurement period."
    ::= { x400pNearEndCurrentEntry 1 }

x400pNearEndCurrentESs OBJECT-TYPE
    SYNTAX      PerfCurrentCount
    UNITS       "seconds"
    MAX-ACCESS  read-only
    STATUS      current
    DESCRIPTION
        "The number of Errored Seconds (ESs) in the current 
         interval.  An Errored Second has one or more Path Code 
         Violations, one or more Out of Frame defects, one or 
         more Controlled Slip events, or a detected Alarm 
         Indication Signal (AIS) defect."
    ::= { x400pNearEndCurrentEntry 2 }

x400pNearEndCurrentSESs OBJECT-TYPE
    SYNTAX      PerfCurrentCount
    UNITS       "seconds"
    MAX-ACCESS  read-only
    STATUS      current
    DESCRIPTION
        "The number of Severely Errored Seconds (SESs) in the 
         current interval.  A Severely Errored Second ...."
    ::= { x400pNearEndCurrentEntry 3 }

x400pNearEndCurrentSEFSs OBJECT-TYPE
    SYNTAX      PerfCurrentCount
    UNITS       "seconds"
    MAX-ACCESS  read-only
    STATUS      current
    DESCRIPTION
        "The number of Severely Errored Framing Seconds (SEFSs) 
         in the current interval.  A Severely Errored Frame 
         Second has one or more Out of Frame defects or a 
         detected AIS defect."
    ::= { x400pNearEndCurrentEntry 4 }

x400pNearEndCurrentUASs OBJECT-TYPE
    SYNTAX      PerfCurrentCount
    UNITS       "seconds"
    MAX-ACCESS  read-only
    STATUS      current
    DESCRIPTION
        "The number of Unavailable Seconds (UASs) in the current 
         interval."
    ::= { x400pNearEndCurrentEntry 5 }

x400pNearEndCurrentCSSs OBJECT-TYPE
    SYNTAX      PerfCurrentCount
    UNITS       "seconds"
    MAX-ACCESS  read-only
    STATUS      current
    DESCRIPTION
        "The number of Controlled Slip Seconds (CSSs) in the 
         current interval."
    ::= { x400pNearEndCurrentEntry 6 }

x400pNearEndCurrentPCVs OBJECT-TYPE
    SYNTAX      PerfCurrentCount
    UNITS       "violations"
    MAX-ACCESS  read-only
    STATUS      current
    DESCRIPTION
        "The number of Path Coding Violations (PCVs) in the 
         current interval.  A Path Coding Violation is a frame 
         syncrhonization bit error in the D4 and E1 no-CRC4 
         formats, or a CRC or frame syncrhonization bit error in 
         the ESF and E1 CRC4 formats."
    ::= { x400pNearEndCurrentEntry 7 }

x400pNearEndCurrentLESs OBJECT-TYPE
    SYNTAX      PerfCurrentCount
    UNITS       "seconds"
    MAX-ACCESS  read-only
    STATUS      current
    DESCRIPTION
        "The number of Line Errored Seconds (LESs) in the 
         current interval.  A Line Errored Second is a second in 
         which one or more Line Code Violation error events are 
         detected."
    ::= { x400pNearEndCurrentEntry 8 }

x400pNearEndCurrentBESs OBJECT-TYPE
    SYNTAX      PerfCurrentCount
    UNITS       "seconds"
    MAX-ACCESS  read-only
    STATUS      current
    DESCRIPTION
        "The number of Bursty Errored Seconds (BESs) in the 
         current interval.  A Bursty Errored Second has 2 to 319 
         Path Coding Violation error events, no Severely Errored 
         Frame defects, and no detected incoming AIS defects."
    ::= { x400pNearEndCurrentEntry 9 }

x400pNearEndCurrentDMs OBJECT-TYPE
    SYNTAX      PerfCurrentCount
    UNITS       "minutes"
    MAX-ACCESS  read-only
    STATUS      current
    DESCRIPTION
        "The number of Degraded Minutes (DMs) in the current 
         interval."
    ::= { x400pNearEndCurrentEntry 10 }

x400pNearEndCurrentLCVs OBJECT-TYPE
    SYNTAX      PerfCurrentCount
    UNITS       "violations"
    MAX-ACCESS  read-only
    STATUS      current
    DESCRIPTION
        "The number of Line Coding Violations (LCVs) in the 
         current interval.  An LCV is the occurence of a Bipolar 
         Violation (BPV) or Excessive Zeroes (EXZ) error event."
    ::= { x400pNearEndCurrentEntry 11 }


x400pNearEndInterval OBJECT IDENTIFIER
    ::= { x400pNearEndStats 2 }

x400pNearEndIntervalTable OBJECT-TYPE
    SYNTAX      SEQUENCE OF X400pNearEndIntervalEntry
    MAX-ACCESS  not-accessible
    STATUS      current
    DESCRIPTION
        "Provides a table of near end performance interval 
         measurements for a given span.  Entries exist the 
         previous 96 intervals associated with each span."
    ::= { x400pNearEndInterval 1 }

x400pNearEndIntervalEntry OBJECT-TYPE
    SYNTAX      X400pNearEndIntervalEntry
    MAX-ACCESS  not-accessible
    STATUS      current
    DESCRIPTION
        "Each entry in the table provides the interval 
         measurements for one of 96 intervals associated with 
         each span.  If the associated span does not support the 
         reporting of near end performance measurements, there 
         may be no intervals in this table for the associated 
         span; or the intervals may have the 
         x400pNearEndIntervalValidData column set to false(2)."
    INDEX       {
        x400pDrivName,  -- shared index
        x400pCardIndex, -- shared index
        x400pSpanIndex, -- shared index
        x400pNearEndIntervalIndex
    }
    ::= { x400pNearEndIntervalTable 1 }

X400pNearEndIntervalEntry ::= SEQUENCE {
    x400pNearEndIntervalIndex
        Unsigned32,
    x400pNearEndIntervalESs
        PerfIntervalCount,
    x400pNearEndIntervalSESs
        PerfIntervalCount,
    x400pNearEndIntervalSEFSs
        PerfIntervalCount,
    x400pNearEndIntervalUASs
        PerfIntervalCount,
    x400pNearEndIntervalCSSs
        PerfIntervalCount,
    x400pNearEndIntervalPCVs
        PerfIntervalCount,
    x400pNearEndIntervalLESs
        PerfIntervalCount,
    x400pNearEndIntervalBESs
        PerfIntervalCount,
    x400pNearEndIntervalDMs
        PerfIntervalCount,
    x400pNearEndIntervalLCVs
        PerfIntervalCount,
    x400pNearEndIntervalValidData
        TruthValue
}

x400pNearEndIntervalIndex OBJECT-TYPE
    SYNTAX      Unsigned32 (1..96)
    MAX-ACCESS  not-accessible
    STATUS      current
    DESCRIPTION
        "Provides an index into the interval table.  Each 
         interval represents 15 minute increments in the past 
         with the lowest index value being most recent."
    ::= { x400pNearEndIntervalEntry 1 }

x400pNearEndIntervalESs OBJECT-TYPE
    SYNTAX      PerfIntervalCount
    UNITS       "seconds"
    MAX-ACCESS  read-only
    STATUS      current
    DESCRIPTION
        "The number of Errored Seconds (ESs) in the indexed 
         interval."
    ::= { x400pNearEndIntervalEntry 2 }

x400pNearEndIntervalSESs OBJECT-TYPE
    SYNTAX      PerfIntervalCount
    UNITS       "seconds"
    MAX-ACCESS  read-only
    STATUS      current
    DESCRIPTION
        "The number of Severely Errored Seconds (SESs) in the 
         indexed interval."
    ::= { x400pNearEndIntervalEntry 3 }

x400pNearEndIntervalSEFSs OBJECT-TYPE
    SYNTAX      PerfIntervalCount
    UNITS       "seconds"
    MAX-ACCESS  read-only
    STATUS      current
    DESCRIPTION
        "The number of Severely Errored Framing Seconds (SEFSs) 
         in the indexed interval."
    ::= { x400pNearEndIntervalEntry 4 }

x400pNearEndIntervalUASs OBJECT-TYPE
    SYNTAX      PerfIntervalCount
    UNITS       "seconds"
    MAX-ACCESS  read-only
    STATUS      current
    DESCRIPTION
        "The number of Unavailable Seconds (UASs) in the indexed 
         interval."
    ::= { x400pNearEndIntervalEntry 5 }

x400pNearEndIntervalCSSs OBJECT-TYPE
    SYNTAX      PerfIntervalCount
    UNITS       "seconds"
    MAX-ACCESS  read-only
    STATUS      current
    DESCRIPTION
        "The number of Controlled Slip Seconds (CSSs) in the 
         indexed interval."
    ::= { x400pNearEndIntervalEntry 6 }

x400pNearEndIntervalPCVs OBJECT-TYPE
    SYNTAX      PerfIntervalCount
    UNITS       "violations"
    MAX-ACCESS  read-only
    STATUS      current
    DESCRIPTION
        "The number of Path Coding Violations (PCVs) in the 
         indexed interval."
    ::= { x400pNearEndIntervalEntry 7 }

x400pNearEndIntervalLESs OBJECT-TYPE
    SYNTAX      PerfIntervalCount
    UNITS       "seconds"
    MAX-ACCESS  read-only
    STATUS      current
    DESCRIPTION
        "The number of Line Errored Seconds (LESs) in the 
         indexed interval."
    ::= { x400pNearEndIntervalEntry 8 }

x400pNearEndIntervalBESs OBJECT-TYPE
    SYNTAX      PerfIntervalCount
    UNITS       "seconds"
    MAX-ACCESS  read-only
    STATUS      current
    DESCRIPTION
        "The number of Bursty Errored Seconds (BESs) in the 
         indexed interval."
    ::= { x400pNearEndIntervalEntry 9 }

x400pNearEndIntervalDMs OBJECT-TYPE
    SYNTAX      PerfIntervalCount
    UNITS       "minutes"
    MAX-ACCESS  read-only
    STATUS      current
    DESCRIPTION
        "The number of Degraded Minutes (DMs) in the indexed 
         interval."
    ::= { x400pNearEndIntervalEntry 10 }

x400pNearEndIntervalLCVs OBJECT-TYPE
    SYNTAX      PerfIntervalCount
    UNITS       "violations"
    MAX-ACCESS  read-only
    STATUS      current
    DESCRIPTION
        "The number of Line Coding Violations (LCVs) in the 
         indexed interval."
    ::= { x400pNearEndIntervalEntry 11 }

x400pNearEndIntervalValidData OBJECT-TYPE
    SYNTAX      TruthValue
    MAX-ACCESS  read-only
    STATUS      current
    DESCRIPTION
        "Indicates whether the performance interval counts are 
         valid for the indexed interval."
    ::= { x400pNearEndIntervalEntry 12 }


x400pNearEndTotal OBJECT IDENTIFIER
    ::= { x400pNearEndStats 3 }

x400pNearEndTotalTable OBJECT-TYPE
    SYNTAX      SEQUENCE OF X400pNearEndTotalEntry
    MAX-ACCESS  not-accessible
    STATUS      current
    DESCRIPTION
        "Provides a table of near end performance measurement 
         totals."
    ::= { x400pNearEndTotal 1 }

x400pNearEndTotalEntry OBJECT-TYPE
    SYNTAX      X400pNearEndTotalEntry
    MAX-ACCESS  not-accessible
    STATUS      current
    DESCRIPTION
        "Each entry in the table provides near end performance 
         statistics for a given span.  Spans whose drivers or 
         equipment does not support the reporting of near end 
         performance measurements will not have an entry in this 
         table, or may have an entry where the 
         x400pNearEndTotalValidIntervals is zero (0)."
    INDEX       {
        x400pDrivName,  -- shared index
        x400pCardIndex, -- shared index
        x400pSpanIndex  -- shared index
    }
    ::= { x400pNearEndTotalTable 1 }

X400pNearEndTotalEntry ::= SEQUENCE {
    x400pNearEndTotalValidIntervals
        HCPerfValidIntervals,
    x400pNearEndTotalInvalidIntervals
        HCPerfInvalidIntervals,
    x400pNearEndTotalESs
        PerfTotalCount,
    x400pNearEndTotalSESs
        PerfTotalCount,
    x400pNearEndTotalSEFSs
        PerfTotalCount,
    x400pNearEndTotalUASs
        PerfTotalCount,
    x400pNearEndTotalCSSs
        PerfTotalCount,
    x400pNearEndTotalPCVs
        PerfTotalCount,
    x400pNearEndTotalLESs
        PerfTotalCount,
    x400pNearEndTotalBESs
        PerfTotalCount,
    x400pNearEndTotalDMs
        PerfTotalCount,
    x400pNearEndTotalLCVs
        PerfTotalCount
}

x400pNearEndTotalValidIntervals OBJECT-TYPE
    SYNTAX      HCPerfValidIntervals
    MAX-ACCESS  read-only
    STATUS      current
    DESCRIPTION
        "The number of intervals for which data was collected."
    ::= { x400pNearEndTotalEntry 1 }

x400pNearEndTotalInvalidIntervals OBJECT-TYPE
    SYNTAX      HCPerfInvalidIntervals
    MAX-ACCESS  read-only
    STATUS      current
    DESCRIPTION
        "The number of intervals in the range from 0 to 
         x400pNearEndTotalValidIntervals for which data is 
         invalid (missing)."
    ::= { x400pNearEndTotalEntry 2 }

x400pNearEndTotalESs OBJECT-TYPE
    SYNTAX      PerfTotalCount
    UNITS       "seconds"
    MAX-ACCESS  read-only
    STATUS      current
    DESCRIPTION
        "The total number of Errored Seconds (ESs) in all 
         available intervals over the last 24-hour period."
    ::= { x400pNearEndTotalEntry 3 }

x400pNearEndTotalSESs OBJECT-TYPE
    SYNTAX      PerfTotalCount
    UNITS       "seconds"
    MAX-ACCESS  read-only
    STATUS      current
    DESCRIPTION
        "The total number of Severly Errored Seconds (SESs) in 
         all available intervals over the last 24-hour period."
    ::= { x400pNearEndTotalEntry 4 }

x400pNearEndTotalSEFSs OBJECT-TYPE
    SYNTAX      PerfTotalCount
    UNITS       "seconds"
    MAX-ACCESS  read-only
    STATUS      current
    DESCRIPTION
        "The total number of Severely Errored Framing Seconds 
         (SEFSs) in all available intervals over the last 
         24-hour period."
    ::= { x400pNearEndTotalEntry 5 }

x400pNearEndTotalUASs OBJECT-TYPE
    SYNTAX      PerfTotalCount
    UNITS       "seconds"
    MAX-ACCESS  read-only
    STATUS      current
    DESCRIPTION
        "The total number of Unavailable Seconds (UASs) in all 
         available intervals over the last 24-hour period."
    ::= { x400pNearEndTotalEntry 6 }

x400pNearEndTotalCSSs OBJECT-TYPE
    SYNTAX      PerfTotalCount
    UNITS       "seconds"
    MAX-ACCESS  read-only
    STATUS      current
    DESCRIPTION
        "The total number of Controlled Slip Seconds (CSSs) in 
         all available intervals over the last 24-hour period."
    ::= { x400pNearEndTotalEntry 7 }

x400pNearEndTotalPCVs OBJECT-TYPE
    SYNTAX      PerfTotalCount
    UNITS       "violations"
    MAX-ACCESS  read-only
    STATUS      current
    DESCRIPTION
        "The total number of Path Coding Violations (PCVs) in 
         all available intervals over the last 24-hour period."
    ::= { x400pNearEndTotalEntry 8 }

x400pNearEndTotalLESs OBJECT-TYPE
    SYNTAX      PerfTotalCount
    UNITS       "seconds"
    MAX-ACCESS  read-only
    STATUS      current
    DESCRIPTION
        "The total number of Line Errored Seconds (LESs) in all 
         available intervals over the last 24-hour period."
    ::= { x400pNearEndTotalEntry 9 }

x400pNearEndTotalBESs OBJECT-TYPE
    SYNTAX      PerfTotalCount
    UNITS       "seconds"
    MAX-ACCESS  read-only
    STATUS      current
    DESCRIPTION
        "The total number of Bursty Errored Seconds (BESs) in 
         all available intervals over the last 24-hour period."
    ::= { x400pNearEndTotalEntry 10 }

x400pNearEndTotalDMs OBJECT-TYPE
    SYNTAX      PerfTotalCount
    UNITS       "minutes"
    MAX-ACCESS  read-only
    STATUS      current
    DESCRIPTION
        "The total number of Degraded Minutes (DMs) in all 
         available intervals over the last 24-hour period."
    ::= { x400pNearEndTotalEntry 11 }

x400pNearEndTotalLCVs OBJECT-TYPE
    SYNTAX      PerfTotalCount
    UNITS       "violations"
    MAX-ACCESS  read-only
    STATUS      current
    DESCRIPTION
        "The total number of Line Coding Violations (LCVs) in 
         all available intervals over the last 24-hour period."
    ::= { x400pNearEndTotalEntry 12 }


x400pFarEndStats OBJECT IDENTIFIER
    ::= { x400pStats 2 }

x400pFarEndCurrent OBJECT IDENTIFIER
    ::= { x400pFarEndStats 1 }

x400pFarEndCurrentTable OBJECT-TYPE
    SYNTAX      SEQUENCE OF X400pFarEndCurrentEntry
    MAX-ACCESS  not-accessible
    STATUS      current
    DESCRIPTION
        "Provides a table of far end current statistic."
    ::= { x400pFarEndCurrent 1 }

x400pFarEndCurrentEntry OBJECT-TYPE
    SYNTAX      X400pFarEndCurrentEntry
    MAX-ACCESS  not-accessible
    STATUS      current
    DESCRIPTION
        "Each entry in this table provides the current 
         accumulation of far end performance statistics for a 
         given span.  Spans that do not support the far end 
         reporting of performance measurements will not have an 
         associated entry in this table."
    INDEX       {
        x400pDrivName,  -- shared index
        x400pCardIndex, -- shared index
        x400pSpanIndex  -- shared index
    }
    ::= { x400pFarEndCurrentTable 1 }

X400pFarEndCurrentEntry ::= SEQUENCE {
    x400pFarEndCurrentTimeElapsed
        HCPerfTimeElapsed,
    x400pFarEndCurrentESs
        PerfCurrentCount,
    x400pFarEndCurrentSESs
        PerfCurrentCount,
    x400pFarEndCurrentSEFSs
        PerfCurrentCount,
    x400pFarEndCurrentUASs
        PerfCurrentCount,
    x400pFarEndCurrentCSSs
        PerfCurrentCount,
    x400pFarEndCurrentPCVs
        PerfCurrentCount,
    x400pFarEndCurrentLESs
        PerfCurrentCount,
    x400pFarEndCurrentBESs
        PerfCurrentCount,
    x400pFarEndCurrentDMs
        PerfCurrentCount
}

x400pFarEndCurrentTimeElapsed OBJECT-TYPE
    SYNTAX      HCPerfTimeElapsed
    UNITS       "seconds"
    MAX-ACCESS  read-only
    STATUS      current
    DESCRIPTION
        "The number of seconds that have elapsed in the current 
         measurement period."
    ::= { x400pFarEndCurrentEntry 1 }

x400pFarEndCurrentESs OBJECT-TYPE
    SYNTAX      PerfCurrentCount
    UNITS       "seconds"
    MAX-ACCESS  read-only
    STATUS      current
    DESCRIPTION
        "The number of Errored Seconds (ESs) in the current 
         interval."
    ::= { x400pFarEndCurrentEntry 2 }

x400pFarEndCurrentSESs OBJECT-TYPE
    SYNTAX      PerfCurrentCount
    UNITS       "seconds"
    MAX-ACCESS  read-only
    STATUS      current
    DESCRIPTION
        "The number of Severely Errored Seconds (SESs) in the 
         current interval."
    ::= { x400pFarEndCurrentEntry 3 }

x400pFarEndCurrentSEFSs OBJECT-TYPE
    SYNTAX      PerfCurrentCount
    UNITS       "seconds"
    MAX-ACCESS  read-only
    STATUS      current
    DESCRIPTION
        "The number of Severely Errored Framing Seconds (SEFSs) 
         in the current interval."
    ::= { x400pFarEndCurrentEntry 4 }

x400pFarEndCurrentUASs OBJECT-TYPE
    SYNTAX      PerfCurrentCount
    UNITS       "seconds"
    MAX-ACCESS  read-only
    STATUS      current
    DESCRIPTION
        "The number of Unavailable Seconds (UASs) in the current 
         interval."
    ::= { x400pFarEndCurrentEntry 5 }

x400pFarEndCurrentCSSs OBJECT-TYPE
    SYNTAX      PerfCurrentCount
    UNITS       "seconds"
    MAX-ACCESS  read-only
    STATUS      current
    DESCRIPTION
        "The number of Controlled Slip Seconds (CSSs) in the 
         current interval."
    ::= { x400pFarEndCurrentEntry 6 }

x400pFarEndCurrentPCVs OBJECT-TYPE
    SYNTAX      PerfCurrentCount
    UNITS       "violations"
    MAX-ACCESS  read-only
    STATUS      current
    DESCRIPTION
        "The number of Path Coding Violations (PCVs) in the 
         current interval."
    ::= { x400pFarEndCurrentEntry 7 }

x400pFarEndCurrentLESs OBJECT-TYPE
    SYNTAX      PerfCurrentCount
    UNITS       "seconds"
    MAX-ACCESS  read-only
    STATUS      current
    DESCRIPTION
        "The number of Line Errored Seconds (LESs) in the 
         current interval."
    ::= { x400pFarEndCurrentEntry 8 }

x400pFarEndCurrentBESs OBJECT-TYPE
    SYNTAX      PerfCurrentCount
    UNITS       "seconds"
    MAX-ACCESS  read-only
    STATUS      current
    DESCRIPTION
        "The number of Bursty Errored Seconds (BESs) in the 
         current interval."
    ::= { x400pFarEndCurrentEntry 9 }

x400pFarEndCurrentDMs OBJECT-TYPE
    SYNTAX      PerfCurrentCount
    UNITS       "minutes"
    MAX-ACCESS  read-only
    STATUS      current
    DESCRIPTION
        "The number of Degraded Minutes (DMs) in the current 
         interval."
    ::= { x400pFarEndCurrentEntry 10 }


x400pFarEndInterval OBJECT IDENTIFIER
    ::= { x400pFarEndStats 2 }

x400pFarEndIntervalTable OBJECT-TYPE
    SYNTAX      SEQUENCE OF X400pFarEndIntervalEntry
    MAX-ACCESS  not-accessible
    STATUS      current
    DESCRIPTION
        "Provides a table of far end performance interval 
         measurements for a given span.  Entries exist the 
         previous 96 intervals associated with each span."
    ::= { x400pFarEndInterval 1 }

x400pFarEndIntervalEntry OBJECT-TYPE
    SYNTAX      X400pFarEndIntervalEntry
    MAX-ACCESS  not-accessible
    STATUS      current
    DESCRIPTION
        "Each entry in the table provides the interval 
         measurements for one of 96 intervals associated with 
         each span.  If the associated span does not support the 
         reporting of far end performance measurements, there 
         may be no intervals in this table for the associated 
         span; or the intervals may have the 
         x400pFarEndIntervalValidData column set to false(2)."
    INDEX       {
        x400pDrivName,  -- shared index
        x400pCardIndex, -- shared index
        x400pSpanIndex, -- shared index
        x400pFarEndIntervalIndex
    }
    ::= { x400pFarEndIntervalTable 1 }

X400pFarEndIntervalEntry ::= SEQUENCE {
    x400pFarEndIntervalIndex
        Unsigned32,
    x400pFarEndIntervalESs
        PerfIntervalCount,
    x400pFarEndIntervalSESs
        PerfIntervalCount,
    x400pFarEndIntervalSEFSs
        PerfIntervalCount,
    x400pFarEndIntervalUASs
        PerfIntervalCount,
    x400pFarEndIntervalCSSs
        PerfIntervalCount,
    x400pFarEndIntervalPCVs
        PerfIntervalCount,
    x400pFarEndIntervalLESs
        PerfIntervalCount,
    x400pFarEndIntervalBESs
        PerfIntervalCount,
    x400pFarEndIntervalDMs
        PerfIntervalCount,
    x400pFarEndIntervalValidData
        TruthValue
}

x400pFarEndIntervalIndex OBJECT-TYPE
    SYNTAX      Unsigned32 (1..96)
    MAX-ACCESS  not-accessible
    STATUS      current
    DESCRIPTION
        "Provides an index in increments of 15 minute intervals 
         with the lowest index value being the most recent 
         interval."
    ::= { x400pFarEndIntervalEntry 1 }

x400pFarEndIntervalESs OBJECT-TYPE
    SYNTAX      PerfIntervalCount
    UNITS       "seconds"
    MAX-ACCESS  read-only
    STATUS      current
    DESCRIPTION
        "The number of Errored Seconds (ESs) in the indexed 
         interval."
    ::= { x400pFarEndIntervalEntry 2 }

x400pFarEndIntervalSESs OBJECT-TYPE
    SYNTAX      PerfIntervalCount
    UNITS       "seconds"
    MAX-ACCESS  read-only
    STATUS      current
    DESCRIPTION
        "The number of Severely Errored Seconds (SESs) in the 
         indexed interval."
    ::= { x400pFarEndIntervalEntry 3 }

x400pFarEndIntervalSEFSs OBJECT-TYPE
    SYNTAX      PerfIntervalCount
    UNITS       "seconds"
    MAX-ACCESS  read-only
    STATUS      current
    DESCRIPTION
        "The number of Severely Errored Framing Seconds (SEFSs) 
         in the indexed interval."
    ::= { x400pFarEndIntervalEntry 4 }

x400pFarEndIntervalUASs OBJECT-TYPE
    SYNTAX      PerfIntervalCount
    UNITS       "seconds"
    MAX-ACCESS  read-only
    STATUS      current
    DESCRIPTION
        "The number of Unavailable Seconds (UASs) in the indexed 
         interval."
    ::= { x400pFarEndIntervalEntry 5 }

x400pFarEndIntervalCSSs OBJECT-TYPE
    SYNTAX      PerfIntervalCount
    UNITS       "seconds"
    MAX-ACCESS  read-only
    STATUS      current
    DESCRIPTION
        "The number of Controlled Slip Seconds (CSSs) in the 
         indexed interval."
    ::= { x400pFarEndIntervalEntry 6 }

x400pFarEndIntervalPCVs OBJECT-TYPE
    SYNTAX      PerfIntervalCount
    UNITS       "violations"
    MAX-ACCESS  read-only
    STATUS      current
    DESCRIPTION
        "The number of Path Coding Violations (PCVs) in the 
         indexed interval."
    ::= { x400pFarEndIntervalEntry 7 }

x400pFarEndIntervalLESs OBJECT-TYPE
    SYNTAX      PerfIntervalCount
    UNITS       "seconds"
    MAX-ACCESS  read-only
    STATUS      current
    DESCRIPTION
        "The number of Line Errored Seconds (LESs) in the 
         indexed interval."
    ::= { x400pFarEndIntervalEntry 8 }

x400pFarEndIntervalBESs OBJECT-TYPE
    SYNTAX      PerfIntervalCount
    UNITS       "seconds"
    MAX-ACCESS  read-only
    STATUS      current
    DESCRIPTION
        "The number of Bursty Errored Seconds (BESs) in the 
         indexed interval."
    ::= { x400pFarEndIntervalEntry 9 }

x400pFarEndIntervalDMs OBJECT-TYPE
    SYNTAX      PerfIntervalCount
    UNITS       "minutes"
    MAX-ACCESS  read-only
    STATUS      current
    DESCRIPTION
        "The number of Degraded Minutes (DMs) in the indexed 
         interval."
    ::= { x400pFarEndIntervalEntry 10 }

x400pFarEndIntervalValidData OBJECT-TYPE
    SYNTAX      TruthValue
    MAX-ACCESS  read-only
    STATUS      current
    DESCRIPTION
        "Indicates whether the performance interval counts are 
         valid for the indexed interval."
    ::= { x400pFarEndIntervalEntry 11 }


x400pFarEndTotal OBJECT IDENTIFIER
    ::= { x400pFarEndStats 3 }

x400pFarEndTotalTable OBJECT-TYPE
    SYNTAX      SEQUENCE OF X400pFarEndTotalEntry
    MAX-ACCESS  not-accessible
    STATUS      current
    DESCRIPTION
        "Provides a table of far end performance statistic 
         totals."
    ::= { x400pFarEndTotal 1 }

x400pFarEndTotalEntry OBJECT-TYPE
    SYNTAX      X400pFarEndTotalEntry
    MAX-ACCESS  not-accessible
    STATUS      current
    DESCRIPTION
        "Each entry in the table provides far end performance 
         statistics for a given span.  Spans whose drivers or 
         equipment does not support the reporting of far end 
         performance measurements will not have an entry in this  
         table, or may have an entry where the 
         x400pFarEndTotalValidIntervals is zero (0)."
    INDEX       {
        x400pDrivName,  -- shared index
        x400pCardIndex, -- shared index
        x400pSpanIndex  -- shared index
    }
    ::= { x400pFarEndTotalTable 1 }

X400pFarEndTotalEntry ::= SEQUENCE {
    x400pFarEndTotalValidIntervals
        HCPerfValidIntervals,
    x400pFarEndTotalInvalidIntervals
        HCPerfInvalidIntervals,
    x400pFarEndTotalESs
        PerfTotalCount,
    x400pFarEndTotalSESs
        PerfTotalCount,
    x400pFarEndTotalSEFSs
        PerfTotalCount,
    x400pFarEndTotalUASs
        PerfTotalCount,
    x400pFarEndTotalCSSs
        PerfTotalCount,
    x400pFarEndTotalPCVs
        PerfTotalCount,
    x400pFarEndTotalLESs
        PerfTotalCount,
    x400pFarEndTotalBESs
        PerfTotalCount,
    x400pFarEndTotalDMs
        PerfTotalCount
}

x400pFarEndTotalValidIntervals OBJECT-TYPE
    SYNTAX      HCPerfValidIntervals
    MAX-ACCESS  read-only
    STATUS      current
    DESCRIPTION
        "The number of intervals for which data was collected."
    ::= { x400pFarEndTotalEntry 1 }

x400pFarEndTotalInvalidIntervals OBJECT-TYPE
    SYNTAX      HCPerfInvalidIntervals
    MAX-ACCESS  read-only
    STATUS      current
    DESCRIPTION
        "The number of intervals in the range from 0 to 
         x400pFarEndTotalValidIntervals for which data is 
         invalid (missing)."
    ::= { x400pFarEndTotalEntry 2 }

x400pFarEndTotalESs OBJECT-TYPE
    SYNTAX      PerfTotalCount
    UNITS       "seconds"
    MAX-ACCESS  read-only
    STATUS      current
    DESCRIPTION
        "The total number of Errored Seconds (ESs) in all 
         available intervals over the last 24-hour period."
    ::= { x400pFarEndTotalEntry 3 }

x400pFarEndTotalSESs OBJECT-TYPE
    SYNTAX      PerfTotalCount
    UNITS       "seconds"
    MAX-ACCESS  read-only
    STATUS      current
    DESCRIPTION
        "The total number of Severly Errored Seconds (SESs) in 
         all available intervals over the last 24-hour period."
    ::= { x400pFarEndTotalEntry 4 }

x400pFarEndTotalSEFSs OBJECT-TYPE
    SYNTAX      PerfTotalCount
    UNITS       "seconds"
    MAX-ACCESS  read-only
    STATUS      current
    DESCRIPTION
        "The total number of Severely Errored Framing Seconds 
         (SEFSs) in all available intervals over the last 
         24-hour period."
    ::= { x400pFarEndTotalEntry 5 }

x400pFarEndTotalUASs OBJECT-TYPE
    SYNTAX      PerfTotalCount
    UNITS       "seconds"
    MAX-ACCESS  read-only
    STATUS      current
    DESCRIPTION
        "The total number of Unavailable Seconds (UASs) in all 
         available intervals over the last 24-hour period."
    ::= { x400pFarEndTotalEntry 6 }

x400pFarEndTotalCSSs OBJECT-TYPE
    SYNTAX      PerfTotalCount
    UNITS       "seconds"
    MAX-ACCESS  read-only
    STATUS      current
    DESCRIPTION
        "The total number of Controlled Slip Seconds (CSSs) in 
         all available intervals over the last 24-hour period."
    ::= { x400pFarEndTotalEntry 7 }

x400pFarEndTotalPCVs OBJECT-TYPE
    SYNTAX      PerfTotalCount
    UNITS       "violations"
    MAX-ACCESS  read-only
    STATUS      current
    DESCRIPTION
        "The total number of Path Coding Violations (PCVs) in 
         all available intervals over the last 24-hour period."
    ::= { x400pFarEndTotalEntry 8 }

x400pFarEndTotalLESs OBJECT-TYPE
    SYNTAX      PerfTotalCount
    UNITS       "seconds"
    MAX-ACCESS  read-only
    STATUS      current
    DESCRIPTION
        "The total number of Line Errored Seconds (LESs) in all 
         available intervals over the last 24-hour period."
    ::= { x400pFarEndTotalEntry 9 }

x400pFarEndTotalBESs OBJECT-TYPE
    SYNTAX      PerfTotalCount
    UNITS       "seconds"
    MAX-ACCESS  read-only
    STATUS      current
    DESCRIPTION
        "The total number of Bursty Errored Seconds (BESs) in 
         all available intervals over the last 24-hour period."
    ::= { x400pFarEndTotalEntry 10 }

x400pFarEndTotalDMs OBJECT-TYPE
    SYNTAX      PerfTotalCount
    UNITS       "minutes"
    MAX-ACCESS  read-only
    STATUS      current
    DESCRIPTION
        "The total number of Degraded Minutes (DMs) in all 
         available intervals over the last 24-hour period."
    ::= { x400pFarEndTotalEntry 11 }

x400pConformance OBJECT IDENTIFIER
    ::= { x400pMIB 2 }

x400pGroups OBJECT IDENTIFIER
    ::= { x400pConformance 1 }

x400pSyncMandatoryGroup OBJECT-GROUP
    OBJECTS     {
        x400pSyncSpanId, x400pSyncRowStatus }
    STATUS      current
    DESCRIPTION
        "A collection of objects identifying the span."
    ::= { x400pGroups 1 }

x400pCardIdGroup OBJECT-GROUP
    OBJECTS     {
        x400pCardType, x400pCardIdentifier, x400pCardRevision }
    STATUS      current
    DESCRIPTION
        "A collection of objects identifying the span type."
    ::= { x400pGroups 2 }

x400pChipGroup OBJECT-GROUP
    OBJECTS     {
        x400pCardChipType, x400pCardChipRevision }
    STATUS      current
    DESCRIPTION
        "A collection of objects identifying the chip type."
    ::= { x400pGroups 3 }

x400pPciGroup OBJECT-GROUP
    OBJECTS     {
        x400pCardPciBus, x400pCardPciSlot, x400pCardPciIrq }
    STATUS      current
    DESCRIPTION
        "A collectin of objects identifying the bus location."
    ::= { x400pGroups 4 }

x400pCardGroup OBJECT-GROUP
    OBJECTS     {
        x400pCardSpanType, x400pCardMode, x400pCardSyncMaster, 
        x400pCardSyncSource, x400pCardSyncGroup, 
        x400pCardAdministrativeState, x400pCardOperationalState, 
        x400pCardUsageState, x400pCardAlarmStatus, 
        x400pCardProceduralStatus, x400pCardAvailabilityStatus, 
        x400pCardControlStatus, x400pCardUnknownStatus, 
        x400pCardSyncSpanId, x400pCardSyncTransitions }
    STATUS      current
    DESCRIPTION
        "A collection of objects identifying the card state."
    ::= { x400pGroups 5 }

x400pSpanGroup OBJECT-GROUP
    OBJECTS     {
        x400pSpanDevice, x400pSpanEquipmentId, x400pSpanType, 
        x400pSpanNumber, x400pSpanRate, x400pSpanMode, 
        x400pSpanCrc, x400pSpanClocking, x400pSpanPriority, 
        x400pSpanCoding, x400pSpanFraming, 
        x400pSpanLineImpedance, x400pSpanLineMode, 
        x400pSpanLineLength, x400pSpanLineAttenuation, 
        x400pSpanLineGain, x400pSpanLineDelay, x400pSpanTxLevel, 
        x400pSpanRxLevel, x400pSpanAlarmSettleTime, 
        x400pSpanLineCodeTime, x400pSpanPrimary, 
        x400pSpanDataLink, x400pSpanLineCode, 
        x400pSpanAlarmSeverityMappingProfile, 
        x400pSpanAdministrativeState, x400pSpanOperationalState, 
        x400pSpanUsageState, x400pSpanAlarmStatus, 
        x400pSpanProceduralStatus, x400pSpanAvailabilityStatus, 
        x400pSpanControlStatus, x400pSpanStandbyStatus, 
        x400pSpanUnknownStatus, x400pSpanSap, 
        x400pSpanLoopbackStatus, x400pSpanLineStatus, 
        x400pSpanAlarms, x400pSpanEvents, x400pSpanReceiveLevel, 
        x400pSpanReceiveThreshold, x400pSpanRowStatus }
    STATUS      current
    DESCRIPTION
        "A collection of objects implementing the span group."
    ::= { x400pGroups 6 }

x400pChanGroup OBJECT-GROUP
    OBJECTS     {
        x400pChanType, x400pChanFormat, x400pChanRate, 
        x400pChanMode, x400pChanAdministrativeState, 
        x400pChanUsageState, x400pChanAvailabilityStatus, 
        x400pChanControlStatus, x400pChanSap }
    STATUS      current
    DESCRIPTION
        "A collection of objects implementing the channel 
         group."
    ::= { x400pGroups 7 }

x400pXconGroup OBJECT-GROUP
    OBJECTS     {
        x400pXconSpanIndex, x400pXconChanIndex, x400pXconType, 
        x400pXconStorageType, x400pXconRowStatus }
    STATUS      current
    DESCRIPTION
        "A collection of objects implementing the cross-connect 
         group."
    ::= { x400pGroups 8 }

x400pBertGroup OBJECT-GROUP
    OBJECTS     {
        x400pBertMode, x400pBertSelect, x400pBertPattern, 
        x400pBertOperationalState, x400pBertProceduralStatus, 
        x400pBertBitCount, x400pBertErrorCount }
    STATUS      current
    DESCRIPTION
        "A collection of objects implementing the bit error rate 
         testing group."
    ::= { x400pGroups 9 }

x400pScalarGroup OBJECT-GROUP
    OBJECTS     { x400pDiscontinuityTime }
    STATUS      current
    DESCRIPTION
        "A collection of scalars."
    ::= { x400pGroups 10 }

x400pNearEndCurrentGroup OBJECT-GROUP
    OBJECTS     {
        x400pNearEndCurrentTimeElapsed, x400pNearEndCurrentESs, 
        x400pNearEndCurrentSESs, x400pNearEndCurrentSEFSs, 
        x400pNearEndCurrentUASs, x400pNearEndCurrentCSSs, 
        x400pNearEndCurrentPCVs, x400pNearEndCurrentLESs, 
        x400pNearEndCurrentBESs, x400pNearEndCurrentDMs, 
        x400pNearEndCurrentLCVs }
    STATUS      current
    DESCRIPTION
        "A collection of objects implementing the near end 
         current group."
    ::= { x400pGroups 11 }

x400pNearEndIntervalGroup OBJECT-GROUP
    OBJECTS     {
        x400pNearEndIntervalESs, x400pNearEndIntervalSESs, 
        x400pNearEndIntervalSEFSs, x400pNearEndIntervalUASs, 
        x400pNearEndIntervalCSSs, x400pNearEndIntervalPCVs, 
        x400pNearEndIntervalLESs, x400pNearEndIntervalBESs, 
        x400pNearEndIntervalDMs, x400pNearEndIntervalLCVs, 
        x400pNearEndIntervalValidData }
    STATUS      current
    DESCRIPTION
        "A collection of objects implementing the near end 
         interval group."
    ::= { x400pGroups 12 }

x400pNearEndTotalGroup OBJECT-GROUP
    OBJECTS     {
        x400pNearEndTotalValidIntervals, 
        x400pNearEndTotalInvalidIntervals, x400pNearEndTotalESs, 
        x400pNearEndTotalSESs, x400pNearEndTotalSEFSs, 
        x400pNearEndTotalUASs, x400pNearEndTotalCSSs, 
        x400pNearEndTotalPCVs, x400pNearEndTotalLESs, 
        x400pNearEndTotalBESs, x400pNearEndTotalDMs, 
        x400pNearEndTotalLCVs }
    STATUS      current
    DESCRIPTION
        "A collection of objects implementing the near end total 
         group."
    ::= { x400pGroups 13 }

x400pFarEndCurrentGroup OBJECT-GROUP
    OBJECTS     {
        x400pFarEndCurrentTimeElapsed, x400pFarEndCurrentESs, 
        x400pFarEndCurrentSESs, x400pFarEndCurrentSEFSs, 
        x400pFarEndCurrentUASs, x400pFarEndCurrentCSSs, 
        x400pFarEndCurrentPCVs, x400pFarEndCurrentLESs, 
        x400pFarEndCurrentBESs, x400pFarEndCurrentDMs }
    STATUS      current
    DESCRIPTION
        "A collection of objects implementing the far end 
         current group."
    ::= { x400pGroups 14 }

x400pFarEndIntervalGroup OBJECT-GROUP
    OBJECTS     {
        x400pFarEndIntervalESs, x400pFarEndIntervalSESs, 
        x400pFarEndIntervalSEFSs, x400pFarEndIntervalUASs, 
        x400pFarEndIntervalCSSs, x400pFarEndIntervalPCVs, 
        x400pFarEndIntervalLESs, x400pFarEndIntervalBESs, 
        x400pFarEndIntervalDMs, x400pFarEndIntervalValidData }
    STATUS      current
    DESCRIPTION
        "A collection of objects implementing the far end 
         interval group."
    ::= { x400pGroups 15 }

x400pFarEndTotalGroup OBJECT-GROUP
    OBJECTS     {
        x400pFarEndTotalValidIntervals, 
        x400pFarEndTotalInvalidIntervals, x400pFarEndTotalESs, 
        x400pFarEndTotalSESs, x400pFarEndTotalSEFSs, 
        x400pFarEndTotalUASs, x400pFarEndTotalCSSs, 
        x400pFarEndTotalPCVs, x400pFarEndTotalLESs, 
        x400pFarEndTotalBESs, x400pFarEndTotalDMs }
    STATUS      current
    DESCRIPTION
        "A collection of objects implementing the far end total 
         group."
    ::= { x400pGroups 16 }

x400pCompliances OBJECT IDENTIFIER
    ::= { x400pConformance 2 }

x400pBasicCompliance MODULE-COMPLIANCE
    STATUS      current
    DESCRIPTION
        "A compliance profile providing basic operation."

    MODULE      -- this module

    MANDATORY-GROUPS    {
        x400pSyncMandatoryGroup, x400pCardIdGroup, 
        x400pChipGroup, x400pCardGroup }

    GROUP       x400pPciGroup
    DESCRIPTION
        "Optional group providing PCI bus information.  Not all 
         implementations are expected to have PCI busses."

    GROUP       x400pXconGroup
    DESCRIPTION
        "Optional group providing cross-connection indication 
         and control."

    GROUP       x400pBertGroup
    DESCRIPTION
        "Optional group providing bit error rate testing."
    OBJECT      x400pBertSelect
    MIN-ACCESS  read-only
    DESCRIPTION
        "Some implementations might not permit BERT test 
         selection from a management station."
    OBJECT      x400pBertPattern
    MIN-ACCESS  read-only
    DESCRIPTION
        "Some implementations might not permit BERT test pattern 
         selection from a management station."

    GROUP       x400pNearEndCurrentGroup
    DESCRIPTION
        "Optional group providing near end current statistics."

    GROUP       x400pNearEndIntervalGroup
    DESCRIPTION
        "Optional group providing near end interval statistics."

    GROUP       x400pNearEndTotalGroup
    DESCRIPTION
        "Optional group providing near end total statistics."

    GROUP       x400pFarEndCurrentGroup
    DESCRIPTION
        "Optional group providing far end current statistics."

    GROUP       x400pFarEndIntervalGroup
    DESCRIPTION
        "Optional group providing far end interval statistics."

    GROUP       x400pFarEndTotalGroup
    DESCRIPTION
        "Optional group providing far end total statistics."

    ::= { x400pCompliances 1 }

x400pEnhancedCompliance MODULE-COMPLIANCE
    STATUS      current
    DESCRIPTION
        "A compliance profile providing enhanced operation."

    MODULE      -- this module

    MANDATORY-GROUPS    {
        x400pScalarGroup, x400pSpanGroup, x400pChanGroup, 
        x400pXconGroup, x400pNearEndCurrentGroup, 
        x400pFarEndCurrentGroup }

    GROUP       x400pBertGroup
    DESCRIPTION
        "Optional group providing bit error rate testing."

    GROUP       x400pNearEndIntervalGroup
    DESCRIPTION
        "Optional group providing near end interval statistics."

    GROUP       x400pNearEndTotalGroup
    DESCRIPTION
        "Optional group providing near end interval totals."

    GROUP       x400pFarEndIntervalGroup
    DESCRIPTION
        "Optional group providing far end interval statistics."

    GROUP       x400pFarEndTotalGroup
    DESCRIPTION
        "Optional group providing far end total statistics."

    ::= { x400pCompliances 2 }

END -- end of module OPENSS7-X400P-MIB.

-- vim: ft=mib comments=\f\:\",\b\:\-\-,\:\-\-,\f\b\:- fo+=tcqlornw tw=64 nocin nosi sts=4 sw=4 et
