-- vim: ft=mib comments=\f\:\",\b\:\-\-,\:\-\-,\f\b\:- fo+=tcqlornw tw=72 nocin nosi sts=4 sw=4
-- =============================================================================
-- 
-- @(#) $RCSfile: OPENSS7-TMN-TC.mib,v $ $Name: OpenSS7-0_9_2 $($Revision: 0.9.2.9 $) $Date: 2008-04-29 07:11:23 $
--
-- -----------------------------------------------------------------------------
--
-- Copyright (c) 2001-2008  OpenSS7 Corporation <http://www.openss7.com/>
-- Copyright (c) 1997-2000  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2008-04-29 07:11:23 $ by $Author: brian $
--
-- -----------------------------------------------------------------------------
--
-- $Log: OPENSS7-TMN-TC.mib,v $
-- Revision 0.9.2.9  2008-04-29 07:11:23  brian
-- - updating headers for release
--
-- Revision 0.9.2.7  2008/01/10 19:55:43  brian
-- - updating mibs
--
-- Revision 0.9.2.6  2008/01/01 13:59:39  brian
-- - added new mibs
--
-- Revision 0.9.2.5  2007/12/29 22:02:00  brian
-- - updates
--
-- Revision 0.9.2.4  2007/12/29 21:57:41  brian
-- - updates
--
-- Revision 0.9.2.3  2007/12/15 20:19:14  brian
-- - updates
--
-- Revision 0.9.2.2  2007/10/15 01:14:28  brian
-- - updated MIBs
--
-- Revision 0.9.2.1  2007/09/29 14:31:39  brian
-- - added new mib files
--
-- =============================================================================

OPENSS7-TMN-TC DEFINITIONS ::= BEGIN

IMPORTS
    MODULE-IDENTITY
	FROM SNMPv2-SMI
    TEXTUAL-CONVENTION, VariablePointer, RowPointer, TruthValue, 
    DisplayString, TimeStamp
	FROM SNMPv2-TC
    openss7
	FROM OPENSS7-SMI;

tmnTC MODULE-IDENTITY
    LAST-UPDATED
	"200801011353Z"
    ORGANIZATION
	"The OpenSS7 Project"
    CONTACT-INFO
	"Brian Bidulock
	 OpenSS7 Corporation
	 1469 Jefferys Crescent
	 Edmonton, Alberta T6L 6T1
	 CANADA
	 Tel: +1 780 490 1141
	 Fax: +1 780 490 1241
	 Mob: +1 780 953 0557
	 E-mail: bidulock@openss7.org"
    DESCRIPTION
	"This is a basic MIB module providing textual conventions based 
	 on the TMN (ITU-T Rec. X.721 (1992)).  One of the major purpose 
	 of providing TMN based textual conventions is to get the 
	 labelling of members or enumerated type the same and even 
	 getting the value of enumerated type and members the same.  
	 This simplifies TMN and SNMP agent design to a great degree 
	 while also to some degree lending SNMP the higher grade 
	 information available from TMN.  For the most part this  module 
	 only contains the textual conventions that correspond to X.721.  
	 Textual conventions belonging to more application area specific 
	 information, such as that of M.3100, are contained in the mibs 
	 which are more related.

	 Note that there is also an OPENSS7-TMN-SMI mib that defines 
	 object identities and general purpose notifications for use 
	 with some of these textual conventions."  
    ::= { openss7 9 3 2 }

ObjectClass ::= TEXTUAL-CONVENTION
    STATUS current
    DESCRIPTION
	"Provides a specification of a managed object class.  Under SNMP 
	 a managed object class is equivalent to an Entry object for a 
	 Table, that identifies a table in which managed objects are 
	 instantiated as conceptual rows.  Therefore, this specification 
	 is a VariablePointer textual convention but is restricted to 
	 identifying the Entry object associated with a given table."
    REFERENCE
	"ITU-T Rec. X.711 | ISO/IEC 9596-1, CMIP-1.ObjectClass"
    SYNTAX OBJECT IDENTIFIER

ObjectInstance ::= TEXTUAL-CONVENTION
    STATUS current
    DESCRIPTION
	"Provides a specification of a managed object instance.  Under 
	 SNMP a managed object instance is equivalent to an entry in a 
	 concepual table where the table represents the managed object 
	 class.  Therefore, this specification is a RowPointer textual 
	 convention identifying the conceptual row associated within a 
	 given table."
    REFERENCE
	"ITU-T Rec. X.711 | ISO/IEC 9596-1, CMIP-1.ObjectInstance"
    SYNTAX RowPointer

AlarmType ::= TEXTUAL-CONVENTION
    STATUS current
    DESCRIPTION
	"The alarm type textual convention is an object identifier that 
	 is one of the object identifiers assigned to TMN notifications 
	 of an alarm type.  The actual alarm type values from X.721 
	 (i.e. in the { joint-iso-ccitt(2) ms(9) smi(3) part2(2) 
	 notifications(10) } arc) may be used directly.  Additional 
	 defined alarm type extensions defined by other documents such 
	 as Q.751.1 may also be used.  Alternately, the corresponding 
	 notification values registered in OPENSS7-TMN-MIB can be used 
	 directly.

	 Object identifiers used with the AlarmType textual convention 
	 must be defined in an OBJECT-IDENTITY macro and their use and 
	 meaning must be described in the DESCRIPTION clause of that 
	 macro."
    REFERENCE
	"ITU-T Rec. X.711 | ISO/IEC 9596-1, CMIP-1.AlarmType"
    SYNTAX OBJECT IDENTIFIER

ProbableCause ::= TEXTUAL-CONVENTION
    STATUS current
    DESCRIPTION
	"This is either an object identifier or an integer.  When valued 
	 as an integer, the integer is coded in the first and only 
	 element of the object identifier.
	 When coded as an integer, because of the way that object 
	 identifiers are BER encoded, the value will likely be displayed 
	 as two elements.

	 This parameter defines further qualification as to the probable 
	 cause of the alarm.  Probable cause values for notifications 
	 shall be indicated in the behaviour clause of the object class 
	 definition.

	 The probable cause textual convention is an object identifier 
	 that is one of the object identifiers assigned to probable 
	 causes.  The actual probable cause values from X.721 (i.e. in 
	 the { joint-iso-ccitt(2) ms(9) smi(3) part2(2) 
	 standardsSpecificExtensions(0) arf(0) } arc) may be used 
	 directly.  Additional defined probable cause extensions defined 
	 by other documents such as Q.751.1 and Q.751.2 may also be 
	 used.
	 
	 Object identifiers used with the ProbableCause textual 
	 convention must be defined in an OBJECT-IDENTITY macro and 
	 their use and meaning must be described in the DESCRIPTION 
	 clause of that macro."
    REFERENCE
	"ITU-T Rec. X.721 (1992) | ISO/IEC 10165-2 : 1992, 
	     Attribute-ASN1Module ProbableCause.
	 ITU-T Rec. X.733 (1992) | ISO/IEC 10164-4 : 1992,
	     Section 8.1.2.1."
    SYNTAX OBJECT IDENTIFIER

SpecificProblems ::= TEXTUAL-CONVENTION
    STATUS current
    DESCRIPTION
	"This parameter, when present, identifies further refinements to 
	 the probable cause of the alarm.  This parameter qualifies the 
	 chosen probable cause and may be used by the managed object 
	 class definer to specify a set of identifiers for use in 
	 managed object classes.

	 This parameter is either a set of integers or a set of object 
	 identifiers.  However, only object identifiers shall be used 
	 within the system management context defined in ITU-T Rec.  
	 X.701 | ISO/IEC 10040.

	 This is either an object identifier or an integer.  When valued 
	 as an integer, the integer is coded in the first and only 
	 element of the object identifier.
	 When coded as an integer, because of the way that object 
	 identifiers are BER encoded, the value will likely be displayed 
	 as two elements.

	 The specific problems textual convention is an object 
	 identifier that is one of the object identifiers assigned to a 
	 specific problem.  The actual specific
	 problem values from TMN specifications may be used directly.  
	 Additional defined specific problem extensions defined by other 
	 documents such a Q.751.1 may also be used.
	 
	 Object identifiers used with the SpecificProblems textual 
	 convention must be defined in an OBJECT-IDENTITY macro and 
	 their use and meaning must be described in the DESCRIPTION 
	 clause of that macro."
    REFERENCE
	"ITU-T Rec. X.721 (1992) | ISO/IEC 10165-2 : 1992, 
	 Attribute-ASN1Module SpecificProblems.
	 ITU-T Rec. X.733 (1992) | ISO/IEC 10164-2 : 1992,
	     Section 8.1.2.2."
    SYNTAX OBJECT IDENTIFIER

PerceivedSeverity ::= TEXTUAL-CONVENTION
    STATUS current
    DESCRIPTION
	"This parameter defines six severity levels that provide an 
	 indication of how it is perceived that the capability of the 
	 managed object has been affected.  Those severity levels that 
	 represent service affecting conditions ordered from most sever 
	 to lease severe are Critical, Major, Minor and Warning.  The 
	 levels defined for use with this mandatory parameter of alarm 
	 notifications are:

	 - cleared: The Cleared severity level indicates the clearing of 
	   one or more previously reported alarms.  This alarm clears 
	   all alarms for this managed object that have the same Alarm 
	   type, Probable cause and Specific problems (if given).  
	   Multiple associated notifications may be cleared by using the 
	   Correlated notifications parameter (defined below).  ITU-T 
	   Rec.  X.733 | ISO/IEC 10164-2 does not require that the 
	   clearing of previously reported alarms be reported.  
	   Therefore, a managing system cannot assume that the absence 
	   of an alarm with the Cleared severity level means that the 
	   condition that caused the generation of previous alarms is 
	   still present. Managed object definers shall state if, and 
	   under which conditions, the Cleared severity level is used.

	 - indeterminate: The Indeterminate severity level indicates 
	   that the severity level cannot be determined.

	 - critical: The Critical severity level indicates that a 
	   service affecting condition has occurred and an immediate 
	   corrective action is required. Such a severity can be 
	   reported, for example, when a managed object becomes totally 
	   out of service and its capability must be restored.

	 - major: The Major severity level indicates that a service 
	   affecting condition has developed and an urgent corrective 
	   action is required. Such a severity can be reported, for 
	   example, when there is a severe degradation in the capability 
	   of the managed object and its full capability must be 
	   restored.

	 - minor: The Minor severity level indicates the existence of a 
	   non-service affecting fault condition and that corrective 
	   action should be taken in order to prevent a more serious 
	   (for example, service affecting) fault. Such a severity can 
	   be reported, for example, when the detected alarm condition 
	   is not currently degrading the capacity of the managed 
	   object.

	 - warning: The Warning severity level indicates the detection 
	   of a potential or impending service affecting fault, before 
	   any significant effects have been felt. Action should be 
	   taken to further diagnose (if necessary) and correct the 
	   problem to prevent it from becoming a more serious service 
	   affecting fault.

	 This is the perceived severity of an alarm defined in 
	 accordance with the definitions in the OSI SMI.  When it 
	 appears within a scalar defined for use in a notification, it 
	 represents the severity of the notification.  Under OSI SMI, 
	 the perceived severity is used to indicate both the onset of an 
	 alarm condition and the clearing of an alarm condition.
	 
	 When set to any value other than cleared(5), the notification 
	 represents the onset of the alarm corresponding to the 
	 notification with a severity level indicated by the value.  
	 Normal telecommunications warning, minor, major, critical alarm 
	 indications can be indicated.  (Note that the setting of 
	 indeterminate(0) is only applied when none of the other 
	 characterizations will suffice.)

	 When set to to cleared(5), the notification represents the 
	 clearing of the alarm condition corresponding to the 
	 notification."
    REFERENCE
	"ITU-T Rec. X.721 (1992) | ISO/IEC 10165-2 : 1992, 
	     Attribute-ASN1Module PerceivedSeverity.
	 ITU-T Rec. X.733 (1992) | ISO/IEC 10164-2 : 1992,
	     Section 8.1.2.3."
    SYNTAX INTEGER {
	indeterminate(0),
	critical(1),
	major(2),
	minor(3),
	warning(4),
	cleared(5) }

BackedUpStatus ::= TEXTUAL-CONVENTION
    STATUS current
    DESCRIPTION
	"This parameter, when present, specifies whether or not the 
	 object emitting the alarm has been backed-up, and services 
	 provided to the user have, therefore, not been disrupted. The 
	 use of this field in conjunction with the severity field 
	 provides information in an independent form to qualify the 
	 seriousness of the alarm and the ability of the system as a 
	 whole to continue to provide services. If the value of this 
	 parameter is true, it indicates that the object emitting the 
	 alarm has been backed-up; if false, the object has not been 
	 backed-up."
    REFERENCE
	"ITU-T Rec. X.721 (1992) | ISO/IEC 10165-2 : 1992, 
	     Attribute-ASN1Module BackedUpStatus.
	 ITU-T Rec. X.733 (1992) | ISO/IEC 10164-2 : 1992,
	     Section 8.1.2.4."
    SYNTAX TruthValue

BackUpObject ::= TEXTUAL-CONVENTION
    STATUS current
    DESCRIPTION
	"This parameter shall be present when the Backed-up status 
	 parameter is present and has the value true.  This parameter 
	 specifies the managed object instance that is providing back-up 
	 services for the managed object about which the notification 
	 pertains. This parameter is useful, for example, when the 
	 back-up object is from a pool of objects any of which may be 
	 dynamically allocated to replace a faulty object.

	 The Back-up object parameter is related to the Back-up object 
	 relationship attribute defined in CCITT Rec.  X.732 | ISO/IEC 
	 10164-3. The value of this parameter shall be the same as the 
	 Back-up object attribute value when the alarm is emitted."
    REFERENCE
	"ITU-T Rec. X.721 (1992) | ISO/IEC 10165-2 : 1992, 
	     Attribute-ASN1Module.ObjectInstance.
	 ITU-T Rec. X.733 (1992) | ISO/IEC 10164-2 : 1992,
	     Section 8.1.2.5."
    SYNTAX ObjectInstance

TrendIndication ::= TEXTUAL-CONVENTION
    STATUS current
    DESCRIPTION
	"This parameter, when present, specifies the current severity 
	 trend of the managed object. If present it indicates that there 
	 are one or more alarms ('outstanding alarms') which have not 
	 been cleared, and pertain to the same managed object as that to 
	 which this alarm ('current alarm') pertains. The Trend 
	 indication parameter has three possible values:
	 
	 - more severe: The Perceived severity in the current alarm is 
	   higher (more severe) than that reported in any of the 
	   outstanding alarms;

	 - no change: The Perceived severity reported in the current 
	   alarm is the same as the highest (most severe) of any of the 
	   outstanding alarms;
	   
	 - less severe: There is at least one outstanding alarm of a 
	   severity higher (more severe) than that in the current alarm.

	 For Trend indication to be meaningful, the Perceived severity 
	 parameter value of each alarm that may be emitted by the 
	 managed object must be defined consistently over all of the 
	 defined alarm types for that managed object class. Trend 
	 indication information is of particular use to managing systems 
	 which receive alarm reports from an event forwarding 
	 discriminator configured to pass alarms above a Perceived 
	 severity level. The severity trend can also be determined by a 
	 managing system that monitors the Perceived severity parameter 
	 in received alarm reports.
	 
	 The Trend indication parameter shall not be present if there 
	 are no outstanding alarms.
	 
	 The absence of the Trend indication parameter cannot be taken 
	 to indicate the existence or non-existence of outstanding 
	 alarms."
    REFERENCE
	"ITU-T Rec. X.721 (1992) | ISO/IEC 10165-2 : 1992, 
	     Attribute-ASN1Module TrendIndication.
	 ITU-T Rec. X.733 (1992) | ISO/IEC 10164-2 : 1992,
	     Section 8.1.2.6."
    SYNTAX INTEGER {
	lessSevere(0),
	noChange(1),
	moreSevere(2) }

ThresholdInfo ::= TEXTUAL-CONVENTION
    STATUS current
    DESCRIPTION
	"This parameter shall be present when the alarm is a result of 
	 crossing a threshold. It consists of four subparameters.

	 - triggered threshold: The identifier of the threshold 
	   attribute that caused the notification;

	 - threshold level: In the case of a gauge the threshold level 
	   specifies a pair of threshold values, the first being the 
	   value of the crossed threshold and the second, its 
	   corresponding hysteresis; in the case of a counter the 
	   threshold level specifies only the threshold value.

	 - observed value: The value of the gauge or counter which 
	   crossed the threshold. This may be different from the 
	   threshold value if, for example, the gauge may only take on 
	   discrete values.

	 - arm time: For a gauge threshold, the time at which the 
	   threshold was last re-armed, namely the time after the 
	   previous threshold crossing at which the hysteresis value of 
	   the threshold was exceeded thus again permitting generation 
	   of notifications when the threshold is crossed. For a counter 
	   threshold, the later of the time at which the threshold 
	   offset was last applied, or the time at which the counter was 
	   last initialized (for resettable counters)."
    REFERENCE
	"ITU-T Rec. X.721 (1992) | ISO/IEC 10165-2 : 1992, 
	     Attribute-ASN1Module ThresholdInfo.
	 ITU-T Rec. X.733 (1992) | ISO/IEC 10164-2 : 1992,
	     Section 8.1.2.7."
    SYNTAX OCTET STRING

NotificationIdentifier ::= TEXTUAL-CONVENTION
    STATUS current
    DESCRIPTION
	"This parameter, when present, provides an identifier for the 
	 notification, which may be carried in the Correlated 
	 notifications parameter (see below) of future notifications. 
	 Notification identifiers must be chosen to be unique across all 
	 notifications of a particular managed object throughout the 
	 time that correlation is significant.

	 A Notification identifier may be reused if there is no 
	 requirement that the previous notification using that 
	 Notification identifier be correlated with future 
	 notifications. Generally, Notification identifiers should be 
	 chosen to ensure uniqueness over as long a time as is feasible 
	 for the managed system."
    REFERENCE
	"ITU-T Rec. X.721 (1992) | ISO/IEC 10165-2 : 1992, 
	     Attribute-ASN1Module NotificationIdentifier.
	 ITU-T Rec. X.733 (1992) | ISO/IEC 10164-2 : 1992,
	     Section 8.1.2.8."
    SYNTAX INTEGER

CorrelatedNotifications ::= TEXTUAL-CONVENTION
    STATUS current
    DESCRIPTION
	"This parameter, when present, contains a set of Notification 
	 identifiers and, if necessary, their associated managed object 
	 instance names. This set is defined to be the set of all 
	 notifications to which this notification is considered to be 
	 correlated. The source object instance shall be present if the 
	 correlated event report is from a managed object instance other 
	 than the one in which the Correlated notifications parameter 
	 appears.

	 The algorithm by which correlation is accomplished is outside 
	 the scope of X.733.

	 CorrelatedNotifications ::= SET OF SEQUENCE {
	    correlatedNotifications SET OF NotificationIdentifier,
	    sourceObjectInst ObjectInstance OPTIONAL }
	"
    REFERENCE
	"ITU-T Rec. X.721 (1992) | ISO/IEC 10165-2 : 1992, 
	     Attribute-ASN1Module CorrelatedNotifications.
	 ITU-T Rec. X.733 (1992) | ISO/IEC 10164-2 : 1992,
	     Section 8.1.2.9."
    SYNTAX OCTET STRING

AttributeValueChangeDefinition ::= TEXTUAL-CONVENTION
    STATUS current
    DESCRIPTION
	"This parameter, when present, is used to indicate a state 
	 transition, as specified in CCITT Rec. X.731 | ISO/IEC 10164-2, 
	 associated with the alarm. In this case, if the managed object 
	 class definition includes state change notifications it shall 
	 also emit a state change notification as specified in CCITT 
	 Rec. X.731 | ISO/IEC 10164-2.
	 
	 This parameter set consists of a set of sequences of the three 
	 parameters: Attribute identifier, Old attribute value and new 
	 attribute value described below. Each individual sequence 
	 describes a single relationship attribute value change. At 
	 least one new relationship attribute value shall be present in 
	 this list."
    REFERENCE
	"ITU-T Rec. X.721 (1992) | ISO/IEC 10165-2 : 1992, 
	     Attribute-ASN1Module.AttributeValueChangeDefinition.
	 ITU-T Rec. X.732 (1992) | ISO/IEC 10164-3 : 1993, 
	     Section 8.2.2.3.
	 ITU-T Rec. X.733 (1992) | ISO/IEC 10164-2 : 1992, 
	     Section 8.1.2.10."
    SYNTAX OCTET STRING

MonitoredAttributes ::= TEXTUAL-CONVENTION
    STATUS current
    DESCRIPTION
	"The Monitored attributes parameter, when present, defines one 
	 or more attributes of the managed object and their 
	 corresponding values at the time of the alarm. Managed object 
	 definers may specify the set of attributes which are of 
	 interest, if any. This allows, for example, the timely 
	 reporting of changing conditions prevalent at the time of the 
	 alarm."
    REFERENCE
	"ITU-T Rec. X.721 (1992) | ISO/IEC 10165-2 : 1992, 
	     Attribute-ASN1Module MonitoredAttributes.
	 ITU-T Rec. X.733 (1992) | ISO/IEC 10164-2 : 1992,
	     Section 8.1.2.11."
    SYNTAX OCTET STRING

ProposedRepairActions ::= TEXTUAL-CONVENTION
    STATUS current
    DESCRIPTION
	"This parameter, when present, is used if the cause is known and 
	 the system being managed can suggest one or more solutions 
	 (such as switch in standby equipment, retry, replace media).  
	 This parameter is a set of possibilities specified by the 
	 object class definer.

	 This parameter is either a set of integers or a set of object 
	 identifiers.  However, only object identifiers shall be used 
	 within the Systems management context defined in CCITT Rec. 
	 X.701 | ISO/IEC 10040.  Such identifiers may be registered 
	 using the registration procedures defined for ASN.1 Object 
	 Identifier values in CCITT Rec. X.208 | ISO/IEC 8824.

	 The following note applies to ITU-T applications only.  Two 
	 values with the following semantics have been assigned to this 
	 parameter in X.733 and X.721:

	 - no repair action required: This value is used to indicate 
	   that the manager is not required to initiate any repair 
	   action because it is not the manager s responsibility;

	 - repair action required: This value is used to indicate that 
	   the manager is required to initiate repair action to correct 
	   the problem reported in the alarm report.  This value also 
	   indicates that no specific repair action is proposed by the 
	   agent system.

	 This is either an object identifier or an integer.  When valued 
	 as an integer, the integer is coded in the first and only 
	 element of the object identifier."
    REFERENCE
	"ITU-T Rec. X.721 (1992) | ISO/IEC 10165-2 : 1992, 
	     Attribute-ASN1Module ProposedRepairActions.
	 ITU-T Rec. X.733 (1992) | ISO/IEC 10164-2 : 1992,
	     Section 8.1.2.12."
    SYNTAX OBJECT IDENTIFIER

AdditionalText ::= TEXTUAL-CONVENTION
    STATUS current
    DESCRIPTION
	"This parameter, when present, allows a free form text 
	 description to be reported. Understanding the semantics of this 
	 field is not required for interpretation of the notification.

	 This X.733 does not specify the format or meaning of the data 
	 contained in the Additional text parameter.  The contents are 
	 not subject to any test of OSI Management conformance.

	 This textual convention represents additional text to be added 
	 to a TMN notification in TMN style."
    REFERENCE
	"ITU-T Rec. X.721 (1992) | ISO/IEC 10165-2 : 1992, 
	     Attribute-ASN1Module AdditionalText.
	 ITU-T Rec. X.733 (1992) | ISO/IEC 10164-2 : 1992,
	     Section 8.1.2.13."
    SYNTAX DisplayString

AdditionalInformation ::= TEXTUAL-CONVENTION
    STATUS current
    DESCRIPTION
	"This parameter, when present, allows the inclusion of a set of 
	 additional information in the event report.  It is a series of 
	 data structures each of which contains three items of 
	 information: an identifier, a significance indicator, and the 
	 problem information.

	 The identifier subparameter carries a registered object 
	 identifier which defines the data type of the information 
	 subparameter.  The data type must be understood by the managing 
	 system in order for the contents of the information 
	 subparameter to be parsed.  

	 The significance subparameter is a boolean value which is set 
	 to true if the receiving system must be able to parse the 
	 contents of the information subparameter for the event report 
	 to be fully understood.  Even if the Additional information 
	 parameter is not fully understood, an event report indication 
	 shall be issued to the user.  Indication that the Additional 
	 information parameter is not fully understood is a local 
	 matter.

	 The information subparameter carries information about the 
	 event.  This information can be parsed if the identifier is 
	 understood.
	 
	 SET OF ManagementExtension.

	 This textual convention represents additional information to be 
	 added to a TMN notification in TMN style.  This could contain 
	 things like an entire communications PDU.  The additionalText 
	 should described this data."
    REFERENCE
	"ITU-T Rec. X.721 (1992) | ISO/IEC 10165-2 : 1992, 
	     Attribute-ASN1Module AdditionalInformation.
	 ITU-T Rec. X.733 (1992) | ISO/IEC 10164-2 : 1992,
	     Section 8.1.2.14."
    SYNTAX OCTET STRING

SourceIndicator ::= TEXTUAL-CONVENTION
    STATUS current
    DESCRIPTION
	"This parameter, when present, indicates the source of the 
	 operation that led to the generation of this notification type 
	 or event record.  It can have one of the following values:

	 - resource operation: The notification was generated in 
	   response to a state attribute value change effected through 
	   the internal operation of the resource.

	 - management operation: The notification was generated in 
	   response to a state attribute value change effected through 
	   an SMI management operation applied accross the managed 
	   object boundary external to the managed object.

	 - unknown: It is not possible to determine the source of the 
	   operation.

	 This parameter, when present, indicates the source of the 
	 operation that led to the generation of this notification type. 
	 It can have one of the following values.

	 - resource operation: The notification was generated in 
	   response to a relationship attribute value change effected 
	   through the internal operation of the resource;

	 - management operation: The notification was generated in 
	   response to a relationship attribute value change effected 
	   through an SMI management operation applied across the 
	   managed object boundary external to the managed object;

	 - unknown: It is not possible to determine the source of the 
	   operation.

	 This textual convention provides the source of an action that 
	 resulted in the change in state of a managed object, alteration 
	 of its attributes or addition or deletion of the object.  
	 resourceOperation(0) indicates that the managed element or 
	 agent performed the change; managementOperation(1) indicates 
	 that a management station was the source of the change; and 
	 unknown(2) indicates that the souce of the change is unknown."
    REFERENCE
	"ITU-T Rec. X.721 (1992) | ISO/IEC 10165-2 : 1992, 
	     Attribute-ASN1Module SourceIndicator.
	 ITU-T Rec. X.731 (1992) | ISO/IEC 10164-2 : 1993, 
	     Section 8.2.2.1.
	 ITU-T Rec. X.732 (1992) | ISO/IEC 10164-3 : 1993, 
	     Section 8.2.2.1."
    SYNTAX INTEGER {
	resourceOperation(0),
	managementOperation(1),
	unknown(2) }

AttributeIdentifierList ::= TEXTUAL-CONVENTION
    STATUS current
    DESCRIPTION
	"This parameter, when present, identifies the set of state 
	 attributes whose value changes are being reported.
	 
	 This parameter, when present, identifies the set of 
	 relationship attributes whose value changes are being 
	 reported."
    REFERENCE
	"ITU-T Rec. X.721 (1992) | ISO/IEC 10165-2 : 1992, 
	     Attribute-ASN1Module AttributeIdentifierList.
	 ITU-T Rec. X.731 (1992) | ISO/IEC 10164-2 : 1993,
	     Section 8.2.2.2.
	 ITU-T Rec. X.732 (1992) | ISO/IEC 10164-3 : 1993,
	     Section 8.2.2.2."
    SYNTAX VariablePointer

SecurityAlarmCause ::= TEXTUAL-CONVENTION
    STATUS current
    DESCRIPTION
	"The security alarm cause textual convention is an object 
	 identifier that is one of the object identifiers assigned to 
	 security alarm causes.  The actual security alarm cause values 
	 from X.721 object identifier arcs may be used directly.  
	 Additional defined security alarm cause extensions defined by 
	 other documents such as Q.751.1 may also be used.

	 Object identifiers used with the SecurityAlarmCause textual 
	 convention must be defined in an OBJECT-IDENTITY marco an their 
	 use and meaning must be described in the DESCRIPTION clause of 
	 that macro."
    REFERENCE
	"ITU-T Rec. X.721 (1992) | ISO/IEC 10165-2 : 1992, 
	     Attribute-ASN1Module SecurityAlarmCause"
    SYNTAX OBJECT IDENTIFIER

SecurityAlarmSeverity ::= TEXTUAL-CONVENTION
    STATUS current
    DESCRIPTION
	"This is the same as PerceivedSeverity but does not have a 
	 cleared(5) value."
    REFERENCE
	"ITU-T Rec. X.721 (1992) | ISO/IEC 10165-2 : 1992, 
	     Attribute-ASN1Module SecurityAlarmSeverity"
    SYNTAX INTEGER {
	indeterminate(0),
	critical(1),
	major(2),
	minor(3),
	warning(4) }

SecurityAlarmDetector ::= TEXTUAL-CONVENTION
    STATUS current
    DESCRIPTION
	"This is either a mechanism identified by an object identifier, 
	 or an object instance (in the same manner as a RowPointer) or 
	 an application object identifier.  All except for the 
	 RowPointer should be defined previously in an OBJECT-IDENTITY 
	 marco with a full description of the detector.

	 SecurityAlarmDetector ::= CHOICE {
	    mechanism [0] OBJECT IDENTIFIER,
	    object [1] ObjectInstance,
	    application [2] AE-title }
	"
    REFERENCE
	"ITU-T Rec. X.721 (1992) | ISO/IEC 10165-2 : 1992, 
	     Attribute-ASN1Module SecurityAlarmDetector"
    SYNTAX OBJECT IDENTIFIER

ServiceUser ::= TEXTUAL-CONVENTION
    STATUS current
    DESCRIPTION
	"Identification of the service user.  In TMN this is an any 
	 defined by type.  Here it is an octet string.

	 ServiceUser ::= SEQUENCE {
	    identifier OBJECT IDENTIFIER,
	    details ANY DEFINED BY identifier }
	 "
    REFERENCE
	"ITU-T Rec. X.721 (1992) | ISO/IEC 10165-2 : 1992, 
	     Attribute-ASN1Module ServiceUser"
    SYNTAX OCTET STRING

ServiceProvider ::= TEXTUAL-CONVENTION
    STATUS current
    DESCRIPTION
	"Identification of the service provider.  In TMN this is an any 
	 defined by type.  Here it is an octet string.

	 ServiceUser ::= SEQUENCE {
	    identifier OBJECT IDENTIFIER,
	    details ANY DEFINED BY identifier }
	 ServiceProvider ::= ServiceUser
	 "
    REFERENCE
	"ITU-T Rec. X.721 (1992) | ISO/IEC 10165-2 : 1992, 
	     Attribute-ASN1Module ServiceProvider"
    SYNTAX OCTET STRING

AttributeList ::= TEXTUAL-CONVENTION
    STATUS current
    DESCRIPTION
	"Should be SET OF VariablePointer."
    REFERENCE
	"ITU-T Rec. X.721 (1992) | ISO/IEC 10165-2 : 1992, 
	     Attribute-ASN1Module AttributeList"
    SYNTAX VariablePointer

InformationType ::= TEXTUAL-CONVENTION
    STATUS current
    DESCRIPTION
	"The information type textual convention is an object identifier 
	 that is one of the object identifiers assigned to an 
	 information type.  The actual information type values from TMN 
	 specifications may be used directly.  Additional defined 
	 information type extensions defined by other documents such as 
	 X.283 may also be used.
	 
	 Object identifiers used with the InformationType textual 
	 convention must be defined in an OBJECT-IDENTITY macro and 
	 their use and meaning must be described in the DESCRIPTION 
	 clause of that macro."
    REFERENCE
	"ITU-T Rec. X.723 (1993) | ISO/IEC 10165-5 : 1993, ASN.1 
	    GMI-AttributeModule.InformationType."
    SYNTAX OBJECT IDENTIFIER

InformationData ::= TEXTUAL-CONVENTION
    STATUS current
    DESCRIPTION
	"This textual convention represents additional information to be 
	 added to a TMN notification in TMN style.  This could contain 
	 things like an entire communications PDU.  The information 
	 should be self-defining."
    REFERENCE
	"ITU-T Rec. X.723 (1993) | ISO/IEC 10165-5 : 1993, ASN.1 
	    GMI-AttributeModule.InformationData."
    SYNTAX OCTET STRING

-- more textual conventions

EventTime ::= TEXTUAL-CONVENTION
    STATUS current
    DESCRIPTION
	"Provides a specification of an event time."
    REFERENCE
	"ITU-T Rec. X.721 (1992) | ISO/IEC 10165-2 : 1992, 
	     Attribute-ASN1Module AttributeList"
    SYNTAX TimeStamp

EventTypeId ::= TEXTUAL-CONVENTION
    STATUS current
    DESCRIPTION
	"Provides a specification of an event type for notifications.

	 This is either an object identifier or an integer.  When valued 
	 as an integer, the integer is coded in the first and only 
	 element of the object identifier.
	 When coded as an integer, because of the way that object 
	 identifiers are BER encoded, the value will likely be displayed 
	 as two elements."
    REFERENCE
	"ITU-T Rec. X.711 | ISO/IEC 9596-1, CMIP-1.EventTypeId"
    SYNTAX OBJECT IDENTIFIER

DiscriminatorContstruct ::= TEXTUAL-CONVENTION
    STATUS current
    DESCRIPTION
	"Provides specificationo of a discriminator construct."
    REFERENCE
	"ITU-T Rec. X.721 (1992) | ISO/IEC 10165-2 : 1992, 
	     Attribute-ASN1Module.DiscriminatorConstruct"
    SYNTAX DisplayString

Destination ::= TEXTUAL-CONVENTION
    STATUS current
    DESCRIPTION
	"Provides specificatino of an event destination.  This is the 
	 SnmpAdminString with the same value as an snmpTargetAddrName 
	 from the SNMP-TARGET-MIB module."
    REFERENCE
	"ITU-T Rec. X.721 (1992) | ISO/IEC 10165-2 : 1992, 
	     Attribute-ASN1Module.DiscriminatorConstruct"
    SYNTAX DisplayString

DestinationList ::= TEXTUAL-CONVENTION
    STATUS current
    DESCRIPTION
	"Provides specificatino of an event destination list.  This is a 
	 list of space separated SnmpAdminString's with the same value 
	 as the snmpTargetAddrName's from the SNMP-TARGET-MIB module."
    REFERENCE
	"ITU-T Rec. X.721 (1992) | ISO/IEC 10165-2 : 1992, 
	     Attribute-ASN1Module.DiscriminatorConstruct"
    SYNTAX DisplayString

Time24 ::= TEXTUAL-CONVENTION
    DISPLAY-HINT "1d:1d"
    STATUS current
    DESCRIPTION
	"This textual convention specifies an hour and minute of the day 
	 and replaces the following ASN.1 syntax:

	 Time24 ::= SEQUENCE {
	    hour INTEGER(0..23),
	    minute INTEGER(0..59) }

	 This is specified as 2 octets in an octet string where the 
	 first octet is the hour(0..23) and the second octet is the 
	 minute(0..59)."
    REFERENCE
	"ITU-T Rec. X.721 (1992) | ISO/IEC 10165-2 : 1992, 
	     Attribute-ASN1Module.Time24"
    SYNTAX OCTET STRING(SIZE(4))

IntervalsOfDay ::= TEXTUAL-CONVENTION
    DISPLAY-HINT "1d:1d-1d:1d,"
    STATUS current
    DESCRIPTION
	"This textual convention specifies intervals in the day by start 
	 hour and minute and end hour and minute and replaces the 
	 following ASN.1 syntax:

	 IntervalsOfDay ::= SET OF SEQUENCE {
	    intervalStart Time24,
	    intervalEnd Time24 }

	 It consists of an octet string that is an integral multiple of 
	 4 octets.  For each 4 octet grouping, the first two octets are 
	 coded as a Time24 textual convention representing the start 
	 time for the interval, and the last two octets are coded as a 
	 Time24 textual convention representing the end time for the 
	 interval.  Each 4-tuple of octets represents a separate 
	 interval."
    REFERENCE
	"ITU-T Rec. X.721 (1992) | ISO/IEC 10165-2 : 1992, 
	     Attribute-ASN1Module.IntervalsOfDay"
    SYNTAX OCTET STRING -- sized in multiples of 4

WeekMask ::= TEXTUAL-CONVENTION
    DISPLAY-HINT "1x(*1d:1d-1d:1d,*),"
    STATUS current
    DESCRIPTION
	"This textual convention specifies intervals in the day for days 
	 of the week and replaces the following ASN.1 syntax:

	 WeekMask ::= SET OF SEQUENCE {
	    daysOfWeek BIT STRING {
		sunday(0),
		monday(1),
		tuesday(2),
		wednesday(3),
		thursday(4),
		friday(5),
		saturday(6) }(SIZE(7)),
	    intervalsOfDay IntervalsOfDay }

	 The first octet of the octet string is a day of week indicator 
	 that can have bit values: sunday(0), monday(1), tuesday(2), 
	 wednesday(3), thursday(4), friday(5) and saturday(6), with bit 
	 position 7 unused and set to zero.  The second octet of the 
	 string is an interval count indicating the number, 'n', of time 
	 intervals (multiples of 4 octets) to follow.  The next nx4 
	 octets represent the time intervals following the 
	 IntervalsOfDay textual convention.  The pattern is repeated 
	 again beginning with the week octet."
    REFERENCE
	"ITU-T Rec. X.721 (1992) | ISO/IEC 10165-2 : 1992, 
	     Attribute-ASN1Module.WeekMask"
    SYNTAX OCTET STRING -- sized in multiples of 2 + nx4

CapacityAlarmThreshold ::= TEXTUAL-CONVENTION
    DISPLAY-HINT "1d:"
    STATUS current
    DESCRIPTION
	"This textual convention specifies the alarm thresholds as a 
	 percentage of capacity and replaces the following ASN.1 syntax:

	 CapacityAlarmThreshold ::= SET OF INTEGER(0..100)

	 Each octet in the octet string consists of one threshold.  
	 Thresholds should be ordered from lowest to highest.  Each 
	 threshold value must be in the range from 1 to 100 (%)."
    REFERENCE
	"ITU-T Rec. X.721 (1992) | ISO/IEC 10165-2 : 1992, 
	     Attribute-ASN1Module.CapacityAlarmThreshold"
    SYNTAX OCTET STRING

LogFullAction ::= TEXTUAL-CONVENTION
    STATUS current
    DESCRIPTION
	"Provides a specification of the action be taken when the 
	 maximum size of the log has been reached.  Options are:

	 - wrap: The oldest records in the log, as determined by the log 
	   record identifier, will be deleted to free resources for the 
	   creation of new records.

	 - halt: No more records will be logged.  Records already in the 
	   log will be retained.

	 Both options are supported by every log."
    REFERENCE
	"ITU-T Rec. X.721 (1992) | ISO/IEC 10165-2 : 1992, 
	     Attribute-ASN1Module.LogFullAction"
    SYNTAX INTEGER {
	wrap(0),
	halt(1) }

-- simple textual conventions

-- LoggingTime ::= ExtUTCTime
-- StartTime ::= ExtUTCTime
-- StopTime ::= ExtUTCTime - or NULL


-- naming, state and status textual conventions

SimpleNameType ::= TEXTUAL-CONVENTION
    STATUS current
    DESCRIPTION
	"The simple name type textual convention is used to specify a 
	 name for a conceptual row in a table for use as an index that 
	 is both an integer representation as well as a string 
	 representation.  When representing an integer, the convention 
	 is coded as a string that represents the displayed value of the 
	 integer.  When representing a string, the string is coded 
	 directly.  Some implementations might not be able to accept 
	 arbitrary string values for this textual convention and may 
	 require integer representations.  When representing a string, 
	 the string must not contain whitespace, control characters or 
	 commas.

	 Note that the X.721 SimpleNameType is a choice between an 
	 INTEGER and a GraphicString.  This textual convention cannot 
	 faithfully represent all values possible for the X.721 
	 SimpleNameType."
    REFERENCE
	"ITU-T Rec. X.721 (1992) | ISO/IEC 10165-2 : 1992 ASN.1 
	 ManagedObjectClassDefinitions.SimpleNameType"
    SYNTAX OCTET STRING

-- NameType ::= SimpleNameType

OperationalState ::= TEXTUAL-CONVENTION
    STATUS current
    DESCRIPTION
	"This is the operational state of an Entry in accordance with 
	 the definitions in ITU-T Recommendation X.731 (1992).  When it 
	 appears within a row of a conceptual table, it refers to the 
	 operational state of the managed object represented by the row.
	 
	 The operational state textual convention is single-valued and 
	 read-only.  It can have one of the following values:

	 - disabled: The resource is totally inoperable and unable to 
	   provide service to the user(s).

	 - enabled: The resource is partially or fully operable and 
	   available for use.

	 Precise definition of the states is specific to the managed 
	 object represented.
	 
	 When placed in a column of a conceptual table, this textual 
	 convention is given a MAX-ACCESS of read-only, permitting 
	 management stations to simply retrieve the state.  The default 
	 value associated with this entry is disabled(0).  Precise 
	 definitions of what conditions exist in each state must appear 
	 in the DESCRIPTION for the object type definition using this 
	 textual convention."
    REFERENCE
	"ITU-T Rec. X.721 (1992) | ISO/IEC 10165-2 : 1992, 
	     Attribute-ASN1Module.OperationalState.
	 ITU-T Rec. X.731 (1992) | ISO/IEC 10164-2 : 1993, 
	     Section 8.1.1.1."
    SYNTAX INTEGER {
	disabled(0),
	enabled(1) }

UsageState ::= TEXTUAL-CONVENTION
    STATUS current
    DESCRIPTION
	"This is the usage state of an Entry in accordance with the 
	 definitions in ITU-T Recommendation X.731 (1992).  When it 
	 appears within a row of a conceptual table, it refers to the 
	 usage state of the object represented by the row.
	 
	 The usage state textual convention is single-valued and 
	 read-only.  It can have one of the following values, not all of 
	 which are applicable to every class of managed object:

	 - idle: The resource is not currently in use.

	 - active: The resource is in used, and has sufficient spare 
	   operating capcity to provide for additional users 
	   simultaneously.

	 - busy: The resource is in use, but it has no spare operating 
	   capacity to provide for additional users at this instant.

	 Precise definition of the states is specific to the managed 
	 object represented.

	 When placed in a conceptual column, this textual convention is 
	 given a MAX-ACCESS of read-only, permitting management stations 
	 to simply retrieve the state.  The default value associated 
	 with this entry is idle(0).  Precise definitions of what 
	 conditions exist in each state must appear in the DESCRIPTION 
	 for the object type definition using this textual convention."
    REFERENCE
	"ITU-T Rec. X.721 (1992) | ISO/IEC 10165-2 : 1992, 
	     Attribute-ASN1Module.UsageState.
	 ITU-T Rec. X.731 (1992) | ISO/IEC 10164-2 : 1993,
	     Section 8.1.1.2."
    SYNTAX INTEGER {
	idle(0),
	active(1),
	busy(2) }

AdministrativeState ::= TEXTUAL-CONVENTION
    STATUS current
    DESCRIPTION
	"This is the adminstrative state of an Entry in accordance with 
	 the definitions in ITU-T Recommendation X.731 (1992).  When it 
	 appears within a row  of a conceptual table it refers to the 
	 administrative state of the object represented by the row.

	 The admninistrative state textual convention is single valued 
	 and read-write.  It can have one of the following values, not 
	 all of which are applicable to every class of managed object:

	 - locked: The resource is administratively prohibited from 
	   performing services for its users.

	 - unlocked: The resource is administratively permitted to 
	   perform services for its users.  This is independent of its 
	   inherent operability.

	 - shutting down: Use of the resource is administratively 
	   permitted to existing instances of use only.  While the 
	   system remains in the shutting down state, the manager may at 
	   any time cause the managed object to revert to the unlocked 
	   state.

	 Precise definition of the states is specific to the managed 
	 object represented.

	 When placed in a column of a conceptual table, this textual 
	 convention is given an MAX-ACCESS of read-write or read-create, 
	 permitting management stations the ability to set the value.
	 
	 Values that can be set are locked(0), unlocked(1) or 
	 shuttingDown(2).  The actions performed when set to locked(0), 
	 unlocked(1) or shuttingDown(2) will be described specifically 
	 in the DESCRIPTION section for the object. however, in general, 
	 setting the object to locked(0) results in immediate and 
	 disruptive withdrawal from service of the object represented by 
	 the row and all contained objects.  Setting the object to 
	 shuttingDown(2) results in the graceful withdrawal from service 
	 of the object represented by the row and all contained objects.  
	 Setting the object to unlocked(1) results in placing back into 
	 service the represented object and all contained objects that 
	 do not have an administrative state of their own, or that have 
	 an administrative state which is also unlocked(1).

	 The default value associated with this row is locked(0) and the 
	 managed object represented by the conceptual row is created in 
	 the administratively locked state.
	 
	 Precise defintions of both the conditions when the state is 
	 fetched and the conditions when the state is set must appear in 
	 the DESCRIPTION of the object type definition using this 
	 textual convention."
    REFERENCE
	"ITU-T Rec. X.721 (1992) | ISO/IEC 10165-2 : 1992, 
	     Attribute-ASN1Module.AdministrativeState.
	 ITU-T Rec. X.731 (1992) | ISO/IEC 10164-2 : 1993, 
	     Section 8.1.1.3."
    SYNTAX INTEGER {
	locked(0),
	unlocked(1),
	shuttingDown(2) }

AlarmStatus ::= TEXTUAL-CONVENTION
    STATUS current
    DESCRIPTION
	"This texutal convention represents the alarm status of an 
	 managed object in accordance with the definitions in the OSI 
	 SMI.  When it appears within a row in a conceptual table, it 
	 refers to the alarm status of the managed object represented by 
	 the row.  Rows in conceptual tables representing managed 
	 objects that may generate alarms should contain this textual 
	 convention.

	 The alarm status textual convention is set-valued and 
	 read-write.  It can have zero or more of the following values, 
	 not all of which are applicable to every class of managed 
	 object:

	 - under repair: The resource is currently being repaired.  When 
	   the under repair value is present, the operational state is 
	   either disabled or enabled.

	 - critical: One or more citical alarms indicating a fault have 
	   been detected in the resource, and have not been cleared.  
	   The operational state of the managed object can be disabled 
	   or enabled.

	 - major: One or more major alarms indicating a fault have been 
	   detected in the resource, and have not yet been cleared.  The 
	   operational state of the managed object can be disabled or 
	   enabled.

	 - minor: One or more minor alarms indicating a fault have been 
	   detected in the resource, and have not yet been cleared.  The 
	   operational state of the managed object can be disabled or 
	   enabled.

	 - alarm outstanding: One or more alarms have been detected in 
	   the resource, the condition of which may or may not be 
	   disabling.  If the operational state is enabled, additional 
	   attributes, particular to the managed object class, may 
	   indicate the nature and cause of the condition and the 
	   services that are affected.

	 The presence of the above alarm state conditions do not 
	 suppress the generation of future fault related notifications.

	 When placed in a column of a conceptual table, this textual 
	 convention is given a MAX-ACCESS of read-write or read-create, 
	 permitting management stations the ability to set the value.

	 Values that can be added to the set are underRepair(0).  Values 
	 that can be removed from the set are critical(1), major(2), 
	 minor(3), and alarmOutstanding(4).

	 The default value associated with this row is the empty set 
	 ('00000'B) and the managed object created by the conceptual row 
	 is created without alarms or repair conditions.

	 Precise defintions of which values are applicable must appear 
	 in the DESCRIPTION claus of the object type definition using 
	 this textual convention."
    REFERENCE
	"ITU-T Rec. X.721 (1992) | ISO/IEC 10165-2 : 1992, 
	     Attribute-ASN1Module.AlarmStatus.
	 ITU-T Rec. X.731 (1992) | ISO/IEC 10164-2 : 1993, 
	     Section 8.1.2.1."
    SYNTAX BITS {
	underRepair(0),
	critical(1),
	major(2),
	minor(3),
	alarmOutstanding(4) }

ProceduralStatus ::= TEXTUAL-CONVENTION
    STATUS current
    DESCRIPTION
	"This is the procedural status of an Entry in accodance with the 
	 definitions in ITU-T Recommendation X.731 (1992).  Under X.731 
	 the syntax of a ProceduralStatus is a SET OF INTEGER with these 
	 defined values, however, SNMP can't do that, so we use BITS 
	 instead.  When it appears in an entry in a conceptual table, 
	 this textual convention refers to the procedural or active 
	 status of the managed object represented by the entry.

	 The procedural status textual convention is supported only by 
	 those managed objects that represent some procedure (e.g, a 
	 test process) which progresses through a sequence of phases.  
	 Depending upon the managed object class definition, the 
	 procedure may be required to reach certain phase for the 
	 resource to be operational and available for use (i.e, for the 
	 managed object to be enabled).  Not all phases may be 
	 applicable to every class of managed object.  If the value of 
	 this textual convention is an emtpy set, the managed object is 
	 ready, for example, the initialization is complete.

	 - intialization required: The resource requires initialization 
	   to be invoked by the manager before it can perform its normal 
	   functions, and this procedure has not been initiated.  The 
	   manager may be able to invoke such initialization through an 
	   action.  The terminating condition may also be present.  The 
	   operational state is disabled.

	 - not initialized: The resource requires initialization before 
	   it can perform its normal functions, and this procedure has 
	   not been initiated.  The resource initializes itself 
	   autonomously, but the operational state may be either 
	   disabled or enabled, depending upon the managed object class 
	   definition.

	 - initializing: The resource requires initialization before it 
	   can perform its normal functions, and this procedure has been 
	   initiated but is not yet complete.  When this condition is 
	   present, the intitialization required condition is absent, 
	   since initialization has already begun.  The operational 
	   state may be disabled or enabled, depending upon the managed 
	   object class defintion.

	 - terminating: The resource is in a termination phase.  If the 
	   resource does not reinitialize itself autonomously, the 
	   initialization required condition is also present and the 
	   operational state is disabled; otherwise, the operational 
	   state may be either disabled or enabled, depending upon the 
	   managed object class definition.

	 When placed in a column of a conceptual table, this textual 
	 convention is given a MAX-ACCESS of read-only, permitting 
	 management station to ability to fetch the value.

	 The default value associated with this row is the empty set 
	 ('00000'B) and the managed object created by the conceptual row 
	 is created in the functional state.

	 Precise definition of the status is specific to the managed 
	 object represented.  Not all status members are applicable to 
	 all managed objects.  Precise definitions of which members are 
	 applicable and what conditions exist for each applicable member 
	 of the state must appear in the DESCRIPTION of the object type 
	 definition using this textual convention."
    REFERENCE
	"ITU-T Rec. X.721 (1992) | ISO/IEC 10165-2 : 1992, 
	     Attribute-ASN1Module.ProceduralStatus.
	 ITU-T Rec. X.731 (1992) | ISO/IEC 10164-2 : 1993,
	     Section 8.1.2.2."
    SYNTAX BITS {
	initializationRequired(0),
	notInitialized(1),
	initializing(2),
	reporting(3),
	terminating(4) }

AvailabilityStatus ::= TEXTUAL-CONVENTION
    STATUS current
    DESCRIPTION
	"This is the availability status of an Entry in accordance with 
	 the definitions in the OSI SMI.  When it appears within a 
	 conceptual row it refers to the availability status of the 
	 manage objected represented by the conceptual row.

	 The availability status textual convention is set-valued and 
	 read-only.  It can have zero or more of the following values, 
	 not all of which are applicable to every class of managed 
	 object.  When the value of this attribute is empty, this 
	 implies that none of the status conditions described below are 
	 present.

	 - in test: The resource is undergoing a test procedure.  If the 
	   administrative state is locked or shutting down then normal 
	   users are precluded from using the resource and the control 
	   status attribute has the value reserved for test.  Tests that 
	   do not exclude additional users can be present in any 
	   operational or administrative state but the reserved for test 
	   condition should not be present.

	 - failed: The resource has an internal fault that prevents it 
	   from operating.  The operational state is disabled.

	 - power off: The resource requires power to be applied and is 
	   not powered on.  For example, a fuse or other protection 
	   device is known to have removed power or a low voltage 
	   condition has been detected.  The operational state is 
	   disabled.

	 - offline: The resource requires a routing operation to be 
	   performed to place it online and make it available for use.  
	   The operation may be manual or automatic, or both.  The 
	   operational state is disabled.

	 - off duty: The resource has been made inactive by an internal 
	   control process in accordance with a predetermined time 
	   schedule.  Under normal conditions the control process can be 
	   expected to reactivate the resource at some scheduled time, 
	   and it is therefore considered to be optional.  The 
	   operational state is enabled or disabled.

	 - dependency: The resource cannot operate because some other 
	   resource on which it depends is (i.e, a resource not 
	   represented by the same managed object) unavailable.  For 
	   example, a device is not accessible because its controller is 
	   powered off.  The operational state is disabled.

	 - degraded: The service available from the resource is degraded 
	   in some respect, such as in speed or operating capacity.  
	   Failure of a teset or an unacceptable performance measurement 
	   has established that some or all services are not functional 
	   or are degraded due to presence of a defect.  However, the 
	   resource remains available for service, either because some 
	   services are satisfactory or because degraded service is 
	   preferable to no service at all.  Object specific attributes 
	   may be deinfed to represent further information indicating, 
	   for example, which serivces are not functional and the nature 
	   of the degradation.  The operational state is enabled.

	 - not installed: The resource represented by the managed object 
	   is not present, or is incomplete.  For example, a plug-in 
	   module is missing, a cable is disconnected or a software 
	   module is not loaded.  The operational state is disabled.

	 - log full: This indicates a log full condition the semantics 
	   of which are defined in ITU-T Rec. X.735.
	
	 When placed in a column of a conceptual table, this textual 
	 convention is given a MAX-ACCESS of read-only, permitting 
	 management stations the ability to retrieve the value only.

	 The default value associated with this row is the empty set 
	 ('000000000'B) and the managed object created by the conceptual 
	 row is created is an available state.

	 Precise definition of the states is specific to the managed 
	 object represented.  Not all states are applicable to all 
	 managed objects.  Precise definitions of which states are 
	 applicable and what conditions exist in each applicable state 
	 must appear in the DESCRIPTION of the object type definition 
	 using this textual convention."
    REFERENCE
	"ITU-T Rec. X.721 (1992) | ISO/IEC 10165-2 : 1992, 
	     Attribute-ASN1Module.AvailabilityStatus
	 ITU-T Rec. X.731 (1992) | ISO/IEC 10164-2 : 1993, 
	     Section 8.1.2.3."
    SYNTAX BITS {
	inTest(0),
	failed(1),
	powerOff(2),
	offLine(3),
	offDuty(4),
	dependency(5),
	degraded(6),
	notInstalled(7),
	logFull(8) }

ControlStatus ::= TEXTUAL-CONVENTION
    STATUS current
    DESCRIPTION
	"This textual convention represents the control status of an 
	 managed object in accordance with the definitions in ITU-T 
	 Recommendation X.731 (1992).  When it appears within a row of a 
	 coneceptual table, it refers to the control status of the 
	 managed object represented by the row.

	 The control status textual convention is read-write and 
	 set-valued.  It can have zero or more of the following values, 
	 not all of which are applicable to every class of managed 
	 object.  When the value of this textual convention is empty, 
	 this implies that none of the status conditions described below 
	 are present.

	 - subject to test: The resource is available to normal users, 
	   but tests may be conducted on it simultaneously at 
	   unpredicatble times, which may cause it to exhibit unusual 
	   characteristics to users.

	 - part of services locked: This value indicates whether a 
	   manager has administratively restricted a particular part of 
	   a service from the user(s) of a resource.  The administrative 
	   state is unlocked.  Examples are incoming service barred, 
	   outgoing service barred, write locked by media key, read 
	   locked.

	 - reserved for test: The resource has been made 
	   administratively unavailable to normal users because it is 
	   undergoing a test procedure.  The administrative state is 
	   locked.

	 - suspended: Service has been administratively suspended to the 
	   users of the resource.  The resource may retain knowledge of 
	   current users and/or requests for usage, depending upon the 
	   managed object class definition, but does not resume 
	   performing serivces until the suspended condition is revoked.  
	   The administrative state is unlocked.

	 When placed in a column of a conceptual table, this textual 
	 convention is given a MAX-ACCESS of read-write or read-create, 
	 permitting management stations the ability to set or retrieve 
	 the value.

	 The default value associated with this row is the empty set 
	 ('0000'B) and the managed object created by the conceptual row 
	 is created in a state available to users.

	 Precise definition of the status is specific to the managed 
	 object represented.  Not all status values are applicable to 
	 all managed objects.  Precise definition of which status values 
	 are applicable, and what conditions exist when each status 
	 exists must appear in the DESCRIPTION clause of the object type 
	 definition using this textual convention."
    REFERENCE
	"ITU-T Rec. X.721 (1992) | ISO/IEC 10165-2 : 1992, 
	     Attribute-ASN1Module.ControlStatus.
	 ITU-T Rec. X.731 (1992) | ISO/IEC 10164-2 : 1993, 
	     Section 8.1.2.4."
    SYNTAX BITS {
	subjectToTest(0),
	partOfServicesLocked(1),
	reservedForTest(2),
	suspended(3) }

StandbyStatus ::= TEXTUAL-CONVENTION
    STATUS current
    DESCRIPTION
	"This textual convention represents the standby status of an 
	 Entry in accordance with the defintions in ITU-T Recommendation 
	 X.731 (1992).  When it appears within a row of a conceptual 
	 table it refers to the standby status of the managed object 
	 represented by the row.

	 The standby status textual convention is single-valued and 
	 read-only.  It shall have one of the following values.  The 
	 value is only meaningful when the back-up relationship role 
	 exists.

	 - hot standby: The resource is not providing service, but is 
	   operating in synchronism with another resource that is to be 
	   backed-up (e.g, a computer shadowing another computer).  A 
	   resource with a hot standby status will be immediately able 
	   to take over the role of the resource to be backed-up, 
	   without the need for intialization activity, and will contain 
	   the same information as the resource being backed up.  The 
	   hot standby condition is mutually exclusive with the cold 
	   standby and providing service conditions.
	   The operational state is enabled.  The administrative state 
	   is unlocked.  The availability status is offline.

	 - cold standby: The resource is to back-up another resource, 
	   but is not syncrhonized with that resource.  A resource with 
	   a cold standby status will not be immediately able to take 
	   over the role of a resource to be backed up, and will require 
	   some initialization activity.  The cold standby condition is 
	   mutually exclusive with the hot standby and providing service 
	   condition.  The operational state is enabled or disabled.  
	   The administrative state is locked or unlocked.  The 
	   procedural status contains not initialized or initialization 
	   required.  The availability status is offline.

	 - providing service: The back-up resource is providing service 
	   and is backing up another resource.  The providing service 
	   condition is mutually exclusive with the hot stanbdy and cold 
	   standby conditions.  The operational state is enabled.  The 
	   administrative state is unlocked.  The availability status is 
	   online.

	 When placed in a column of a conceptual table, this textual 
	 convention is given a MAX-ACCESS of read-only, permitting 
	 management stations the ability to retrieve the value only.

	 The default value associated with this row is coldStandby(1).

	 Precise definition of the states is specific to the managed 
	 object represented.  Not all states are applicable to all 
	 managed objects.  Precise definition of which states are 
	 applicable, and what conditions exist in each applicable state 
	 must appear in the DESCRIPTION claus of the object type 
	 definition using this textual convention."
    REFERENCE
	"ITU-T Rec. X.721 (1992) | ISO/IEC 10165-2 : 1992, 
	     Attribute-ASN1Module.StandbyStatus.
	 ITU-T Rec. X.731 (1992) | ISO/IEC 10164-2 : 1993, 
	     Section 8.1.2.5."
    SYNTAX INTEGER {
	hotStandby(0),
	coldStandby(1),
	providingService(2) }

UnknownStatus ::= TEXTUAL-CONVENTION
    STATUS current
    DESCRIPTION
	"The unknown status textual convention is used to indicated that 
	 the state of the resource represented by the managed object is 
	 unknown.  When the unknown status textual convention value is 
	 true, the value of the other state textual conventions may not 
	 reflect the actual state of the resource."
    REFERENCE
	"ITU-T Rec. X.721 (1992) | ISO/IEC 10165-2 : 1992, 
	     Attribute-ASN1Module.UnknownStatus.
	 ITU-T Rec. X.731 (1992) | ISO/IEC 10164-2 : 1993, 
	     Section 8.1.2.6."
    SYNTAX INTEGER {
	false(0),
	true(1) }


END

-- =============================================================================
-- vim: ft=mib comments=\f\:\",\b\:\-\-,\:\-\-,\f\b\:-,\f\b\:· fo+=tcqlornw tw=72 nocin nosi sts=4 sw=4
