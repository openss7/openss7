-- vim: ft=mib comments=\f\:\",\b\:\-\-,\:\-\-,\f\b\:- fo+=tcqlornw tw=72 nocin nosi sts=4 sw=4
-- =============================================================================
-- 
-- @(#) $RCSfile: OPENSS7-SS7-OM-MIB.mib,v $ $Name: OpenSS7-0_9_2 $($Revision: 0.9.2.2 $) $Date: 2009-01-10 17:09:27 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-10 17:09:27 $ by $Author: brian $
--
-- -----------------------------------------------------------------------------
--
-- $Log: OPENSS7-SS7-OM-MIB.mib,v $
-- Revision 0.9.2.2  2009-01-10 17:09:27  brian
-- - updated agents
--
-- Revision 0.9.2.1  2008-12-20 12:55:44  brian
-- - add new mibs and agents
--
-- =============================================================================

OPENSS7-SS7-OM-MIB DEFINITIONS ::= BEGIN

IMPORTS
    MODULE-IDENTITY, TEXTUAL-CONVENTION, enterprises
	FROM SNMPv2-SMI
    MODULE-COMPLIANCE
	FROM SNMPv2-TC
    NetworkPointCode
	FROM OPENSS7-SS7-MIB
    openss7, openss7Q, openss7Q752
	FROM OPENSS7-SMI;

ss7OmMIB MODULE-IDENTITY
    LAST-UPDATED "200812201153Z"
    ORGANIZATION "The OpenSS7 Project"
    CONTACT-INFO
	"Brian Bidulock
	 OpenSS7 Corporation
	 1469 Jefferys Crescent
	 Edmonton, Alberta  T6L 6T1
	 CANADA
	 Tel: +1 780 490 1141
	 Fax: +1 780 490 1241
	 Mob: +1 780 953 0557
	 mailto:bidulock@openss7.org"
    DESCRIPTION
	"The purpose of this MIB is to provide SNMP support for the 
	 common operational measurements provided in ITU-T Q.752 and 
	 ANSI T1.116.  There exists a draft GDMO specification for ANSI 
	 T1.116.1 from which this MIB is based.  Strangely enough, no 
	 GDMO is standardized for SS7 operational measurements.

	 The objective of this MIB is to support both the reporting of 
	 statistics obtained from Operational Measurements as well as 
	 providing a mechanism to activate and report the results of OM 
	 studies.

	 This is one of a set of MIB modules that support SS7 
	 operational measurements.  This MIB module provides the common 
	 defintions necessary for the MIB modules for each of the 
	 protocol layers."
    REVISION "200812201153Z"
    DESCRIPTION
	"Additional workup."
    REVISION "200812141308Z"
    DESCRIPTION
	"This is the initial revision of this MIB."
    ::= { openss7Q752 0 }

 -- top level organization of the MIB

ss7OmNotifications	OBJECT IDENTIFIER ::= { ss7OmMIB	 0 }
ss7OmObjects		OBJECT IDENTIFIER ::= { ss7OmMIB	 1 }
ss7OmConformance	OBJECT IDENTIFIER ::= { ss7OmMIB	 2 }

ss7OmTables		OBJECT IDENTIFIER ::= { ss7OmObjects	 1 }
ss7OmScalars		OBJECT IDENTIFIER ::= { ss7OmObjects	 2 }
ss7OmNotifs		OBJECT IDENTIFIER ::= { ss7OmObjects	 3 }
ss7OmOids		OBJECT IDENTIFIER ::= { ss7OmObjects	 4 }

ss7OmCompliance		OBJECT IDENTIFIER ::= { ss7OmConformance 1 }
ss7OmGroups		OBJECT IDENTIFIER ::= { ss7OmConformance 2 }
ss7OmCapabilities	OBJECT IDENTIFIER ::= { ss7OmConformance 3 }

pointCode OBJECT-TYPE
    SYNTAX NetworkPointCode
    MAX-ACCESS accessible-for-notify
    STATUS current
    DESCRIPTION
	"Provides a notification paramter for use with the mtpRestarting 
	 notification."
    ::= { ss7OmNotifs 1 }

mtpRestarting NOTIFICATION-TYPE
    OBJECTS {
	pointCode
    }
    STATUS current
    DESCRIPTION
	"This notification is use to indicate that a given MTP is 
	 restarting."
    ::= { ss7OmNotifications 1 }

ss7OnOccEvent NOTIFICATION-TYPE
    OBJECTS {
	tmnObjectInstance,
	tmnProbableCause,
	-- specificProblems,
	tmnPerceivedSeverity
	-- notificationIdentifier
	-- correlatedNotifications
	-- additionalText
	-- additionalInformation
    }
    STATUS current
    DESCRIPTION
	"This notification type is used to report when an SS7 object 
	 encounter the first event within an interval for an operational 
	 measurement that is activated for first-and-interval operation.

	 This notification is used to report the T1.116.2 on-occurence 
	 measurement results and other MTP events, that are not reported 
	 as a communication alarm.

	 First-and-interval operation is when a notification is given of 
	 the first event to occur within a collection period and then 
	 the first and remaining events are counted within the interval.  
	 The first event in the next collection period with then be 
	 reported, and so on.

	 This notification type is used to generate the reports.  Note 
	 that many of these first-and-interval events also have a TMN 
	 communicationsAlarm or qualityOfService alarm defined for them, 
	 but this notification is used for generating the indication to 
	 an operational measurements subsystem of the manager instead of 
	 the maintenance subsystem."
    REFERENCE
	"ITU-T Rec. Q.752 (1993) ss7OnOccEvent NOTIFICATION.
	 ANSI T1.116.1/2000 ss7OnOccEvent NOTIFICATION."
    ::= { ss7OmNotifications 2 }

END -- OPENSS7-SS7-OM-MIB

-- vim: ft=mib comments=\f\:\",\b\:\-\-,\:\-\-,\f\b\:- fo+=tcqlornw tw=72 nocin nosi sts=4 sw=4
