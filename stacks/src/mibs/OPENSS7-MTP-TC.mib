-- vim: ft=mib comments=\f\:\",\b\:\-\-,\:\-\-,\f\b\:- fo+=tcqlornw tw=72 nocin nosi sts=4 sw=4
-- =============================================================================
-- 
-- @(#) $RCSfile: OPENSS7-MTP-TC.mib,v $ $Name: OpenSS7-0_9_2 $($Revision: 0.9.2.9 $) $Date: 2009-01-10 17:09:26 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-10 17:09:26 $ by $Author: brian $
--
-- -----------------------------------------------------------------------------
--
-- $Log: OPENSS7-MTP-TC.mib,v $
-- Revision 0.9.2.9  2009-01-10 17:09:26  brian
-- - updated agents
--
-- Revision 0.9.2.8  2008-12-20 12:55:44  brian
-- - add new mibs and agents
--
-- Revision 0.9.2.7  2008-10-11 04:34:39  brian
-- - cleanup MIBs
--
-- Revision 0.9.2.6  2008-04-29 07:11:22  brian
-- - updating headers for release
--
-- Revision 0.9.2.4  2008/01/10 19:55:42  brian
-- - updating mibs
--
-- Revision 0.9.2.3  2007/12/15 20:19:14  brian
-- - updates
--
-- Revision 0.9.2.2  2007/10/15 01:14:28  brian
-- - updated MIBs
--
-- Revision 0.9.2.1  2007/09/29 14:31:39  brian
-- - added new mib files
--
-- =============================================================================

OPENSS7-MTP-TC DEFINITIONS ::= BEGIN

IMPORTS
	MODULE-IDENTITY
		FROM SMNPv2-SMI
	TEXTUAL-CONVENTION
		FROM SNMPv2-TC
	openss7, openss7Q, openss7Q704
		FROM OPENSS7-SMI;

mtpTC MODULE-IDENTITY
	LAST-UPDATED "200812201153Z"
	ORGANIZATION "OpenSS7 Corporation"
	CONTACT-INFO
		"Brian Bidulock
		 OpenSS7 Corporation
		 1469 Jefferys Crescent
		 Edmonton, Alberta T6L 6T1
		 CANADA
		 Tel: +1 780 490 1141
		 Fax: +1 780 490 1241
		 Mob: +1 780 953 0557
		 E-mail: bidulock@openss7.org"
	DESCRIPTION
		"Textual conventions for MTP."
	REVISION "200812201153Z"
	DESCRIPTION
		"Additional workup."
	::= { openss7Q704 1 }

MtpAvailabilityStatus ::= TEXTUAL-CONVENTION
	STATUS		current
	DESCRIPTION
		"This textual convention provides the status of an MTP 
		 entity, such as a route set, route or signalling point.  
		 When inactive(0), the route set is inactive and does 
		 not carry user traffic; blocked(1), configured and able 
		 to carry traffic but blocked by transport; 
		 inhibited(2), management inhibited, but able to carry 
		 traffic; prohibited(3), prohibited by relay; 
		 restart(4), relay or endpoint restarting; 
		 restricted(5), restricted by relay; congested(6), 
		 endpoint congested; danger(7), in danger of congestion; 
		 allowed(8), allowed to to destination.

		 Where the MTP managed object whose status is 
		 represented contains other managed objects with an MTP 
		 status, the MTP status of the managed object is the 
		 set-union (logical OR) of the contained managed 
		 objects."
	REFERENCE
		"ITU-T Rec. Q.704 (1997), ANSI T1.111.4/2000, ETSI ETS 
		 300 008-1"
	SYNTAX	BITS {
			inactive(0),
			blocked(1),
			inhibited(2),
			prohibited(3),
			restart(4),
			restricted(5),
			congested(6),
			danger(7),
			allowed(8)
		}

MtpOptions ::= TEXTUAL-CONVENTION
	STATUS		current
	DESCRIPTION
		"This textual convention provides options for use with 
		 MTP and MTP users.  Not all options are applicable to 
		 all managed objects in all circumstances.  Options that 
		 are not applicable are ignored.  The DESCRIPTION clause 
		 of the OBJECT-TYPE must specify which options are 
		 applicable."
	SYNTAX	BITS {
			cluster(0),
			transferFunction(1),
			adjacent(2),
			security(3),
			linkOscillationA(4),
			linkOscillationB(5)
		}

MtpTransmissionRate ::= TEXTUAL-CONVENTION
	STATUS		current
	DESCRIPTION
		"Describes applicable transmission rate.  This can be 
		 4800, 56000, 64000, 1536000 or 1984000, which 
		 corresponds to modem, ds0a, ds0, t1 or e1."
	SYNTAX	INTEGER {
			modem(1),
			ds0a(2),
			ds0(3),
			t1(4),
			e1(5)
		}

END
-- vim: ft=mib comments=\f\:\",\b\:\-\-,\:\-\-,\f\b\:- fo+=tcqlornw tw=72 nocin nosi sts=8
