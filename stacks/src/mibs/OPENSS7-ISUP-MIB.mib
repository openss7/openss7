-- vim: ft=mib comments=\f\:\",\b\:\-\-,\:\-\-,\f\b\:- fo+=tcqlornw tw=72 nocin nosi sts=4 sw=4
-- =============================================================================
-- 
-- @(#) $RCSfile: OPENSS7-ISUP-MIB.mib,v $ $Name: OpenSS7-0_9_2 $($Revision: 0.9.2.6 $) $Date: 2009-01-10 17:09:24 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-10 17:09:24 $ by $Author: brian $
--
-- -----------------------------------------------------------------------------
--
-- $Log: OPENSS7-ISUP-MIB.mib,v $
-- Revision 0.9.2.6  2009-01-10 17:09:24  brian
-- - updated agents
--
-- Revision 0.9.2.5  2008-12-14 12:55:56  brian
-- - working up mibs
--
-- Revision 0.9.2.4  2008-10-11 04:34:39  brian
-- - cleanup MIBs
--
-- Revision 0.9.2.3  2008-04-29 07:11:21  brian
-- - updating headers for release
--
-- Revision 0.9.2.1  2007/12/15 20:16:34  brian
-- - added new mib files
--
-- =============================================================================

OPENSS7-ISUP-MIB DEFINITIONS ::= BEGIN

IMPORTS
    openss7Q751
	FROM OPENSS7-SMI
    AdministrativeState, AvailabilityStatus, OperationalState, 
    ProceduralStatus, SimpleNameType, UsageState, 
    attributeValueChangeNotificationPackage, communicationsAlarmPackage, 
    createDeleteNotificationsPackage, tmnObjectInstance, 
    tmnPerceivedSeverity, tmnProbableCause
        FROM OPENSS7-SMI-MIB
    MtpCongestionLevel, MtpLinkFailureReason, MtpUserPartStatus, 
    NetworkPointCode
        FROM OPENSS7-SS7-MIB
    MODULE-COMPLIANCE, NOTIFICATION-GROUP, OBJECT-GROUP
        FROM SNMPv2-CONF
    Gauge32, Integer32, MODULE-IDENTITY, NOTIFICATION-TYPE, 
    OBJECT-IDENTITY, OBJECT-TYPE, Unsigned32, zeroDotZero
        FROM SNMPv2-SMI
    AutonomousType, RowPointer, RowStatus, TEXTUAL-CONVENTION, 
    TimeInterval, TruthValue
        FROM SNMPv2-TC;

isupMIB MODULE-IDENTITY
    LAST-UPDATED "200810092250Z"
    ORGANIZATION 
        "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         E-mail: bidulock@openss7.org"
    DESCRIPTION 
        "This is a MIB providing management information is 
         accordance with ITU-T Rec. Q.751.1, ITU-T Rec. 
         Q.2751.1, ANSI T1.116.1."
    REVISION	"200810092250Z"
    DESCRIPTION
	"First release of this module."
    ::= { openss7Q751 3 }

isupNotifications OBJECT IDENTIFIER
    ::= { isupMIB 0 }

isupSpecificExtensions OBJECT IDENTIFIER
    ::= { isupMIB 1 }

isupDefaults OBJECT IDENTIFIER
    ::= { isupMIB 2 }

isupObjectClass OBJECT IDENTIFIER
    ::= { isupMIB 3 }

isupParameters OBJECT IDENTIFIER
    ::= { isupMIB 4 }

isupScalars OBJECT IDENTIFIER
    ::= { isupMIB 5 }

isupPackage OBJECT IDENTIFIER
    ::= { isupMIB 6 }

isupCompliances OBJECT IDENTIFIER
    ::= { isupMIB 7 }

END -- end of module OPENSS7-ISUP-MIB

-- vim: ft=mib comments=\f\:\",\b\:\-\-,\:\-\-,\f\b\:- fo+=tcqlornw tw=64 nocin nosi sts=4 sw=4 et
