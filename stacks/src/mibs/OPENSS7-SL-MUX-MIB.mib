-- vim: ft=mib comments=\f\b\:\"ITU\-T,\f\b\:ITU\-T,\f\:\",\b\:\-\-,\:\-\-,\f\b\:\- fo+=tcqlornw12 tw=64 ai nocin nosi sts=4 sw=4 et
-- =============================================================================
-- 
-- @(#) $RCSfile: OPENSS7-SL-MUX-MIB.mib,v $ $Name: OpenSS7-0_9_2 $($Revision: 0.9.2.13 $) $Date: 2009-01-21 07:41:43 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-21 07:41:43 $ by $Author: brian $
--
-- -----------------------------------------------------------------------------
--
-- $Log: OPENSS7-SL-MUX-MIB.mib,v $
-- Revision 0.9.2.13  2009-01-21 07:41:43  brian
-- - restructure
--
-- Revision 0.9.2.12  2009-01-21 07:02:39  brian
-- - fill out mib
--
-- Revision 0.9.2.11  2009-01-10 17:09:26  brian
-- - updated agents
--
-- Revision 0.9.2.10  2008-12-24 13:08:29  brian
-- - building ss7confd
--
-- Revision 0.9.2.9  2008-12-20 12:55:44  brian
-- - add new mibs and agents
--
-- Revision 0.9.2.7  2008-12-12 05:34:24  brian
-- - correction
--
-- Revision 0.9.2.6  2008-10-11 04:34:39  brian
-- - cleanup MIBs
--
-- Revision 0.9.2.5  2008-04-29 07:11:22  brian
-- - updating headers for release
--
-- Revision 0.9.2.3  2008/01/10 19:55:43  brian
-- - updating mibs
--
-- Revision 0.9.2.2  2007/12/15 20:19:14  brian
-- - updates
--
-- Revision 0.9.2.1  2007/11/06 09:47:06  brian
-- - updated mibs
--
-- =============================================================================

OPENSS7-SL-MUX-MIB DEFINITIONS ::= BEGIN

IMPORTS
    MODULE-IDENTITY, OBJECT-TYPE
        FROM SNMPv2-SMI
    RowStatus
        FROM SNMPv2-TC
    openss7, openss7Modules
        FROM OPENSS7-SMI;

slMuxMIB MODULE-IDENTITY
    LAST-UPDATED "200901210702Z"
    ORGANIZATION "The OpenSS7 Project"
    CONTACT-INFO
        "Brian Bidulock
         OpenSS7 Corporation
         1469 Jefferys Crescent
         Emonton, Alberta T6L 6T1
         CANADA
         Tel: +1 780 490 1141
         Fax: +1 780 490 1241
         Mob: +1 780 953 0557
         mailto:bidulock@openss7.org"
    DESCRIPTION
        "MIB module for the Signalling Link Multiplexer.

         The SL-MUX is a signalling link multiplexer implemented 
         as a STREAMS multiplexing driver that is used to 
         organize and manage signalling links on the OpenSS7 
         platform.  Streams are opened on device drivers to 
         obtain signalling link Streams which are then linked 
         under the multiplexing driver and assigned a global PPA 
         (Physical Point of Attachement) and a CLEI (Common 
         Language Equipment Identifier) or other administrative 
         string.  Signalling links so established can be 
         accessed by opening a Stream on the SL multiplexer.  
         The multiplexer hides device specifics from the user of 
         the SL multiplexer.  This MIB provides the ability to 
         establish these Streams and reference them from other 
         MIBs."
    REVISION    "200901210702Z"
    DESCRIPTION
        "Flattened mib."
    REVISION    "200812201153Z"
    DESCRIPTION
        "Additional workup."
    ::= { openss7Modules 40 }

GlobalPPA ::= TEXTUAL-CONVENTION
    DISPLAY-HINT "1x:"
    STATUS current
    DESCRIPTION
        "The GlobalPPA textual convention defines a Global PPA 
         (Physical Point of Attachement).  The syntax is 
         a 4 octet string.  Embedded in the octet string is the 
         encoding of a reference to a specific TDM channel on 
         the managed element."
    SYNTAX OCTET STRING (SIZE(4))

LocalPPA ::= TEXTUAL-CONVENTION
    DISPLAY-HINT "1x:"
    STATUS current
    DESCRIPTION
        "The LocalPPA textual convention defines a Local PPA 
         (Physical Point of Attachment).  The syntax is 
         a 2 octet string.  The interpretation of the bits 
         within the octets is device specific."
    SYNTAX OCTET STRING (SIZE(2))

LinkDriver ::= TEXTUAL-CONVENTION
    STATUS current
    DESCRIPTION
        "The LinkDriver textual convention defines a STREAMS 
         driver that will be used to provide the signalling 
         link."
    SYNTAX OCTET STRING


-- ====================================================================

slMuxNotifications OBJECT IDENTIFIER
    ::= { slMuxMIB 0 }

slMuxObjects OBJECT IDENTIFIER
    ::= { slMuxMIB 1 }

slMuxScalars OBJECT IDENTIFIER
    ::= { slMuxObjects 1 }

slMuxTables OBJECT IDENTIFIER
    ::= { slMuxObjects 2 }

slMuxName OBJECT IDENTIFIER
    ::= { slMuxTables 1 }

slMuxNameTable OBJECT-TYPE
    SYNTAX      SEQUENCE OF SlMuxNameEntry
    MAX-ACCESS  not-accessible
    STATUS      current
    DESCRIPTION
        ""
    REFERENCE
        ""
    ::= { slMuxName 1 }

slMuxNameEntry OBJECT-TYPE
    SYNTAX      SlMuxNameEntry
    MAX-ACCESS  not-accessible
    STATUS      current
    DESCRIPTION
        ""
    REFERENCE
        ""
    INDEX {
        slMuxNameName
    }
    ::= { slMuxNameTable 1 }

SlMuxNameEntry ::=
    SEQUENCE {
        slMuxNameName
            SnmpAdminString,
        slMuxNamePPA
            GlobalPPA,
        slMuxNameRowStatus
            RowStatus
    }

slMuxNameName OBJECT-TYPE
    SYNTAX      SnmpAdminString
    MAX-ACCESS  read-create
    STATUS      current
    DESCRIPTION
        ""
    REFERENCE
        ""
    ::= { slMuxNameEntry 1 }

slMuxNamePPA OBJECT-TYPE
    SYNTAX      GlobalPPA
    MAX-ACCESS  read-create
    STATUS      current
    DESCRIPTION
        ""
    REFERENCE
        ""
    ::= { slMuxNameEntry 2 }

slMuxNameRowStatus OBJECT-TYPE
    SYNTAX      RowStatus
    MAX-ACCESS  read-create
    STATUS      current
    DESCRIPTION
        ""
    REFERENCE
        ""
    ::= { slMuxNameEntry 3 }


slMuxLink OBJECT IDENTIFIER
    ::= { slMuxTables 2 }

slMuxLinkTable OBJECT-TYPE
    SYNTAX      SEQUENCE OF SlMuxLinkEntry
    MAX-ACCESS  not-accessible
    STATUS      current
    DESCRIPTION
        ""
    REFERENCE
        ""
    ::= { slMuxLink 1 }

slMuxLinkEntry OBJECT-TYPE
    SYNTAX      SlMuxLinkEntry
    MAX-ACCESS  not-accessible
    STATUS      current
    DESCRIPTION
        ""
    REFERENCE
        ""
    INDEX   {
        slMuxLinkPPA
    }
    ::= { slMuxLinkTable 1 }

SlMuxLinkEntry ::=
    SEQUENCE {
        slMuxLinkPPA
            GlobalPPA,
        slMuxLinkName
            SnmpAdminString,
        slMuxLinkOperationalState
            OperationalState,
        slMuxLinkUsageState
            UsageState,
        slMuxLinkAdministrativeState
            AdministrativeState,
        slMuxLinkAlarmStatus
            AlarmStatus,
        slMuxLinkProceduralStatus
            ProceduralStatus,
        slMuxLinkAvailabilityStatus
            AvailabilityStatus,
        slMuxLinkControlStatus
            ControlStatus,
        slMuxLinkUnknownStatus
            UnknownStatus,
        slMuxLinkDriver
            RowPointer,
        slMuxLinkLocalPPA
            LocalPPA,
        slMuxLinkStatus
            RowStatus
    }

slMuxLinkPPA OBJECT-TYPE
    SYNTAX      GlobalPPA
    MAX-ACCESS  not-accessible
    STATUS      current
    DESCRIPTION
        ""
    REFERENCE
        ""
    ::= { slMuxLinkEntry 1 }

slMuxLinkName OBJECT-TYPE
    SYNTAX      SnmpAdminString
    MAX-ACCESS  read-create
    STATUS      current
    DESCRIPTION
        ""
    REFERENCE
        ""
    ::= { slMuxLinkEntry 2 }

slMuxLinkOperationalState OBJECT-TYPE
    SYNTAX      OperationalState
    MAX-ACCESS  read-only
    STATUS      current
    DESCRIPTION
        ""
    REFERENCE
        ""
    ::= { slMuxLinkEntry 3 }

slMuxLinkUsageState OBJECT-TYPE
    SYNTAX      UsageState
    MAX-ACCESS  read-only
    STATUS      current
    DESCRIPTION
        ""
    REFERENCE
        ""
    ::= { slMuxLinkEntry 4 }

slMuxLinkAdministrativeState OBJECT-TYPE
    SYNTAX      AdministrativeState
    MAX-ACCESS  read-create
    STATUS      current
    DESCRIPTION
        ""
    REFERENCE
        ""
    ::= { slMuxLinkEntry 5 }

slMuxLinkAlarmStatus OBJECT-TYPE
    SYNTAX      AlarmStatus
    MAX-ACCESS  read-create
    STATUS      current
    DESCRIPTION
        ""
    REFERENCE
        ""
    ::= { slMuxLinkEntry 6 }

slMuxLinkProceduralStatus OBJECT-TYPE
    SYNTAX      ProceduralStatus
    MAX-ACCESS  read-only
    STATUS      current
    DESCRIPTION
        ""
    REFERENCE
        ""
    ::= { slMuxLinkEntry 7 }

slMuxLinkAvailabilityStatus OBJECT-TYPE
    SYNTAX      AvailabilityStatus
    MAX-ACCESS  read-only
    STATUS      current
    DESCRIPTION
        ""
    REFERENCE
        ""
    ::= { slMuxLinkEntry 8 }

slMuxLinkControlStatus OBJECT-TYPE
    SYNTAX      ControlStatus
    MAX-ACCESS  read-only
    STATUS      current
    DESCRIPTION
        ""
    REFERENCE
        ""
    ::= { slMuxLinkEntry 9 }

slMuxLinkUnknownStatus OBJECT-TYPE
    SYNTAX      UnknownStatus
    MAX-ACCESS  read-only
    STATUS      current
    DESCRIPTION
        ""
    REFERENCE
        ""
    ::= { slMuxLinkEntry 10 }

slMuxLinkDriver OBJECT-TYPE
    SYNTAX      RowPointer
    MAX-ACCESS  read-create
    STATUS      current
    DESCRIPTION
        ""
    REFERENCE
        ""
    ::= { slMuxLinkEntry 11 }

slMuxLinkLocalPPA OBJECT-TYPE
    SYNTAX      LocalPPA
    MAX-ACCESS  read-create
    STATUS      current
    DESCRIPTION
        ""
    REFERENCE
        ""
    ::= { slMuxLinkEntry 12 }

slMuxLinkStatus OBJECT-TYPE
    SYNTAX      RowStatus
    MAX-ACCESS  read-create
    STATUS      current
    DESCRIPTION
        ""
    REFERENCE
        ""
    ::= { slMuxLinkEntry 13 }

slMuxStats OBJECT IDENTIFIER
    ::= { slMuxObjects 3 }

slMuxNotifs OBJECT IDENTIFIER
    ::= { slMuxObjects 4 }

slMuxOids OBJECT IDENTIFIER
    ::= { slMuxObjects 5 }

slMuxConformance OBJECT IDENTIFIER
    ::= { slMuxMIB 2 }

slMuxGroups OBJECT IDENTIFIER
    ::= { slMuxConformance 1 }

slMuxCompliances OBJECT IDENTIFIER
    ::= { slMuxConformance 2 }

END

-- vim: ft=mib comments=\f\b\:\"ITU\-T,\f\b\:ITU\-T,\f\:\",\b\:\-\-,\:\-\-,\f\b\:\- fo+=tcqlornw12 tw=64 ai nocin nosi sts=4 sw=4 et
