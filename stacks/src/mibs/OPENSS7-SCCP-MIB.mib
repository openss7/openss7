-- vim: ft=mib comments=\f\:\",\b\:\-\-,\:\-\-,\f\b\:- fo+=tcqlornw tw=72 nocin nosi sts=4 sw=4
-- =============================================================================
-- 
-- @(#) $RCSfile: OPENSS7-SCCP-MIB.mib,v $ $Name: OpenSS7-0_9_2 $($Revision: 0.9.2.16 $) $Date: 2009-03-02 05:14:55 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-03-02 05:14:55 $ by $Author: brian $
--
-- -----------------------------------------------------------------------------
--
-- $Log: OPENSS7-SCCP-MIB.mib,v $
-- Revision 0.9.2.16  2009-03-02 05:14:55  brian
-- - updates
--
-- Revision 0.9.2.15  2009-02-21 08:16:37  brian
-- - updates
--
-- Revision 0.9.2.14  2009-02-19 12:06:03  brian
-- - correction
--
-- Revision 0.9.2.13  2009-02-19 11:44:38  brian
-- - timer corrections
--
-- Revision 0.9.2.12  2009-02-19 10:47:49  brian
-- - some cleanup of SCCP MIB
--
-- Revision 0.9.2.11  2009-01-10 17:09:26  brian
-- - updated agents
--
-- Revision 0.9.2.10  2009-01-03 10:51:09  brian
-- - updated agent
--
-- Revision 0.9.2.9  2008-12-24 13:08:28  brian
-- - building ss7confd
--
-- Revision 0.9.2.8  2008-12-20 12:55:44  brian
-- - add new mibs and agents
--
-- Revision 0.9.2.7  2008-12-14 12:55:56  brian
-- - working up mibs
--
-- Revision 0.9.2.6  2008-12-12 05:09:32  brian
-- - add compliance statement
--
-- Revision 0.9.2.5  2008-04-29 07:11:22  brian
-- - updating headers for release
--
-- Revision 0.9.2.3  2008/01/10 19:55:42  brian
-- - updating mibs
--
-- Revision 0.9.2.2  2007/12/29 21:57:41  brian
-- - updates
--
-- Revision 0.9.2.1  2007/12/15 20:16:34  brian
-- - added new mib files
--
-- =============================================================================

OPENSS7-SCCP-MIB DEFINITIONS ::= BEGIN

IMPORTS
    MODULE-IDENTITY, OBJECT-TYPE, TEXTUAL-CONVENTION, enterprises
	FROM SNMPv2-SMI
    MODULE-COMPLIANCE, RowStatus, RowPointer, AutonomousType, 
    TimeInterval, DisplayString, TruthValue
	FROM SNMPv2-TC
    CommonLanguageName
	FROM OPENSS7-TC
    AdministrativeState, OperationalState, ProceduralStatus, 
    AvailabilityStatus, AlarmStatus, SimpleNameType, UsageState
	FROM OPENSS7-SMI-MIB
    NEntitySystemTypes, NEntitySystemType
	FROM OPENSS7-CLNS-MIB
    Ss7ProtocolVariant
	FROM OPENSS7-SS7-MIB
    mtpMsId, MtpSapAddress, MtpUserPart, MtpUserPartStatus, 
    MtpCongestedState, MtpCongestionLevel
	FROM OPENSS7-MTP-MIB
    openss7, openss7Q, openss7Q751
	FROM OPENSS7-SMI;

sccpMIB MODULE-IDENTITY
    LAST-UPDATED "200812201153Z"
    ORGANIZATION "The OpenSS7 Project"
    CONTACT-INFO
	"Brian Bidulock
	 OpenSS7 Corporation
	 1469 Jefferys Crescent
	 Edmonton, Alberta  T6L 6T1
	 CANADA
	 Tel: +1 780 490 1141
	 Fax: +1 780 490 1241
	 Mob: +1 780 953 0557
	 mailto:bidulock@openss7.org"
    DESCRIPTION
	"This MIB provides configuration and status information of an 
	 SCCP subsystem, where SCCP is in accordance with ITU-T Rec.  
	 Q.711 and managed according to ITU-T Rec.  Q.751.2 or ANSI 
	 T1.116.2."
    REVISION "200812201153Z"
    DESCRIPTION
	"Additional workup."
    REVISION "200812082322Z"
    DESCRIPTION
	"This is an update to the MIB that includes changes mostly to 
	 the descriptions of the managed objects.  Added missing 
	 TruthValue import.  Type name corrections to 
	 AdminstrativeState, SystemTypes and GtNumeringPlan."
    REVISION "200711281740Z"
    DESCRIPTION
	"This is the initial revision of this MIB that was released with 
	 the strss7-0.9a.8 release package."
    ::= { openss7Q751 2 }

 -- top level organization of the MIB

sccpNotifications	OBJECT IDENTIFIER ::= { sccpMIB      0 }
sccpObjects		OBJECT IDENTIFIER ::= { sccpMIB      1 }
sccpConformance		OBJECT IDENTIFIER ::= { sccpMIB      2 }

sccpTables		OBJECT IDENTIFIER ::= { sccpObjects  1 }
sccpScalars		OBJECT IDENTIFIER ::= { sccpObjects  2 }
sccpNotifs		OBJECT IDENTIFIER ::= { sccpObjects  3 }
sccpOids		OBJECT IDENTIFIER ::= { sccpObjects  4 }

sccpCompliance		OBJECT IDENTIFIER ::= { sccpConformance  1 }
sccpGroups		OBJECT IDENTIFIER ::= { sccpConformance  2 }

sccpProtocols		OBJECT IDENTIFIER ::= { sccpOids  1 }
sccpProbableCauses	OBJECT IDENTIFIER ::= { sccpOids  2 }
sccpSpecificProblems	OBJECT IDENTIFIER ::= { sccpOids  3 }
sccpSpecificExtensions	OBJECT IDENTIFIER ::= { sccpOids  4 }
sccpLoadSharing		OBJECT IDENTIFIER ::= { sccpOids  5 }

sccpNetworkEntity	OBJECT IDENTIFIER ::= { sccpTables   1 } -- SCCP_OBJ_TYPE_SP
sccpAccessPoint		OBJECT IDENTIFIER ::= { sccpTables   2 } -- SCCP_OBJ_TYPE_SS, SCCP_OBJ_TYPE_RS
sccpLinkage		OBJECT IDENTIFIER ::= { sccpTables   3 } -- SCCP_OBJ_TYPE_MT, SCCP_OBJ_TYPE_SR
sccpMtp			OBJECT IDENTIFIER ::= { sccpTables   4 } -- SCCP_OBJ_TYPE_SR
sccpSclc		OBJECT IDENTIFIER ::= { sccpTables   5 }
sccpScoc		OBJECT IDENTIFIER ::= { sccpTables   6 }
sccpScrc		OBJECT IDENTIFIER ::= { sccpTables   7 }
sccpEntitySet		OBJECT IDENTIFIER ::= { sccpTables   8 }
sccpConcernedArea	OBJECT IDENTIFIER ::= { sccpTables   9 }
sccpGtConversionRule	OBJECT IDENTIFIER ::= { sccpTables  10 }
sccpGtTranslator	OBJECT IDENTIFIER ::= { sccpTables  11 }
sccpGtRule		OBJECT IDENTIFIER ::= { sccpTables  12 }
sccpSrvt		OBJECT IDENTIFIER ::= { sccpTables  13 }

-- (1.3.6.1.4.1.29591.1.1) openss7
-- |__(xx) sccpMIB
--    |__(0) sccpNotifications
--    |  |__(1) sccpRouteTestResult
--    |
--    |__(1) sccpObjects
--    |  |
--    |  |__(1) sccpTables
--    |  |  |__( 1) sccpNetworkEntity
--    |  |  |  |__(1) sccpNetworkEntityTable
--    |  |  |  |  |__(1) sccpNetworkEntityEntry
--    |  |  |  |      |__( 1) sccpNetworkEntityId
--    |  |  |  |      |__( 2) sccpNetworkEntityAlarmStatus
--    |  |  |  |      |__( 3) sccpNetworkEntityLocalSapNames
--    |  |  |  |      |__( 4) sccpNetworkEntityOperationalState
--    |  |  |  |      |__( 5) sccpNetworkEntityTitles
--    |  |  |  |      |__( 6) sccpNetworkEntitySystemTypes
--    |  |  |  |      |__( 7) sccpNetworkEntityVersion
--    |  |  |  |      |__( 8) sccpNetworkEntityLUDTandLUDTSSupported
--    |  |  |  |      |__( 9) sccpNetworkEntityCoordChangeTimer
--    |  |  |  |      |__(10) sccpNetworkEntityIgnoreSSTTimer
--    |  |  |  |      |__(11) sccpNetworkEntityMaxStatInfoTimer
--    |  |  |  |      |__(12) sccpNetworkEntityAsaProfilePointer
--    |  |  |  |      |__(13) sccpNetworkEntityName
--    |  |  |  |      |__(14) sccpNetworkEntityRowStatus
--    |  |  |  |
--    |  |  |  |__(2) sccpLocalSapNamesTable
--    |  |  |     |__(1) sccpLocalSapNamesEntry
--    |  |  |         |__( 1) sccpLocalSapNamesId
--    |  |  |         |__( 2) sccpLocalSapNamesPointer
--    |  |  |         |__( 3) sccpLocalSapNamesRowStatus
--    |  |  |
--    |  |  |__( 2) sccpAccessPoint
--    |  |  |  |__(1) sccpAccessPointTable
--    |  |  |     |__(1) sccpAccessPointEntry
--    |  |  |         |__( 1) sccpAccessPointSapId
--    |  |  |         |__( 2) sccpAccessPointAlarmStatus
--    |  |  |         |__( 3) sccpAccessPointSap2Address
--    |  |  |         |__( 4) sccpAccessPointUserEntityNames
--    |  |  |         |__( 5) sccpAccessPointProviderEntityNames
--    |  |  |         |__( 6) sccpAccessPointAvailabilityStatus
--    |  |  |         |__( 7) sccpAccessPointConcernedAreaPointer
--    |  |  |         |__( 8) sccpAccessPointLinkagePointer
--    |  |  |         |__( 9) sccpAccessPointSsAvailableAfterSpRestart
--    |  |  |         |__(10) sccpAccessPointAsaProfilePointer
--    |  |  |         |__(11) sccpAccessPointName
--    |  |  |         |__(12) sccpAccessPointRowStatus
--    |  |  |
--    |  |  |__( 3) sccpLinkage
--    |  |  |  |__(1) sccpLinkageTable
--    |  |  |     |__(1) sccpLinkageEntry
--    |  |  |         |__( 1) sccpLinkageId
--    |  |  |         |__( 2) sccpLinkageOperationalProtocols
--    |  |  |         |__( 3) sccpLinkageSnSAP
--    |  |  |         |__( 4) sccpLinkageAttackTimerValue
--    |  |  |         |__( 5) sccpLinkageDecayTimerValue
--    |  |  |         |__( 6) sccpLinkageNrOfRestrictionLevels
--    |  |  |         |__( 7) sccpLinkageNrOfSubLevels
--    |  |  |         |__( 8) sccpLinkageCLS
--    |  |  |         |__( 9) sccpLinkageCongestionTimerValue
--    |  |  |         |__(10) sccpLinkageP
--    |  |  |         |__(11) sccpLinkageImportanceLevelCR
--    |  |  |         |__(12) sccpLinkageImportanceLevelCC
--    |  |  |         |__(13) sccpLinkageImportanceLevelCREF
--    |  |  |         |__(14) sccpLinkageImportanceLevelDT1
--    |  |  |         |__(15) sccpLinkageImportanceLevelDT2
--    |  |  |         |__(16) sccpLinkageImportanceLevelAK
--    |  |  |         |__(17) sccpLinkageImportanceLevelIT
--    |  |  |         |__(18) sccpLinkageImportanceLevelED
--    |  |  |         |__(19) sccpLinkageImportanceLevelEA
--    |  |  |         |__(20) sccpLinkageImportanceLevelRSR
--    |  |  |         |__(21) sccpLinkageImportanceLevelRSC
--    |  |  |         |__(22) sccpLinkageImportanceLevelERR
--    |  |  |         |__(23) sccpLinkageImportanceLevelRLC
--    |  |  |         |__(24) sccpLinkageImportanceLevelRLSD
--    |  |  |         |__(25) sccpLinkageImportanceLevelUDT
--    |  |  |         |__(26) sccpLinkageImportanceLevelUDTS
--    |  |  |         |__(27) sccpLinkageImportanceLevelXUDT
--    |  |  |         |__(28) sccpLinkageImportanceLevelXUDTS
--    |  |  |         |__(29) sccpLinkageImportanceLevelLUDT
--    |  |  |         |__(30) sccpLinkageImportanceLevelLUDTS
--    |  |  |         |__(31) sccpLinkageRLM
--    |  |  |         |__(32) sccpLinkageRSLM
--    |  |  |         |__(33) sccpLinkageConcernedAreaPointer
--    |  |  |         |__(34) sccpLinkageLowerLimitForSegmentation
--    |  |  |         |__(35) sccpLinkageUpperLimitForSegmentation
--    |  |  |         |__(36) sccpLinkageName
--    |  |  |         |__(37) sccpLinkageRowStatus
--    |  |  |
--    |  |  |__( 4) sccpMtp
--    |  |  |  |__(1) sccpMtpTable
--    |  |  |     |__(1) sccpMtpEntry
--    |  |  |         |__( 1) sccpMtpSapId
--    |  |  |         |__( 2) sccpMtpSap2Address
--    |  |  |         |__( 3) sccpMtpUserPart
--    |  |  |         |__( 4) sccpMtpUserPartStatus
--    |  |  |         |__( 5) sccpMtpUserEntityNames
--    |  |  |         |__( 6) sccpMtpProviderEntityNames
--    |  |  |         |__( 7) sccpMtpUsageState
--    |  |  |         |__( 8) sccpMtpAdministrativeState
--    |  |  |         |__( 9) sccpMtpOperationalState
--    |  |  |         |__(10) sccpMtpCongestedState
--    |  |  |         |__(11) sccpMtpCongestionLevel
--    |  |  |         |__(12) sccpMtpRemoteExchangeLabel
--    |  |  |         |__(13) sccpMtpName
--    |  |  |         |__(14) sccpMtpRowStatus
--    |  |  |
--    |  |  |__( 5) sccpSclc
--    |  |  |  |__(1) sccpSclcTable
--    |  |  |     |__(1) sccpSclcEntry
--    |  |  |         |__( 1) sccpSclcAlarmStatus
--    |  |  |         |__( 2) sccpSclcClProtocolMachineId
--    |  |  |         |__( 3) sccpSclcOperationalState
--    |  |  |         |__( 4) sccpSclcTotalRemoteSAPs
--    |  |  |         |__( 5) sccpSclcAdministrativeState
--    |  |  |         |__( 6) sccpSclcSupportedProtocols
--    |  |  |         |__( 7) sccpSclcOperationalSystemType
--    |  |  |         |__( 8) sccpSclcInitialValueReassTimer
--    |  |  |         |__( 9) sccpSclcAsaProfilePointer
--    |  |  |         |__(10) sccpSclcName
--    |  |  |         |__(11) sccpSclcRowStatus
--    |  |  |
--    |  |  |__( 6) sccpScoc
--    |  |  |  |__(1) sccpScocTable
--    |  |  |     |__(1) sccpScocEntry
--    |  |  |         |__( 1) sccpScocCoProtocolMachineId
--    |  |  |         |__( 2) sccpScocOperationalState
--    |  |  |         |__( 3) sccpScocAdministrativeState
--    |  |  |         |__( 4) sccpScocOperationalSystemType
--    |  |  |         |__( 5) sccpScocSupportedProtocols
--    |  |  |         |__( 6) sccpScocName
--    |  |  |         |__( 7) sccpScocRowStatus
--    |  |  |
--    |  |  |__( 7) sccpScrc
--    |  |  |  |__(1) sccpScrcTable
--    |  |  |     |__(1) sccpScrcEntry
--    |  |  |         |__( 1) sccpScrcId
--    |  |  |         |__( 2) sccpScrcAlarmStatus
--    |  |  |         |__( 3) sccpScrcAsaProfilePointer
--    |  |  |         |__( 4) sccpScrcName
--    |  |  |         |__( 5) sccpScrcRowStatus
--    |  |  |
--    |  |  |__( 8) sccpEntitySet
--    |  |  |  |__(1) sccpEntitySetTable
--    |  |  |  |  |__(1) sccpEntitySetEntry
--    |  |  |  |      |__( 1) sccpEntitySetId
--    |  |  |  |      |__( 2) sccpEntitySetSharingMode
--    |  |  |  |      |__( 3) sccpEntitySetLoadSharingAlgPointer
--    |  |  |  |      |__( 4) sccpEntitySetName
--    |  |  |  |      |__( 5) sccpEntitySetType
--    |  |  |  |      |__( 6) sccpEntitySetSsn
--    |  |  |  |      |__( 7) sccpEntitySetRowStatus
--    |  |  |  |
--    |  |  |  |__(2) sccpEntitySetSapTable
--    |  |  |     |__(1) sccpEntitySetSapEntry
--    |  |  |         |__( 1) sccpEntitySetSapId
--    |  |  |         |__( 2) sccpEntitySetSapType
--    |  |  |         |__( 3) sccpEntitySetSapPointer
--    |  |  |         |__( 4) sccpEntitySetSapRowStatus
--    |  |  |
--    |  |  |__( 9) sccpConcernedArea
--    |  |  |  |__(1) sccpConcernedAreaTable
--    |  |  |  |  |__(1) sccpConcernedAreaEntry
--    |  |  |  |      |__( 1) sccpConcernedAreaId
--    |  |  |  |      |__( 2) sccpConcernedAreaRowStatus
--    |  |  |  |
--    |  |  |  |__(2) sccpRemoteSCCPTable
--    |  |  |     |__(1) sccpRemoteSCCPEntry
--    |  |  |         |__( 1) sccpRemoteSCCPId
--    |  |  |         |__( 2) sccpRemoteSCCPMTPAccessPoint
--    |  |  |         |__( 3) sccpRemoteSCCPName
--    |  |  |         |__( 4) sccpRemoteSCCPRowStatus
--    |  |  |
--    |  |  |__(10) sccpGtConversionRule
--    |  |  |  |__(1) sccpGtConversionRuleTable
--    |  |  |  |  |__(1) sccpGtConversionRuleEntry
--    |  |  |  |      |__( 1) sccpGtConversionRuleId
--    |  |  |  |      |__( 2) sccpGtConversionRuleNewEncodingScheme
--    |  |  |  |      |__( 3) sccpGtConversionRuleNewNatureOfAddress
--    |  |  |  |      |__( 4) sccpGtConversionRuleNewNumberingPlan
--    |  |  |  |      |__( 5) sccpGtConversionRuleNewTranslationType
--    |  |  |  |      |__( 6) sccpGtConversionRuleName
--    |  |  |  |      |__( 7) sccpGtConversionRuleRowStatus
--    |  |  |  |
--    |  |  |  |__(2) sccpAddressInfoTable
--    |  |  |     |__(1) sccpAddressInfoEntry
--    |  |  |         |__( 1) sccpAddressInfoOperationId
--    |  |  |         |__( 2) sccpAddressInfoOperation
--    |  |  |         |__( 3) sccpAddressInfoAddressElement
--    |  |  |         |__( 4) sccpAddressInfoNrOfAddressElements
--    |  |  |         |__( 5) sccpAddressInfoRowStatus
--    |  |  |
--    |  |  |__(11) sccpGtTranslator
--    |  |  |  |__(1) sccpGtTranslatorTable
--    |  |  |     |__(1) sccpGtTranslatorEntry
--    |  |  |         |__( 1) sccpGtTranslatorId
--    |  |  |         |__( 2) sccpGtTranslatorGtIndicator
--    |  |  |         |__( 3) sccpGtTranslatorNatureOfAddress
--    |  |  |         |__( 4) sccpGtTranslatorNumberingPlan
--    |  |  |         |__( 5) sccpGtTranslatorTranslationType
--    |  |  |         |__( 6) sccpGtTranslatorAdministrativeState
--    |  |  |         |__( 7) sccpGtTranslatorName
--    |  |  |         |__( 8) sccpGtTranslatorRowStatus
--    |  |  |
--    |  |  |__(12) sccpGtRule
--    |  |  |  |__(1) sccpGtRuleTable
--    |  |  |     |__(1) sccpGtRuleEntry
--    |  |  |         |__( 1) sccpGtRuleId
--    |  |  |         |__( 2) sccpGtRuleAdministrativeState
--    |  |  |         |__( 3) sccpGtRuleAddressInformation
--    |  |  |         |__( 4) sccpGtRuleGtConversionRulePointer
--    |  |  |         |__( 5) sccpGtRuleEncodingScheme
--    |  |  |         |__( 6) sccpGtRuleEntitySetPointer
--    |  |  |         |__( 7) sccpGtRuleName
--    |  |  |         |__( 8) sccpGtRuleRowStatus
--    |  |  |
--    |  |  |__(13) sccpSrvt
--    |  |     |__(1) sccpSrvtTable
--    |  |        |__(1) sccpSrvtEntry
--    |  |            |__( 1) sccpSrvtId
--    |  |            |__( 2) sccpSrvtDSRVT
--    |  |            |__( 3) sccpSrvtNSRVT
--    |  |            |__( 4) sccpSrvtName
--    |  |            |__( 5) sccpSrvtAdministrativeState
--    |  |            |__( 6) sccpSrvtOperationalState
--    |  |            |__( 7) sccpSrvtProceduralStatus
--    |  |            |__( 8) sccpSrvtTraceRequested
--    |  |            |__( 9) sccpSrvtThreshold
--    |  |            |__(10) sccpSrvtMtpBackwardRoutingRequested
--    |  |            |__(11) sccpSrvtOriginalGT
--    |  |            |__(12) sccpSrvtInfoRequest
--    |  |            |__(13) sccpSrvtReturnUnknownParams
--    |  |            |__(14) sccpSrvtRowStatus
--    |  |
--    |  |__(2) sccpScalars
--    |  |
--    |  |__(3) sccpNotifs
--    |  |  |__( 1) failureType
--    |  |  |__( 2) traceSent
--    |  |  |__( 3) pointCodeList
--    |  |  |__( 4) routePriorityList
--    |  |  |__( 5) copyData
--    |  |  |__( 6) congestionLevel
--    |  |  |__( 7) globalTitle
--    |  |
--    |  |__(4) sccpOids
--    |     |__( 1) sccpLoadSharingRouteRobin
--    |     |__( 2) sccpLoadSharingSlsSplitting
--    |
--    |__(2) sccpConformance
--       |__(1) sccpCompliance
--       |__(2) sccpGroups
--
-- (0.0.18.751.2.0.0) specificExtensions
-- |       (ProbableCause)
-- |__( 1) hopCounterViolation
-- |__( 2) localSubsystemProhibited
-- |__( 3) localSccpUnavailable
-- |__( 4) noReassemblySpace
-- |__( 5) noRuleForAddress
-- |__( 6) noSegmentationSupporth
-- |__( 7) noTranslatorForAddress
-- |__( 8) pointCodeCongested
-- |__( 9) pointCodeNotAvailable
-- |__(10) reassemblyFailure
-- |__(11) reassemblyTimeOut
-- |__(12) routingFilureNoReasonOrUnqualified
-- |__(13) sccpCongested
-- |__(14) segmentationFailure
-- |__(15) segmentOutOfOrder
-- |__(16) subsystemCongested
-- |__(17) subsystemOoSdenied
-- |__(18) subsystemOoSgranted
-- |__(19) subsystemProhibited
-- |__(20) subsystemUnavailable
-- |__(21) syntaxErrorDetected
-- |__(22) tooLargeForSegmenetation
-- |__(23) unequippedSubssytem
-- |       (OpertionalProtocols)
-- |__(24) sccpProtocolClass0
-- |__(25) sccpProtocolClass1
-- |__(26) sccpProtocolClass2
-- |__(27) sccpProtocolClass3


-- =====================================================================
--
-- TEXTUAL CONVENTIONS defined by this module
--
-- =====================================================================

FailureString ::= TEXTUAL-CONVENTION
    STATUS current
    DESCRIPTION
	"This textual convetion models a set of failure reasons for the 
	 failure of an SCCP Route Verification Test (SRVT) modelled as a 
	 BITS construct.  The reasons for failure are as follows:
	 
	 - detectedLoop(0),
	 - excessiveLengthRoute(1),
	 - unknownDestination(2),
	 - routeInaccesible(3),
	 - processingFailure(4),
	 - unknownInitiatingSP(5),
	 - timerExpired(6),
	 - wrongSP(7),
	 - incorrectTranslation-Primary(8),
	 - incorrectTranslation-Secondary(9),
	 - incorrectTranslation-Intermediate(10),
	 - notPrimaryDestination(11),
	 - notSecondaryDestination(12),
	 - notRecognizedPrimary(13),
	 - notRecognizedSecondary(14),
	 - routingProblem(15),
	 - maxNrSRVTTestsAlready(16),
	 - indirectRoute(17),
	 
	 "
    REFERENCE
	""
    SYNTAX BITS {
	    detectedLoop(0),
	    excessiveLengthRoute(1),
	    unknownDestination(2),
	    routeInaccesible(3),
	    processingFailure(4),
	    unknownInitiatingSP(5),
	    timerExpired(6),
	    wrongSP(7),
	    -- wrongSP is a synonym, used in SRVT, of 
	    -- sPNotAnSTP. --
	    incorrectTranslation-Primary(8),
	    incorrectTranslation-Secondary(9),
	    incorrectTranslation-Intermediate(10),
	    notPrimaryDestination(11),
	    notSecondaryDestination(12),
	    notRecognizedPrimary(13),
	    notRecognizedSecondary(14),
	    routingProblem(15),
	    -- bits 8 through 15 might only be sent in SRVT, 
	    -- not MRVT. --
	    maxNrSRVTTestsAlready(16),
	    -- maxNrSRVTTestsAlready is a synonym, using in 
	    -- SRVT, of maxNrMRVTTestAlready. --
	    indirectRoute(17)
	    --- indirectRoute migh only be set in MRVT, not 
	    --SRVT. --
	    }

PointCodeList ::= TEXTUAL-CONVENTION
    DISPLAY-HINT "1d:1d-1d-1d,"
    STATUS current
    DESCRIPTION
	"This is a list of network references signalling point codes 
	 which uniquely identifies both the national or international 
	 SS7 newtork (point code numbering space) to which the point 
	 code belongs as well as the point code within the network.  The 
	 list is composed of a integral multiple of 4 octets.  Of each 4 
	 octet sequence, the first octet is a network identifier which 
	 identifies the larger national or international SS7 network; 
	 the second octet is the 'network' portion of the signalling 
	 point code as defined in Q.704; the third, the 'cluster'; and, 
	 the fourth and last in each set, the 'member'.  Multiple 
	 network referenced point codes are listed in sequential groups 
	 of 4 octets, where the first 4 octets represent the first point 
	 code and the next four octets represent the next point code, 
	 and so on.  This list is display with a colon separating the 
	 network number and the normal numbers and dashes notation for 
	 the signalling point code, with grouping separated by commas: 
	 e.g. 1:5-1-1,1:5-1-2,1:5-1-3.  Note that an ITU-T signalling 
	 point code is unpacked by network, cluster and member into 
	 separate octets.  Also not that hwen the first octet of each 4 
	 octet grouping is zero (0) it does not specify a larger 
	 national or International network and thus the network point 
	 code applies only to a locally defined network."
    REFERENCE
	"ITU-T Recommendation Q.754 (1997) ASN.1 PointCodeList, see also 
	     NetworkPointCode from module OPENSS7-SS7-MIB."
    SYNTAX OCTET STRING

Priority ::= TEXTUAL-CONVENTION
    STATUS current
    DESCRIPTION
	""
    REFERENCE
	"ITU-T Recommendation Q.754 (1997) ASN.1 Priority."
    SYNTAX INTEGER {
	    unknown(0),
	    firstChoice(1),
	    secondChoice(2),
	    thirdChoice(3)
	}

RoutePriorityList ::= TEXTUAL-CONVENTION
    DISPLAY-HINT "1d,"
    STATUS current
    DESCRIPTION
	""
    REFERENCE
	"ITU-T Recommdendation Q.754 (1997) ASN.1 RoutePriorityList."
    SYNTAX OCTET STRING

GlobalTitle ::= TEXTUAL-CONVENTION
    STATUS current
    DESCRIPTION
	"Provides a specification of a global title.  The global title 
	 is represented as an octet string containing the same bit 
	 encoding as the global title that appears in an SCCP message as 
	 described in ITU-T Recommendation Q.713, with the exception 
	 that the first octet contains only the Global Title Indicator 
	 as illustrated in 3.4.1/Q.713, and the remaining octet contain 
	 only the Global Title as in 3.4.2.1 through 3.4.2.4/Q.713 as 
	 appropriate for the GTI (and not the SubSystem Number or 
	 Signalling Point Code) as illustrated in Q.713 ."
    REFERENCE
	"ITU-T Recommendation Q.713 3.4.1, and 3.4.2.1 through 3.4.2.4, 
	 ITU-T Recommendation Q.754 (1997) ASN.1 GlobalTitle."
    SYNTAX OCTET STRING

GtEncodingScheme ::= TEXTUAL-CONVENTION
    STATUS current
    DESCRIPTION
	"Provides a specification of the encoding scheme to be used in 
	 Global Titles."
    REFERENCE
	"ITU-T Rec. Q.751.2 ASN.1 GtEncodingScheme."
    SYNTAX INTEGER {
	    unknown(0),
	    bCDODD(1),
	    bCDEVEN(2),
	    nationalSpecific(3),
	    notUsedOrNoOverwite(256)
	}

GtNatureOfAddress ::= TEXTUAL-CONVENTION
    STATUS current
    DESCRIPTION
	"Provides a specification of the nature of address to be used in 
	 or matched against Global Titles."
    REFERENCE
	"ITU-T Rec. Q.751.2 ASN.1 GtNatureOfAddress."
    SYNTAX INTEGER {
	    unknown(0),
	    iSDNTNP(1),
	    genericNumberingPlan(2),
	    dNP(3),
	    tNP(4),
	    mMNP(5),
	    lMNP(6),
	    iSDNMNP(7),
	    privateNumberingPlan(14),
	    notUsedOrNoOverwite(256)
	}

GtNumberingPlan ::= TEXTUAL-CONVENTION
    STATUS current
    DESCRIPTION
	"Provides a specification of the numbering plan to be used in or 
	 matched against Global Titles."
    REFERENCE
	"ITU-T Rec. Q.751.2 ASN.1 GtNumberingPlan."
    SYNTAX INTEGER {
	    unknown(0),
	    subscriber(1),
	    national(3),
	    international(4),
	    notUsedOrNoOverwrite(256)
	}

GtTranslationType ::= TEXTUAL-CONVENTION
    STATUS current
    DESCRIPTION
	"Provides a specification of the translation type to be used in 
	 or matched against Global Titles."
    REFERENCE
	"ITU-T Q.751.2 ASN.1 GtTranslationType."
    SYNTAX INTEGER {
	    unknown(0),
	    iTCC(1),
	    genericNumberingPlan(14),
	    iEESS(17),
	    notUsedOrNoOverwrite(256)
	}

GtIndicator ::= TEXTUAL-CONVENTION
    STATUS current
    DESCRIPTION
	"Provides a specification of the Global Title Indicator to be 
	 used in or matched against Global Titles."
    REFERENCE
	"ITU-T Rec. Q.751.2 ASN.1 GtIndicator."
    SYNTAX INTEGER {
	    noGlobalTitle(0),
	    nOAonly(1),
	    tTonly(2),
	    tT-NP-ES(3),
	    tT-NP-ES-NOA(4)
	}

GtAddressInformation ::= TEXTUAL-CONVENTION
    STATUS current
    DESCRIPTION
	"Provides a specification of of the Global Title Address 
	 Information to be used in or matched against Global Titles."
    REFERENCE
	"ITU-T Rec. Q.751.2 ASN.1 GtAddressInformation, 3.4.2/Q.713."
    SYNTAX OCTET STRING

SubSystemNumber ::= TEXTUAL-CONVENTION
    DISPLAY-HINT    "1d"
    STATUS current
    DESCRIPTION
	"Provides a specification of an SCCP subsystem number (SSN) to 
	 be used in or matched against Global Titles."
    REFERENCE
	"ITU-T Rec. Q.751.2 sap2Address, 3.4/Q.713."
    SYNTAX OCTET STRING(SIZE(0..1))

SubSystemNumbers ::= TEXTUAL-CONVENTION
    DISPLAY-HINT    "1d"
    STATUS current
    DESCRIPTION
	"Provides a specification of list of SCCP subsystem numbers 
	 represented as an octet string.  Each octet in the string 
	 represents one SCCP subsystem number (SSN).  Because only the 
	 range of values from 1 to 255 are usable, the octet string can 
	 be no longer than 255."
    REFERENCE
	"ITU-T Rec. Q.751.2 sap2Addresses, 3.4/Q.713."
    SYNTAX OCTET STRING(SIZE(0..255))

ImportanceLevel ::= TEXTUAL-CONVENTION
    DISPLAY-HINT "1d-1d"
    STATUS current
    DESCRIPTION
	"Provides a set values specification of the importance level.  
	 The first octet in the two-octet string is the default 
	 importance level, the second octet in the two-octet string is 
	 the maximum importance level.  Importance levels are only 
	 allowed to range from 0 to 255.
	 
	 Not all uses of this textual convention will specify both 
	 default and maximum values.  When a value is not to be 
	 specified, the corresponding octet is coded zero by the 
	 management station and ignored by the agent on write.  When a 
	 value is not to be sepcified, the returned value from the agent 
	 will always have zero in the corresponding octet."
    REFERENCE
	"ITU-T Rec. Q.751.2 ASN.1 ImportanceLevel, 2.6.2/Q.714."
    SYNTAX OCTET STRING(SIZE(2))

OperationalProtocols ::= TEXTUAL-CONVENTION
    STATUS current
    DESCRIPTION
	"Specifies the OperationalProtocols that are supported.  When 
	 class0(0) is set, it specifies that the basic connectionless 
	 class, protocol class 0, is supported.  When class1(1) is set, 
	 it specifies that the sequenced connectionless class, protocol 
	 class 1, is supported.  When class2(2) is set, it specifies 
	 that the basic connection-oriented class, protocol class 2, is 
	 supported.  WHen class3(3) is set, it specifies that the flow 
	 control connection oriented calss, protocol class 3, iss 
	 supported.  This is a set-valued attribute."
    REFERENCE
	"ITU-T Rec. Q.751.2 ASN.1 OperationalProtols."
    SYNTAX BITS { class0(0), class1(1), class2(2), class3(3) }

SccpSyntaxErrorList ::= TEXTUAL-CONVENTION
    STATUS current
    DESCRIPTION
	"Provides a means for specifying SCCP syntax errors.  Typically 
	 used with an accessible-for-notify scalar to be used in 
	 notifications to indicate the syntax error experienced."
    REFERENCE
	"ITU-T Rec. Q.751.2 ASN.1 SccpSyntaxErrorList."
    SYNTAX INTEGER {
	    unknownMessageType(0),
	    invalidValueOfProtocolClass(1),
	    invalidValueOfGTI(2),
	    invalidValueForEncodingScheme(3),
	    invalidParameterLength(4),
	    invalidPointerToOptionalParameter(5),
	    optionalParameterTooLong(6),
	    pointerInconsistentWithLengths(7),
	    incompatibleAddressLength(8),
	    expectedSSNotFound(9)
	}

PrimaryOrBackup ::= TEXTUAL-CONVENTION
    STATUS current
    DESCRIPTION
	"Provides a means for specifying whether an entity in an entity 
	 set is an equal(0), primary(1) or backup(2) member of the 
	 entity set.  When all memebrs of the entity set are equal(0), 
	 loadsharing will occur accross members of the entity set.  When 
	 one member is primary(1) and the other members are backup(2), 
	 the traffic load will be directed at the primary(1)."
    REFERENCE   
	"ITU-T Rec. Q.751.2 ASN.1 PrimaryOrBackup."
    SYNTAX INTEGER { equal(0), primary(1), backup(2) }

SharingMode ::= TEXTUAL-CONVENTION
    STATUS current
    DESCRIPTION
	"Provides a means for specifying the sharing mode between 
	 entities in an entity set.  Solitary means that there is only 
	 one entity in the entity set.  Duplicated dominant.  Duplicated 
	 replacement.  Duplicated load shared indicates that the traffic 
	 is load shared over the two entities in the entity set."
    REFERENCE
	"ITU-T Rec. Q.751.2 ASN.1 SharingMode."
    SYNTAX INTEGER {
	    solitary(0),
	    dupliDominant(1),
	    dupliReplacement(2),
	    dupliLoadShared(3)
	}

SccpNAddress ::= TEXTUAL-CONVENTION
    DISPLAY-HINT "1d:1d-1d-1d[1d]"
    STATUS current
    DESCRIPTION
	"Provides a means for specifying the SccpNAddress in the form of 
	 an NSAP Address for use with the networkEntityTitles that are 
	 associated with an SCCP network entity to uniquely identify it.  
	 An SCCP Adress is the combination of a network references point 
	 code (NetworkPointCode textual convention from the 
	 OPENSS7-SS7-MIB module) and a SubSystemNumber.  Therefore, the 
	 first octet represents the larger national or International 
	 network, the second octet represents the value of the 'network' 
	 component of the SS7 signalling point code, the third octet, 
	 the 'cluster' component, the fourth, the 'member' component, 
	 and the fifth, the SCCP subsystem number.  This is displayed 
	 with a colon between the national or International network 
	 identifier, dashes between the components of the signalling 
	 point code, and square brackets around the subsystem number; 
	 e.g. 1:5-1-2[5]."
    REFERENCE
	"ITU-T Rec. X.283 (1992) | ISO/IEC 10733 : 1993 ASN.1 
	     NLM.NAddress."
    SYNTAX OCTET STRING(SIZE(5))

SccpNAddresses ::= TEXTUAL-CONVENTION
    DISPLAY-HINT "1d:1d-1d-1d[1d],"
    STATUS current
    DESCRIPTION
	"Provides a means for specifying a list of SCCP addresses.  Each 
	 SCCP address in the list is represented by 5 octets that appear 
	 in the form specified for the SccpNAddress.  Each successive 5 
	 octets represents another SccpNAddress.  The SccpNAddresses 
	 textual convention is, therefore, a multiple of 5 octets in 
	 length."
    REFERENCE
	"ITU-T Rec. X.283 (1992) | ISO/IEC 10733 : 1993 ASN.1 
	     NLM.NAddresses."
    SYNTAX OCTET STRING(SIZE(0|5|10|..))

-- =====================================================================
-- 
-- NOTIFICATIONS defined by this module.
-- 

sccpRouteTestResult NOTIFICATION-TYPE
    OBJECTS {
	objectInstance
	-- pointCodeList,
	-- routePriorityList,
	-- copyData
	-- or --
	-- failureType,
	-- taceSent,
	-- copyData
    }
    STATUS current
    DESCRIPTION
	"This is the sccpRouteTestResult notification.  When an SRVT 
	 (SCCP Route Verification test) is initated, and either succeeds 
	 or fails, the sccpRouteTestResult notification is issued.  This 
	 notification always contains the objectInstance, which is a 
	 RowPointer into the sccpSrvtTable table that indicates the 
	 specific SCCP Route Verification test that has succeeded or 
	 failed.
	 
	 When the notification indicates success, the notification may 
	 include a pointCodeList, routePriorityList and copyData 
	 parameters, depending upon what was requested in the test (see 
	 the sccpSrvtTraceRequested and sccpSrvtInfoRequest columns in 
	 the sccpSrvtTable); or it could indicate failure, in which case 
	 the notifcation must include failureType and traceSent 
	 parameters and might optionally include the copyData parameter 
	 depending upon the failure and the requested information."
    REFERENCE
	"ITU-T Recommendation Q.751.2 (1992) sccpRouteTestResult."
    ::= { sccpNotifications 1 }

-- =====================================================================
--
-- notification PARAMETERS defined by this module
--

failureType OBJECT-TYPE
    SYNTAX FailureString
    MAX-ACCESS accessible-for-notify
    STATUS current
    DESCRIPTION
	""
    REFERENCE
	""
    ::= { sccpNotifs 1 }

traceSent OBJECT-TYPE
    SYNTAX BOOLEAN
    MAX-ACCESS accessible-for-notify
    STATUS current
    DESCRIPTION
	""
    REFERENCE
	""
    ::= { sccpNotifs 2 }

pointCodeList OBJECT-TYPE
    SYNTAX PointCodeList
    MAX-ACCESS accessible-for-notify
    STATUS current
    DESCRIPTION
	"This is an object for use with notification and specifically 
	 the sccpRouteTestResult notification.  The parameter provides 
	 information concerning.
	 
	 This notification parameter uses the PointCodeList textual 
	 convention for representing lists of network-referenced SS7 
	 signalling point codes.  The PointCodeList textual convention 
	 is also defined in this OPENSS7-SCCP-MIB module."
    REFERENCE
	""
    ::= { sccpNotifs 3 }

routePriorityList OBJECT-TYPE
    SYNTAX RoutePriorityList
    MAX-ACCESS accessible-for-notify
    STATUS current
    DESCRIPTION
	"This notification parameter uses the RoutePriorityList textual 
	 convention for representing lists of route priorities.  The 
	 RoutePriorityList textual convention is also defined in this 
	 OPENSS7-SCCP-MIB module."
    REFERENCE
	""
    ::= { sccpNotifs 4 }

copyData OBJECT-TYPE
    SYNTAX OCTET STRING
    MAX-ACCESS accessible-for-notify
    STATUS current
    DESCRIPTION
	"This notification parameter is a rather arbitrary octet string 
	 containing requested returned information or additional failure 
	 information.  It should be displayed in hexadecimal."
    REFERENCE
	""
    ::= { sccpNotifs 5 }

congestionLevel OBJECT-TYPE
    SYNTAX INTEGER
    MAX-ACCESS accessible-for-notify
    STATUS current
    DESCRIPTION
	"Provides a varbind for notification of the congestion level 
	 parameter associated with the communicationsAlarm on an entry 
	 of the sccpAccessPointTable."
    REFERENCE
	"ITU-T Recommendation Q.751.2 congestionLevel PARAMETER."
    ::= { sccpNotifs 6 }

globalTitle OBJECT-TYPE
    SYNTAX GlobalTitle
    MAX-ACCESS accessible-for-notify
    STATUS current
    DESCRIPTION
	"Provides a varbind for notification of the global title 
	 associated with a communicationAlarm or other event or alarm 
	 notification.  The parameter uses the GlobalTitle textual 
	 convention to represent the global title."
    REFERENCE
	""
    ::= { sccpNotifs 7 }

-- =====================================================================

-- Module specific object identifiers for use with the 
-- sccpEntitySetLoadSharingAlgPointer autonomous type.

sccpLoadSharingRoundRobin OBJECT-IDENTITY
    STATUS current
    DESCRIPTION
	"This load sharing algorithm for splitting the traffic load 
	 betweeen two entities in an entity set consists of load 
	 splitting using a round-robin algorithm.  The first message 
	 sent is set to the first entity in the entity set, the second 
	 message to the second entity, the third message to the first 
	 entity, and so on.  This results in an equal load distribution 
	 between the entities in the entity set.  Note that this 
	 loadsharing is only performed for the initial message of a 
	 transaction or connection (the only one which contains route on 
	 GT), and therefore the remainder of the messages belonging to 
	 the same transaction or connection are routed to the entity 
	 based on MTP Point Code and no transaction or connection state 
	 sharing is required between entities in the entity set."
    REFERENCE
	"ITU-T Rec. Q.751.2 loadSharingAlgPointer."
    ::= { sccpLoadSharing 1 }

sccpLoadSharingSlsSplitting OBJECT-IDENTITY
    STATUS current
    DESCRIPTION
	"This load sharing algorithm for splitting the traffic load 
	 between two entities in an entity set consists of load 
	 splitting using the SLS value in the MTP header of the message.  
	 When the SLS value is even (after bit rotation for ANSI, or for 
	 the selected SLS bit for ITU-T), the traffic will be sent to 
	 the the first entity in the entity set.  When the SLS value is 
	 odd (after bit rotation for ANSI, or the selected SLS bit for 
	 ITU-T), the traffic will be sent to the second entry in the 
	 entity set this should result in an even traffic load across 
	 both entities in the entity set, even if one of an associated 
	 pair of STPs should fail.  This results in an equal load 
	 distribution between the entities in the entity set."
    REFERENCE
	"ITU-T Rec. Q.751.2 loadSharingAlgPointer."
    ::= { sccpLoadSharing 2 }

-- =====================================================================
--
-- The TMN (Q.751.2) way of providing on-occurence events from Q.752 
-- notifications is to provide a special ss7OnOccEvent notification 
-- which performs double duty as a communicationsAlarm (that is, it 
-- contains the same information as a communicationsAlarm).  That 
-- approach is duplicated here to limit the number of unique 
-- notifications necessary to represent all of the events to one, which 
-- also provides alarms.
--

-- ITU-T Rec. Q.751.2 sccpSpecificExtensions
-- sccpSpecificExtensions OBJECT IDENTIFIER
--     ::= { ccitt(0) recommendation(0) q(17) omap(751) sccp(2) informationModel(0) specificExtensions(0) }

hopCounterViolation OBJECT-IDENTITY
    STATUS current
    DESCRIPTION
	"ProbableCause.  Used as the ProbableCause with the 
	 qualityofServiceAlarm.  Parameters include the RowPointer of 
	 the sccpScrcTable entry that generated the alarm.  The 
	 Perceived severity is Major/Minor/Warning.  It corresponds to 
	 Q.752 7.13.  No automatic clearing notification is defined: 
	 alarms must be cleared by explicit management action.
	 
	 This alarm is generate when the Hop Counter is zero.  The Hop 
	 Counter is used to detect circular routings.  This counter is 
	 decremented each time a Global Title translation occurs.  The 
	 Hop Counter is only part of specific SCCP messages: XUDT, 
	 XUDTS, CR, LUDT and LDUTS."
    REFERENCE
	"ITU-T Rec. Q.751.2 (1996) : hopCounterViolation,
	 ITU-T Rec. Q.752 7.13."
    ::= { sccpSpecificExtensions 1 }

localSubsystemProhibited OBJECT-IDENTITY
    STATUS current
    DESCRIPTION
	"ProbableCause.  Used as the ProbableCause with the 
	 communicationsAlarm.  Parameters include the RowPointer of the 
	 sccpAccessPointTable that generated the alarm.  The Perceived 
	 severity is Major/Minor/Warning for Q.752 
	 8.9 and Cleared for 8.10."
    REFERENCE
	"ITU-T Rec. Q.751.2 (1996) : localSubsystemProhibited,
	 ITU-T Rec. Q.752 8.9 and 8.10."
    ::= { sccpSpecificExtensions 2 }

localSccpUnavailable OBJECT-IDENTITY
    STATUS current
    DESCRIPTION
	"ProbableCause.  Used as the ProbableCause with the 
	 communicationsAlarm.  Prameters include the RowPointer of the 
	 sccpNetworkEntityTable entry that generated the error.  Also included is 
	 SpecificProblems which can either be Failure, Maintenance or 
	 Congestion.  When the PerceivedSeverity is Major/Minor/Warning, 
	 it corresponds to measurement Q.752 8.3.  When the 
	 PerceivedSeverity is Cleared, it corresponds to measurement 
	 Q.752 8.4."
    REFERENCE
	"ITU-T Rec. Q.751.2 (1996) : localSccpUnavailable,
	 ITU-T Rec. Q.752 8.1, 8.3 and 8.4."
    ::= { sccpSpecificExtensions 3 }

noReassemblySpace OBJECT-IDENTITY
    STATUS current
    DESCRIPTION
	"ProbableCause.  Used as the ProbableCause with the 
	 qualityofServiceAlarm.  Parameters include the RowPointer of 
	 the sccpSclcTable entry that generated the alarm.
	 
	 This alarm is generate by the SCLC to indicate a resource 
	 limitation when the first segment of a sequence is received.  
	 This alarm is generated only at SCCP nodes where SCCP 
	 segmentation and reassembly is supported."
    REFERENCE
	"ITU-T Rec. Q.751.2 (1996) : noReassemblySpace,
	 ITU-T Rec. Q.752 7.12."
    ::= { sccpSpecificExtensions 4 }

noRuleForAddress OBJECT-IDENTITY
    STATUS current
    DESCRIPTION
	"ProbableCause.  Used as the ProbableCause with the 
	 qualityofServiceAlarm.  Parameters include the RowPointer of 
	 the sccpScrcTable entry that generated the alarm.  Perceived 
	 severity is Major/Minor/Warning.  This alarm corresponds to 
	 measurement Q.752 7.2.  There is no specified clearing event: 
	 the alarm conditions must be cleared by explicit management 
	 action.
	 
	 The failure occurs when the translation of the Global Title 
	 fails because the address cannot be translated although the 
	 type is known to the translation function."
    REFERENCE
	"ITU-T Rec. Q.751.2 (1996) : noRuleForAddress,
	 ITU-T Rec. Q.752 7.2."
    ::= { sccpSpecificExtensions 5 }

noSegmentationSupport OBJECT-IDENTITY
    STATUS current
    DESCRIPTION
	"ProbableCause.  Used as the ProbableCause with the 
	 qualityofServiceAlarm.  Parameters include the RowPointer of 
	 the sccpSclcTable entry that generated the alarm.
	 
	 This alarm is generated by the SCLC when a message has to be 
	 segmented but the segmentation function is not implemented.  
	 This alarm is only generated by SCCP nodes where the 
	 segmentation function is not implemented."
    REFERENCE
	"ITU-T Rec. Q.751.2 (1996) : noSegmentationSupport,
	 ITU-T Rec. Q.752 7.19."
    ::= { sccpSpecificExtensions 6 }

noTranslatorForAddress OBJECT-IDENTITY
    STATUS current
    DESCRIPTION
	"ProbableCause.  Used as the ProbableCause with the 
	 qualityofServiceAlarm.  Parameters include the RowPointer of 
	 the sccpScrcTable entry that generated the alarm.  Perceived 
	 severity is Major/Minor/Warning.  This alarm corresponds to 
	 measurement Q.752 7.1.  There is no specific clearing event: 
	 the alarm condition must be cleared by explicit management 
	 action.
	 
	 The failure occurs when the translation of the Global Title 
	 fails because the type of address is unknown to the translation 
	 function."
    REFERENCE
	"ITU-T Rec. Q.751.2 (1996) : noTranslatorForAddress,
	 ITU-T Rec. Q.752 7.1."
    ::= { sccpSpecificExtensions 7 }

pointCodeCongested OBJECT-IDENTITY
    STATUS current
    DESCRIPTION
	"ProbableCause.  Used as the ProbableCause with the 
	 qualityofServiceAlarm.  Parameters include the RowPointer of 
	 the sccpScrcTable entry that generated the alarm.  Perceived 
	 severity is Major/Minor/Warning.  This alarm corresponds to 
	 measurement Q.752 7.4.  There is no specific clearing event: 
	 the alarm condition must be cleared by explicit management 
	 action.
	 
	 The failure occurs when the translation of the Global Title 
	 fails because no available route could be found for the 
	 concerned destination address, due to congestion in MTP and/or 
	 SCCP."
    REFERENCE
	"ITU-T Rec. Q.751.2 (1996) : pointCodeCongested,
	 ITU-T Rec. Q.752 7.4."
    ::= { sccpSpecificExtensions 8 }

pointCodeNotAvailable OBJECT-IDENTITY
    STATUS current
    DESCRIPTION
	"ProbableCause.  Used as the ProbableCause with the 
	 qualityofServiceAlarm.  Parameters include the RowPointer of 
	 the sccpScrcTable entry that generated the alarm.  Perceived 
	 severity is Major/Minor/Warning.  This alarm corresponds to 
	 measurement Q.752 7.3. There is no specific clearing event: the 
	 alarm condition must be cleared by explicit management action.
	 
	 The failure occurs when the translation of the Global Title 
	 fails because no available route could be found for the 
	 concerned destination address, due to failures in MTP and/or 
	 SCCP."
    REFERENCE
	"ITU-T Rec. Q.751.2 (1996) : pointCodeNotAvailable,
	 ITU-T Rec. Q.752 7.3."
    ::= { sccpSpecificExtensions 9 }

reassemblyFailure OBJECT-IDENTITY
    STATUS current
    DESCRIPTION
	"ProbableCause.  Used as the ProbableCause with the 
	 qualityofServiceAlarm.  Parameters include the RowPointer of 
	 the sccpSclcTable entry that generated the alarm."
    REFERENCE
	"ITU-T Rec. Q.751.2 (1996) : reassemblyFailure,
	 ITU-T Rec. Q.752 7.21."
    ::= { sccpSpecificExtensions 10 }

reassemblyTimeOut OBJECT-IDENTITY
    STATUS current
    DESCRIPTION
	"ProbableCause.  Used as the ProbableCause with the 
	 qualityofServiceAlarm.  Parameters include the RowPointer of 
	 the sccpSclcTable entry that generated the alarm.
	 
	 This alarm is generated by one of the Reassembly Timers when 
	 this timer expires.  This alarm is generated only at SCCP nodes 
	 where SCCP segmentation and reassembly is supported."
    REFERENCE
	"ITU-T Rec. Q.751.2 (1996) : reassemblyTimeOut,
	 ITU-T Rec. Q.752 7.10"
    ::= { sccpSpecificExtensions 11 }

routingFailureNoReasonOrUnqualified OBJECT-IDENTITY
    STATUS current
    DESCRIPTION
	"ProbableCause.  Used as the ProbableCause with the 
	 qualityofServiceAlarm.  Parameters include the RowPointer of 
	 the sccpScrcTable entry that generated the alarm.  The 
	 perceived severity is Major/Minor/Warning.  This alarm event 
	 represents measurement Q.752 7.9.  There is no specific 
	 clearing event defined: explicit clearing by management action 
	 may be required."
    REFERENCE
	"ITU-T Rec. Q.751.2 (1996) : 
	     routingFailureNoReasonOrUnqualified, ITU-T Rec. Q.752 7.9."
    ::= { sccpSpecificExtensions 12 }

sccpCongested OBJECT-IDENTITY
    STATUS current
    DESCRIPTION
	"ProbableCause.  Use as the ProbableCause with the 
	 communicationsAlarm.  Parameters include the RowPointer of the 
	 sccpAccessPointTable entry that generated the alarm.  The 
	 congestion level is given as a parameter of the notification."
    REFERENCE
	"ITU-T Rec. Q.751.2 (1996) : sccpCongested,
	 ITU-T Rec. Q.752 8.8."
    ::= { sccpSpecificExtensions 13 }

segmentationFailure OBJECT-IDENTITY
    STATUS current
    DESCRIPTION
	"ProbableCause.  Used as the ProbableCause with the 
	 qualityofServiceAlarm.  Parameters include the RowPointer of 
	 the sccpSclcTable entry that generated the alarm.
	 
	 This alarm is generated by the SCLC to indicate that 
	 segmentation failed due to, for example, a lack of resources.  
	 This alarm is generated only on SCCP nodes that support SCCP 
	 segmentation and reassembly."
    REFERENCE
	"ITU-T Rec. Q.751.2 (1996) : segmentationFailure,
	 ITU-T Rec. Q.752 7.20."
    ::= { sccpSpecificExtensions 14 }

segmentOutOfOrder OBJECT-IDENTITY
    STATUS current
    DESCRIPTION
	"ProbableCause.  Used as the ProbableCause with the 
	 qualityofServiceAlarm.  Parameters include the RowPointer of 
	 the sccpSclcTable entry that generated the alarm.
	 
	 This alarm is generated if one of the reassembly processes 
	 receives a segment that is out of order.  This alarm is only 
	 generated at SCCP nodes where SCCP segmentation and reassebly 
	 is supported."
    REFERENCE
	"ITU-T Rec. Q.751.2 (1996) : segmentOutOfOrder,
	 ITU-T Rec. Q.752 7.11."
    ::= { sccpSpecificExtensions 15 }

subsystemCongested OBJECT-IDENTITY
    STATUS current
    DESCRIPTION
	"ProbableCause.  Used as the ProbableCause with the 
	 qualityofServiceAlarm.  Parameters include the sccpScrcTable 
	 entry the generated the alarm.  Perceived severity is 
	 Major/Minor/Warning.  This alarm represents measurement Q.752 
	 7.6.
	 
	 The failure occurs when the translation of the Global Title 
	 fails because no available route could be found for the 
	 concerned destination address, due to congestion in the SCCP 
	 subsystem."
    REFERENCE
	"ITU-T Rec. Q.751.2 (1996) : subsystemCongested,
	 ITU-T Rec. Q.752 7.6."
    ::= { sccpSpecificExtensions 16 }

subsystemOoSdenied OBJECT-IDENTITY
    STATUS current
    DESCRIPTION
	"ProbableCause.  Used as the ProbableCause in the 
	 communicationsAlarm.  Parameters include the RowPointer of the 
	 sccpNetworkEntityTable entry that generated the alarm."
    REFERENCE
	"ITU-T Rec. Q.751.2 (1996) : subsystemOoSdenied,
	 ITU-T Rec. Q.752 8.7."
    ::= { sccpSpecificExtensions 17 }

subsystemOoSgranted OBJECT-IDENTITY
    STATUS current
    DESCRIPTION
	"ProbableCause.  Used as the ProbableCause in the 
	 communicationsAlarm.  Parameters include the RowPointer of the 
	 sccpNetworkEntityTable entry that generated the alarm."
    REFERENCE
	"ITU-T Rec. Q.751.2 (1996) : subsystemOoSgranted,
	 ITU-T Rec. Q.752 8.6."
    ::= { sccpSpecificExtensions 18 }

subsystemProhibited OBJECT-IDENTITY
    STATUS current
    DESCRIPTION
	"ProbableCause. Used as the ProbableCause in the 
	 qualityofServiceAlarm.  Parameters include the RowPointer of 
	 the sccpAccessPointTable entry which generated the alarm.  The 
	 perceived severity is Major/Minor/Warning/Cleared.  This alarm 
	 represents measurements Q.752 8.11 (Major/Minor/Warning) and 
	 8.12 (Cleared)."
    REFERENCE
	"ITU-T Rec. Q.751.2 (1996) : subsystemProhibited,
	 ITU-T Rec. Q.752 8.11 and 8.12."
    ::= { sccpSpecificExtensions 19 }

subsystemUnavailable OBJECT-IDENTITY
    STATUS current
    DESCRIPTION
	"ProbableCause.  Used as the ProbableCause with the 
	 qualityofServiceAlarm.  Parameters include the RowPointer of 
	 the sccpScrcTable entry that generated the alarm.  The 
	 perceived severity is Major/Minor/Warning.  This alarm 
	 represents measurement Q.752 7.5.  There is no specific 
	 clearing event defined: explicit clearing by management action 
	 may be required.
	 
	 The failure occurs when the translation of the Global Title 
	 fails because no available route could be found for the 
	 concerned destination address, due to failures in the SCCP 
	 subsystem."
    REFERENCE
	"ITU-T Rec. Q.751.2 (1996) : subsystemUnavailable,
	 ITU-T Rec. Q.752 7.5."
    ::= { sccpSpecificExtensions 20 }

syntaxErrorDetected OBJECT-IDENTITY
    STATUS current
    DESCRIPTION
	"ProbableCause.  Used as the ProbableCause with the 
	 qualityofServceAlarm.  Parameters inlucde the RowPointer of the 
	 sccpScrcTable entry that generated the alarm.  The perceived 
	 severity is Major/Minor/Warning.  This alarm event represents 
	 measurement Q.752 7.8.  There is no specific clearing event 
	 defined; explicit clearing by management action may be 
	 required.
	 
	 The failure occurs when syntax errors are detected in the SCCP 
	 message."
    REFERENCE
	"ITU-T Rec. Q.751.2 (1996) : syntaxErrorDetected,
	 ITU-T Rec. Q.752 7.8."
    ::= { sccpSpecificExtensions 21 }

tooLargeForSegmentation OBJECT-IDENTITY
    STATUS current
    DESCRIPTION
	"ProbableCause.  Used as the ProbableCause in the 
	 qualityofServiceAlarm.  Parameters include the RowPointer of 
	 the sccpAccessPointTable entry that generated the alarm.  The 
	 perceived severity is Major/Minor/Warning.  This alarm event 
	 corresponds to mesurement Q.752 7.14.  No specific clearing 
	 event is defined: alarm clearing may require explicity 
	 management action.
	 
	 This alarm is generated by the SCLC when the length of the user 
	 data is greater than 3952 octets."
    REFERENCE
	"ITU-T Rec. Q.751.2 (1996) : tooLargeForSegmentation
	 ITU-T Rec. Q.752 7.14."
    ::= { sccpSpecificExtensions 22 }

unequippedSubsystem OBJECT-IDENTITY
    STATUS current
    DESCRIPTION
	"ProbableCause.  Used as the ProbableCause with the 
	 qualityofServiceAlarm.  Parameters include the sccpScrcTable 
	 entry that generated the alarm.  Perceived severity is 
	 Major/Minor/Warning.  This alarm event represents measurement 
	 Q.752 7.7.
	 
	 The failure occurs when the received SSN is unequipped in the 
	 local node."
    REFERENCE
	"ITU-T Rec. Q.751.2 (1996) : unequippedSubsystem,
	 ITU-T Rec. Q.752 7.7."
    ::= { sccpSpecificExtensions 23 }

--
-- These four object identifier correspond to the classes that are 
-- available or can be operationally supported by an instance.  They are 
-- used with the sccpLinkageOperationalProtocols attribute of the 
-- sccpLinkageTable entry.
--
sccpProtocolClass0 OBJECT IDENTIFIER ::= { sccpSpecificExtensions 24 }-- basic connectionless
sccpProtocolClass1 OBJECT IDENTIFIER ::= { sccpSpecificExtensions 25 }-- sequenced connectionless
sccpProtocolClass2 OBJECT IDENTIFIER ::= { sccpSpecificExtensions 26 }-- basic connection-oriented
sccpProtocolClass3 OBJECT IDENTIFIER ::= { sccpSpecificExtensions 27 }-- flow control connection oriented


-- =====================================================================

sccpNetworkEntityTable OBJECT-TYPE
    SYNTAX SEQUENCE OF SccpEntry
    MAX-ACCESS not-accessible
    STATUS current
    DESCRIPTION
	""
    REFERENCE
	"ITU-T Rec. Q.751.2 sccp MO."
    ::= { sccpNetworkEntity 1 }

sccpNetworkEntityEntry OBJECT-TYPE
    SYNTAX SccpEntry
    MAX-ACCESS not-accessible
    STATUS current
    DESCRIPTION
	"The sccpNetworkEntityEntry is the placeholder for all SCCP related managed 
	 objects.  No specific management aspects have been identified.
	 
	 The localSapNames attribute contains a set of distinguished 
	 names of SCCP SAPs at which services are provided to the 
	 entity.
	 
	 The systemTypes attributes is a set-valued attribute with 
	 possible values: End System (ES) indicates an SCCP destination 
	 node, Intermediate System (IS) indicates an SCCP relay node.
	 
	 The networkEntityTitles attribute unambiguously identifies the 
	 name of the SCCP in an end or intermediate node.  The value may 
	 be entered by a system management operation or it may be 
	 derived by some local means, for example by auto configuration.
	 
	 A communications entity supports the disabled and enabled 
	 values of the operationalState attribute as described in ITU-T 
	 Rec.  X.731 (1992) | ISO/IEC 10164-2:1992 as follows:
	 
	 - an entity is disabled if it is inoperable or a resource on 
	   which it depends is inoperable,
	   
	 - an entity is enabled if it is operable.
	 
	 The communicationsEntityId is use for naming.

	 The communicationsAlarm can have the following probable causes:

	 - ProbableCause = localSccpUnavailable which represents 
	   measurements Q.752/8.1 measurement Q.752/8.3 
	   (SpecificProblems = Failure, Maintenance, Congestion) 
	   (PerceivedSeverity = Major/Minor/Warning) and measurement 
	   Q.752/8.4 (PerceivedSeverity = Cleared),
	 
	 - ProbableCause = subsystemOoSgranted which represents 
	   measurement Q.752/8.6, and
	 
	 - ProbableCause = subsystemOoSdenied which represents 
	   measurement Q.752/8.7."
    REFERENCE
	"ITU-T Rec. Q.751.2 sccp MO."
    INDEX   {
	    mtpMsId,	 -- shared index
	    sccpNetworkEntityId	 -- index
	}
    ::= { sccpNetworkEntityTable 1 }
	

SccpEntry ::=
    SEQUENCE {
	sccpNetworkEntityId			SimpleNameType, -- index
	sccpNetworkEntityAlarmStatus		AlarmStatus,
	sccpNetworkEntityLocalSapNames		OCTET STRING, -- needs to be a sidetable
	sccpNetworkEntityOperationalState	OperationalState,
	sccpNetworkEntityTitles			SccpNAddresses,
	sccpNetworkEntitySystemTypes		NEntitySystemTypes,
	sccpNetworkEntityVersion		Ss7ProtocolVariant,
	sccpNetworkEntityLUDTandLUDTSSupported	TruthValue,
	sccpNetworkEntityCoordChangeTimer	TimeInterval,
	sccpNetworkEntityIgnoreSSTTimer		TimeInterval,
	sccpNetworkEntityMaxStatInfoTimer	TimeInterval,
	sccpNetworkEntityAsaProfilePointer	RowPointer,
	sccpNetworkEntityName			CommonLanguageName,
	sccpNetworkEntityRowStatus		RowStatus
    }

sccpNetworkEntityId OBJECT-TYPE
    SYNTAX SimpleNameType
    MAX-ACCESS not-accessible
    STATUS current
    DESCRIPTION
	"Provides a identifier of the Network Entity.  Each network 
	 entity corresponds to an instance of SCCP."
    REFERENCE
	"ITU-T Rec. X.723 communicationsEntityId."
    ::= { sccpNetworkEntityEntry 1 }

sccpNetworkEntityAlarmStatus OBJECT-TYPE
    SYNTAX AlarmStatus
    MAX-ACCESS read-create
    STATUS current
    DESCRIPTION
	"Provides the alarm status, following the AlarmStatus textual 
	 convention of the OPENSS7-SMI-MIB module, of the SCCP network 
	 entity corresponding to the conceptual row in which the status 
	 occurs.  This managed object generates the following alarms:
	 
	 The communicationsAlarm can have the following probable causes:
	 
	 - ProbableCause = localSccpUnavailable which represents 
	   measurements Q.752/8.1 measurement Q.752/8.3 
	   (SpecificProblems = Failure, Maintenance, Congestion) 
	   (PerceivedSeverity = Major/Minor/Warning) and measurement 
	   Q.752/8.4 (PerceivedSeverity = Cleared),
	 
	 - ProbableCause = subsystemOoSgranted which represents 
	   measurement Q.752/8.6, and
	 
	 - ProbableCause = subsystemOoSdenied which represents 
	   measurement Q.752/8.7."
    REFERENCE
	"ITU-T Rec. X.731 (1993) : 8.1.2.1,
	 ITU-T Rec. X.721 (1992) : ISO/IEC 10165-2 : 1992, alarmStatus 
	     attribute."
    ::= { sccpNetworkEntityEntry 2 }

-- need to implement as side-table
sccpNetworkEntityLocalSapNames OBJECT-TYPE
    SYNTAX OCTET STRING
    MAX-ACCESS not-accessible
    STATUS current
    DESCRIPTION
	"The localSapNames attribute contains a set of distinguished 
	 names of SCCP SAPs at which services are provided to the 
	 entity."
    REFERENCE
	"ITU-T Rec. X.723 localSapNames."
    ::= { sccpNetworkEntityEntry 3 }

sccpNetworkEntityOperationalState OBJECT-TYPE
    SYNTAX OperationalState
    MAX-ACCESS read-only
    STATUS current
    DESCRIPTION
	"Provides the operational state of the SCCP network entity 
	 following the OperationalState textual convention and ITU-T 
	 Rec. X.721 | ISO/IEC 10165-2.  This object is single-valued and 
	 can assume one of the following values:
	 
	 - disabled(0), the SCCP network entity is not operational or a 
	   resource upon which the SCCP network entity depends is 
	   unavailable;
	 
	 - enabled(1), the SCCP network entity is operational.
	 
	 The operational state is read-only to the management station 
	 and can only be altered by the agent or from within the managed 
	 system."
    REFERENCE
	"ITU-T Rec. X.721 (1992) | ISO/IEC 10165-2 : 1992, 
	     Attribute-ASN1Module.OperationalState.
	 ITU-T Rec. X.723 (1993) | ISO/IEC 10165-5 : 1993, 
	     communicationsEntity:operationalState.
	 ITU-T Rec. X.731 (1992) | ISO/IEC 10164-2 : 1993, 
	     Section 8.1.1.1., operationalState.
	 ITU-T Rec. Q.751.1 (1997), ANSI T1.116.1 (2000), 
	     operationalState attribute."
    DEFVAL { disabled }
    ::= { sccpNetworkEntityEntry 4 }

sccpNetworkEntityTitles OBJECT-TYPE
    SYNTAX SccpNAddresses
    MAX-ACCESS not-accessible
    STATUS current
    DESCRIPTION
	"The networkEntityTitles attribute unambiguously identifies the 
	 name of the SCCP in an end or intermediate node. The value may 
	 be entered by a system management operation or it may be 
	 derived by some local means, for example by auto 
	 configuration."
    REFERENCE
	"ITU-T Rec. X.283 networkEntityTitles."
    ::= { sccpNetworkEntityEntry 5 }

sccpNetworkEntitySystemTypes OBJECT-TYPE
    SYNTAX NEntitySystemTypes
    MAX-ACCESS read-only
    STATUS current
    DESCRIPTION
	"The system types supported by the network entity uinsg the 
	 NEntitySystemTypes textual convention from the 
	 OPENSS7-CLNS-MIB.  This borrows from X.283 (CLNS GDMO).  This 
	 is set-valued and can contain one or both of the following 
	 types:
	 
	 - eS(0), End-System, SCCP Destination Node.
	 
	 - iS(1), Intermediate-System, SCCP Relay Node.
	 
	 This reports the capabilities of the SCCP Network Entity.  It 
	 is set by the agent and cannot be written by the management 
	 system.  Typically SCCP implementations support eS(0) or both 
	 es(0) and iS(1).
	 
	 The systemTypes attribute is a set-valued attribute with 
	 possible values: End System (ES) indicates an SCCP destination 
	 node, Intermediate System indicates an SCCP relay node."
    REFERENCE
	"ITU-T Rec. X.283 systemTypes."
    ::= { sccpNetworkEntityEntry 6 }

sccpNetworkEntityVersion OBJECT-TYPE
    SYNTAX Ss7ProtocolVariant
    MAX-ACCESS read-create
    STATUS current
    DESCRIPTION
	"This attribute is single-valued.  It refers to the 
	 recommendation on which the SCCP implementation is based.  It 
	 is an object identifier of autonomous type."
    REFERENCE
	"ITU-T Rec. Q.751.2 sccpVersion."
    ::= { sccpNetworkEntityEntry 7 }

sccpNetworkEntityLUDTandLUDTSSupported OBJECT-TYPE
    SYNTAX TruthValue
    MAX-ACCESS read-create
    STATUS current
    DESCRIPTION
	"This attribute indicates whether the implementation supports 
	 LUTD(S) messages.  The provisional default is false(2)."
    REFERENCE
	"ITU-T Rec. Q.751.2 lUDTandLUDTSSupported."
    DEFVAL  { false } -- provisional
    ::= { sccpNetworkEntityEntry 8 }

sccpNetworkEntityCoordChangeTimer OBJECT-TYPE
    SYNTAX TimeInterval(3000..12000)
    UNITS       "seconds"
    MAX-ACCESS read-create
    STATUS current
    DESCRIPTION
	"This attribute represents the initial value of timer tCoordChg: 
	 waiting for grant for subsystem to go out of service, as 
	 defined in 5.3.5.2/Q.714.  This timer is started when the 
	 subsystem out of service request is issued to the duplicate 
	 subsystem and is stopped when a subsystem out of service grant 
	 is received.  When the timer expires, the subsystem out of 
	 service request is implicitly denied.
	 
	 ITU-T Q.714 (05/2001) D.4 specifies a range of 1 to 2 minutes.
	 ANSI T1.112.4/2000 6.8 recommends a value of 30 seconds.  A 
	 provisional value of 30 seconds is used."
    REFERENCE
	"ITU-T Rec. Q.751.2 coordChangeTimer.
	 ANSI T1.112.4/2000 6.8."
    DEFVAL  { 3000 } -- 30.00 seconds
    ::= { sccpNetworkEntityEntry 9 }

sccpNetworkEntityIgnoreSSTTimer OBJECT-TYPE
    SYNTAX TimeInterval
    UNITS       "seconds"
    MAX-ACCESS read-create
    STATUS current
    DESCRIPTION
	"This attribute represents the initial value of timer 
	 TignoreSST: delay for subsystem between receiving grant to go 
	 out of service and actually going out of service, as defined in 
	 3.5.2/Q.714.  This timer is started when the subsystem out of 
	 service grant is issued to the local subsystem.  While the 
	 timer is running, subsystem status test messages for the 
	 granted subsystem are ignored (in preparation for going out of 
	 service).
	 
	 This timer is largely a local matter and no range or default is 
	 specified in ITU-T/Q.714 D.4.  ANSI T1.112.4/2000 6.8 
	 recommends a value of 30 seconds."
    REFERENCE
	"ITU-T Rec. Q.751.2 ignoreSSTTimer.
	 ANSI T1.112.4/2000 6.8."
    DEFVAL  { 3000 } -- 30.00 seconds
    ::= { sccpNetworkEntityEntry 10 }

sccpNetworkEntityMaxStatInfoTimer OBJECT-TYPE
    SYNTAX TimeInterval(500..120000)
    UNITS       "seconds"
    MAX-ACCESS read-create
    STATUS current
    DESCRIPTION
	"This attribute represents the maximum value of timer TstatInfo: 
	 delay between requests for subsystem status information, as 
	 defined in 5.3.4.2/Q.714.  This timer is started when a 
	 subsystem status test message is sent to a remote SCCP and 
	 cancelled when a subsystem status response message (SSA, SSP) 
	 is received.
	 
	 ITU-TQ.714 (05/2001) D.4 specifies an increasing value, 
	 starting from 5 to 10 seconds to a maximum of 10 to 20 minutes.  
	 ANSI T1.112/2000 6.8 recommends a value of 30 seconds."
    REFERENCE
	"ITU-T Rec. Q.751.2 maxStatInfoTimer.
	 ANSI T1.112.4/2000 6.8."
    DEFVAL  { 3000 } -- 30.00 seconds
    ::= { sccpNetworkEntityEntry 11 }

sccpNetworkEntityAsaProfilePointer OBJECT-TYPE
    SYNTAX RowPointer
    MAX-ACCESS read-create
    STATUS current
    DESCRIPTION
	"Provides a pointer to an alarm severity assignment profile to 
	 be used for alarms generated by this SCCP network entity, or 
	 zeroDotZero."
    REFERENCE
	"ITU-T Rec. Q.751.2 (1997), ANSI T1.116.1 (2000), 
	     alarmSeverityAssignmentProfilePointer attribute.
	 ITU-T Rec. M.3100 (1995), 
	     alarmSeverityAssignmentProfilePointer.
	 ITU-T Rec. M.3100 (1995), ASN1DefinedTypesModule:PointerOrNull."
    DEFVAL { { zeroDotZero } }
    ::= { sccpNetworkEntityEntry 12 }

sccpNetworkEntityName OBJECT-TYPE
    SYNTAX CommonLanguageName
    MAX-ACCESS read-create
    STATUS current
    DESCRIPTION
	"Provide an optional network entity name following COMMON 
	 LANGUAGE procedures and the CommonLanguageName textual 
	 convention."
    REFERENCE
	"ITU-T Rec. Q.751.2 (1992) networkEntityName."
    ::= { sccpNetworkEntityEntry 13 }

sccpNetworkEntityRowStatus OBJECT-TYPE
    SYNTAX RowStatus
    MAX-ACCESS read-create
    STATUS current
    DESCRIPTION
	"Provides a means, according to the RowStatus textual 
	 convention, for management stations to create and delete rows 
	 from this table.  When created by management stations, entries 
	 in this table have no other entries in other tables associated 
	 with the newly created SCCP network entity.  Before an entry 
	 may be deleted by a management station, all side-tables that 
	 use the sccpNetworkEntityId as an index or which reference this row in the 
	 table using the RowPointer or SimpleNameType textual convention 
	 must be deleted or altered respectively."
    REFERENCE
	"STD 58, SNMPv2-TC RowStatus"
    ::= { sccpNetworkEntityEntry 14 }

-- sidetable for localSapNames

sccpLocalSapNamesTable OBJECT-TYPE
    SYNTAX SEQUENCE OF SccpLocalSapNamesEntry
    MAX-ACCESS not-accessible
    STATUS current
    DESCRIPTION
	""
    REFERENCE
	""
    ::= { sccpNetworkEntity 2 }

sccpLocalSapNamesEntry OBJECT-TYPE
    SYNTAX SccpLocalSapNamesEntry
    MAX-ACCESS not-accessible
    STATUS current
    DESCRIPTION
	""
    REFERENCE
	""
    INDEX {
	    mtpMsId,		 -- shared index
	    sccpNetworkEntityId, -- shared index
	    sccpLocalSapNamesId	 -- index
    }
    ::= { sccpLocalSapNamesTable 1 }

SccpLocalSapNamesEntry ::=
    SEQUENCE {
	sccpLocalSapNamesId			Unsigned32,
	sccpLocalSapNamesPointer		Unsigned32,
	sccpLocalSapNamesRowStatus		RowStatus
    }

sccpLocalSapNamesId OBJECT-TYPE
    SYNTAX Unsigned32
    MAX-ACCESS not-accessible -- index
    STATUS current
    DESCRIPTION
	""
    REFERENCE
	""
    ::= { sccpLocalSapNamesEntry 1 }

sccpLocalSapNamesPointer OBJECT-TYPE
    SYNTAX Unsigned32
    MAX-ACCESS read-create
    STATUS current
    DESCRIPTION
	""
    REFERENCE
	""
    DEFVAL { { zeroDotZero } }
    ::= { sccpLocalSapNamesEntry 2 }

sccpLocalSapNamesRowStatus OBJECT-TYPE
    SYNTAX RowStatus
    MAX-ACCESS read-create
    STATUS current
    DESCRIPTION
	""
    REFERENCE
	""
    DEFVAL { notReady }
    ::= { sccpLocalSapNamesEntry 3 }

-- =====================================================================

sccpAccessPointTable OBJECT-TYPE
    SYNTAX SEQUENCE OF SccpAccessPointEntry
    MAX-ACCESS not-accessible
    STATUS current
    DESCRIPTION
	"The SCCP access point table provides a table of SCCP-SAP 
	 instances.  Each SCCP-SAP represents an instance of an SCCP 
	 subsystem.  SCCP-SAPs may represent either local or remote SCCP 
	 subsystems.
	 
	 Local SCCP-SAPs represent instances of SCCP subsystems that are 
	 local to the managed element.  Remote SCCP-SAPs represent 
	 instances of SCCP subsystems that are remote to the managed 
	 element.
	 
	 An SCCP subsystem number is used for the address associated 
	 with the SCCP-SAP.  The SCCP subsystem number used is the 
	 actual subsystem number.  That is, it follows the SCCP 
	 subsystem numbering scheme used by the SCCP at the local or 
	 remote SCCP."
    REFERENCE
	"ITU-T Rec. Q.751.2 sccpAccessPoint,
	 ITU-T Rec. X.283 (1993) | ISO/IEC 10733 : 1992 nSAP,
	 ITU-T Rec. X.723 (1993) | ISO/IEC 10165-5 : 1993 sap2."
    ::= { sccpAccessPoint 1 }

sccpAccessPointEntry OBJECT-TYPE
    SYNTAX SccpAccessPointEntry
    MAX-ACCESS not-accessible
    STATUS current
    DESCRIPTION
	"This is an SCCP-SAP table entry that is indexed by 
	 sccpAccessPointSapId.  It provides information on each of the 
	 SCCP-SAPs in the system.
	 
	 Each entry in this table is either a local SCCP-SAP (one for 
	 which there is a local SCCP-User at a SCCP end-system) or a 
	 remote SCCP-SAP (representing a remote SCCP-User at an SCCP 
	 intermediate or end system).  Each SCCP-SAP, whether local or 
	 remote, can be part of zero or more concerned areas.
	 
	 The sapId attribute is used in naming instances of the 
	 sccpAccessPoint managed object class.
	 
	 The sap2Address attribute contains the address of the 
	 sccpAccessPoint. The address contains the SubSystem Number 
	 (SSN). The sap2Address is of type SET OF OCTETSTRING. For 
	 sccpAccessPoints, the set size is 1.  For SCCP-SAPs defined 
	 across multiple networks, this is always the actual local or 
	 remote SSN.
	 
	 The userEntityNames attribute contains the distinguished names 
	 of the managed objects that represent the user entities that 
	 are using the sccpAccessPoint, i.e. instances of the SCCP 
	 subsystem.
	 
	 The providerEntityNames attribute contains the distinguished 
	 names of the managed objects that represent the provider 
	 entities that are supporting the sccpAccessPoint, i.e. the 
	 instance of the SCCP.
	 
	 The status of the sccpAccessPoint is represented by the 
	 availability status attribute. A subsystem can have the status: 
	 allowed, the sccpAccessPoint is reachable and is functioning 
	 normally (availability status = available) prohibited, the 
	 sccpAccessPoint not reachable (availability status = 
	 unavailable) congested (availability status = degraded)
	 
	 The optional (national network provider option) 
	 ssAvailableAfterSpRestart attribute holds the default subsystem 
	 status as described in the procedure of 5.2.3/Q.714.
	 
	 The concernedAreaPointer specifies the concerned area to be 
	 used by SCCP Management for primary broadcast in case this 
	 access point is local. In case of a remote access point, the 
	 pointed concerned area will be used by SCCP Management for the 
	 secondary broadcast. The concernedAreaPointer has value 'NULL' 
	 if no concerned area is pointed at.
	 
	 The sccpAccessPointLinkagePointer specifies the sccpLinkage 
	 that is associated with remote sccpAccessPoints only. In case 
	 of a local sccpAccessPoint, the sccpAccessPointLinkagePointer 
	 has value NULL. A remote sccpAccessPoint cannot be created 
	 without a valid pointer to an sccpLinkage.
	 
	 The qualityofServiceAlarm can have the following probable 
	 cause:

	 - ProbableCause = TooLargeForSegmentation which represents 
	   measurement Q.752/7.14 (PerceivedSeverity = 
	   Major/Minor/Warning).

	 - ProbableCause = subsystemProhibited which represents 
	   measurement Q.752/8.11 and Q.752/8.12 (PerceivedSeverity = 
	   Major/Minor/Warning/Cleared).

	 The communicationsAlarm can have the following probable causes:

	 - ProbableCause = sccpCongested which represents measurement 
	   Q.752/8.8 (PerceivedSeverity = Major/Minor/Warning). The 
	   congestion level is given as a parameter of the notification.

	 - ProbableCause = localSubsystemProhibited which represents 
	   measurements Q.752/8.9 and Q.752/8.10 (PerceivedSeverity = 
	   Major/Minor/Warning/Cleared)"
    REFERENCE
	"ITU-T Rec. Q.751.2 sccpAccessPoint,
	 ITU-T Rec. X.283 (1993) | ISO/IEC 10733 : 1992 nSAP,
	 ITU-T Rec. X.723 (1993) | ISO/IEC 10165-5 : 1993 sap2."
    INDEX   {
	    mtpMsId,		  -- shared index
	    sccpNetworkEntityId,  -- shared index
	    sccpAccessPointSapId  -- index
	}
    ::= { sccpAccessPointTable 1 }

SccpAccessPointEntry ::=
    SEQUENCE {
	-- sap2 attributes:
	sccpAccessPointSapId			Unsigned32,
	sccpAccessPointAlarmStatus		AlarmStatus,
	sccpAccessPointSap2Address		SubSystemNumber,
	sccpAccessPointUserEntityNames		OCTET STRING,
	sccpAccessPointProviderEntityNames	PointCodeList,
	-- nSAP attributes: (none)
	-- sccpAccessPoint attributes:
	sccpAccessPointAvailabilityStatus	AvailabilityStatus,
	sccpAccessPointConcernedAreaPointer	Unsigned32,
	sccpAccessPointLinkagePointer		Unsigned32,
	-- ssAvailableAfterSpRestartPackage
	sccpAccessPointSsAvailableAfterSpRestart TruthValue,
	sccpAccessPointAsaProfilePointer	RowPointer,
	sccpAccessPointName			CommonLanguageName,
	sccpAccessPointRowStatus		RowStatus
    }

sccpAccessPointSapId OBJECT-TYPE
    SYNTAX Unsigned32
    MAX-ACCESS not-accessible
    STATUS current
    DESCRIPTION
	"Provides a non-zero ordinal index into the SCCP-SAP table.  The 
	 sapId attribute is used in naming instances of the 
	 sccpAccessPoint managed object class."
    REFERENCE
	"ITU-T Rec. X.723 (1992) | ISO/IEC 10165-5 : 1992 sapId."
    ::= { sccpAccessPointEntry 1 }

sccpAccessPointAlarmStatus OBJECT-TYPE
    SYNTAX AlarmStatus
    MAX-ACCESS read-create
    STATUS current
    DESCRIPTION
	"Provides the alarm status of this SCCP access point, following 
	 the AlarmStatus textual convention of the OPENSS7-SMI-MIB 
	 module and ITU-T Rec. X.721 | ISO/IEC 10165-2.  SCCP access 
	 points generate the following alarms:
	 
	 The qualityofServiceAlarm can have the following probable 
	 cause:
	 
	 - ProbableCause = tooLargeForSegmentation which represents 
	   measurement Q.752/7.14 (Perceived Severity = 
	   Major/Minor/Warning).
	 
	 - ProbableCause = subsystemProhibited which represents 
	   measurement Q.752/8.11 and Q.752/8.12 (Perceived Severity = 
	   Major/Minor/Warning/Cleared).
	 
	 The communicationsAlarm can have the following probable causes:
	 
	 - ProbableCause = sccpCongested which represents measurement 
	   Q.752/8.8 (Perceived Severity = Major/Minor/Warning).  The 
	   congestion level is given as a parameter of the notification.
	 
	 - ProbableCause = localSubsystemProhibited which represents 
	   measurements Q.752/8.9 and Q.752/8.10 (PerceivedSeverity = 
	   Major/Minor/Warning/Cleared)."
    REFERENCE
	"ITU-T Rec. X.731 (1993) : 8.1.2.1,
	 ITU-T Rec. X.721 (1992) : ISO/IEC 10165-2 : 1992, alarmStatus 
	     attribute."
    ::= { sccpAccessPointEntry 2 }

sccpAccessPointSap2Address OBJECT-TYPE
    SYNTAX SubSystemNumber
    MAX-ACCESS read-create
    STATUS current
    DESCRIPTION
	"The set of addresses associated with the SCCP-SAP.  An SCCP-SAP 
	 is ultimately a SCCP network entity and a list of subsystem 
	 numbers.  This set-valued attribute is modelled here as an 
	 octet string, with each octet in the string representing a 
	 subsystem number.
	 
	 The sap2Address attribute contains the address of the 
	 sccpAccessPoint.  The address contains the SubSystem Number 
	 (SSN).  The sap2Address is of type SET OF OCTET STRING.  For 
	 sccpAccessPoints, the set size is 1.
	 
	 This SCCP subsystem number (SSN) is the actual SSN.  That is, 
	 it is the SCCP subsystem number using the numbering scheme of 
	 the local or remote SCCP instance.
	 
	 For a local SCCP-SAP, the subsystem number is associated with 
	 the local SCCP entity indexed by this entry and the 
	 sccpAccessPointLinkagePointer is 0.0.
	 
	 For a remote SCCP-SAP, the subsystem number is associated with 
	 the remote SCCP entity for the sccpAccessPointLinkagePointer."
    REFERENCE
	"ITU-T Rec. X.723 | ISO/IEC 10165-5 asp2Address."
    ::= { sccpAccessPointEntry 3 }

sccpAccessPointUserEntityNames OBJECT-TYPE
    SYNTAX OCTET STRING
    MAX-ACCESS read-create
    STATUS current
    DESCRIPTION
	"The userEntityNames attribute contains the distinguished names 
	 of the managed objects that represent the user entities that 
	 are using the sccpAccessPoint, i.e. instances of the SCCP 
	 subsystem."
    ::= { sccpAccessPointEntry 4 }

sccpAccessPointProviderEntityNames OBJECT-TYPE
    SYNTAX PointCodeList
    MAX-ACCESS read-create
    STATUS current
    DESCRIPTION
	"The providerEntityNames attribute contains the distinguished 
	 names of the managed objects that represent the provider 
	 entities that are supporting the sccpAccessPoint, i.e. the 
	 instance of the SCCP.
	 
	 The value uses the PointCodeList textual convention and the 
	 value represents the list of MTP Point Codes that represent the 
	 MTP systems providing network access to this SCCP-SAP.
	 
	 Typically there is no need to have more than one point code for 
	 an SCCP entity; therefore, this list will normally contain a 
	 single point code."
    ::= { sccpAccessPointEntry 5 }

sccpAccessPointAvailabilityStatus OBJECT-TYPE
    SYNTAX AvailabilityStatus
    MAX-ACCESS read-only
    STATUS current
    DESCRIPTION
	"The status of the sccpAcessPoint is represented by the 
	 availability status attribute.  A subsystem can have status: 
	 
	 - allowed, the sccpAccessPoint is reachable and is functioning 
	   normally (availability status = available)
	 
	 - prohibited, the sccpAccessPoint not reachable (availability 
	   status = unavailable)
	 
	 - congested (avaiability status = degraded).
	 
	 This attribute uses the AvailabilityStatus textual convention 
	 of the OPENSS7-SMI-MIB module."
    REFERENCE
	"ITU-T Rec. X.721 (1992) | ISO/IEC 10165-2 : 1992 
	     availabilityStatus attribute."
    ::= { sccpAccessPointEntry 6 }

--
-- sccpAccessPointConcernedAreaPointer could have been implemented as a 
-- RowPointer, however, because the only table referenced is the 
-- sccpConcernedAreaTable, using the index is sufficient.
--
sccpAccessPointConcernedAreaPointer OBJECT-TYPE
    SYNTAX Unsigned32  -- was RowPointer
    MAX-ACCESS read-create
    STATUS current
    DESCRIPTION
	"The concernedAreaPointer specifies the concerned area to be 
	 used by SCCP Management for primary broadcast in case this 
	 access point is local.  In case of a remote access point, the 
	 pointer to concerned area will be used by SCCP Management for 
	 the secondary broadcast.  The concernedAreaPointer has value 
	 zero (0) if no concerned area is pointed at.
	 
	 There are two levels of concerned area: one at the SCCP level, 
	 and one at the SCCP subsystem level.  This concerned area is at 
	 the SCCP subsystem level.  For the indexed SCCP-SAP, this 
	 concerned area contains all of the SCCP-SAPs that are to 
	 receive broadcast SCCP management messages concerning the SCCP 
	 subsystem.  Concerned areas are an optional concept in SCCP and 
	 affect the broadcast of SCCP management messaages.  Concerned 
	 areas may also be used as a access control list (prohibiting 
	 access to messages received from remote or local subsystems not 
	 within the concerned area)."
    REFERENCE
	"ITU-T Rec. Q.751.2 (1992) concernedAreaPointer."
    DEFVAL { }
    ::= { sccpAccessPointEntry 7 }

--
-- sccpAccessPointLinkagePointer could have been implemented as a RowPointer, 
-- however, because the only table referenced is the sccpLinkageTable, 
-- using the index is sufficient.
--
sccpAccessPointLinkagePointer OBJECT-TYPE
    SYNTAX Unsigned32  -- was RowPointer
    MAX-ACCESS read-create
    STATUS current
    DESCRIPTION
	"The sccpAccessPointLinkagePointer specifies the sccpLinkage 
	 that is associated with the remote sccpAccessPoints only.  In 
	 case of a local sccpAccessPoint, the 
	 sccpAccessPointLinkagePointer has value zero (0).  A remote 
	 sccpAccessPoint cannot be created without a valid pointer to an 
	 sccpLinkage.
	 
	 Each remote SCCP-SAP needs an MTP-SAP through which the remote 
	 SCCP-SAP is accessed.  The linkage index identifies the MTP-SAP  
	 that is used to communicate with the remote SCCP-SAP.  Local 
	 SCCP-SAP do not require external communications and, therefore, 
	 for local SCCP-SAPs this pointer is zero (0)."
    ::= { sccpAccessPointEntry 8 }

sccpAccessPointSsAvailableAfterSpRestart OBJECT-TYPE
    SYNTAX TruthValue
    MAX-ACCESS read-create
    STATUS current
    DESCRIPTION
	"The optional (national network provider option) 
	 ssAvailableAfterRestart attribute holds the default subsystem 
	 status as described in the procedure of 5.2.3/Q.714.  It can 
	 have the following values:
	 
	 - false(1): The subsystem associated with the SCCP-SAP is 
	   assumed to be unavailable when the SCCP Network Entity 
	   restarts.
	 
	 - true(2): The subsystem associated with the SCCP-SAP is 
	   assumed to be available when the SCCP Network Entity 
	   restarts.  This is the default value when the value is not 
	   specified on row creation.
	 
	 This value is only meaningful for remote SCCP-SAPs.  Local 
	 SCCP-SAPs are always assumed available and the value for a 
	 local SCCP-SAP is pinned at true(2)."
    DEFVAL { 2 }
    ::= { sccpAccessPointEntry 9 }

sccpAccessPointAsaProfilePointer OBJECT-TYPE
    SYNTAX RowPointer
    MAX-ACCESS read-create
    STATUS current
    DESCRIPTION
	"Provides a pointer to an alarm severity assignment profile to 
	 be used for alarms generated by this SCCP access point, or 
	 zeroDotZero."
    REFERENCE
	"ITU-T Rec. Q.751.2 (1997), ANSI T1.116.1 (2000), 
	     alarmSeverityAssignmentProfilePointer attribute.
	 ITU-T Rec. M.3100 (1995), 
	     alarmSeverityAssignmentProfilePointer.
	 ITU-T Rec. M.3100 (1995), ASN1DefinedTypesModule:PointerOrNull."
    DEFVAL { { zeroDotZero } }
    ::= { sccpAccessPointEntry 10 }

sccpAccessPointName OBJECT-TYPE
    SYNTAX CommonLanguageName
    MAX-ACCESS read-create
    STATUS current
    DESCRIPTION
	"The common language name of the local or remote SCCP-SAP.  This 
	 is an administrative name."
    REFERENCE
	"ITU-T Rec. Q.751.2 sccpAccessPointName."
    ::= { sccpAccessPointEntry 11 }

sccpAccessPointRowStatus OBJECT-TYPE
    SYNTAX RowStatus
    MAX-ACCESS read-create
    STATUS current
    DESCRIPTION
	"Provides a mechanism whereby management systems may create or 
	 destroy rows in this table.  Rows in this table are persistent 
	 and survive an agent reboot."
    REFERENCE
	"STD 58, SNMPv2-TC RowStatus"
    ::= { sccpAccessPointEntry 12 }

-- =====================================================================

sccpLinkageTable OBJECT-TYPE
    SYNTAX SEQUENCE OF SccpLinkageEntry
    MAX-ACCESS not-accessible
    STATUS current
    DESCRIPTION
	"The SCCP linkage table contains SCCP linkages.  An SCCP linkage 
	 is a relationship between an SCCP network entity and another 
	 SCCP network entity.  Linkages can either be local or remote.  
	 Local linkages represent the relationship between a local 
	 MTP-SAP and the local SCCP entity.  Remote linkages represent 
	 the relationship between a remote MTP-SAP and the remote SCCP 
	 entity."
    REFERENCE
	""
    ::= { sccpLinkage 1 }

sccpLinkageEntry OBJECT-TYPE
    SYNTAX SccpLinkageEntry
    MAX-ACCESS not-accessible
    STATUS current
    DESCRIPTION
	"This manged object class stores data about the specific 
	 capabilities of the underlying MTP acess point.  It is analogue 
	 to the generic managed object class linkage that is described 
	 in Recommendation X.283.  For this managed object class 
	 subclasses may be specified for vendor-specific additions.
	 
	 The sN-SAP attribute indicates a relationship to the underlying 
	 MTP access point.
	 
	 The operationalProtocols attribute indicates the protocol 
	 classes actually supported by this MTP network.  The 'version' 
	 field of the attribute is always 'empty'.
	 
	 The concernedAreaPointer attribute indicates the concerned area 
	 to be used for broadcasting the SCCP status after completion of 
	 SCCP Restart.  It has value 'NULL' if no concerned area is 
	 pointed at."
    REFERENCE
	"ITU-T Rec. Q.751.2 sccpLinkage,
	 ITU-T Rec. X.283 | ISO/IEC 10733 linkage."
    INDEX   {
	    mtpMsId,		 -- shared index
	    sccpNetworkEntityId, -- shared index
	    sccpLinkageId	 -- index
	}
    ::= { sccpLinkageTable 1 }

SccpLinkageEntry ::=
    SEQUENCE {
	sccpLinkageId				Unsigned32,
	sccpLinkageOperationalProtocols		OperationalProtocols,
	sccpLinkageSnSAP			RowPointer,
	-- congestion package
	sccpLinkageAttackTimerValue		TimeInterval,
	sccpLinkageDecayTimerValue		TimeInterval,
	sccpLinkageNrOfRestrictionLevels	INTEGER,
	sccpLinkageNrOfSubLevels		INTEGER,
	sccpLinkageCLS				INTEGER,
	sccpLinkageCongestionTimerValue		TimeInterval,
	sccpLinkageP				INTEGER,
	sccpLinkageImportanceLevelCR		ImportanceLevel,
	sccpLinkageImportanceLevelCC		ImportanceLevel,
	sccpLinkageImportanceLevelCREF		ImportanceLevel,
	sccpLinkageImportanceLevelDT1		ImportanceLevel,
	sccpLinkageImportanceLevelDT2		ImportanceLevel,
	sccpLinkageImportanceLevelAK		ImportanceLevel,
	sccpLinkageImportanceLevelIT		ImportanceLevel,
	sccpLinkageImportanceLevelED		ImportanceLevel,
	sccpLinkageImportanceLevelEA		ImportanceLevel,
	sccpLinkageImportanceLevelRSR		ImportanceLevel,
	sccpLinkageImportanceLevelRSC		ImportanceLevel,
	sccpLinkageImportanceLevelERR		ImportanceLevel,
	sccpLinkageImportanceLevelRLC		ImportanceLevel,
	sccpLinkageImportanceLevelRLSD		ImportanceLevel,
	sccpLinkageImportanceLevelUDT		ImportanceLevel,
	sccpLinkageImportanceLevelUDTS		ImportanceLevel,
	sccpLinkageImportanceLevelXUDT		ImportanceLevel,
	sccpLinkageImportanceLevelXUDTS		ImportanceLevel,
	sccpLinkageImportanceLevelLUDT		ImportanceLevel,
	sccpLinkageImportanceLevelLUDTS		ImportanceLevel,
	sccpLinkageRLM				INTEGER,
	sccpLinkageRSLM				INTEGER,
	-- localSccpLinkagePackage
	sccpLinkageConcernedAreaPointer		Unsigned32,
	sccpLinkageLowerLimitForSegmentation	INTEGER,
	sccpLinkageUpperLimitForSegmentation	INTEGER,
	sccpLinkageName				CommonLanguageName,
	sccpLinkageRowStatus			RowStatus
    }


sccpLinkageId OBJECT-TYPE
    SYNTAX Unsigned32
    MAX-ACCESS not-accessible
    STATUS current
    DESCRIPTION
	"Provides a non-zero ordinal index for this SCCP Linkage 
	 (MTP-SAP) within a given SCCP network entity.  It is 
	 recommended that these indices be generated in a contiguous 
	 ascending order beginning at 1.  Linkage indexes can be 
	 generated either by the management station when creating 
	 entries, or by the managed system when creating entries 
	 locally."
    REFERENCE
	""
    ::= { sccpLinkageEntry 1 }

sccpLinkageOperationalProtocols OBJECT-TYPE
    SYNTAX OperationalProtocols
    MAX-ACCESS read-create
    STATUS current
    DESCRIPTION
	"Indicates the operational protocols (protocol classses) that 
	 are supported on this linkage.  When class0(0) is present, 
	 protocol class 0, the basic connectionless class, is supported; 
	 class1(1), the sequenced connectionless class; class2(2), basic 
	 connection-oriented class; class3(3), the flow control 
	 connection-oriented class.
	 
	 The operationalProtocols attribute indicates the protocol 
	 classes supported by this MTP network linkage.  The 'version' 
	 field of the corresponding X.283 attribute is always 'empty'."
    REFERENCE
	"ITU-T Rec. Q.751.2, ITU-T Rec. X.283 | ISO/IEC 10733 
	     operationalProtocols"
    DEFVAL { { class0, class1, class2, class3 } }
    ::= { sccpLinkageEntry 2 }

sccpLinkageSnSAP OBJECT-TYPE
    -- Because this object could reference one of many different 
    -- tables, the RowPointer textual convention is used  rather 
    -- than the index of any given table.
    SYNTAX RowPointer
    MAX-ACCESS read-create
    STATUS current
    DESCRIPTION
	"Specifies the MTP-SAP providing this linkage to the MTP 
	 sub-network (SnSAP) using the RowPointer textual convention.  
	 
	 SCCP linkages can be local or remote:
	 
	 - A local SCCP linkage references an MTP-SAP in the same 
	   managed switching element to which the local SCCP belongs.  
	   In this case, the pointer is a pointer to an 
	   OPENSS7-MTP-MIB::mtpSapTable instance.
	 
	 - A remote SCCP linkage references an MTP-SAP in another 
	   managed switching element.  The managed switching element 
	   referenced may be local (under control of the agent) or 
	   remote (under the control of another agent).
	 
	 For example, this might be a pointer to an entry in the 
	 mtpSapTable in the OPENSS7-MTP-MIB, or a pointer into the 
	 m3uaSapTable in the OPENSS7-M3UA-MIB.  Reference to entries in 
	 some tables might be restricted to those supported by the 
	 specific agent.
	 
	 Under ITU-T Rec. X.283 | ISO/IEC 10733, this is the 
	 distinguished name of the service provider SAP MO (if present).  
	 This is obtained via an internal interface when the linkage is 
	 enabled.  The sN-SAP may be a relationship to an SAP MO in the 
	 Datalink Layer, or it may be a relationship to another Managed 
	 Object within the network layer which is not an SAP MO.  For 
	 example, when operating ITU-T Rec.  X.233 |ISO/IEC 8473-1 over 
	 the ISO/IEC 8208 or ITU-T Rec. X.25 SNDCF, it is a relationship 
	 to the same x25PLE-DTE MO which is pointed to by the 
	 sN-ServiceProvider Attribute.
	 
	 For SCCP, the sN-SAP attribute indicates a relationship to the 
	 underlying MTP access point."
    REFERENCE
	"ITU-T Rec. X.283 | ISO/IEC 10733 sN-SAP."
    ::= { sccpLinkageEntry 3 }

-- congestion package
--
sccpLinkageAttackTimerValue OBJECT-TYPE
    SYNTAX TimeInterval(6..60)
    UNITS       "seconds"
    MAX-ACCESS read-create
    STATUS current
    DESCRIPTION
	"This attribute models the congestion control parameter Ta, as 
	 described in 5.2.4/Q.714.  This is the time during which the 
	 MTP-STATUS primitive are ignored for setting the RLm and RSLm.  
	 It is only applicable if congestion is supported and the MTP 
	 uses the International method of congestion indication.
	 
	 The attack timer determines the rate at which SCCP will 
	 increase the restricted importance level for outbound messages 
	 while congestion continues to be indicated by MTP.  (Messages 
	 with an importance level of less than the restricted importance 
	 level will not be issued.)  Under full congestion, the 
	 restricted importance level will be increased by one for each M 
	 expiries of the attack timer, where M is the number of 
	 sublevels specified in sccpNrOfSublevels.  It will therefore 
	 take Ta x M x N seconds for the full congestion signal to be 
	 applied (8 seconds using default values).
	 
	 In general, a more stable network results from decay timers 
	 that are longer than attack timers.
	 
	 ITU-T/Q.714 D.4 specifies a range of 60 to 600 milliseconds.  A 
	 provisional value of 250 milliseconds is used."
    REFERENCE
	"ITU-T Rec. Q.751.2 attackTimerValue, 5.2.4/Q.714 Ta."
    DEFVAL  { 25 } -- 0.25 seconds
    ::= { sccpLinkageEntry 4 }

sccpLinkageDecayTimerValue OBJECT-TYPE
    SYNTAX TimeInterval(100..1000)
    UNITS       "seconds"
    MAX-ACCESS read-create
    STATUS current
    DESCRIPTION
	"This attribute models the congestion control parameter Td, as 
	 described in 5.2.4/Q.714.  It is only applicable if congestion 
	 is supported and the MTP uses the International method of 
	 congestion indication.
	 
	 The decay timer determines the rate at which SCCP will decrease 
	 the restricted importance level for outbound messages when 
	 congestion is no longer indicated by MTP.  (Messages with an 
	 importance level of less than the restricted imporance level 
	 will not be issued.)  Under full congestion abatement, the 
	 restricted importance level will be decreased by on for each M 
	 expiries of the decay timer, where M is the number of sublevels 
	 specified in sccpNrOfSublevels.  It will therefore take Td x M 
	 x N seconds for full congestion abatement to occur (160 seconds 
	 using default values).
	 
	 In general, a more stable network results from decay timers 
	 that are longer than attack timers.
	 
	 ITU-T/Q.714 D.4 specifies a range of 1 to 10 seconds.  A 
	 provisional value of 5 seconds is used."
    REFERENCE
	"ITU-T Rec. Q.751.2 decayTimeValue, 5.2.4/Q.714 Td."
    DEFVAL  { 500 } -- 5.00 seconds
    ::= { sccpLinkageEntry 5 }

sccpLinkageNrOfRestrictionLevels OBJECT-TYPE
    SYNTAX INTEGER
    MAX-ACCESS read-create
    STATUS current
    DESCRIPTION
	"This attribute models the congestion control parameter N, as 
	 described in 5.2.7/Q.714.  It is only applicable if the 
	 international method of congestion is provided by MTP.
	 
	 Default values are not specified by ITU-T/Q.714 so the default 
	 value of 8 is provsional."
    REFERENCE
	"ITU-T Rec. Q.751.2 nrOfRestrictionLevels, 5.2.7/Q.714 N."
    DEFVAL { 8 }
    ::= { sccpLinkageEntry 6 }

sccpLinkageNrOfSubLevels OBJECT-TYPE
    SYNTAX INTEGER
    MAX-ACCESS read-create
    STATUS current
    DESCRIPTION
	"This attribute models the congestion control parameter M, as 
	 described in 5.2.7/Q.714.  It is only applicable if the 
	 international method of congestion is provided by MTP.
	 
	 Default values are not specified by ITU-T/Q.714 so the default 
	 value of 4 is provsional."
    REFERENCE
	"ITU-T Rec. Q.751.2 nrOfSubLevels, 5.2.7/Q.714 M."
    DEFVAL { 4 }
    ::= { sccpLinkageEntry 7 }

sccpLinkageCLS OBJECT-TYPE
    SYNTAX INTEGER
    MAX-ACCESS read-create
    STATUS current
    DESCRIPTION
	"This attribute models the congestion control parameter CLS, as 
	 described in 5.2.7/Q.714.  It is only applicable if the 
	 international congestion method is supported.
	 
	 This parameter specifies the range of SCCP congestion levels 
	 the may be inicated in a subsystem congested message.  
	 ITU-T/Q,714 specifies a value of 8.  This number should not be 
	 changed."
    REFERENCE
	"ITU-T Rec. Q.751.2 cLS, 5.2.7/Q.714 CLS."
    DEFVAL { 8 }
    ::= { sccpLinkageEntry 8 }

sccpLinkageCongestionTimerValue OBJECT-TYPE
    SYNTAX TimeInterval(100..1000)
    UNITS       "seconds"
    MAX-ACCESS read-create
    STATUS current
    DESCRIPTION
	"This attribute modesl the congestion control parameter Tcon, as 
	 described in 5.2.7/Q.714.  It is only applicable if the 
	 international congestion method is supported.
	 
	 When congestion abates at the remote SCCP, the local CLs 
	 parameter is decremented once for each expiry of Tcon.  
	 Therefore, it will take Tcon x CLs for the congestion to fully 
	 abate (16 seconds with default values).
	 
	 Caution should be applied when modifying this congestion 
	 parameter: coordination within and between networks might be 
	 required.
	 
	 ITU-T/Q.714 D.4 specifies a range of 1 to 10 seconds.  A 
	 provisional value of 5 seconds is used."
    REFERENCE
	"ITU-T Rec. Q.751.2 congestionTimerValue, 5.2.7/Q.714 Tcon."
    DEFVAL { 500 } -- 5.00 seconds
    ::= { sccpLinkageEntry 9 }

sccpLinkageP OBJECT-TYPE
    SYNTAX INTEGER
    MAX-ACCESS read-create
    STATUS current
    DESCRIPTION
	"This attribute models the congestion control parameter P, as 
	 described in 5.2.7/Q.714.  It is only applicable if the 
	 international congestion method is supported.
	 
	 When an SCCP experiences local congestion due to receipt of an 
	 SCCP message, it will send an SSC (subsystem-congested) message 
	 with the appropriate CLs parameter toward the originator of the 
	 message that triggered congestion.  While congestion perists, 
	 it will send an SSC message with the CLs parameter upon receipt 
	 of each Pth additional message to the originator of that 
	 message.
	 
	 Caution should be applied when modifying this congestion 
	 parameter: coordination within and between networks might be 
	 required.
	 
	 The default value is 8 and is provisionally specified in 
	 ITU-T/Q.714."
    REFERENCE
	"ITU-T Rec. Q.751.2 p, 5.2.7/Q.714 P."
    DEFVAL { 8 }
    ::= { sccpLinkageEntry 10 }

sccpLinkageImportanceLevelCR OBJECT-TYPE
    SYNTAX ImportanceLevel
    MAX-ACCESS read-create
    STATUS current
    DESCRIPTION
	"Provides the default and maximum importance levels for the CR 
	 message.  It is only applicable if the international method of 
	 congestion is supported.  For recommended values, see 
	 2.6.2/Q.714.  Caution should be taken when modifying the 
	 importance levels: co-ordination within and in between 
	 different networks might be required."
    REFERENCE
	"ITU-T Rec. Q.751.2 importanceLevel-CR, Table 2/2.6.2/Q.714."
    DEFVAL { '0204'X }
    ::= { sccpLinkageEntry 11 }

sccpLinkageImportanceLevelCC OBJECT-TYPE
    SYNTAX ImportanceLevel
    MAX-ACCESS read-create
    STATUS current
    DESCRIPTION
	"Provides the default and maximum importance levels for the CC 
	 message.  It is only applicable if the international method of 
	 congestion is supported.  For recommended values, see 
	 2.6.2/Q.714.  Caution should be taken when modifying the 
	 importance levels: co-ordination within and in between 
	 different networks might be required."
    REFERENCE
	"ITU-T Rec. Q.751.2 importanceLevel-CC, Table 2/2.6.2/Q.714."
    DEFVAL { '0304'X }
    ::= { sccpLinkageEntry 12 }

sccpLinkageImportanceLevelCREF OBJECT-TYPE
    SYNTAX ImportanceLevel
    MAX-ACCESS read-create
    STATUS current
    DESCRIPTION
	"Provides the default and maximum importance levels for the CREF 
	 message.  It is only applicable if the international method of 
	 congestion is supported.  For recommended values, see 
	 2.6.2/Q.714.  Caution should be taken when modifying the 
	 importance levels: co-ordination within and in between 
	 different networks might be required."
    REFERENCE
	"ITU-T Rec. Q.751.2 importanceLevel-CREF, Table 2/2.6.2/Q.714."
    DEFVAL { '0204'X }
    ::= { sccpLinkageEntry 13 }

sccpLinkageImportanceLevelDT1 OBJECT-TYPE
    SYNTAX ImportanceLevel
    MAX-ACCESS read-create
    STATUS current
    DESCRIPTION
	"Provides the default and maximum importance levels for the DT1 
	 message.  It is only applicable if the international method of 
	 congestion is supported.  For recommended values, see 
	 2.6.2/Q.714.  Caution should be taken when modifying the 
	 importance levels: co-ordination within and in between 
	 different networks might be required."
    REFERENCE
	"ITU-T Rec. Q.751.2 importanceLevel-DT1, Table 2/2.6.2/Q.714."
    DEFVAL { '0406'X }
    ::= { sccpLinkageEntry 14 }

sccpLinkageImportanceLevelDT2 OBJECT-TYPE
    SYNTAX ImportanceLevel
    MAX-ACCESS read-create
    STATUS current
    DESCRIPTION
	"Provides the default and maximum importance levels for the DT2 
	 message.  It is only applicable if the international method of 
	 congestion is supported.  For recommended values, see 
	 2.6.2/Q.714.  Caution should be taken when modifying the 
	 importance levels: co-ordination within and in between 
	 different networks might be required."
    REFERENCE
	"ITU-T Rec. Q.751.2 importanceLevel-DT2, Table 2/2.6.2/Q.714."
    DEFVAL { '0406'X }
    ::= { sccpLinkageEntry 15 }

sccpLinkageImportanceLevelAK OBJECT-TYPE
    SYNTAX ImportanceLevel
    MAX-ACCESS read-create
    STATUS current
    DESCRIPTION
	"Provides the importance level for the AK message.  It is only 
	 applicable if the international method of congestion is 
	 supported.  For recommended values, see 2.6.2/Q.714.  Caution 
	 should be taken when modifying the importance levels: 
	 co-ordination within and in between different networks might be 
	 required."
    REFERENCE
	"ITU-T Rec. Q.751.2 importanceLevel-AK, Table 2/2.6.2/Q.714."
    DEFVAL { '0600'X }
    ::= { sccpLinkageEntry 16 }

sccpLinkageImportanceLevelIT OBJECT-TYPE
    SYNTAX ImportanceLevel
    MAX-ACCESS read-create
    STATUS current
    DESCRIPTION
	"Provides the importance level for the IT message.  It is only 
	 applicable if the international method of congestion is 
	 supported.  For recommended values, see 2.6.2/Q.714.  Caution 
	 should be taken when modifying the importance levels.  
	 co-ordination within and in between different networks might be 
	 required."
    REFERENCE
	"ITU-T Rec. Q.751.2 importanceLevel-IT, Table 2/2.6.2/Q.714."
    DEFVAL { '0600'X }
    ::= { sccpLinkageEntry 17 }

sccpLinkageImportanceLevelED OBJECT-TYPE
    SYNTAX ImportanceLevel
    MAX-ACCESS read-create
    STATUS current
    DESCRIPTION
	"Provides the importance level for the ED message.  It is only 
	 applicable if the international method of congestion is 
	 supported.  For recommended values, see 2.6.2/Q.714.  Caution 
	 should be taken when modifying the importance levels.  
	 co-ordination within and in between different networks might be 
	 required."
    REFERENCE
	"ITU-T Rec. Q.751.2 importanceLevel-ED, Table 2/2.6.2/Q.714."
    DEFVAL { '0700'X }
    ::= { sccpLinkageEntry 18 }

sccpLinkageImportanceLevelEA OBJECT-TYPE
    SYNTAX ImportanceLevel
    MAX-ACCESS read-create
    STATUS current
    DESCRIPTION
	"Provides the importance level for the EA message.  It is only 
	 applicable if the international method of congestion is 
	 supported.  For recommended values, see 2.6.2/Q.714.  Caution 
	 should be taken when modifying the importance levels.  
	 co-ordination within and in between different networks might be 
	 required."
    REFERENCE
	"ITU-T Rec. Q.751.2 importanceLevel-EA, Table 2/2.6.2/Q.714."
    DEFVAL { '0700'X }
    ::= { sccpLinkageEntry 19 }

sccpLinkageImportanceLevelRSR OBJECT-TYPE
    SYNTAX ImportanceLevel
    MAX-ACCESS read-create
    STATUS current
    DESCRIPTION
	"Provides the importance level for the RSR message.  It is only 
	 applicable if the international method of congestion is 
	 supported.  For recommended values, see 2.6.2/Q.714.  Caution 
	 should be taken when modifying the importance levels.  
	 co-ordination within and in between different networks might be 
	 required."
    REFERENCE
	"ITU-T Rec. Q.751.2 importanceLevel-RSR, Table 2/2.6.2/Q.714."
    DEFVAL { '0600'X }
    ::= { sccpLinkageEntry 20 }

sccpLinkageImportanceLevelRSC OBJECT-TYPE
    SYNTAX ImportanceLevel
    MAX-ACCESS read-create
    STATUS current
    DESCRIPTION
	"Provides the importance level for the RSC message.  It is only 
	 applicable if the international method of congestion is 
	 supported.  For recommended values, see 2.6.2/Q.714.  Caution 
	 should be taken when modifying the importance levels.  
	 co-ordination within and in between different networks might be 
	 required."
    REFERENCE
	"ITU-T Rec. Q.751.2 importanceLevel-RSC, Table 2/2.6.2/Q.714."
    DEFVAL { '0600'X }
    ::= { sccpLinkageEntry 21 }

sccpLinkageImportanceLevelERR OBJECT-TYPE
    SYNTAX ImportanceLevel
    MAX-ACCESS read-create
    STATUS current
    DESCRIPTION
	"Provides the importance level for the ERR message.  It is only 
	 applicable if the international method of congestion is 
	 supported.  For recommended values, see 2.6.2/Q.714.  Caution 
	 should be taken when modifying the importance levels.  
	 co-ordination within and in between different networks might be 
	 required."
    REFERENCE
	"ITU-T Rec. Q.751.2 importanceLevel-ERR, Table 2/2.6.2/Q.714."
    DEFVAL { '0700'X }
    ::= { sccpLinkageEntry 22 }

sccpLinkageImportanceLevelRLC OBJECT-TYPE
    SYNTAX ImportanceLevel
    MAX-ACCESS read-create
    STATUS current
    DESCRIPTION
	"Provides the importance levels for the RLC message.  It is only 
	 applicable if the international method of congestion is 
	 supported.  For recommended values, see 2.6.2/Q.714.  Caution 
	 should be taken when modifying the importance levels.  
	 co-ordination within and in between different networks might be 
	 required."
    REFERENCE
	"ITU-T Rec. Q.751.2 importanceLevel-RLC, Table 2/2.6.2/Q.714."
    DEFVAL { '0400'X }
    ::= { sccpLinkageEntry 23 }

sccpLinkageImportanceLevelRLSD OBJECT-TYPE
    SYNTAX ImportanceLevel
    MAX-ACCESS read-create
    STATUS current
    DESCRIPTION
	"Provides the default and maximum importance levels for the RLSD 
	 message.  It is only applicable if the international method of 
	 congestion is supported.  For recommended values, see 
	 2.6.2/Q.714.  Caution should be taken when modifying the 
	 importance levels: co-ordination within and in between 
	 different networks might be required."
    REFERENCE
	"ITU-T Rec. Q.751.2 importanceLevel-RLSD, Table 2/2.6.2/Q.714."
    DEFVAL { '0606'X }
    ::= { sccpLinkageEntry 24 }

sccpLinkageImportanceLevelUDT OBJECT-TYPE
    SYNTAX ImportanceLevel
    MAX-ACCESS read-create
    STATUS current
    DESCRIPTION
	"Provides the default and maximum importance levels for the UDT 
	 message.  It is only applicable if the international method of 
	 congestion is supported.  For recommended values, see 
	 2.6.2/Q.714.  Caution should be taken when modifying the 
	 importance levels: co-ordination within and in between 
	 different networks might be required."
    REFERENCE
	"ITU-T Rec. Q.751.2 importanceLevel-UDT, Table 2/2.6.2/Q.714."
    DEFVAL { '0406'X }
    ::= { sccpLinkageEntry 25 }

sccpLinkageImportanceLevelUDTS OBJECT-TYPE
    SYNTAX ImportanceLevel
    MAX-ACCESS read-create
    STATUS current
    DESCRIPTION
	"Provides the importance level for the UDTS message.  It is only 
	 applicable if the international method of congestion is 
	 supported.  For recommended values, see 2.6.2/Q.714.  Caution 
	 should be taken when modifying the importance levels.  
	 co-ordination within and in between different networks might be 
	 required."
    REFERENCE
	"ITU-T Rec. Q.751.2 importanceLevel-UDTS, Table 2/2.6.2/Q.714."
    DEFVAL { '0300'X }
    ::= { sccpLinkageEntry 26 }

sccpLinkageImportanceLevelXUDT OBJECT-TYPE
    SYNTAX ImportanceLevel
    MAX-ACCESS read-create
    STATUS current
    DESCRIPTION
	"Provides the default and maximum importance levels for the XUDT 
	 message.  It is only applicable if the international method of 
	 congestion is supported.  For recommended values, see 
	 2.6.2/Q.714.  Caution should be taken when modifying the 
	 importance levels: co-ordination within and in between 
	 different networks might be required."
    REFERENCE
	"ITU-T Rec. Q.751.2 importanceLevel-XUDT, Table 2/2.6.2/Q.714."
    DEFVAL { '0406'X }
    ::= { sccpLinkageEntry 27 }

sccpLinkageImportanceLevelXUDTS OBJECT-TYPE
    SYNTAX ImportanceLevel
    MAX-ACCESS read-create
    STATUS current
    DESCRIPTION
	"Provides the importance level for the XUDTS message.  It is 
	 only applicable if the international method of congestion is 
	 supported.  For recommended values, see 2.6.2/Q.714.  Caution 
	 should be taken when modifying the importance levels.  
	 co-ordination within and in between different networks might be 
	 required."
    REFERENCE
	"ITU-T Rec. Q.751.2 importanceLevel-XUDTS, Table 2/2.6.2/Q.714."
    DEFVAL { '0300'X }
    ::= { sccpLinkageEntry 28 }

sccpLinkageImportanceLevelLUDT OBJECT-TYPE
    SYNTAX ImportanceLevel
    MAX-ACCESS read-create
    STATUS current
    DESCRIPTION
	"Provides the default and maximum importance levels for the LUDT 
	 message.  It is only applicable if the international method of 
	 congestion is supported.  For recommended values, see 
	 2.6.2/Q.714.  Caution should be taken when modifying the 
	 importance levels: co-ordination within and in between 
	 different networks might be required."
    REFERENCE
	"ITU-T Rec. Q.751.2 importanceLevel-LUDT, Table 2/2.6.2/Q.714."
    DEFVAL { '0406'X }
    ::= { sccpLinkageEntry 29 }

sccpLinkageImportanceLevelLUDTS OBJECT-TYPE
    SYNTAX ImportanceLevel
    MAX-ACCESS read-create
    STATUS current
    DESCRIPTION
	"Provides the importance level for the LDUTS message.  It is 
	 only applicable if the international method of congestion is 
	 supported.  For recommended values, see 2.6.2/Q.714.  Caution 
	 should be taken when modifying the importance levels.  
	 co-ordination within and in between different networks might be 
	 required."
    REFERENCE
	"ITU-T Rec. Q.751.2 importanceLevel-LUDTS, Table 2/2.6.2/Q.714."
    DEFVAL { '0300'X }
    ::= { sccpLinkageEntry 30 }

sccpLinkageRLM OBJECT-TYPE
    SYNTAX INTEGER
    MAX-ACCESS read-only
    STATUS current
    DESCRIPTION
	"This attribute models the restriction level parameter RLm as 
	 defined in 5.2.4/Q.714.  It is only applicable if the 
	 international method of congestion is supported."
    REFERENCE
	"ITU-T Rec. Q.751.2 rLM, 5.2.4/Q.714."
    ::= { sccpLinkageEntry 31 }

sccpLinkageRSLM OBJECT-TYPE
    SYNTAX INTEGER
    MAX-ACCESS read-only
    STATUS current
    DESCRIPTION
	"This attribute models the restriction sub-level parameter RSLm 
	 as defined in 5.2.4/Q.714.  It is only applicable if the 
	 international method of congestion is supported."
    REFERENCE
	"ITU-T Rec. Q.751.2 rSLM, 5.2.4/Q.714."
    ::= { sccpLinkageEntry 32 }

-- localSccpLinkagePackage
--
sccpLinkageConcernedAreaPointer OBJECT-TYPE
    -- sccpLinkageConcernedAreaPointer used to be implemented as a 
    -- RowPointer, however, as the columnar object never refers to 
    -- other than entries in the sccpLinkageTable, the index to that 
    -- table is sufficient.
    SYNTAX Unsigned32  -- was RowPointer
    MAX-ACCESS read-create
    STATUS current
    DESCRIPTION
	"This attribute is used for referring to instances of 
	 concernedArea.  It has the value 'NULL' if no concerned are a 
	 is pointed at.  It is only applicable if this is a local 
	 linkage.
	 
	 Specifies the concerned area to be used for broadcasting the 
	 SCCP status after completion of SCCP Restart.  It has value 
	 'NULL' if no concerned area is pointed at.
	 
	 The concernedAreaPointer attribute indicates the concerned area 
	 to be used for broadcasting the SCCP status after completion of 
	 SCCP Restart.  It has value 'NULL' if no concerned area is 
	 pointed at.  If there is a concerned area, the value of this 
	 object is an sccpConcernedAreaId index value used for entries 
	 in the sccpConcernedAreaTable and sccpRemoteSCCPTable and 
	 therefore identifies a set of remote SCCP entities that make up 
	 the concerned area."
    REFERENCE
	"ITU-T Rec. Q.751.2 concernedAreaPointer."
    ::= { sccpLinkageEntry 33 }

sccpLinkageLowerLimitForSegmentation OBJECT-TYPE
    SYNTAX INTEGER (150..3592)
    UNITS "octets"
    MAX-ACCESS read-create
    STATUS current
    DESCRIPTION
	"This attributes represents a number of octets.  If the length 
	 of the user data exceeds this length then it depends on the 
	 status of the network whether the message is segmented or not.  
	 The attribute coresponds to the parameter Z as described in 
	 ITU-T 4.1.1.1.1/Q.714 or the parameter X as described in ANSI 
	 T1.112/4.1.1.1.1.  The value of this attribute shall obey the 
	 relation 150 <= Z <= Y <= 3592, as described in 4.1.1.1.1/Q.714 
	 and the relation 0 <= X <= Y <= 3904 described in ANSI 
	 T1.112/2000 4.1.1.1.1.  It is only applicable if this is a 
	 local linkage."
    REFERENCE
	"ITU-T Rec. Q.751.2 lowerLimitForSegmentation."
    ::= { sccpLinkageEntry 34 }

sccpLinkageUpperLimitForSegmentation OBJECT-TYPE
    SYNTAX INTEGER (150..3592)
    UNITS "octets"
    MAX-ACCESS read-create
    STATUS current
    DESCRIPTION
	"This attribute represents a number of octets.  If the length of 
	 the user data exceeds this length then the message is always 
	 segmented.  The attribute coresponds to the parameter Y as 
	 described in ITU-T 4.1.1.1.1/Q.714 and ANSI T1.112/4.1.1.1.1.  
	 The value of this attribute shall obey the relation 160 <= Z <= 
	 Y <= 3592, as described in 4.1.1.1.1/Q.714 or 0 <= X <= Y <= 
	 3904, as described in ANSI T1.112/4.1.1.1.1.  It is only 
	 applicable if this is a local linkage."
    REFERENCE
	"ITU-T Rec. Q.751.2 upperLimitForSegmentation."
    ::= { sccpLinkageEntry 35 }

sccpLinkageName OBJECT-TYPE
    SYNTAX CommonLanguageName
    MAX-ACCESS read-create
    STATUS current
    DESCRIPTION
	"It is only applicable if when supported.  When not supported 
	 both management GET and management SET operations will fail."
    ::= { sccpLinkageEntry 36 }

sccpLinkageRowStatus OBJECT-TYPE
    SYNTAX RowStatus
    MAX-ACCESS read-create
    STATUS current
    DESCRIPTION
	"Provides a mechanism whereby management stations may create or 
	 delete conceptual rows in this table."
    ::= { sccpLinkageEntry 37 }

-- =====================================================================

sccpMtpTable OBJECT-TYPE
    SYNTAX SEQUENCE OF SccpMtpEntry
    MAX-ACCESS not-accessible
    STATUS current
    DESCRIPTION
	"The MTP layer does not maintain the availability of MTP user parts 
	 at remote signalling points.  This is the responsibility of the 
	 local MTP user.  This table contains the known remote MTP-SAPs 
	 (remote SCCP) and maintains their MTP user part status.  The 
	 SCCP layer updates the status of the MTP-SAP based on the 
	 receipt of MTP-STATUS primitives from the MTP layer.
	 
	 ITU-T Rec. Q.751.2 (1996) provides an sN-SAP pointer that 
	 points to a sN-SAP managed object from ITU-T Rec. X.283 | 
	 ISO/IEC 10733; however, it does not define the pointed to 
	 managed object class.  ITU-T Rec. Q.751.1 (1997) and ANSI 
	 T1.116.1 (2000) provide an mtpAccessPoint managed object; 
	 however, this managed object is only for local MTP-SAPs.
	 
	 This table represents the sN-SAP managed object class for 
	 remote MTP-SAPs."
    REFERENCE
	"ITU-T Rec. X.283 (1992) | ISO/IEC 10733 : 1993.
	 ITU-T Rec. Q.751.1 (1997), ANSI T1.116.1 (2000).
	 ITU-T Rec. Q.751.2 (1996), ANSI T1.116.2 (2000)."
    ::= { sccpMtp 1 }

sccpMtpEntry OBJECT-TYPE
    SYNTAX SccpMtpEntry
    MAX-ACCESS not-accessible
    STATUS current
    DESCRIPTION
	"This is an MTP-SAP entry that defines the MTP-SAPs (SCCP) that 
	 are available at a remote signalling point.
	 
	 The sapId attribute is used in indexing entries of the remote 
	 MTP-SAP table.
	 
	 The sap2Address attribute containes the address of the remote 
	 MTP-SAP.  It contains the global Network Identifier (NI), 
	 Signalling Point Code (SPC), and Service Indicator (SI).

	 The userEntityNames attribute contains the distinguished names 
	 of the managed objects that represent the user entities that 
	 are using the remote MTP-SAP, e.g. the local SCCP instance.

	 The providerEntityNames attribute contains the distinguished 
	 names of the managed objects that represent the provider 
	 entities that are supporting the remote MTP-SAP, i.e. the 
	 instance of the local SCCP linkage which the remote MTP-SAP is 
	 accessed."
    REFERENCE
	"ITU-T Rec. Q.751.1 (1997), ANSI T1.116.1 (2000), mtpAccessPoint 
	     MO."
    INDEX {
	    mtpMsId,		 -- shared index
	    sccpNetworkEntityId, -- shared index
	    sccpMtpSapId	 -- index
    }
    ::= { sccpMtpTable 1 }

SccpMtpEntry ::= 
    SEQUENCE {
	sccpMtpSapId				Unsigned32,
	sccpMtpSap2Address			MtpSapAddress,
	sccpMtpUserPart				MtpUserPart,
	sccpMtpUserPartStatus			MtpUserPartStatus,
	sccpMtpUserEntityNames			RowPointer,
	sccpMtpProviderEntityNames		RowPointer,
	sccpMtpUsageState			UsageState,
	sccpMtpAdministrativeState		AdministrativeState,
	sccpMtpOperationalState			OperationalState,
	sccpMtpCongestedState			MtpCongestedState,
	sccpMtpCongestionLevel			MtpCongestionLevel,
	sccpMtpRemoteExchangeLabel		CommonLanguageName,
	sccpMtpName				SimpleNameType,
	sccpMtpRowStatus			RowStatus
    }

sccpMtpSapId OBJECT-TYPE
    SYNTAX Unsigned32
    MAX-ACCESS not-accessible -- index
    STATUS current
    DESCRIPTION
	""
    REFERENCE
	"ITU-T Rec. Q.751.1 (1997), ANSI T1.116.1 (2000),
	 ITU-T Rec. X.723 | ISO/IEC 10165-5, sapId attibute."
    ::= { sccpMtpEntry 1 }

sccpMtpSap2Address OBJECT-TYPE
    SYNTAX MtpSapAddress
    MAX-ACCESS read-create
    STATUS current
    DESCRIPTION
	"Provides the global MTP-SAP address of the remote MTP-SAP using 
	 the MtpSapAddress textual convention of the OPENSS7-MTP-MIB.  
	 This textual convention provides the global network identifier 
	 (NI), Signalling Point Code (SPC), and Service Indicator (SI) 
	 associated with the remote MTP-SAP."
    REFERENCE
	"ITU-T Rec. Q.751.1 (1997), ANSI T1.116.1 (2000),
	 ITU-T Rec. X.723 | ISO/IEC 10165-5, sap2Address attibute."
    ::= { sccpMtpEntry 2 }

sccpMtpUserPart OBJECT-TYPE
    SYNTAX MtpUserPart
    MAX-ACCESS read-create
    STATUS current
    DESCRIPTION
	"Provides the MTP user part (Service Indicator or SI value) 
	 associated with the MTP-SAP using the MtpUserPart textual 
	 convention from the OPENSS7-MTP-MIB module."
    REFERENCE
	""
    ::= { sccpMtpEntry 3 }

sccpMtpUserPartStatus OBJECT-TYPE
    SYNTAX MtpUserPartStatus
    MAX-ACCESS read-only
    STATUS current
    DESCRIPTION
	"Provides, using the MtpUserPartStatus textual convention, the 
	 status of the remote MTP-SAP.  The object is single-valued and 
	 can assume one of the following values:
	 
	 - unknown(0), the status of the remote user is unknown;
	 - inaccessible(1), the remote user is equipped but inaccessible;
	 - unequipped(2), the remote user is unequipped.
	 
	 When the remote user part is present but currently unavaiable, 
	 the value is inaccessible(1)."
    REFERENCE
	"sccpMtpUsageState"
    ::= { sccpMtpEntry 4 }

sccpMtpUserEntityNames OBJECT-TYPE
    SYNTAX RowPointer
    MAX-ACCESS read-create
    STATUS current
    DESCRIPTION
	"Provides the local user entity names for the users of the 
	 remote MTP-SAP (signalling relation).  In this case it is the 
	 local SCCP entity and therefore a pointer into the 
	 sccpNetworkEntityTable."
    REFERENCE
	"ITU-T Rec. Q.751.1 (1997), ANSI T1.116.1 (2000),
	 ITU-T Rec. X.723 | ISO/IEC 10165-5, userEntityNames attibute."
    ::= { sccpMtpEntry 5 }

sccpMtpProviderEntityNames OBJECT-TYPE
    SYNTAX RowPointer
    MAX-ACCESS read-create
    STATUS current
    DESCRIPTION
	"Provides the local provider entity names for the providers of 
	 the remote MTP-SAP (signalling relation).  In this case, it is 
	 the local SCCP linkage that provides access to the remote 
	 MTP-SAP (signalling relation) and therefore a pointer into the 
	 sccpLinkageTable."
    REFERENCE
	"ITU-T Rec. Q.751.1 (1997), ANSI T1.116.1 (2000),
	 ITU-T Rec. X.723 | ISO/IEC 10165-5, providerEntityNames 
	     attibute."
    ::= { sccpMtpEntry 6 }

sccpMtpUsageState OBJECT-TYPE
    SYNTAX UsageState
    MAX-ACCESS read-only
    STATUS current
    DESCRIPTION
	"Provides the usage state of the remote MTP-SAP following the 
	 UsageState textual convention and ITU-T Rec. X.721 | ISO/IEC 
	 10165-2.
	 
	 - idle(0), no local SCCP is using the remote MTP-SAP,
	 
	 - active(1), a local SCCP is using the remote MTP-SAP,
	 
	 - busy(2), a local SCCP is passing traffic to a remote MTP-SAP, 
	   however, congestion exists in the path toward the remote 
	   MTP-SAP.
	   
	 Note that a usage state of active(1) or busy(2) does not mean 
	 that traffic is currently being passed to the remote MTP-SAP."
    REFERENCE
	"ITU-T Rec. X.721 | ISO/IEC 10165-2 usageState attribute."
    ::= { sccpMtpEntry 7 }

sccpMtpAdministrativeState OBJECT-TYPE
    SYNTAX AdministrativeState
    MAX-ACCESS read-create
    STATUS current
    DESCRIPTION
	"Provides the administrative state of the remote SCCP following 
	 the AdministrativeState textual convention and ITU-T Rec. X.721 
	 | ISO/IEC 10165-2.

	 - locked(0), the remote SCCP is administratively prohibited 
	   from use,
	 - unlocked(1), the remote SCCP is administratively permitted 
	   for use,
	 - shuttingDown(2), not used.
	"
    REFERENCE
	"ITU-T Rec. X.721 (1992) | ISO/IEC 10165-2 : 1992, 
	     Attribute-ASN1Module.AdministrativeState.
	 ITU-T Rec. Q.751.1 (1997), ANSI T1.116.1 (2000), 
	     administrativeState attribute."
    ::= { sccpMtpEntry 8 }

sccpMtpOperationalState OBJECT-TYPE
    SYNTAX OperationalState
    MAX-ACCESS read-only
    STATUS current
    DESCRIPTION
	"Provides the operational state of the remote SCCP following the 
	 OperationalState textual convention and ITU-T Rec. X.721 | 
	 ISO/IEC 10165-2.
	 
	 - disabled(0), the remote SCCP SPC is inaccessible due to the 
	   associated SPC being prohibited;
	 
	 - enabled(1), the remote SCCP SPC is accessible: the associated 
	   SCP is allowed;
	
	 This operational state only reflects the operational state of 
	 the remote signalling point code associated with the remote 
	 SCCP.  The state is altered based on MTP-PAUSE and MTP-RESUME 
	 primitive received from the associated MTP layer."
    REFERENCE
	"ITU-T Rec. X.721 (1992) | ISO/IEC 10165-2 : 1992, 
	     Attribute-ASN1Module.OperationalState.
	 ITU-T Rec. X.731 (1992) | ISO/IEC 10164-2 : 1993, 
	     Section 8.1.1.1.
	 ITU-T Rec. Q.751.1 (1997), ANSI T1.116.1 (2000), 
	     operationalState attribute."
    ::= { sccpMtpEntry 9 }

sccpMtpCongestedState OBJECT-TYPE
    SYNTAX MtpCongestedState
    MAX-ACCESS read-only
    STATUS current
    DESCRIPTION
	"This attribute is used to reflect MTP congestion toward the 
	 remote SCCP, when multiple congestion levels are not used.  Its 
	 value is:
	 
	 - congested(1) in case of MTP congestion, and
	 - notCongested(0) otherwise.
	 
	 Its value is changed by the local SCCP upon receipt of 
	 MTP-STATUS primitives indicating congestion toward the remote 
	 SCPC.  Note that the remote SCCP can be administratively locked 
	 and still congested."
    REFERENCE
	"ITU-T Rec. Q.751.1 (1997), ANSI T1.116.1 (2000), congestedState 
	     attribute."
    ::= { sccpMtpEntry 10 }

sccpMtpCongestionLevel OBJECT-TYPE
    SYNTAX MtpCongestionLevel
    MAX-ACCESS read-only
    STATUS current
    DESCRIPTION
	"This attribute is used to reflect MTP congestion toward the 
	 remote SCCP, when multiple congestion levels are used.  Its 
	 value is:
	 
	 - none(0), no congestion exists toward the remote SCCP;
	 
	 - congestionlevel1(1), congestion exists at level 1 toward the 
	   remote SCCP;
	 
	 - congestionlevel2(2), congestion exists at level 2 toward the 
	   remote SCCP;
	 
	 - congestionlevel3(3), congestion exists at level 3 toward the 
	   remote SCCP.
	 
	 Its value is changed by the local SCCP upon receipt of 
	 MTP-STATUS primitives indicating congestion toward the remote 
	 SPC.  Note that the remote SCCP can be administratively locked 
	 and still congested."
    REFERENCE
	"ITU-T Rec. Q.751.1 (1997), ANSI T1.116.1 (2000), congestedState 
	     attribute."
    ::= { sccpMtpEntry 11 }

sccpMtpRemoteExchangeLabel OBJECT-TYPE
    SYNTAX CommonLanguageName
    MAX-ACCESS read-create
    STATUS current
    DESCRIPTION
	"Provides an optional administrative name for the remote SCCP.  
	 It is typical to name remote SCCP using the common language 
	 name of the managed switching element at which the remote SCCP  
	 exists (e.g. EDTNAB01DS1)."
    REFERENCE
	"ITU-T Rec. Q.751.1 (1997), ANSI T1.116.1 (2000), 
	     signRouteSetNePartName attribute."
    ::= { sccpMtpEntry 12 }

sccpMtpName OBJECT-TYPE
    SYNTAX SimpleNameType
    MAX-ACCESS read-create
    STATUS current
    DESCRIPTION
	"Provides an additional administrative name for the remote MTP 
	 access point.  This name also identifies a remote SCCP; its 
	 value is unique within the sccpMtpTable.  If at creation time 
	 the value of this attribute given for the sccpMtpEntry to be 
	 created already exists in another sccpMtpEntry, then the 
	 creation is rejected."
    REFERENCE
	"ITU-T Rec. Q.751.1 (1997), ANSI T1.116.1 (2000),
	     mtpAccessPointName attibute."
    ::= { sccpMtpEntry 13 }

sccpMtpRowStatus OBJECT-TYPE
    SYNTAX RowStatus
    MAX-ACCESS read-create
    STATUS current
    DESCRIPTION
	"Provides a mechanism whereby management stations may create and 
	 delete entries in this table.  Rows may also be created and 
	 deleted by the managed system as a part of system operation.
	 
	 If the name package is supported: a create request with a value 
	 for the name attribute that is already used by another instance 
	 of the same object class will be rejected."
    REFERENCE
	"STD 58, SNMPv2-TC RowStatus.
	 ITU-T Rec. Q.751.1 (1997) : mtpSignPoint-mtpAccessPoint NAME 
	     BINDING."
    ::= { sccpMtpEntry 14 }

-- =====================================================================

sccpSclcTable OBJECT-TYPE
    SYNTAX SEQUENCE OF SccpSclcEntry
    MAX-ACCESS not-accessible
    STATUS current
    DESCRIPTION
	"This managed object class contains the management information 
	 concerning the SCCP connectionless services.  The managed 
	 object class is derived from ITU-T Rec. X.283 | ISO/IEC 10733 
	 cLNS.
	 
	 The following states of the administrative state are 
	 appropriate: locked and unlocked.
	 
	 The operationalSystem Type attribute is an attribute with 
	 possible values: End System (ES) indicates an ScCP destination 
	 node, Intermediate System (IS) indicates an SCCP relay node.  
	 If the operationalSystemType equals 'Destination Node' it 
	 indicates that the system shall perform no forwarding 
	 operations upon non-local SCCP messages.  A value of 
	 'Intermediate Node' indicates that the system is permitted to 
	 perform forwarding operations, but the decision to forward 
	 individual SCCP messages or not to forward them, shall be taken 
	 on the basis of the available routing information.
	 
	 If the managed object is created by management operation, the 
	 initial value of the operationalSystemType shall be specified 
	 in the CMIP create.  Otherwise, the value shall be determined 
	 in an implementation specific manner.  The value shall be one 
	 of those present in the systemTypes attribute of the superior 
	 SCCP managed object.
	 
	 The set of connectionless network protocols supported by this 
	 instance of the sclc protocol machine is represented by the 
	 supportedProtocols attribute.  For the connectionless protocol, 
	 it can be either class 0 or 1, or both."
    REFERENCE
	""
    ::= { sccpSclc 1 }

sccpSclcEntry OBJECT-TYPE
    SYNTAX SccpSclcEntry
    MAX-ACCESS not-accessible
    STATUS current
    DESCRIPTION
	""
    REFERENCE
	""
    INDEX   {
	    mtpMsId,		 -- shared index
	    sccpNetworkEntityId	 -- shared index
	}
    ::= { sccpSclcTable 1 }

SccpSclcEntry ::=
    SEQUENCE {
	sccpSclcAlarmStatus			AlarmStatus,
	-- clProtocolMachine attributes
	sccpSclcClProtocolMachineId		SimpleNameType,
	sccpSclcOperationalState		OperationalState,
	sccpSclcTotalRemoteSAPs			INTEGER,
	-- cLNS attributes
	sccpSclcAdministrativeState		AdministrativeState,
	sccpSclcSupportedProtocols		OperationalProtocols,
	sccpSclcOperationalSystemType		NEntitySystemType,
	-- sclc attributes
	sccpSclcInitialValueReassTimer		TimeInterval,
	sccpSclcAsaProfilePointer		RowPointer,
	sccpSclcName				CommonLanguageName,
	sccpSclcRowStatus			RowStatus
    }

sccpSclcAlarmStatus OBJECT-TYPE
    SYNTAX AlarmStatus
    MAX-ACCESS read-create
    STATUS current
    DESCRIPTION
	"Provides the alarm status, following the AlarmStatus textual 
	 convention of the OPENSS7-SMI-MIB module, of the SCCP SCLC 
	 corresponding to the conceptual row in which the status occurs.  
	 This managed object generates the folowing alarms:
	 
	 The qualityofServiceAlarm can have the following probable 
	 causes:
	 
	 - ProbableCause = reassemblyTimeOut which represents 
	   measurement Q.752/7.10 (PerceivedSeverty = 
	   Major/Minor/Warning),
	 
	 - ProbableCause = segmentOutOfOrder which represents 
	   measurement Q.752/7.11 (PerceivedSeverity = 
	   Major/Minor/Warning),
	 
	 - ProbableCause = noReassemblySpace which represents 
	   measurement Q.752/7.12 (PerceivedSeverity = 
	   Major/Minor/Warning),
	 
	 - ProbableCause = noSegmentationSupport which represents 
	   measurement Q.752/7.19 (PerceivedSeverity = 
	   Major/Minor/Warning),
	 
	 - ProbableCause = segmentationFailure which represents 
	   measurement Q.752/7.20 (PerceivedSeverity = 
	   Major/Minor/Warning),
	 
	 - ProbableCause = reassemblyFailure which represents 
	   measurement Q.752/7.21 (PerceivedSeverity = 
	   Major/Minor/Warning)."
    REFERENCE
	"ITU-T Rec. X.731 (1993) : 8.1.2.1,
	 ITU-T Rec. X.721 (1992) : ISO/IEC 10165-2 : 1992, alarmStatus 
	     attribute."
    ::= { sccpSclcEntry 1 }

sccpSclcClProtocolMachineId OBJECT-TYPE
    SYNTAX SimpleNameType
    MAX-ACCESS read-create
    STATUS current
    DESCRIPTION
	"Provides an identifier for the base clProtocolMachine managed 
	 object represented by the conceptual row.  This value is not 
	 used as an index because there is a one-to-one relationship 
	 between SCCP (network entities) and SCLC (clProtocolMachine)."
    REFERENCE
	"ITU-T Rec. X.723 | ISO/IEC 10165-5 clProtocolMachineId."
    ::= { sccpSclcEntry 2 }

sccpSclcOperationalState OBJECT-TYPE
    SYNTAX OperationalState
    MAX-ACCESS read-only
    STATUS current
    DESCRIPTION
	""
    REFERENCE
	""
    DEFVAL { disabled }
    ::= { sccpSclcEntry 3 }

sccpSclcTotalRemoteSAPs OBJECT-TYPE
    SYNTAX INTEGER
    MAX-ACCESS read-only
    STATUS current
    DESCRIPTION
	""
    REFERENCE
	""
    ::= { sccpSclcEntry 4 }

-- cLNS attributes
sccpSclcAdministrativeState OBJECT-TYPE
    SYNTAX AdministrativeState
    MAX-ACCESS read-create
    STATUS current
    DESCRIPTION
	"
	 The following states of the administrative state are 
	 appropriate: locked and unlocked.
	"
    REFERENCE
	"ITU-T Rec. X.721 (1992) | ISO/IEC 10165-2 : 1992, 
	     administrativeState attribute."
    DEFVAL { locked }
    ::= { sccpSclcEntry 5 }

sccpSclcSupportedProtocols OBJECT-TYPE
    SYNTAX OperationalProtocols
    MAX-ACCESS read-only
    STATUS current
    DESCRIPTION
	"The set of Connectionless Network protocols upported by this 
	 instancse of the cLNS protocol machine, expressed except where 
	 otherwise indicated (for example because there are more than 
	 one protocol described in a single International Standard) as 
	 the registered object identifiers of the relevant International 
	 Standard.  The operation of a particular protocol over a 
	 particular linkage is determined by the linkage 
	 operationalProtocols attribute.  The value of the 
	 supportedProtocols attribute is determined by the 
	 implementation.
	 
	 The set of connectionless network protocols supported by this 
	 instance of the sclc protocol machine is represented by the 
	 supportedProtocols attribute.  For the connectionless protocol, 
	 it can be either class 0 or 1, or both."
    REFERENCE
	""
    ::= { sccpSclcEntry 6 }

sccpSclcOperationalSystemType OBJECT-TYPE
    SYNTAX NEntitySystemType
    MAX-ACCESS read-create
    STATUS current
    DESCRIPTION
	"The system role in which this instance is operating.  A value 
	 of ES indicates taht the system shall perform no forawarding 
	 operations upon non-local PDUs.  A value of IS indicates that 
	 the system is permitted to perform forwarding operations, but 
	 the decision to forward individual PDUs, or not to forward 
	 them, shall be taken on the basis of the available routing 
	 information.
	 
	 The operationalSystem Type attribute is an attribute with 
	 possible values: End System (ES) indicates an ScCP destination 
	 node, Intermediate System (IS) indicates an SCCP relay node.  
	 If the operationalSystemType euals 'Destination Node' it 
	 indicates that the system shall perform no forwarding 
	 operations upon non-local SCCP messages.  A value of 
	 'Intermediate Node' indicates that the system is permitted to 
	 perform forwarding operations, but the decision to forward 
	 individual SCCP messages or not to forward them, shall be taken 
	 on the basis of the available routing information."
    REFERENCE
	""
    ::= { sccpSclcEntry 7 }

-- sclc attributes
sccpSclcInitialValueReassTimer OBJECT-TYPE
    SYNTAX TimeInterval
    UNITS       "seconds"
    MAX-ACCESS read-create
    STATUS current
    DESCRIPTION
	"This attribute represents the initial value of Reassembly 
	 Timers, when they are created."
    REFERENCE
	"ITU-T Rec. Q.751.2 initialValueReassTimer."
    ::= { sccpSclcEntry 8 }

sccpSclcAsaProfilePointer OBJECT-TYPE
    SYNTAX RowPointer
    MAX-ACCESS read-create
    STATUS current
    DESCRIPTION
	"Provides a pointer to an alarm severity assignment profile to 
	 be used for alarms generated by this SCCP connectionless 
	 protocol state machine, or zeroDotZero."
    REFERENCE
	"ITU-T Rec. Q.751.2 (1997), ANSI T1.116.1 (2000), 
	     alarmSeverityAssignmentProfilePointer attribute.
	 ITU-T Rec. M.3100 (1995), 
	     alarmSeverityAssignmentProfilePointer.
	 ITU-T Rec. M.3100 (1995), ASN1DefinedTypesModule:PointerOrNull."
    DEFVAL { { zeroDotZero } }
    ::= { sccpSclcEntry 9 }

sccpSclcName OBJECT-TYPE
    SYNTAX CommonLanguageName
    MAX-ACCESS read-create
    STATUS current
    DESCRIPTION
	""
    REFERENCE
	""
    ::= { sccpSclcEntry 10 }

sccpSclcRowStatus OBJECT-TYPE
    SYNTAX RowStatus
    MAX-ACCESS read-create
    STATUS current
    DESCRIPTION
	"If the managed object is created by management operation, the 
	 initial value of the operationalSystemType shall be specified 
	 in the CMIP create.  Otherwise, the value shall be determined 
	 in an implementation specific manner.  The value shall be one 
	 of those present in the systemTypes attribute of the superior 
	 SCCP managed object."
    REFERENCE
	""
    ::= { sccpSclcEntry 11 }

-- =====================================================================

sccpScocTable OBJECT-TYPE
    SYNTAX SEQUENCE OF SccpScocEntry
    MAX-ACCESS not-accessible
    STATUS current
    DESCRIPTION
	"This table contains instances of SCOC protocol machines.  The 
	 SCOC is analogue to the CONS protocol machine and is a 
	 coProtocolMachine.  There can only be one entry for each SCCP 
	 (network entity) and the table is indexed by 
	 sccpNetworkEntityId."
    REFERENCE
	"ITU-T Rec. Q.751.2 scoc MO."
    ::= { sccpScoc 1 }

sccpScocEntry OBJECT-TYPE
    SYNTAX SccpScocEntry
    MAX-ACCESS not-accessible
    STATUS current
    DESCRIPTION
	"If a conceptual row is created by management operation, the 
	 initial value of the operationalSystemType shall be specified 
	 in the CMIP create.  Otherwise, the value shall be determined 
	 in an implementation specific manner.  The value shall be one 
	 of those present in the systemTypes attribute of the superior 
	 SCCP managed object.
	 
	 There can only be one SCOC per SCCP (network entity) and the 
	 table is indexed by sccpNetworkEntityId to reflect that 
	 one-to-one relationship."
    REFERENCE
	"ITU-T Rec. Q.751.2 scoc MO."
    INDEX   {
	    mtpMsId,		 -- shared index
	    sccpNetworkEntityId	 -- shared index
	}
    ::= { sccpScocTable 1 }

SccpScocEntry ::=
    SEQUENCE {
	-- coProtocolMachine attributes
	sccpScocCoProtocolMachineId		SimpleNameType,
	sccpScocOperationalState		OperationalState,
	sccpScocAdministrativeState		AdministrativeState,
	sccpScocOperationalSystemType		NEntitySystemType,
	sccpScocSupportedProtocols		OperationalProtocols,
	sccpScocName				CommonLanguageName,
	sccpScocRowStatus			RowStatus
    }

sccpScocCoProtocolMachineId OBJECT-TYPE
    SYNTAX SimpleNameType
    MAX-ACCESS read-create
    STATUS current
    DESCRIPTION
	"Provides an identifier for the base coProtocolMachine managed 
	 object represented by the conceptual row.  This value is not 
	 used as an index because there is a one-to-one relationship 
	 between SCCP (network entities) and SCOC (coProtocolMachine)."
    REFERENCE
	"ITU-T Rec. X.723 | ISO/IEC 10165-5 coProtocolMachineId."
    ::= { sccpScocEntry 1 }

sccpScocOperationalState OBJECT-TYPE
    SYNTAX OperationalState
    MAX-ACCESS read-only
    STATUS current
    DESCRIPTION
	"Provides the operational state of the object represented by 
	 this conceptual row following the OperationalState textual 
	 convention from OPENSS7-SMI-MIB.  The operational state has 
	 value disabled when the SCOC is totally inoperable and unable 
	 to provide service to users; enabled when the SCOC is partially 
	 or fully operable and available for use."
    REFERENCE
	"ITU-T Rec. X.721 | ISO/IEC 10165-2 operationalState."
    DEFVAL { disabled }
    ::= { sccpScocEntry 2 }

sccpScocAdministrativeState OBJECT-TYPE
    SYNTAX AdministrativeState
    MAX-ACCESS read-create
    STATUS current
    DESCRIPTION
	"Provides the administative state of the object represented by 
	 this conceptual row following the OperationalState textual 
	 convention of OPENSS7-SMI-MIB.  The following states of the 
	 administrative state are appropriate: locked and unlocked.  
	 When locked, the SCOC is administratively prohibited from 
	 providing service to its users; when unlocked, the SCOC is 
	 administratively permitted to perform services for its users; 
	 when shutting down, use of SCOC is adminitratively permitted to 
	 the extent that existing uses of the SCOC are allowed but new 
	 instances of use will be refused."
    REFERENCE
	"ITU-T Rec. X.721 (1992) | ISO/IEC 10165-2 : 1992, 
	     administrativeState attribute."
    DEFVAL { locked }
    ::= { sccpScocEntry 3 }

sccpScocOperationalSystemType OBJECT-TYPE
    SYNTAX NEntitySystemType
    MAX-ACCESS read-create
    STATUS current
    DESCRIPTION
	"The operationalSystemType attribute is borrowed from X.283 and 
	 is an attribute with possible values: End System (ES) indicates 
	 an SCCP destination node, Intermediate System (IS) indicates an 
	 SCCP relay node.  The operationalSystemType indicates the 
	 system role in which the instance is operating.   A value of 
	 'Destination Node' indicates that the system shall perform no 
	 forwarding operations upon non-local SCCP messages.  A value of 
	 Intermediate Node indicates that the system is permitted to 
	 perform forwarding operations, but the decision to forward 
	 invividual SCCP messages or not to forward them, shall be taken 
	 on the basis of the available routing information."
    REFERENCE
	"ITU-T Rec. Q.751.2, ITU-T Rec. X.283 | ISO/IEC 10733 
	 operationalSystemType."
    ::= { sccpScocEntry 4 }

sccpScocSupportedProtocols OBJECT-TYPE
    SYNTAX OperationalProtocols
    MAX-ACCESS read-only
    STATUS current
    DESCRIPTION
	"The set of connection-oriented network protocols supported by 
	 this instance of the scoc protocol machine is represented by 
	 the supportedProtocols attribute.  For the connection-oriented 
	 protocol, it can either be class 2 or 3, or both.
	 This is a read-only value which reflects the capabilities of 
	 the underlying implementation.
	 
	 Under the TMN, this attribute is a complex set valued attribute 
	 that contains a protocol OBJECT IDENTIFIER followed by an 
	 optional version number and updates applied filed for each 
	 protocol identifier.  For SCCP the version number and updates 
	 applies is not used and four object identifiers are defined by 
	 Q.751.2 for protocol classes 0, 1, 2 and 3.  In SNMP we define 
	 the OperationalProtocols textual convention as the only set 
	 valued SNMP construct (BITS), and define class0(0), class1(1), 
	 class(2) and class3(3) values for it."
    REFERENCE
	"ITU-T Rec. Q.751.2, ITU-T Rec. X.283 | ISO/IEC 10733 
	     supportedProtocols."
    ::= { sccpScocEntry 5 }

sccpScocName OBJECT-TYPE
    SYNTAX CommonLanguageName
    MAX-ACCESS read-create
    STATUS current
    DESCRIPTION
	"Provides a optional name for the SCOC.  When not used, this 
	 value is set to and defaults to a null string."
    REFERENCE
	"ITU-T Rec. Q.751.2 scocName."
    DEFVAL { }
    ::= { sccpScocEntry 6 }

sccpScocRowStatus OBJECT-TYPE
    SYNTAX RowStatus
    MAX-ACCESS read-create
    STATUS current
    DESCRIPTION
	"If the MO is created by management operation, the inital value 
	 of the operationalSystemType shall be specified in the CMIP 
	 create.  Otherwise, the value shall be determined in an 
	 implementation specific manner.  The value shall be one of 
	 those present in the sytemTypes attribute of the superior 
	 sccpNetworkEntityTable entry."
    REFERENCE
	"STD 58, SNMPv2-TC RowStatus."
    ::= { sccpScocEntry 7 }

-- =====================================================================

sccpScrcTable OBJECT-TYPE
    SYNTAX SEQUENCE OF SccpScrcEntry
    MAX-ACCESS not-accessible
    STATUS current
    DESCRIPTION
	"The scrc managed object class contains the management 
	 information concerning the SCCP routing control (SCRC).  One 
	 SCRC protocol machine managed object exists for each SCCP 
	 (network entity)."
    REFERENCE
	"ITU-T Rec. Q.751.2 scrc MO."
    ::= { sccpScrc 1 }

sccpScrcEntry OBJECT-TYPE
    SYNTAX SccpScrcEntry
    MAX-ACCESS not-accessible
    STATUS current
    DESCRIPTION
	"Entries in this table can generate qualityofSerivceAlarm 
	 notifications which are detailed under the sccpScrcAlarmStatus 
	 column, below.  Although an sccpScrcRowStatus column is 
	 provided, entries in this table are not normally created by 
	 management stations, and are instead created by system 
	 operation when SCCP network entities are created.  It is not 
	 necessary for implementations to permit management stations to 
	 create entries in this table."
    REFERENCE
	"ITU-T Rec. Q.751.2 scrc MO."
    INDEX   {
	    mtpMsId,		 -- shared index
	    sccpNetworkEntityId	 -- shared index
	}
    ::= { sccpScrcTable 1 }

SccpScrcEntry ::=
    SEQUENCE {
	sccpScrcId				SimpleNameType,
	sccpScrcAlarmStatus			AlarmStatus,
	sccpScrcAsaProfilePointer		RowPointer,
	sccpScrcName				CommonLanguageName,
	sccpScrcRowStatus			RowStatus
    }

sccpScrcId OBJECT-TYPE
    SYNTAX SimpleNameType
    MAX-ACCESS read-create
    STATUS current
    DESCRIPTION
	"This attribute is used for naming instances.  Because there is 
	 a one-to-one relationship between SCCP (network entity) and a 
	 contained SCRC (SCCP routing control protocol machine), this 
	 attribute is not an index."
    REFERENCE
	"ITU-T Rec. Q.751.2 scrcId."
    DEFVAL { }
    ::= { sccpScrcEntry 1 }

sccpScrcAlarmStatus OBJECT-TYPE
    SYNTAX AlarmStatus
    MAX-ACCESS read-create
    STATUS current
    DESCRIPTION
	"Provides the alarm status, following the AlarmStatus textual 
	 convention of the OPENSS7-SMI-MIB module, of the SCRC protocol 
	 machine corresponding to the conceptual row in which this 
	 status occurs.  This managed object generates the following 
	 alarms:
	 
	 The qualityofServiceAlarm can have the following probably 
	 causes:
	 
	 - ProbableCause = noTranslatorForAddress which represents 
	   measurement Q.752/7.1 (PerceivedSeverity = 
	   Major/Minor/Warning),
	 
	 - ProbableCause = noRuleForAddress which represents measurement 
	   Q.752/7.2 (PerceivedSeverity = Major/Minor/Warning),
	 
	 - ProbableCause = pointCodeNotAvailable which represents 
	   measurement Q.752/7.3 (PerceivedSeverity = 
	   Major/Minor/Warning),
	 
	 - ProbableCause = pointCodeCongested which represents 
	   measurement Q.752/7.4 (PerceivedSeverity = 
	   Major/Minor/Warning),
	 
	 - ProbableCause = subsystemUnavailable which represents 
	   measurement Q.752/7.5 (PerceivedSeverity = 
	   Major/Minor/Warning),
	 
	 - ProbableCause = subsystemCongested which represents 
	   measurement Q.752/7.6 (PerceivedSeverity = 
	   Major/Minor/Warning),
	 
	 - ProbableCause = unequippedSubsystem which represents 
	   measurement Q.752/7.7 (PerceivedSeverity = 
	   Major/Minor/Warning),
	 
	 - ProbableCause = syntaxErrorDetected which represents 
	   measurement Q.752/7.8 (PerceivedSeverity = 
	   Major/Minor/Warning),
	 
	 - ProbableCause = routingFailureNoReasonOrUnqualified which 
	   represents measurement Q.752/7.9 (PerceivedSeverity = 
	   Major/Minor/Warning), and
	 
	 - ProbableCause = hopCounterViolation which represents 
	   measurement Q.752/7.13 (PerceivedSeverity = 
	   Major/Minor/Warning)."
    REFERENCE
	"ITU-T Rec. X.731 (1993) : 8.1.2.1,
	 ITU-T Rec. X.721 (1992) : ISO/IEC 10165-2 : 1992, alarmStatus 
	     attribute."
    DEFVAL { } -- '0000'B
    ::= { sccpScrcEntry 2 }

sccpScrcAsaProfilePointer OBJECT-TYPE
    SYNTAX RowPointer
    MAX-ACCESS read-create
    STATUS current
    DESCRIPTION
	"Provides a pointer to an alarm severity assignment profile to 
	 be used for alarms generated by this SCCP routing control state 
	 machine, or zeroDotZero."
    REFERENCE
	"ITU-T Rec. Q.751.2 (1997), ANSI T1.116.1 (2000), 
	     alarmSeverityAssignmentProfilePointer attribute.
	 ITU-T Rec. M.3100 (1995), 
	     alarmSeverityAssignmentProfilePointer.
	 ITU-T Rec. M.3100 (1995), ASN1DefinedTypesModule:PointerOrNull."
    DEFVAL { { zeroDotZero } }
    ::= { sccpScrcEntry 3 }

sccpScrcName OBJECT-TYPE
    SYNTAX CommonLanguageName
    MAX-ACCESS read-create
    STATUS current
    DESCRIPTION
	"Provides the optional ability to associate a name with the the 
	 conceptual row following the CommonLanguageName textual 
	 convention.  When unused, this attribute is a null string."
    REFERENCE
	"ITU-T Rec. Q.751.2 scrcName."
    DEFVAL { }
    ::= { sccpScrcEntry 4 }

sccpScrcRowStatus OBJECT-TYPE
    SYNTAX RowStatus
    MAX-ACCESS read-create
    STATUS current
    DESCRIPTION
	"Provides a means, following the RowStatus textual convention, 
	 for management stations to create or destroy conceptul rows 
	 corresponding to SCRC protocol machine instances in this 
	 table."
    REFERENCE
	"STD 58, SNMPv2-TC RowStatus"
    ::= { sccpScrcEntry 5 }

-- =====================================================================

sccpEntitySetTable OBJECT-TYPE
    SYNTAX SEQUENCE OF SccpEntitySetEntry
    MAX-ACCESS not-accessible
    STATUS current
    DESCRIPTION
	""
    REFERENCE
	""
    ::= { sccpEntitySet 1 }

sccpEntitySetEntry OBJECT-TYPE
    SYNTAX SccpEntitySetEntry
    MAX-ACCESS not-accessible
    STATUS current
    DESCRIPTION
	"An Entity Set is a group of redundant set of SCCP subsystems of 
	 the same Subsystem Identifier (SSN) belonging to separate SCCP 
	 entities.  The entity set describes a set of redundant 
	 subsystems over which a redundancy algorithm (load sharing 
	 mechanism) is described.  An SCCP Entity Set can be the target 
	 of a Global Title Translation, in which case, the SCCP 
	 distributes message traffic over the members of the entity set 
	 depending upon their availability and service state.
	 
	 Note that an specific Entity Set belongs to an SCRC (protocol 
	 machine) which also belongs to a SCCP (network entity).  
	 Because there is a one-to-one relationship between an SCCP 
	 (network entity) and an SCRC (protocol machine), the 
	 sccpNetworkEntityId is sufficient to identify both, and it is 
	 used as the shared index of this table."
    REFERENCE
	""
    INDEX   {
	    mtpMsId,		 -- shared index
	    sccpNetworkEntityId, -- shared index
	    sccpEntitySetId	 -- index
	}
    ::= { sccpEntitySetTable 1 }

SccpEntitySetEntry ::=
    SEQUENCE {
	sccpEntitySetId				SimpleNameType,
	sccpEntitySetSharingMode		SharingMode,
	sccpEntitySetLoadSharingAlgPointer	AutonomousType,
	sccpEntitySetName			CommonLanguageName,
	sccpEntitySetType			INTEGER,
	sccpEntitySetSsn			SubSystemNumber,
	sccpEntitySetRowStatus			RowStatus
    }

sccpEntitySetId OBJECT-TYPE
    SYNTAX SimpleNameType
    MAX-ACCESS not-accessible
    STATUS current
    DESCRIPTION
	"Provides an identifier for use in naming the conceptual row of 
	 the sccpEntitySetTable table."
    REFERENCE
	"ITU-T Rec. Q.751.2 entitySetId."
    ::= { sccpEntitySetEntry 1 }

sccpEntitySetSharingMode OBJECT-TYPE
    SYNTAX SharingMode
    MAX-ACCESS read-create
    STATUS current
    DESCRIPTION
	"This attribute models the sharing mode of the SCCP Entity Set.  
	 Possible values are:
	 
	 - solitary, an entity set consisting of a solitary subsystem to 
	   which all traffic is offered;
	 
	 - duplicated-replacement, a duplicated entity set that contains 
	   two redundant subsystems;
	 
	 - duplicated-dominant, a duplicated entity set that contains 
	   two redundant subsystems of which one is dominant and the 
	   other is passive; and,
	 
	 - duplicated-loadshared, a duplicated entity set that contains 
	   two redundant subsystems over both of which message traffic 
	   is loadshared."
    REFERENCE
	"ITU-T Rec. Q.751.2 sharingMode."
    ::= { sccpEntitySetEntry 2 }

sccpEntitySetLoadSharingAlgPointer OBJECT-TYPE
    SYNTAX AutonomousType
    MAX-ACCESS read-create
    STATUS current
    DESCRIPTION
	"Provides a specification of a load sharing algorithm using the 
	 AutonomousType texutual convention.  This can be a defined 
	 value.  Several load sharing algorithms are defined by this 
	 MIB: sccpLoadSharingRoundRobin and sccpLoadSharingSlsSplitting 
	 object identities defined for this MIB (above).  Management 
	 agents are permitted to recognize more than the set of 
	 algorithms defined here.
	 
	 - sccpLoadSharingRoundRobin, the first message is sent to the 
	   first entity in the set, the second message is sent to the 
	   second entity in the set, the third message is sent to the 
	   first entity in the set, and so on.
	 
	 - sccpLoadSharingSlsSplitting, the entity in the entity set is 
	   selected using a significant bit in the SLS (Signalling Link 
	   Selection) contained in the MTP portion of the message.
	 
	 The sccpEntitySetLoadSharingAlgPointer is only significant when 
	 the sccpEntitySetSharingMode is set to duplicated-loadshared."
    REFERENCE
	"ITU-T Rec. Q.751.2 loadSharingAlgPointer."
    ::= { sccpEntitySetEntry 3 }

sccpEntitySetName OBJECT-TYPE
    SYNTAX CommonLanguageName
    MAX-ACCESS read-create
    STATUS current
    DESCRIPTION
	"Provides an optional name for the entity set represented by 
	 this conceptual row.  When unused (the default), this value 
	 should be set to a null string."
    REFERENCE
	"ITU-T Rec. Q.751.2 entitySetName."
    DEFVAL { }
    ::= { sccpEntitySetEntry 4 }

sccpEntitySetType OBJECT-TYPE
    SYNTAX INTEGER {
		endNodeEntitySetWithoutSSN(2),
		endNodeEntitySetWithSSN(3),
		relayNodeEntitySet(7)
	    }
    MAX-ACCESS read-create
    STATUS current
    DESCRIPTION
	"These type are represented by derivation in TNM, however, here 
	 they are respresented by this attribute and one other.  The 
	 values are as follows:
	 
	 - endNodeEntitySetWithoutSSN(2): This maanged object class is 
	   an sccpEntitySet that indentifies SCCP end nodes.  Because of 
	   this, the entitySetSapPointer attribute is only allowed to 
	   refer to instances of the sccpLinkage class.  A subsystem 
	   number is not specified by this entity set, but routing is on 
	   SSN.
	 
	 - endNodeEntitySetWithSSN(3): This managed object class is an 
	   sccpEntitySet that identifies SCCP Access Points.  Because of 
	   this, the SAP pointer attribute is only allowed to refer to 
	   instances of the sccpAccessPoint class.
	 
	 - relayNodeEntitySet(7): This managed object class is a 
	   sccpEntitySet that identifies SCCP relay nodes, i.e.  MTP 
	   Access Points.  Because of this, the entitySetSapPointer 
	   attribute is only allowed to refer to instances of the 
	   sccpLinkage class.  The ssn attribtute allows to optionally 
	   set the subsystem number as a result of a Global Title 
	   Translation, if routing is done on Global Title and DPC to a 
	   relay node."
    REFERENCE
	"ITU-T Rec. Q.751"
    ::= { sccpEntitySetEntry 5 }

sccpEntitySetSsn OBJECT-TYPE
    SYNTAX SubSystemNumber
    MAX-ACCESS read-create
    STATUS current
    DESCRIPTION
	"Provides an optional subsystem number when the entity set type 
	 is relayNodeEntitySet(7).  Otherwise, the value is ignored."
    DEFVAL { 0 }
    REFERENCE
	"ITU-T Rec. Q.751.2 ssn ATTRIBUTE."
    ::= { sccpEntitySetEntry 6 }


sccpEntitySetRowStatus OBJECT-TYPE
    SYNTAX RowStatus
    MAX-ACCESS read-create
    STATUS current
    DESCRIPTION
	"Provides a mechanism by what of which management stations, 
	 using the RowStatus textual convention can create or destroy 
	 conceptual rows in this table.  When entity sets are created in 
	 this fashion, they are created empty in that there are no 
	 entities contained in the sccpEnttySetSapTable corresndpoing to 
	 the same index as the sccpENtitySetId values for the created 
	 conceptual row.  Also, before entries can be destroyned, all of 
	 the entits within the entity set (those that appear in the 
	 sccpEntitySetSapTable with the same value of the 
	 sccpEntitySetId index) must be destroyed first."
    REFERENCE
	"STD 58, SNMPv2-TC RowStatus."
    ::= { sccpEntitySetEntry 7 }

-- SAP side-table for entity set

sccpEntitySetSapTable OBJECT-TYPE
    SYNTAX SEQUENCE OF SccpEntitySetSapEntry
    MAX-ACCESS not-accessible
    STATUS current
    DESCRIPTION
	"This side-table provides a list of SAP types and pointers for 
	 each SAP contained in the entity set.  Up to two SAPs can occur 
	 per entity set.  Before entires are created in this subtable an 
	 entry for the corresponding sccpEntitySetId must already exist 
	 in the sccpEntitySetTable.  Before entries are destroyed in the 
	 sccpEntitySetTable, all entries for the coresponding 
	 sccpEntitySetId in this table must first be destroyed."
    REFERENCE
	""
    ::= { sccpEntitySet 2 }

sccpEntitySetSapEntry OBJECT-TYPE
    SYNTAX SccpEntitySetSapEntry
    MAX-ACCESS not-accessible
    STATUS current
    DESCRIPTION
	""
    REFERENCE
	""
    INDEX   {
	    mtpMsId,		 -- shared index
	    sccpNetworkEntityId, -- shared index
	    sccpEntitySetId,	 -- shared index
	    sccpEntitySetSapId	 -- index
	}
    ::= { sccpEntitySetSapTable 1 }

SccpEntitySetSapEntry ::=
    SEQUENCE {
	sccpEntitySetSapId			SimpleNameType, --index
	sccpEntitySetSapType			PrimaryOrBackup,
	sccpEntitySetSapPointer			RowPointer,
	sccpEntitySetSapRowStatus		RowStatus
    }

sccpEntitySetSapId OBJECT-TYPE
    SYNTAX SimpleNameType
    MAX-ACCESS not-accessible
    STATUS current
    DESCRIPTION
	"Provides the index of the entity represented by the SAP within 
	 the entity set.  This is used as an index.  Not all entities or 
	 algorithms will support more than 2 entities in the entity set 
	 (Q.751.2 limits the entity set membership to 2).  Not all 
	 implementations will support more than one entity in an entity 
	 set.  All implementations will support one entity in the entity 
	 set."
    REFERENCE
	"ITU-T Rec. Q.751.2 ANS.1 EntitySetSapPointer."
    ::= { sccpEntitySetSapEntry 1 }

sccpEntitySetSapType OBJECT-TYPE
    SYNTAX PrimaryOrBackup
    MAX-ACCESS read-create
    STATUS current
    DESCRIPTION
	"Specifies the role of the entity corresponding to the SAP 
	 within the Entity Set.  The role can be equal(0), primary(1) or 
	 backup(2)."
    REFERENCE
	"ITU-T Rec. Q.751.2 entitSetSapPointer, ASN.1 PrimaryOrBackup."
    ::= { sccpEntitySetSapEntry 2 }

sccpEntitySetSapPointer OBJECT-TYPE
    --
    -- Because this pointer can point to an entry selected from one 
    -- of several tables, the index of any given table cannot be 
    -- used and the RowPointer textual convention is therefore 
    -- necessary.
    --
    SYNTAX RowPointer
    MAX-ACCESS read-create
    STATUS current
    DESCRIPTION
	"Provides a row pointer to an entry in the sccpAccesssPointTable 
	 table or in the sccpLinkageTable table that identifies the 
	 local or remote SAP (resp.) for the member of the entity set.  
	 When the type of the entity set is endNodeEntitySetWithoutSSN 
	 or relayNodeEntitySet, this column must point to an row of the 
	 sccpLinkageTable table.  When the type of the entity set is 
	 endNodeEntitySetWithSSN, this column must point to a rows in 
	 the sccpAccessPointTable table."
    REFERENCE
	"ITU-T Rec. Q.751.2 entitSetSapPointer, ASN.1 SAPPointer."
    ::= { sccpEntitySetSapEntry 3 }

sccpEntitySetSapRowStatus OBJECT-TYPE
    SYNTAX RowStatus
    MAX-ACCESS read-create
    STATUS current
    DESCRIPTION
	"Used by managements stations, according to the RowStatus 
	 textual convention, to create or destroy conceptual rows in 
	 this table.  Before a row may be created, the corresponding 
	 sccpEntitySetId must exist as a conceptual row"
    REFERENCE
	""
    ::= { sccpEntitySetSapEntry 4 }



-- =====================================================================

sccpConcernedAreaTable OBJECT-TYPE
    SYNTAX SEQUENCE OF SccpConcernedAreaEntry
    MAX-ACCESS not-accessible
    STATUS current
    DESCRIPTION
	"A concernedArea contains a list of remote SCCP's 
	 (mtpAccessPoints) to be informed of local (primary broadcast), 
	 or remote (secondary broadcast), SCCP subsystem changes, or to 
	 informed of the SCCP status after completion of SCCP Restart.  
	 The concernedArea may also optionally be used as an access 
	 control list for the local (end-system) or remote (intermediate 
	 system) SCCP subsystem."
    REFERENCE
	"ITU-T Rec. Q.751.2, ANSI T1.116.2 concernedArea."
    ::= { sccpConcernedArea 1 }

sccpConcernedAreaEntry OBJECT-TYPE
    SYNTAX SccpConcernedAreaEntry
    MAX-ACCESS not-accessible
    STATUS current
    DESCRIPTION
	"Rows may be added to this table.  Rows need to be added to the 
	 sccpRemoteSCCPTable to add remote SCCP to the concerned area.  
	 Rows removed from this table will remove all the rows 
	 corresponding to this index from the corresponding index 
	 entries in the sccpRemoteSCCPTable; that is, the concerned area 
	 will be emptied before it is deleted.  Concerned areas are 
	 specific to a SCRC protocol module and its associated SCCP 
	 network entity."
    REFERENCE
	"ITU-T Rec. Q.751.2, ANSI T1.116.2 concernedArea."
    INDEX   {
	    mtpMsId,		 -- shared index
	    sccpNetworkEntityId, -- shared index
	    sccpConcernedAreaId	 -- index
	}
    ::= { sccpConcernedAreaTable 1 }

SccpConcernedAreaEntry ::=
    SEQUENCE {
	sccpConcernedAreaId			SimpleNameType, -- index
	sccpConcernedAreaRemoteSCCPList		Unsigned32,
	sccpConcernedAreaRowStatus		RowStatus
    }

sccpConcernedAreaId OBJECT-TYPE
    SYNTAX SimpleNameType
    MAX-ACCESS not-accessible
    STATUS current
    DESCRIPTION
	"Provides the name of the concerned area following the 
	 SimpleNameType textual convention.  This is also a secondary 
	 index into the table."
    REFERENCE
	"ITU-T Rec. Q.751.2 concernedAreaId."
    ::= { sccpConcernedAreaEntry 1 }

sccpConcernedAreaRemoteSCCPList OBJECT-TYPE
    SYNTAX Unsigned32
    MAX-ACCESS read-only
    STATUS current
    DESCRIPTION
	"Provides the number of entries, corresponding to this concerned 
	 area index, in the corresponding indexed entries of the 
	 sccpRemoteSCCPTable."
    REFERENCE
	"ITU-T Rec. Q.751.2 remoteSCCPList."
    ::= { sccpConcernedAreaEntry 2 }

sccpConcernedAreaRowStatus OBJECT-TYPE
    SYNTAX RowStatus
    MAX-ACCESS read-create
    STATUS current
    DESCRIPTION
	"Provides a mechanism according to the RowStatus textual  
	 convention by which management stations may create and destroy 
	 entries in this table.  New entires are created empty: that is, 
	 they have no remote SCCP MTP-SAPs associated with them.  Before 
	 entries can be deleted, all remote MTP-SAPs will be removed by 
	 removing the corresponding entries in the sccpRemoteSCCPTable 
	 for the corresponding sccpNetworkEntityId and 
	 sccpConcernedAreaId indices."
    REFERENCE
	"STD 58, SNMPv2-TC RowStatus.
	 ITU-T Rec. Q.751.2 (1992): scrc-concernedArea NAME BINDING."
    ::= { sccpConcernedAreaEntry 3 }

-- remoteSCCPList side-table

sccpRemoteSCCPTable OBJECT-TYPE
    SYNTAX SEQUENCE OF SccpRemoteSCCPEntry
    MAX-ACCESS not-accessible
    STATUS current
    DESCRIPTION
	"This table is a side-table that provides a list of remote SCCP 
	 entitites that belong to a concerned area."
    REFERENCE
	"ITU-T Rec. Q.751.2 remoteSCCPList."
    ::= { sccpConcernedArea 2 }

sccpRemoteSCCPEntry OBJECT-TYPE
    SYNTAX SccpRemoteSCCPEntry
    MAX-ACCESS not-accessible
    STATUS current
    INDEX   {
	    mtpMsId,		 -- shared index
	    sccpNetworkEntityId, -- shared index
	    sccpConcernedAreaId, -- shared index
	    sccpRemoteSCCPId	 -- index
	}
    ::= { sccpRemoteSCCPTable 1 }

SccpRemoteSCCPEntry ::=
    SEQUENCE {
	sccpRemoteSCCPId			SimpleNameType, -- index
	sccpRemoteSCCPMTPAccessPoint		RowPointer,
	sccpRemoteSCCPName			CommonLanguageName,
	sccpRemoteSCCPRowStatus			RowStatus
    }

sccpRemoteSCCPId OBJECT-TYPE
    SYNTAX SimpleNameType
    MAX-ACCESS not-accessible
    STATUS current
    DESCRIPTION
	""
    REFERENCE
	""
    ::= { sccpRemoteSCCPEntry 1 }

sccpRemoteSCCPMTPAccessPoint OBJECT-TYPE
    SYNTAX RowPointer
    MAX-ACCESS read-create
    STATUS current
    DESCRIPTION
	"This attribute models a list of remote MTP Access Points all 
	 belonging to the same MTP network."
    REFERENCE
	""
    ::= { sccpRemoteSCCPEntry 2 }

sccpRemoteSCCPName OBJECT-TYPE
    SYNTAX CommonLanguageName
    MAX-ACCESS read-create
    STATUS current
    DESCRIPTION
	""
    REFERENCE
	""
    ::= { sccpRemoteSCCPEntry 3 }

sccpRemoteSCCPRowStatus OBJECT-TYPE
    SYNTAX RowStatus
    MAX-ACCESS read-create
    STATUS current
    DESCRIPTION
	"Provides a mechanism whereby management agents may create and 
	 delete conceptual rows from this table.  Conceptual rows in 
	 this table are persistent over agent reboots.  Adding a 
	 conceptual row to this table adds a remote SCCP entity to the 
	 concerned area and local SCCP network entity used as an index.  
	 Deleting a conceptual row from this table removes a remote SCCP 
	 entity from the concerned area and local SCCP network entity 
	 that was previously used as an index."
    REFERENCE
	""
    ::= { sccpRemoteSCCPEntry 4 }

-- =====================================================================

sccpGtConversionRuleTable OBJECT-TYPE
    SYNTAX SEQUENCE OF SccpGtConversionRuleEntry
    MAX-ACCESS not-accessible
    STATUS current
    DESCRIPTION
	"This table defines the rules that can be used to change the 
	 global title in a called party address.  The conversion can 
	 replace all parts of the global title with a new value.  If the 
	 addressInfoConversionRulePackage is present, it specifies how 
	 address elements can be inserted, replaced, passed 
	 transparently, or deleted from the (old) GTAI into a new GTAI.  
	 The procedures for Global Title Conversion are described in 
	 7.3/Q.715.  Only those parts of the GT information are modified 
	 that have a corresponding new value identified by entries in 
	 this table.  In case an attribute representing GT information 
	 is present, but is not used for converting Global Titles, it 
	 has value NULL.  As a result, the particular part of the Global 
	 Title will not be overwritten."
    REFERENCE
	"ITU-T Rec. Q.751.2 gtConversionRule."
    ::= { sccpGtConversionRule 1 }

sccpGtConversionRuleEntry OBJECT-TYPE
    SYNTAX SccpGtConversionRuleEntry
    MAX-ACCESS not-accessible
    STATUS current
    DESCRIPTION
	"GT Conversion rules can be created and deleted by management 
	 stations.  When created by management stations GT Conversion 
	 rules are created empty, in that they do not contain 
	 gtAddressInfoConversionRules, and are unreferenced, in that 
	 they are not referred to by a gtRule.  When created by system 
	 operations, they can be created with contained and referring 
	 entires.  Before an entry can be deleted by a management 
	 station, it must have gtAddressInfoConversionRules deleted 
	 (must be empty) and must not be referred to by a gtRule."
    REFERENCE
	"ITU-T Rec. Q.751.2 gtConversionRule."
    INDEX   {
	    mtpMsId,		   -- shared index
	    sccpNetworkEntityId,   -- shared index
	    sccpGtConversionRuleId -- index
	}
    ::= { sccpGtConversionRuleTable 1 }

SccpGtConversionRuleEntry ::=
    SEQUENCE {
	sccpGtConversionRuleId			SimpleNameType,
	sccpGtConversionRuleNewEncodingScheme	GtEncodingScheme,
	sccpGtConversionRuleNewNatureOfAddress	GtNatureOfAddress,
	sccpGtConversionRuleNewNumberingPlan	GtNumberingPlan,
	sccpGtConversionRuleNewTranslationType	GtTranslationType,
	sccpGtConversionRuleName		CommonLanguageName,
	sccpGtConversionRuleRowStatus		RowStatus
    }

sccpGtConversionRuleId OBJECT-TYPE
    SYNTAX SimpleNameType
    MAX-ACCESS not-accessible
    STATUS current
    DESCRIPTION
	"Provides a name for this entry corresponding to this conversion 
	 rule."
    REFERENCE
	"ITU-T Q.751.2 gtConversionRuleId."
    ::= { sccpGtConversionRuleEntry 1 }

sccpGtConversionRuleNewEncodingScheme OBJECT-TYPE
    SYNTAX GtEncodingScheme
    MAX-ACCESS read-create
    STATUS current
    DESCRIPTION
	"When set to a value of other than notUsedOrNoOverwite, it 
	 specifies the encoding scheme which is to be overwritten in 
	 Global Titles to which this rule applies."
    REFERENCE
	"ITU-T Q.751.2 newEncodingScheme."
    DEFVAL { 256 } -- notUsedOrNoOverwite
    ::= { sccpGtConversionRuleEntry 2 }

sccpGtConversionRuleNewNatureOfAddress OBJECT-TYPE
    SYNTAX GtNatureOfAddress
    MAX-ACCESS read-create
    STATUS current
    DESCRIPTION
	"When set to a value of other than notUsedOrNoOverwrite, it 
	 specifies the nature of address which is to be overitten in 
	 Global Titles to which this rule applies."
    REFERENCE
	"ITU-T Q.751.2 newNatureOfAddress."
    DEFVAL { 256 } -- notUsedOrNoOverwite
    ::= { sccpGtConversionRuleEntry 3 }

sccpGtConversionRuleNewNumberingPlan OBJECT-TYPE
    SYNTAX GtNumberingPlan
    MAX-ACCESS read-create
    STATUS current
    DESCRIPTION
	"When set to a value of other than notUsedOrNoOverwrite, it 
	 specifies the numbering plan which is to be overwritten in 
	 Global Titles to which this rule applies."
    REFERENCE
	"ITU-T Q.751.2 newNumberingPlan."
    DEFVAL { 256 } -- notUsedOrNoOverwite
    ::= { sccpGtConversionRuleEntry 4 }

sccpGtConversionRuleNewTranslationType OBJECT-TYPE
    SYNTAX GtTranslationType
    MAX-ACCESS read-create
    STATUS current
    DESCRIPTION
	"When set to a value of other than notUsedOrNoOverwrite, it 
	 specifies the numbering plan which is to be overwritten in 
	 Global Titles to which this rule applies."
    REFERENCE
	"ITU-T Q.751.2 newTranslationType."
    DEFVAL { 256 } -- notUsedOrNoOverwite
    ::= { sccpGtConversionRuleEntry 5 }

sccpGtConversionRuleName OBJECT-TYPE
    SYNTAX CommonLanguageName
    MAX-ACCESS read-create
    STATUS current
    DESCRIPTION
	""
    REFERENCE
	""
    DEFVAL { }
    ::= { sccpGtConversionRuleEntry 6 }

sccpGtConversionRuleRowStatus OBJECT-TYPE
    SYNTAX RowStatus
    MAX-ACCESS read-create
    STATUS current
    DESCRIPTION
	"Provides a means, according to the RowStatus textual 
	 convention, of creating and deleting rows from this table.  A 
	 GT conversion rule table entry must be empty (no side-table 
	 entries in the sccpAddressInfoTable under the corresponding 
	 rule) before it can be deleted.  Newly created GT conversion 
	 rules created by management stations are empty in that there 
	 are no side-table address information conversion rules 
	 associated with them.  Entries created through system 
	 operations"
    REFERENCE
	"SNMPv2-TC"
    ::= { sccpGtConversionRuleEntry 7 }


-- side-table containing addressInfoConversionRules belonging to a 
-- gtConversionRule.  This is a list of operations for each conversion 
-- rule.

sccpAddressInfoTable OBJECT-TYPE
    SYNTAX SEQUENCE OF SccpAddressInfoEntry
    MAX-ACCESS not-accessible
    STATUS current
    DESCRIPTION
	"Provides a side table which provides a list of 
	 addressInfoGtConversionRules, each of which represents an 
	 operation to be performed in sequence on Global Titles which 
	 are subject to the corresponding conversion rule."
    REFERENCE
	"ITU-T Rec. Q.751.2 addressInfoConversionRules."
    ::= { sccpGtConversionRule 2 }

sccpAddressInfoEntry OBJECT-TYPE
    SYNTAX SccpAddressInfoEntry
    MAX-ACCESS not-accessible
    STATUS current
    DESCRIPTION
	"Provides a single operation in a sequential list of operations 
	 to be performed on address elements for Global Titles which are 
	 subject to the coresponding conversion rule at this point in 
	 the conversion.  The sccpNetworkEntityId and 
	 sccpGtConversionRuleId specify to  which GT conversion rule the 
	 current operation applies and the sccpAddressInfoOperationId 
	 provides the index in the sequence of operations of the current 
	 operation."
    REFERENCE
	"ITU-T Rec. Q.751.2 addressInfoConversionRules."
    INDEX   {
	    mtpMsId,			-- shared index
	    sccpNetworkEntityId,	-- shared index
	    sccpGtConversionRuleId,	-- shared index
	    sccpAddressInfoOperationId  -- index
	}
    ::= { sccpAddressInfoTable 1 }

SccpAddressInfoEntry ::=
    SEQUENCE {
	sccpAddressInfoOperationId		SimpleNameType,
	sccpAddressInfoOperation		INTEGER,
	sccpAddressInfoAddressElement		INTEGER,
	sccpAddressInfoNrOfAddressElements	Unsigned32,
	sccpAddressInfoRowStatus		RowStatus
    }

sccpAddressInfoOperationId OBJECT-TYPE
    SYNTAX SimpleNameType
    MAX-ACCESS not-accessible
    STATUS current
    DESCRIPTION
	"Provides an index of the entry corresponding to an operation in 
	 a list of operations corresponding to a GT conversion rule.  
	 The index is not significant.  Entries may be created wth index 
	 zero(0) and they will be assigned the next available index."
    REFERENCE
	"ITU-T Rec. Q.751.2 ASN.1 AddressInfoConversionRule."
    ::= { sccpAddressInfoEntry 1 }


sccpAddressInfoOperation OBJECT-TYPE
    SYNTAX INTEGER {
		insert(0),
		replace(1),
		passTransparently(2),
		delete(3),
		stop(4),
		copyRemain(5)
	    }
    MAX-ACCESS read-create
    STATUS current
    DESCRIPTION
	"Specifies the operation to be performed by this entry in the Gt 
	 conversion rule.
	 
	 - insert(0) specifies that an address element is to be inserted 
	   into Global Titles to which this rule applies at this point 
	   in the operations;
	 
	 - replace(1) specifies that an address element is to be replace 
	   in Global Titles to which this rule applies at this point in 
	   the operations;
	 
	 - passTransparently(2) specifies that a number of address 
	   elements are to be passed transparently from Global Titles to 
	   which this rule applies at this point in the operations;
	 
	 - delete(3) specifies that an address eleemnt is to be deleted 
	   from Global Titles to which this rule applies at this point 
	   in the operations;
	 
	 - stop(4) specifies that Gt conversion is to stop at this point 
	   in the operations;
	 
	 - copyRemain(5) specifies that the remaining Gt address 
	   elements are to be copied from Global Titles to which this 
	   rule applies at this point in the operations.
	 
	 See ITU-T Rec. Q.715 for more information."
    REFERENCE
	"ITU-T Q.751.2 ASN.1 Operation."
    ::= { sccpAddressInfoEntry 2 }

sccpAddressInfoAddressElement OBJECT-TYPE
    SYNTAX INTEGER(0..15)
    MAX-ACCESS read-create
    STATUS current
    DESCRIPTION
	"Only significant when the operation is insert(0) or replace(1).  
	 When the operation is insert(0) or replace(1), this object 
	 specifies the address element to be inserted or replaced."
    REFERENCE
	"ITU-T Q.751.2 ASN.1 AddressElement, ITU-T Rec. Q.715."
    ::= { sccpAddressInfoEntry 3 }

sccpAddressInfoNrOfAddressElements OBJECT-TYPE
    SYNTAX INTEGER
    MAX-ACCESS read-create
    STATUS current
    DESCRIPTION
	"Only significant when the operation is passTransparently(2) or 
	 delete(3).  When the operation is compatible, this obejct 
	 specifies the number of address elements to pass transparently 
	 or the number of address elements to delete.  When incompatible 
	 this value is ignored."
    REFERENCE
	"ITU-T Q.751.2 ASN.1 NrOfAddressElements, ITU-T Rec. 
	 Q.715."
    ::= { sccpAddressInfoEntry 4 }

sccpAddressInfoRowStatus OBJECT-TYPE
    SYNTAX RowStatus
    MAX-ACCESS read-create
    STATUS current
    DESCRIPTION
	"Provides a means, according to the RowStatus textual convention 
	 from SNMPv2-TC, to create and delele address information 
	 operations in and from a GT conversion rule.  The 
	 sccpOperationIndex is not significant. When entries are added, 
	 the sccpOperationIndex may be specified as zero (0) and the 
	 next sequential index value will be used.  It would be nice to 
	 also provide a mechanism whereby rules can be inserted into and 
	 deleted from the list."
    REFERENCE
	"SNMPv2-TC"
    ::= { sccpAddressInfoEntry 5 }

-- =====================================================================

sccpGtTranslatorTable OBJECT-TYPE
    SYNTAX SEQUENCE OF SccpGtTranslatorEntry
    MAX-ACCESS not-accessible
    STATUS current
    DESCRIPTION
	""
    REFERENCE
	"ITU-T Rec. Q.751.2 gtTranslator MO."
    ::= { sccpGtTranslator 1 }

sccpGtTranslatorEntry OBJECT-TYPE
    SYNTAX SccpGtTranslatorEntry
    MAX-ACCESS not-accessible
    STATUS current
    DESCRIPTION
	"The Global Title Translator is selected on a combination of the 
	 values of the Nature of Address, the Translation Type, and the 
	 Numbering Plan (if available).  As a consequence, the Global 
	 Title Translator is modelled as a class with three 
	 characteristic attributes: Nature of Address, TranslationType, 
	 and Numbering Plan.  If a Global Title address field is not 
	 used, it has the value NULL.  The gtIndicator attribute is a 
	 read-only and is derived from the combination of Nature of 
	 Address, the Translation Type, and Numbering Plan used.  If for 
	 a given combination no Global Title Translator exists, a 
	 Routing Failure notification with the reason 'no translation 
	 for address of this nature' is emitted by the SCRC.  The 
	 administrativeState attribute can have the following states: 
	 locked and unlocked.
	 
	 The sccpNetworkEntityId identifies the SCCP network entity and 
	 the contained SCRC (SCCP routing control) protocol module to 
	 which the GT translator belongs."
    REFERENCE
	"ITU-T Rec. Q.751.2 gtTranslator MO."
    INDEX   {
	    mtpMsId,		 -- shared index
	    sccpNetworkEntityId, -- shared index
	    sccpGtTranslatorId   -- index
	}
    ::= { sccpGtTranslatorTable 1 }

SccpGtTranslatorEntry ::=
    SEQUENCE {
	sccpGtTranslatorId			SimpleNameType, -- index
	sccpGtTranslatorGtIndicator		GtIndicator,
	sccpGtTranslatorNatureOfAddress		GtNatureOfAddress,
	sccpGtTranslatorNumberingPlan		GtNumberingPlan,
	sccpGtTranslatorTranslationType		GtTranslationType,
	sccpGtTranslatorAdministrativeState	AdministrativeState,
	sccpGtTranslatorName			CommonLanguageName,
	sccpGtTranslatorRowStatus		RowStatus
    }

sccpGtTranslatorId OBJECT-TYPE
    SYNTAX SimpleNameType
    MAX-ACCESS not-accessible
    STATUS current
    DESCRIPTION
	""
    REFERENCE
	"ITU-T Rec. Q.751.2 gtTranslatorId."
    ::= { sccpGtTranslatorEntry 1 }

sccpGtTranslatorGtIndicator OBJECT-TYPE
    SYNTAX GtIndicator
    MAX-ACCESS read-create
    STATUS current
    DESCRIPTION
	""
    REFERENCE
	"ITU-T Rec. Q.751.2 gtIndicator."
    ::= { sccpGtTranslatorEntry 2 }

sccpGtTranslatorNatureOfAddress OBJECT-TYPE
    SYNTAX GtNatureOfAddress
    MAX-ACCESS read-create
    STATUS current
    DESCRIPTION
	""
    REFERENCE
	"ITU-T Rec. Q.751.2 gtNatureOfAddress."
    ::= { sccpGtTranslatorEntry 3 }

sccpGtTranslatorNumberingPlan OBJECT-TYPE
    SYNTAX GtNumberingPlan
    MAX-ACCESS read-create
    STATUS current
    DESCRIPTION
	""
    REFERENCE
	"ITU-T Rec. Q.751.2 gtNumberingPlan."
    ::= { sccpGtTranslatorEntry 4 }

sccpGtTranslatorTranslationType OBJECT-TYPE
    SYNTAX GtTranslationType
    MAX-ACCESS read-create
    STATUS current
    DESCRIPTION
	""
    REFERENCE
	"ITU-T Rec. Q.751.2 gtTranslationType."
    ::= { sccpGtTranslatorEntry 5 }

sccpGtTranslatorAdministrativeState OBJECT-TYPE
    SYNTAX AdministrativeState
    MAX-ACCESS read-create
    STATUS current
    DESCRIPTION
	""
    REFERENCE
	"ITU-T Rec. X.721 (1992) | ISO/IEC 10165-2 : 1992, 
	     administrativeState attribute."
    DEFVAL { locked }
    ::= { sccpGtTranslatorEntry 6 }

sccpGtTranslatorName OBJECT-TYPE
    SYNTAX CommonLanguageName
    MAX-ACCESS read-create
    STATUS current
    DESCRIPTION
	""
    REFERENCE
	""
    DEFVAL { }
    ::= { sccpGtTranslatorEntry 7 }

sccpGtTranslatorRowStatus OBJECT-TYPE
    SYNTAX RowStatus
    MAX-ACCESS read-create
    STATUS current
    DESCRIPTION
	""
    REFERENCE
	"SNMPv2-TC"
    ::= { sccpGtTranslatorEntry 8 }

-- =====================================================================

sccpGtRuleTable OBJECT-TYPE
    SYNTAX SEQUENCE OF SccpGtRuleEntry
    MAX-ACCESS not-accessible
    STATUS current
    DESCRIPTION
	""
    REFERENCE
	"ITU-T Q.751.2 gtRule MO."
    ::= { sccpGtRule 1 }
	

sccpGtRuleEntry OBJECT-TYPE
    SYNTAX SccpGtRuleEntry
    MAX-ACCESS not-accessible
    STATUS current
    DESCRIPTION
	"A Global Title Rule is selected based on the (matching) Global 
	 Title Address Information and possibly the Encoding Scheme.  If 
	 there is no matching Translation Rule for a given Global Title, 
	 then a Routing Failure notification with the reason 'no 
	 translation for an address of this nature' is emitted by the 
	 SCRC.  The Global Title Rule points to the Entity Set resulting 
	 from the Global Title Transation.  The Global Title Conversion 
	 Rule pointer referes to an operation Global Title Conversion 
	 Rule that may modify the Global Title.  The new Routing 
	 Indicator is implicitly set according to the sccpEntitySet 
	 pointer to.  The administrativeState attribute can have the 
	 following states: locked and unlocked."
    REFERENCE
	"ITU-T Q.751.2 gtRule MO."
    INDEX   {
	    mtpMsId,		 -- shared index
	    sccpNetworkEntityId, -- shared index
	    sccpGtTranslatorId,	 -- shared index
	    sccpGtRuleId	 -- index
	}
    ::= { sccpGtRuleTable 1 }

SccpGtRuleEntry ::=
    SEQUENCE {
	sccpGtRuleId				SimpleNameType,
	sccpGtRuleAdministrativeState		AdminstrativeState,
	sccpGtRuleAddressInformation		GtAddressInformation,
	sccpGtRuleGtConversionRulePointer	SimpleNameType,
	sccpGtRuleEncodingScheme		GtEncodingScheme,
	sccpGtRuleEntitySetPointer		SimpleNameType,
	sccpGtRuleName				CommonLanguageName,
	sccpGtRuleRowStatus			RowStatus
    }

sccpGtRuleId OBJECT-TYPE
    SYNTAX SimpleNameType
    MAX-ACCESS not-accessible
    STATUS current
    DESCRIPTION
	""
    REFERENCE
	""
    ::=  { sccpGtRuleEntry 1 }

sccpGtRuleAdministrativeState OBJECT-TYPE
    SYNTAX AdministrativeState
    MAX-ACCESS read-create
    STATUS current
    DESCRIPTION
	""
    REFERENCE
	"ITU-T Rec. X.721 (1992) | ISO/IEC 10165-2 : 1992, 
	     administrativeState attribute."
    DEFVAL { locked }
    ::=  { sccpGtRuleEntry 2 }

sccpGtRuleAddressInformation OBJECT-TYPE
    SYNTAX GtAddressInformation
    MAX-ACCESS read-create
    STATUS current
    DESCRIPTION
	"Provides the address information against which to match the 
	 Global Title for this GT Rule to be applicable.
	 
	 The gtAddressInformation attribute contains the value of the 
	 Global Title address information, as indicated in 3.4.2/Q.713."
    REFERENCE
	"ITU-T Rec. Q.751.2 gtAddressInformation."
    ::=  { sccpGtRuleEntry 3 }

sccpGtRuleGtConversionRulePointer OBJECT-TYPE
    --
    -- Because this pointer only points to entries in one table, the 
    -- sccpGtConversionRuleTable, this pointer is formatted the same 
    -- as the secondary index to that table.  When finding the entry 
    -- in the table, the same value of the sccpNetworkEntityId as is 
    -- used to index this table is used as the primary index into 
    -- the sccpGtConversionRuleTable table as well.
    --
    SYNTAX SimpleNameType  -- was RowPointer
    MAX-ACCESS read-create
    STATUS current
    DESCRIPTION
	"Provides a row pointer that indicates the GT Conversion Rule to 
	 be applied for this GT Rule, using the RowPointer textual 
	 convention.  This is a pointer to an entry in the 
	 sccpGtConversionRuleTable.  The sccpNetworkEntityId of the row 
	 pointed to and the sccpNetworkEntityId of this GT Rule entry 
	 must be the same or an error will result."
    ::=  { sccpGtRuleEntry 4 }

sccpGtRuleEncodingScheme OBJECT-TYPE
    SYNTAX GtEncodingScheme
    MAX-ACCESS read-create
    STATUS current
    DESCRIPTION
	"Provides the encoding scheme against which to match the Global 
	 Title for this GT Rule to be applicable."
    REFERENCE
	"ITU-T Rec. Q.751.2 gtEncodingScheme."
    ::=  { sccpGtRuleEntry 5 }

sccpGtRuleEntitySetPointer OBJECT-TYPE
    --
    -- Beacuse this pointer only points to entries in one table, the 
    -- sccpEntitySetTable, this pointer is formatted the same as the 
    -- secondary index to that table.  When finding the entry in the 
    -- table, the same value of the sccpNetworkENtityId as is used 
    -- to index this table is used as the primary index into the 
    -- sccpEntitySetTable as well.
    --
    SYNTAX SimpleNameType  -- was RowPointer
    MAX-ACCESS read-create
    STATUS current
    DESCRIPTION
	"Proivdes a row pointer that indicates the SCCP Entity Set to 
	 which this translation results.  Using the RowPointer textual 
	 convention, this is a pointer to an entry in the 
	 sccpEntitySetTable.  The sccpNetworkEntityId of the row pointed 
	 to and the sccpNetworkEntityId of this GT Rule entry must be 
	 the same or an error will result."
    REFERENCE
	"ITU-T Rec. Q.751.2 entitySetPointer."
    ::=  { sccpGtRuleEntry 6 }

sccpGtRuleName OBJECT-TYPE
    SYNTAX CommonLanguageName
    MAX-ACCESS read-create
    STATUS current
    DESCRIPTION
	""
    REFERENCE
	""
    DEFVAL { }
    ::=  { sccpGtRuleEntry 7 }

sccpGtRuleRowStatus OBJECT-TYPE
    SYNTAX RowStatus
    MAX-ACCESS read-create
    STATUS current
    DESCRIPTION
	""
    REFERENCE
	"SNMPv2-TC RowStatus"
    ::=  { sccpGtRuleEntry 8 }

-- =====================================================================

sccpSrvtTable OBJECT-TYPE
    SYNTAX SEQUENCE OF SccpSrvtEntry
    MAX-ACCESS not-accessible
    STATUS current
    DESCRIPTION
	"This managed object represents the management information of 
	 the SCCP Routing Verification Test.  This test is described in 
	 Recommendation Q.753.  The SCCP Routing Verification Test 
	 (srvt) is used to test the Global Title Translation service of 
	 the SCCP."
    REFERENCE
	""
    ::= { sccpSrvt 1 }

sccpSrvtEntry OBJECT-TYPE
    SYNTAX SccpSrvtEntry
    MAX-ACCESS not-accessible
    STATUS current
    DESCRIPTION
	"A svrt "
    REFERENCE
	""
    INDEX   {
	    mtpMsId,		 -- shared index
	    sccpNetworkEntityId, -- shared index
	    sccpSrvtId		 -- index
	}
    ::= { sccpSrvtTable 1 }

SccpSrvtEntry ::=
    SEQUENCE {
	sccpSrvtId				SimpleNameType,
	sccpSrvtDSRVT				TimeInterval,
	sccpSrvtNSRVT				INTEGER,
	sccpSrvtName				CommonLanguageName,
	sccpSrvtAdministrativeState		AdministrativeState,
	sccpSrvtOperationalState		OperationalState,
	sccpSrvtProceduralStatus		ProceduralStatus,
	sccpSrvtTraceRequested			TruthValue,
	sccpSrvtThreshold			INTEGER,
	sccpSrvtMtpBackwardRoutingRequested	TruthValue,
	sccpSrvtOriginalGT			GlobalTitle,
	sccpSrvtInfoRequest			BITS,
	sccpSrvtReturnUnknownParams		BITS,
	sccpSrvtRowStatus			RowStatus
    }

sccpSrvtId OBJECT-TYPE
    SYNTAX SimpleNameType
    MAX-ACCESS not-accessible
    STATUS current
    DESCRIPTION
	"This attribute is used for naming conceptual rows following the 
	 SimpleNameType textual convention."
    REFERENCE
	"ITU-T Rec. Q.751.2 routeTestId."
    ::= { sccpSrvtEntry 1 }

sccpSrvtDSRVT OBJECT-TYPE
    SYNTAX TimeInterval
    UNITS       "seconds"
    MAX-ACCESS read-create
    STATUS current
    DESCRIPTION
	"The estimated maximum delay between relay points DSRVT as 
	 described in 3.2.2.5/Q.753.  This value is needed for the 
	 calculation of the SRVT Guard Timer T2."
    REFERENCE
	"ITU-T Rec. Q.752.1 dSRVT ATTRIBUTE, ITU-T Rec. Q.753 3.2.2.5."
    ::= { sccpSrvtEntry 2 }

sccpSrvtNSRVT OBJECT-TYPE
    SYNTAX INTEGER
    MAX-ACCESS read-create
    STATUS current
    DESCRIPTION
	"This attribute equals to the value of the NSRVT as described in 
	 3.2.2.5/Q.753."
    REFERENCE
	"ITU-T Rec. Q.752.1 nSRVT ATTRIBUTE, ITU-T Rec. Q.753 3.2.2.5."
    ::= { sccpSrvtEntry 3 }

sccpSrvtName OBJECT-TYPE
    SYNTAX CommonLanguageName
    MAX-ACCESS read-create
    STATUS current
    DESCRIPTION
	"Provides an optional COMMON LANGAUGE name for the SCCP Route 
	 Verification test module in accordance with the common language 
	 textual convention.  This attribute is optional and when unused 
	 (the defautl) is set to the null string."
    REFERENCE
	"ITU-T Rec. Q.752.1 srvtName ATTRIBUTE."
    DEFVAL { }
    ::= { sccpSrvtEntry 4 }

sccpSrvtAdministrativeState OBJECT-TYPE
    SYNTAX AdministrativeState
    MAX-ACCESS read-create
    STATUS current
    DESCRIPTION
	"Unlike CMIP, SNMP has no way of providing actions nor 
	 parameters for actions: this column (and the perationalState 
	 and proceduralStatus below) appear in this table to model the 
	 startSRVT action and subsequent columns model the parameters of 
	 the startSVRT action.  The sccpRouteTestResult notification and 
	 the operationalStatus and proceduralStatus columns model the 
	 result of the action.
	 
	 Rows in this table are created by default in the locked(0) 
	 administrativeState unless the adminstrativeState is explicity 
	 set by management action when a row is created.  Setting the 
	 administrativeState to unlocked(1) results in the initiation of 
	 the startSRVT action with the parameters indicated in 
	 subsequent columns.  After being launched, the 
	 sccpSrvtOperationalState and sccpSrvtProceduralStatus columsn 
	 reflect the operational and procedural state of the SRVT test.  
	 A sccpRouteTestResult notification will be issued when SRVT 
	 test either fails or succeeds (but not if it is cancelled).
	 
	 Setting the administrative state to locked(1) when the 
	 operational state is enabled(1) will result in the cancellation 
	 of the test.  The results will not be reported.  Setting the 
	 adminstrative state to shuttingDown(2) has no effect: the test 
	 will completed and the results reported."
    REFERENCE
	"ITU-T Rec. Q.753 startSRVT ConfirmedAction,
	 ITU-T Rec. Q.751.2 startSccpRouteTest ACTION.
	 ITU-T Rec. X.721 (1992) | ISO/IEC 10165-2 : 1992, 
	     administrativeState attribute."
    DEFVAL { locked }
    ::= { sccpSrvtEntry 5 }

sccpSrvtOperationalState OBJECT-TYPE
    SYNTAX OperationalState
    MAX-ACCESS read-only
    STATUS current
    DESCRIPTION
	"Provides the operational state of the SCCP Route Verification 
	 test in progress.  The operational state is disabled(0) when 
	 the test is not running, or when it has concluded.  The 
	 operational state is enabled(1) when the test is running and 
	 has not yet concluded.
	 
	 This object uses the OperationalState textual convention from 
	 the OPENSS7-SMI-MIB module."
    REFERENCE
	"ITU-T Rec. Q.753 (1997) startSRVT ConfirmedAction,
	 ITU-T Rec. Q.751.2 (1992) startSccpRouteTest ACTION,
	 ITU-T Rec. X.721 (1992) | ISO/IEC 10165-2 : 1992 
	 operationalState."
    DEFVAL { disabled }
    ::= { sccpSrvtEntry 6 }

sccpSrvtProceduralStatus OBJECT-TYPE
    SYNTAX ProceduralStatus
    MAX-ACCESS read-only
    STATUS current
    DESCRIPTION
	"Provides the procedural statu of the SCCP Route Verification 
	 test in progress.
	 
	 - initializationRequired(0): The procedural status contains 
	   initialization required when the test requires initialization 
	   to be invoked by the manager before it will run, and such 
	   initialization has not yet been invoked.  The manager may 
	   invoke intialization by setting the 
	   sccpSrvtAdministrativeState to unlocked(1).
	 
	 - notInitialized(1): The procedural status contains not 
	   initialized when the test requires intialization before it 
	   can run and the test has not been initialized.  The test 
	   initializes itself autononomously, and the operational state 
	   is disabled.
	 
	 - intializing(2): The procedural status contains initializing 
	   when the test required initialization before it can run, and 
	   this initialization has been initiated but is not yet 
	   complete.  When this condition is present, the initialization 
	   required condition is absent, since initialization has 
	   already begun.  The operational state is enabled.
	 
	 - reporting(3): The procedural status contains reporting when 
	   the test has terminated succesfully or unsuccessfully, and 
	   the result is being reported.
	 
	 - teminating(4): The procedural status contains terminating 
	   when the test is in a termination phase.  The 
	   initializationRequired condition is not present and the 
	   operational state is disabled.
	 
	 This object uses the ProceduralStatus textual convention from 
	 the OPENSS7-SMI-MIB module."
    REFERENCE
	"ITU-T Rec. Q.753 (1997) startSRVT ConfirmedAction,
	 ITU-T Rec. Q.751.2 (1992) startSccpRouteTest ACTION,
	 ITU-T Rec. X.721 (1992) | ISO/IEC 10165-2 : 1992 
	     proceduralStatus attribute."
    ::= { sccpSrvtEntry 7 }

sccpSrvtTraceRequested OBJECT-TYPE
    SYNTAX TruthValue
    MAX-ACCESS read-create
    STATUS current
    DESCRIPTION
	"Unlike CMIP, SNMP has no specific way of providing parameters 
	 for actions: this column appears in this table to model an 
	 action parameter.  This column models a mandatory parameter of 
	 the startSRVT action."
    REFERENCE
	"ITU-T Recommendation Q.753 (1997) ASN.1 startSVRT 
	 traceRequested."
    ::= { sccpSrvtEntry 8 }

sccpSrvtThreshold OBJECT-TYPE
    SYNTAX INTEGER
    MAX-ACCESS read-create
    STATUS current
    DESCRIPTION
	"Unlike CMIP, SNMP has no specific way of providing parameters 
	 for actions: this column appears in this table to model an 
	 action parameter.  This column models a mandatory parameter of 
	 the startSRVT action."
    REFERENCE
	"ITU-T Recommendation Q.753 (1997) ASN.1 startSVRT threshold."
    ::= { sccpSrvtEntry 9 }

sccpSrvtMtpBackwardRoutingRequested OBJECT-TYPE
    SYNTAX TruthValue
    MAX-ACCESS read-create
    STATUS current
    DESCRIPTION
	"Unlike CMIP, SNMP has no specific way of providing parameters 
	 for actions: this column appears in this table to model an 
	 action parameter.  This column models an optional parameter of 
	 the startSRVT action.  When not present, the value is false."
    REFERENCE
	"ITU-T Recommendation Q.753 (1997) ASN.1 startSVRT 
	 mtpBackwardRoutingRequested."
    DEFVAL { 2 } -- false
    ::= { sccpSrvtEntry 10 }

sccpSrvtOriginalGT OBJECT-TYPE
    SYNTAX GlobalTitle
    MAX-ACCESS read-create
    STATUS current
    DESCRIPTION
	"Unlike CMIP, SNMP has no specific way of providing parameters 
	 for actions: this column appears in this table to model an 
	 action parameter.  This column models an optional parameter of 
	 the startSRVT action.  When not present, the length of the 
	 octet string representing the GlobalTitle will be zero (null 
	 string)."
    REFERENCE
	"ITU-T Recommendation Q.753 (1997) ASN.1 startSVRT originalGT."
    DEFVAL { }
    ::= { sccpSrvtEntry 11 }

sccpSrvtInfoRequest OBJECT-TYPE
    SYNTAX BITS {
	    pointCode(0),
	    pointCodeList(1),
	    routePriorityList(2)
	}
    MAX-ACCESS read-create
    STATUS current
    DESCRIPTION
	"Unlike CMIP, SNMP has no specific way of providing parameters 
	 for actions: this column appears in this table to model an 
	 action parameter.  This column models an optional parameter of 
	 the startSRVT action.  When not present, the value is set to 
	 all zeros, '000'B.  sccpSrvtInfoRequest is used to inidicate 
	 that the test initiator node can accept a routeTraceNew RVR 
	 message, and also asks for particular parameters to be returned 
	 in it, if it is sent.  This parameter can only be inserted at 
	 the initiator node, but it can be copied into regenerated 
	 MRVTs."
    REFERENCE
	"ITU-T Recommendation Q.753 (1997) ASN.1 startSVRT infoRequest."
    DEFVAL { } -- '000'B
    ::= { sccpSrvtEntry 12 }

sccpSrvtReturnUnknownParams OBJECT-TYPE
    SYNTAX BITS {
	    tag15(0),
	    tag16(1)
	}
    MAX-ACCESS read-create
    STATUS current
    DESCRIPTION
	"Unlike CMIP, SNMP has no specific way of providing parameters 
	 for actions: this column appears in this table to model an 
	 action parameter.  This column models an optional parameter of 
	 the startSRVT action.  When not present, the value is set to 
	 all zeros, '00'B.  The sccpSrvtReturnUnknownParams is used to 
	 indicate which parameters that a node does not understand 
	 should be returned in an RVR if one is sent (or in an RVA 
	 message in the copyData field if the test initiator is 
	 unknown).  Bit 0 represents an RVT parameter with tag value 15, 
	 bit 1 an RVT parameter with tage value 16, etc.  This parameter 
	 can only be present if sccpSrvtInfoRequest is present."
    REFERENCE
	"ITU-T Recommendation Q.753 (1997) ASN.1 startSVRT 
	 returnUnknownParams."
    DEFVAL { } -- '00'B
    ::= { sccpSrvtEntry 13 }

sccpSrvtRowStatus OBJECT-TYPE
    SYNTAX RowStatus
    MAX-ACCESS read-create
    STATUS current
    DESCRIPTION
	""
    REFERENCE
	""
    ::= { sccpSrvtEntry 14 }

sccpNetworkEntityGroup OBJECT-GROUP
    OBJECTS	{
	sccpNetworkEntityId, 
	sccpNetworkEntityAlarmStatus, 
	sccpNetworkEntityLocalSapNames, 
	sccpNetworkEntityOperationalState, 
	sccpNetworkEntityTitles, 
	sccpNetworkEntitySystemTypes, 
	sccpNetworkEntityVersion, 
	sccpNetworkEntityLUDTandLUDTSSupported, 
	sccpNetworkEntityCoordChangeTimer, 
	sccpNetworkEntityIgnoreSSTTimer, 
	sccpNetworkEntityMaxStatInfoTimer, 
	sccpNetworkEntityRowStatus
    }
    STATUS current
    DESCRIPTION
	""
    ::= { sccpGroups 1 }

sccpAccessPointGroup OBJECT-GROUP
    OBJECTS	{
	sccpAccessPointSapId, 
	sccpAccessPointAlarmStatus, 
	sccpAccessPointSap2Address, 
	sccpAccessPointUserEntityNames, 
	sccpAccessPointProviderEntityNames, 
	sccpAccessPointAvailabilityStatus, 
	sccpAccessPointConcernedAreaPointer, 
	sccpAccessPointRowStatus
    }
    STATUS current
    DESCRIPTION
	""
    ::= { sccpGroups 2 }

sccpRemoteSAPGroup OBJECT-GROUP
    OBJECTS	{
	sccpAccessPointLinkagePointer
    }
    STATUS current
    DESCRIPTION
	""
    ::= { sccpGroups 3 }

sccpAlarmSeverityAssignmentPointerPackage OBJECT-GROUP
    OBJECTS	{
	sccpNetworkEntityAsaProfilePointer,
	sccpAccessPointAsaProfilePointer,
	sccpSclcAsaProfilePointer,
	sccpScrcAsaProfilePointer
    }
    STATUS	current
    DESCRIPTION
	"A collcation of objects that impelement the 
	 alarmSeverityAssignmentPointerPackage."
    ::= { sccpGroups 4 }

sccpAvailableAfterSpRestartPackage OBJECT-GROUP
    OBJECTS	{
	sccpAccessPointSsAvailableAfterSpRestart
    }
    STATUS	current
    DESCRIPTION
	"A collection of objects that implement the 
	 ssAvailableAfterSpRestartPackage."
    ::= { sccpGroups 5 }

sccpLinkageGroup OBJECT-GROUP
    OBJECTS	{
	sccpLinkageId, 
	sccpLinkageOperationalProtocols, 
	sccpLinkageSnSAP, 
	sccpLinkageRowStatus
    }
    STATUS current
    DESCRIPTION
	""
    ::= { sccpGroups 6 }

sccpSclcGroup OBJECT-GROUP
    OBJECTS	{
	sccpSclcAlarmStatus, 
	sccpSclcClProtocolMachineId, 
	sccpSclcOperationalState, 
	sccpSclcTotalRemoteSAPs, 
	sccpSclcAdministrativeState, 
	sccpSclcSupportedProtocols, 
	sccpSclcOperationalSystemType, 
	sccpSclcInitialValueReassTimer, 
	sccpSclcRowStatus -- really should not be here at all
    }
    STATUS current
    DESCRIPTION
	""
    ::= { sccpGroups 7 }

sccpScocGroup OBJECT-GROUP
    OBJECTS	{
	sccpScocCoProtocolMachineId, 
	sccpScocOperationalState, 
	sccpScocAdministrativeState, 
	sccpScocOperationalSystemType, 
	sccpScocSupportedProtocols, 
	sccpScocRowStatus -- really should not be here at all
    }
    STATUS current
    DESCRIPTION
	""
    ::= { sccpGroups 8 }

sccpScrcGroup OBJECT-GROUP
    OBJECTS	{
	sccpScrcId, 
	sccpScrcAlarmStatus, 
	sccpScrcRowStatus -- really should not be here at all
    }
    STATUS current
    DESCRIPTION
	""
    ::= { sccpGroups 9 }

sccpEntitySetGroup OBJECT-GROUP
    OBJECTS	{
	sccpEntitySetId, 
	sccpEntitySetSharingMode, 
	sccpEntitySetLoadSharingAlgPointer, 
	sccpEntitySetType, 
	sccpEntitySetSsn, 
	sccpEntitySetRowStatus,
	sccpEntitySetSapId, 
	sccpEntitySetSapType, 
	sccpEntitySetSapPointer, 
	sccpEntitySetSapRowStatus
    }
    STATUS current
    DESCRIPTION
	""
    ::= { sccpGroups 10 }

sccpConcernedAreaGroup OBJECT-GROUP
    OBJECTS	{
	sccpConcernedAreaId, 
	sccpConcernedAreaRowStatus
    }
    STATUS current
    DESCRIPTION
	""
    ::= { sccpGroups 11 }

sccpRemoteSCCPGroup OBJECT-GROUP
    OBJECTS	{
	sccpRemoteSCCPId, 
	sccpRemoteSCCPMTPAccessPoint, 
	sccpRemoteSCCPRowStatus
    }
    STATUS current
    DESCRIPTION
	""
    ::= { sccpGroups 12 }

sccpGtTranslatorGroup OBJECT-GROUP
    OBJECTS	{
	sccpGtTranslatorId,
	sccpGtTranslatorGtIndicator,
	sccpGtTranslatorNatureOfAddress,
	sccpGtTranslatorNumberingPlan,
	sccpGtTranslatorTranslationType,
	sccpGtTranslatorAdministrativeState,
	sccpGtTranslatorRowStatus,
	sccpGtRuleId,
	sccpGtRuleAdministrativeState,
	sccpGtRuleAddressInformation,
	sccpGtRuleGtConversionRulePointer,
	sccpGtRuleEncodingScheme,
	sccpGtRuleEntitySetPointer,
	sccpGtRuleRowStatus
    }
    STATUS current
    DESCRIPTION
	""
    ::= { sccpGroups 13 }

sccpSrvtGroup OBJECT-GROUP
    OBJECTS	{
	sccpSrvtId,
	sccpSrvtDSRVT,
	sccpSrvtNSRVT,
	sccpSrvtAdministrativeState,
	sccpSrvtOperationalState,
	sccpSrvtProceduralStatus,
	sccpSrvtTraceRequested,
	sccpSrvtThreshold,
	sccpSrvtMtpBackwardRoutingRequested,
	sccpSrvtOriginalGT,
	sccpSrvtInfoRequest,
	sccpSrvtReturnUnknownParams,
	sccpSrvtRowStatus
    }
    STATUS current
    DESCRIPTION
	""
    ::= { sccpGroups 14 }


sccpLocalSccpLinkagePackage OBJECT-GROUP
    OBJECTS	{
	sccpLinkageConcernedAreaPointer, 
	sccpLinkageLowerLimitForSegmentation, 
	sccpLinkageUpperLimitForSegmentation
    }
    STATUS	current
    DESCRIPTION
	"A collection of objects that implement the 
	 localSccpLinkagePackage.  Unless this group is implemented, 
	 entries in the sccpLinkageTable cannot represent a local 
	 linkage.  Only Network Entities that implement end-systems need 
	 local linkages.
	 
	 - sccpLinkageConcernedAreaPointer, is a reference to a 
	   concerned area that describes for which remote subsystems the 
	   local user will be informed of status changes.
	 
	 - sccpLinkageLowerLimitForSegmentation, is the size (in octets) 
	   of unit data supplied by the user in the N-UNITDATA-Request 
	   primitive above which the data may be segmented depending on 
	   network conditions.
	 
	 - sccpLinkageUpperLimitForSegmentation, is the size (in octets) 
	   of unit data supplied by the user in the N-UNITDATA-Request 
	   primitive above which the data will always be segmented.
	"
    ::= { sccpGroups 15 }

sccpCongestionPackage OBJECT-GROUP
    OBJECTS	{
	sccpLinkageAttackTimerValue, 
	sccpLinkageDecayTimerValue, 
	sccpLinkageNrOfRestrictionLevels, 
	sccpLinkageNrOfSubLevels, 
	sccpLinkageCLS, 
	sccpLinkageCongestionTimerValue, 
	sccpLinkageP, 
	sccpLinkageImportanceLevelCR, 
	sccpLinkageImportanceLevelCC, 
	sccpLinkageImportanceLevelCREF, 
	sccpLinkageImportanceLevelDT1, 
	sccpLinkageImportanceLevelDT2, 
	sccpLinkageImportanceLevelAK, 
	sccpLinkageImportanceLevelIT, 
	sccpLinkageImportanceLevelED, 
	sccpLinkageImportanceLevelEA, 
	sccpLinkageImportanceLevelRSR, 
	sccpLinkageImportanceLevelRSC, 
	sccpLinkageImportanceLevelERR, 
	sccpLinkageImportanceLevelRLC, 
	sccpLinkageImportanceLevelRLSD, 
	sccpLinkageImportanceLevelUDT, 
	sccpLinkageImportanceLevelUDTS, 
	sccpLinkageImportanceLevelXUDT, 
	sccpLinkageImportanceLevelXUDTS, 
	sccpLinkageImportanceLevelLUDT, 
	sccpLinkageImportanceLevelLUDTS, 
	sccpLinkageRLM, 
	sccpLinkageRSLM
    }
    STATUS current
    DESCRIPTION
	""
    ::= { sccpGroups 16 }

sccpAddressInfoConversionRulePackage OBJECT-GROUP
    OBJECTS	{
	sccpGtConversionRuleId, 
	sccpGtConversionRuleNewEncodingScheme, 
	sccpGtConversionRuleNewNatureOfAddress, 
	sccpGtConversionRuleNewNumberingPlan, 
	sccpGtConversionRuleNewTranslationType, 
	sccpGtConversionRuleRowStatus,
	sccpAddressInfoOperationId, 
	sccpAddressInfoOperation, 
	sccpAddressInfoAddressElement, 
	sccpAddressInfoNrOfAddressElements, 
	sccpAddressInfoRowStatus
    }
    STATUS current
    DESCRIPTION
	"For performing global title translations, rules can be 
	 described that are used to change the global title in a called 
	 party address.  The conversion can replace all parts of the 
	 global title with a new value.  If the 
	 addressInfoConversionRulePackage is present, it specfies ho 
	 address elements can be inserted, replaced, passed 
	 transparently, or deleted from the (old) GTAI into a new GTAI.  
	 The procedures for global title conversion are described in 
	 7.3/Q.715.  Only those parts of the GT information are modified 
	 that have a corresponding new value identified by entries in 
	 the sccpGtConversionRuleTable.  This object group implements 
	 the sccpGtConversionRuleTable."
    ::= { sccpGroups 17 }

sccpCommonLanguageNameGroup OBJECT-GROUP
    OBJECTS {
	sccpNetworkEntityName,
	sccpAccessPointName,
	sccpLinkageName,
	sccpSclcName,
	sccpScocName,
	sccpScrcName,
	sccpEntitySetName,
	sccpRemoteSCCPName,
	sccpGtConversionRuleName,
	sccpGtTranslatorName,
	sccpGtRuleName,
	sccpSrvtName
    }
    STATUS current
    DESCRIPTION
	"These objects are optional names following the 
	 CommonLanguageName textual convention that can be used to 
	 identify elements of the configuration."
    ::= { sccpGroups 18 }

sccpMIBCompliance MODULE-COMPLIANCE
    STATUS current
    DESCRIPTION
	"Provides the module compliance requirements for the SCCP MIB."

    MODULE -- this module

    MANDATORY-GROUPS	{
	    sccpNetworkEntityGroup, 
	    sccpAccessPointGroup, 
	    sccpLinkageGroup, 
	    sccpScrcGroup, 
	    sccpConcernedAreaGroup, 
	    sccpRemoteSCCPGroup
	}

	GROUP sccpAvailableAfterSpRestartPackage
	DESCRIPTION
	    ""

	GROUP sccpRemoteSAPGroup
	DESCRIPTION
	    "Mandatory if remote SCCP service access points (SCCP-SAP) 
	     are supported.  Remote SCCP-SAPs are used by SCCP relay 
	     nodes that perform global title translation in conjunction 
	     with concerned areas for secondary broadcast."

	GROUP sccpCongestionPackage
	DESCRIPTION
	    "Mandatory if a network entity supports SCCP congestion 
	     procedures."

	GROUP sccpLocalSccpLinkagePackage
	DESCRIPTION
	    "Mandatory if the network entity is capable of implementing  
	     an end-system."

	GROUP sccpSclcGroup
	DESCRIPTION
	    "Mandatory if the implementation supports either 
	     connectionless protocol class: 0 or 1."

	GROUP sccpScocGroup
	DESCRIPTION
	    "Mandatory if the implementation supports either connection 
	     oriented protocol class: 2 or 3."

	GROUP sccpEntitySetGroup
	DESCRIPTION
	    "Mandatory if the implementation supports global title 
	     translations to, or direct routing to, an Entity Set."

	GROUP sccpGtTranslatorGroup
	DESCRIPTION
	    "Mandatory if the implementation supports global title 
	     translations."

	GROUP sccpAddressInfoConversionRulePackage
	DESCRIPTION
	    "Mandatory if address information conversion rules are 
	     implemented as a part of global title translations.  This 
	     group also requires implementation of the 
	     sccpGtTranslatorGroup."

	GROUP sccpSrvtGroup
	DESCRIPTION
	    ""

	GROUP sccpCommonLanguageNameGroup
	DESCRIPTION
	    ""

    ::= { sccpCompliance 1 }


END

-- =============================================================================
-- vim: ft=mib comments=\f\:\",\b\:\-\-,\:\-\-,\f\b\:- fo+=tcqlornw tw=72 nocin nosi sts=4 sw=4
