-- vim: ft=mib comments=\f\:\",\b\:\-\-,\:\-\-,\f\b\:- fo+=tcqlornw tw=72 nocin nosi sts=4 sw=4
-- =============================================================================
-- 
-- @(#) $RCSfile: OPENSS7-MTP-OM-MIB2.mib,v $ $Name: OpenSS7-0_9_2 $($Revision: 0.9.2.3 $) $Date: 2009-01-10 17:09:26 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-10 17:09:26 $ by $Author: brian $
--
-- -----------------------------------------------------------------------------
--
-- $Log: OPENSS7-MTP-OM-MIB2.mib,v $
-- Revision 0.9.2.3  2009-01-10 17:09:26  brian
-- - updated agents
--
-- Revision 0.9.2.2  2008-12-31 16:04:49  brian
-- - updated mibs
--
-- Revision 0.9.2.1  2008-12-27 15:29:50  brian
-- - split MTP and MTP OM mib
--
-- =============================================================================

OPENSS7-MTP-OM-MIB2 DEFINITIONS ::= BEGIN

IMPORTS
    MODULE-IDENTITY, OBJECT-TYPE, enterprises, Integer32, Unsigned32, 
    Counter32
	FROM SNMPv2-SMI

    TEXTUAL-CONVENTION, InstancePointer, TimeStamp, TimeInterval, 
    RowStatus
	FROM SNMPv2-TC

    MODULE-COMPLIANCE, OBJECT-GROUP, NOTIFICATION-GROUP
	FROM SNMPv2-CONF

    PerfCurrentCount, PerfIntervalCount
	FROM PerfHist-TC-MIB

    HCPerfIntervalThreshold, HCPerfValidIntervals
	FROM HC-PerfHist-TC-MIB

    mtpLsId, mtpRsId, mtpSlSlCode, mtpSpId, mtpSlEntry, mtpSdtEntry, 
    mtpSdlEntry, MtpUserPart
	FROM OPENSS7-MTP-MIB

    openss7, openss7Q, openss7Q752
	FROM OPENSS7-SMI;

mtpOmMIB MODULE-IDENTITY
    LAST-UPDATED
	"200812092229Z"
    ORGANIZATION
	"The OpenSS7 Project"
    CONTACT-INFO
	"Brian Bidulock
	 OpenSS7 Corporation
	 1469 Jefferys Crescent
	 Edmonton, Alberta  T6L 6T1
	 CANADA
	 Tel: +1 780 490 1141
	 Fax: +1 780 490 1241
	 Mob: +1 780 953 0557
	 mailto:bidulock@openss7.org"
    DESCRIPTION
	"The purpose of this MIB is to provide SNMP support for the MTP 
	 operational measurements provided in ITU-T Q.752 and ANSI 
	 T1.116.  There exists a draft GDMO specification for ANSI 
	 T1.116.1 from which this MIB is based.  Strangely enough, no 
	 GDMO is standardized for SS7 operational measurements.

	 The objective of this MIB is to support both the reporting of 
	 statistics obtained from Operational Measurements as well as 
	 providing a mechanism to activate and report the results of OM 
	 studies."
    REVISION
	"200812092229Z"
    DESCRIPTION
	"This is the initial revision of this MIB."
    ::= { openss7Q752 1 }

 -- top level organization of the MIB

mtpOmNotifications	OBJECT IDENTIFIER ::= { mtpOmMIB	 0 }
mtpOmObjects		OBJECT IDENTIFIER ::= { mtpOmMIB	 1 }
mtpOmConformance	OBJECT IDENTIFIER ::= { mtpOmMIB	 2 }

mtpOmTables		OBJECT IDENTIFIER ::= { mtpOmObjects	 1 }
mtpOmScalars		OBJECT IDENTIFIER ::= { mtpOmObjects	 2 }
mtpOmNotifs		OBJECT IDENTIFIER ::= { mtpOmObjects	 3 }
mtpOmOids		OBJECT IDENTIFIER ::= { mtpOmObjects	 4 }

mtpOmCompliance		OBJECT IDENTIFIER ::= { mtpOmConformance 1 }
mtpOmGroups		OBJECT IDENTIFIER ::= { mtpOmConformance 2 }
mtpOmCapabilities	OBJECT IDENTIFIER ::= { mtpOmConformance 3 }

mtpOmSpStats		OBJECT IDENTIFIER ::= { mtpOmTables	 1 }
mtpOmRsStats		OBJECT IDENTIFIER ::= { mtpOmTables	 2 }
mtpOmLsStats		OBJECT IDENTIFIER ::= { mtpOmTables	 3 }
mtpOmSlStats		OBJECT IDENTIFIER ::= { mtpOmTables	 4 }
mtpOmSdtStats		OBJECT IDENTIFIER ::= { mtpOmTables	 5 }
mtpOmSdlStats		OBJECT IDENTIFIER ::= { mtpOmTables	 6 }


-- (1.3.6.1.4.1.29591.17.752.1) openss7Q.752.1 (mtpOmMIB)
-- |__(0) mtpOmNotifications
-- |  |__( 1) mtpOm5minSpReport
-- |  |__( 2) mtpOm15minSpReport
-- |  |__( 3) mtpOm5minRsReport
-- |  |__( 4) mtpOm15minRsReport
-- |  |__( 5) mtpOm5minLsReport
-- |  |__( 6) mtpOm15minLsReport
-- |  |__( 7) mtpOm5minSlReport
-- |  |__( 8) mtpOm15minSlReport
-- |  |__( 9) mtpOm5minSdtReport
-- |  |__(10) mtpOm15minSdtReport
-- |  |__(11) mtpOm5minSdlReport
-- |  |__(12) mtpOm15minSdlReport
-- |
-- |__(1) mtpOmObjects
-- |  |__( 1) mtpOmTables
-- |  |  |__( 1) mtpOmSpStats
-- |  |  |  |__( 1) mtpOmSpTable
-- |  |  |  |  |__( 1) mtpOmSpEntry
-- |  |  |  |     |__( 1) mtpOmSpValidIntervals
-- |  |  |  |     |__( 2) mtpOmSpTimeDiscontinuity
-- |  |  |  |     |__( 3) mtpOmSpDiscardedMSUs
-- |  |  |  |     |__( 4) mtpOmSpReceivedTFCstatus0
-- |  |  |  |     |__( 5) mtpOmSpReceivedTFCstatus1
-- |  |  |  |     |__( 6) mtpOmSpReceivedTFCstatus2
-- |  |  |  |     |__( 7) mtpOmSpOctetsXferred
-- |  |  |  |
-- |  |  |  |__( 2) mtpOmSpInt5minTable
-- |  |  |  |  |__( 1) mtpOmSpInt5minEntry
-- |  |  |  |     |__( 1) mtpOmSpInt5minInterval
-- |  |  |  |     |__( 2) mtpOmSpInt5minTimeStamp
-- |  |  |  |     |__( 3) mtpOmSpInt5minDiscardedMSUs
-- |  |  |  |     |__( 4) mtpOmSpInt5minReceivedTFCstatus0
-- |  |  |  |     |__( 5) mtpOmSpInt5minReceivedTFCstatus1
-- |  |  |  |     |__( 6) mtpOmSpInt5minReceivedTFCstatus2
-- |  |  |  |     |__( 7) mtpOmSpInt5minOctetsXferred
-- |  |  |  |
-- |  |  |  |__( 3) mtpOmSpInt15minTable
-- |  |  |  |  |__( 1) mtpOmSpInt15minEntry
-- |  |  |  |     |__( 1) mtpOmSpInt15minInterval
-- |  |  |  |     |__( 2) mtpOmSpInt15minTimeStamp
-- |  |  |  |     |__( 3) mtpOmSpInt15minDiscardedMSUs
-- |  |  |  |     |__( 4) mtpOmSpInt15minReceivedTFCstatus0
-- |  |  |  |     |__( 5) mtpOmSpInt15minReceivedTFCstatus1
-- |  |  |  |     |__( 6) mtpOmSpInt15minReceivedTFCstatus2
-- |  |  |  |     |__( 7) mtpOmSpInt15minOctetsXferred
-- |  |  |  |
-- |  |  |  |__( 4) mtpOmSpSiTable
-- |  |  |  |  |__( 1) mtpOmSpSiEntry
-- |  |  |  |     |__( 1) mtpOmSpSiCode
-- |  |  |  |     |__( 2) mtpOmSpSiValidIntervals
-- |  |  |  |     |__( 3) mtpOmSpSiTimeDiscontinuity
-- |  |  |  |     |__( 4) mtpOmSpSiTransmittedUPUnavailable
-- |  |  |  |     |__( 5) mtpOmSpSiReceivedUPUnavailable
-- |  |  |  |     |__( 6) mtpOmSpSiHandledOctetsSIO
-- |  |  |  |     |__( 7) mtpOmSpSiStatus
-- |  |  |  |
-- |  |  |  |__( 5) mtpOmSpSiInt5minTable
-- |  |  |  |  |__( 1) mtpOmSpSiInt5minEntry
-- |  |  |  |     |__( 1) mtpOmSpSiInt5minInterval
-- |  |  |  |     |__( 2) mtpOmSpSiInt5minTimeStamp
-- |  |  |  |     |__( 3) mtpOmSpSiInt5minTransmittedUPUnavailable
-- |  |  |  |     |__( 4) mtpOmSpSiInt5minReceivedUPUnavailable
-- |  |  |  |     |__( 5) mtpOmSpSiInt5minHandledOctetsSIO
-- |  |  |  |
-- |  |  |  |__( 6) mtpOmSpSiInt15minTable
-- |  |  |  |  |__( 1) mtpOmSpSiInt15minEntry
-- |  |  |  |     |__( 1) mtpOmSpSiInt15minInterval
-- |  |  |  |     |__( 2) mtpOmSpSiInt15minTimeStamp
-- |  |  |  |     |__( 3) mtpOmSpSiInt15minTransmittedUPUnavailable
-- |  |  |  |     |__( 4) mtpOmSpSiInt15minReceivedUPUnavailable
-- |  |  |  |     |__( 5) mtpOmSpSiInt15minHandledOctetsSIO
-- |  |  |  |
-- |  |  |  |__( 7) mtpOmSpStudyTable
-- |  |  |  |  |__( 1) mtpOmSpStudyEntry
-- |  |  |  |     |__( 1) mtpOmSpStudyId
-- |  |  |  |     |__( 2) mtpOmSpStudyValidIntervals
-- |  |  |  |     |__( 3) mtpOmSpStudyTimeDiscontinuity
-- |  |  |  |     |__( 4) mtpOmSpStudyHandledOctetsOpcDpcSio
-- |  |  |  |     |__( 5) mtpOmSpStudyHandledMSUsOpcDpcSio
-- |  |  |  |     |__( 6) mtpOmSpStudyStatus
-- |  |  |  |
-- |  |  |  |__( 8) mtpOmSpStudyInt5minTable
-- |  |  |  |  |__( 1) mtpOmSpStudyInt5minEntry
-- |  |  |  |     |__( 1) mtpOmSpStudyInt5minInterval
-- |  |  |  |     |__( 2) mtpOmSpStudyInt5minTimeStamp
-- |  |  |  |     |__( 3) mtpOmSpStudyInt5minHandledOctetsOpcDpcSio
-- |  |  |  |     |__( 4) mtpOmSpStudyInt5minHandledMSUsOpcDpcSio
-- |  |  |  |
-- |  |  |  |__( 9) mtpOmSpStudyInt15minTable
-- |  |  |  |  |__( 1) mtpOmSpStudyInt15minEntry
-- |  |  |  |     |__( 1) mtpOmSpStudyInt15minInterval
-- |  |  |  |     |__( 2) mtpOmSpStudyInt15minTimeStamp
-- |  |  |  |     |__( 3) mtpOmSpStudyInt15minHandledOctetsOpcDpcSio
-- |  |  |  |     |__( 4) mtpOmSpStudyInt15minHandledMSUsOpcDpcSio
-- |  |  |  |
-- |  |  |  |__(10) mtpOmSpStudyMapTable
-- |  |  |     |__( 1) mtpOmSpStudyMapEntry
-- |  |  |        |__( 1) mtpOmOpcRsId
-- |  |  |        |__( 2) mtpOmDpcRsId
-- |  |  |        |__( 3) mtpOmSpStudyMapStatus
-- |  |  |
-- |  |  |__( 2) mtpOmRsStats
-- |  |  |  |__( 1) mtpOmRsTable
-- |  |  |  |  |__( 1) mtpOmRsEntry
-- |  |  |  |     |__( 1) mtpOmRsValidIntervals
-- |  |  |  |     |__( 2) mtpOmRsTimeDiscontinuity
-- |  |  |  |     |__( 3) mtpOmRsReceivedOctetsOPC
-- |  |  |  |     |__( 4) mtpOmRsTransmittedOctetsDPC
-- |  |  |  |     |__( 5) mtpOmRsReceivedMSUsOpc
-- |  |  |  |     |__( 6) mtpOmRsTransmittedMSUsDpc
-- |  |  |  |     |__( 7) mtpOmRsRouteSetUnavailable
-- |  |  |  |     |__( 8) mtpOmRsRouteSetUnavailableDuration
-- |  |  |  |
-- |  |  |  |__( 2) mtpOmRsInt5minTable
-- |  |  |  |  |__( 1) mtpOmRsInt5minEntry
-- |  |  |  |     |__( 1) mtpOmRsInt5minInterval
-- |  |  |  |     |__( 2) mtpOmRsInt5minTimeStamp
-- |  |  |  |     |__( 3) mtpOmRsInt5minReceivedOctetsOPC
-- |  |  |  |     |__( 4) mtpOmRsInt5minTransmittedOctetsDPC
-- |  |  |  |     |__( 5) mtpOmRsInt5minReceivedMSUsOpc
-- |  |  |  |     |__( 6) mtpOmRsInt5minTransmittedMSUsDpc
-- |  |  |  |     |__( 7) mtpOmRsInt5minRouteSetUnavailable
-- |  |  |  |     |__( 8) mtpOmRsInt5minRouteSetUnavailableDuration
-- |  |  |  |
-- |  |  |  |__( 3) mtpOmRsInt15minTable
-- |  |  |  |  |__( 1) mtpOmRsInt15minEntry
-- |  |  |  |     |__( 1) mtpOmRsInt15minInterval
-- |  |  |  |     |__( 2) mtpOmRsInt15minTimeStamp
-- |  |  |  |     |__( 3) mtpOmRsInt15minReceivedOctetsOPC
-- |  |  |  |     |__( 4) mtpOmRsInt15minTransmittedOctetsDPC
-- |  |  |  |     |__( 5) mtpOmRsInt15minReceivedMSUsOpc
-- |  |  |  |     |__( 6) mtpOmRsInt15minTransmittedMSUsDpc
-- |  |  |  |     |__( 7) mtpOmRsInt15minRouteSetUnavailable
-- |  |  |  |     |__( 8) mtpOmRsInt15minRouteSetUnavailableDuration
-- |  |  |  |
-- |  |  |  |__( 4) mtpOmRsSiTable
-- |  |  |  |  |__( 1) mtpOmRsSiEntry
-- |  |  |  |     |__( 1) mtpOmRsSiCode
-- |  |  |  |     |__( 2) mtpOmRsSiValidIntervals
-- |  |  |  |     |__( 3) mtpOmRsSiTimeDiscontinuity
-- |  |  |  |     |__( 4) mtpOmRsSiReceivedOctetsOpcSio
-- |  |  |  |     |__( 5) mtpOmRsSiTransmittedOctetsDpcSio
-- |  |  |  |     |__( 6) mtpOmRsSiReceivedMSUsOpcSio
-- |  |  |  |     |__( 7) mtpOmRsSiTransmittedMSUsDpcSio
-- |  |  |  |     |__( 8) mtpOmRsSiStatus
-- |  |  |  |
-- |  |  |  |__( 5) mtpOmRsSiInt5minTable
-- |  |  |  |  |__( 1) mtpOmRsSiInt5minEntry
-- |  |  |  |     |__( 1) mtpOmRsSiInt5minInterval
-- |  |  |  |     |__( 2) mtpOmRsSiInt5minTimeStamp
-- |  |  |  |     |__( 3) mtpOmRsSiInt5minReceivedOctetsOpcSio
-- |  |  |  |     |__( 4) mtpOmRsSiInt5minTransmittedOctetsDpcSio
-- |  |  |  |     |__( 5) mtpOmRsSiInt5minReceivedMSUsOpcSio
-- |  |  |  |     |__( 6) mtpOmRsSiInt5minTransmittedMSUsDpcSio
-- |  |  |  |
-- |  |  |  |__( 6) mtpOmRsSiInt15minTable
-- |  |  |     |__( 1) mtpOmRsSiInt15minEntry
-- |  |  |        |__( 1) mtpOmRsSiInt15minInterval
-- |  |  |        |__( 2) mtpOmRsSiInt15minTimeStamp
-- |  |  |        |__( 3) mtpOmRsSiInt15minReceivedOctetsOpcSio
-- |  |  |        |__( 4) mtpOmRsSiInt15minTransmittedOctetsDpcSio
-- |  |  |        |__( 5) mtpOmRsSiInt15minReceivedMSUsOpcSio
-- |  |  |        |__( 6) mtpOmRsSiInt15minTransmittedMSUsDpcSio
-- |  |  |
-- |  |  |__( 3) mtpOmLsStats
-- |  |  |  |__( 1) mtpOmLsTable
-- |  |  |  |  |__( 1) mtpOmLsEntry
-- |  |  |  |     |__( 1) mtpOmLsValidIntervals
-- |  |  |  |     |__( 2) mtpOmLsTimeDiscontinuity
-- |  |  |  |     |__( 3) mtpOmLsAdjacentInaccessibleEvents
-- |  |  |  |     |__( 4) mtpOmLsAdjacentInaccessibleDuration
-- |  |  |  |     |__( 5) mtpOmLsSlsUnavailable
-- |  |  |  |
-- |  |  |  |__( 2) mtpOmLsInt5minTable
-- |  |  |  |  |__( 1) mtpOmLsInt5minEntry
-- |  |  |  |     |__( 1) mtpOmLsInt5minInterval
-- |  |  |  |     |__( 2) mtpOmLsInt5minTimeStamp
-- |  |  |  |     |__( 3) mtpOmLsInt5minAdjacentInaccessibleEvents
-- |  |  |  |     |__( 4) mtpOmLsInt5minAdjacentInaccessibleDuration
-- |  |  |  |     |__( 5) mtpOmLsInt5minSlsUnavailable
-- |  |  |  |
-- |  |  |  |__( 3) mtpOmLsInt15minTable
-- |  |  |     |__( 1) mtpOmLsInt15minEntry
-- |  |  |        |__( 1) mtpOmLsInt15minInterval
-- |  |  |        |__( 2) mtpOmLsInt15minTimeStamp
-- |  |  |        |__( 3) mtpOmLsInt15minAdjacentInaccessibleEvents
-- |  |  |        |__( 4) mtpOmLsInt15minAdjacentInaccessibleDuration
-- |  |  |        |__( 5) mtpOmLsInt15minSlsUnavailable
-- |  |  |
-- |  |  |__( 4) mtpOmSlStats
-- |  |  |  |__( 1) mtpOmSlStatsTable
-- |  |  |  |  |__( 1) mtpOmSlStatsEntry
-- |  |  |  |     |__( 1) mtpOmSlStatsDurInService
-- |  |  |  |     |__( 2) mtpOmSlStatsFailAlignOrProving
-- |  |  |  |     |__( 3) mtpOmSlStatsNacksReceived
-- |  |  |  |     |__( 4) mtpOmSlStatsDurUnavail
-- |  |  |  |     |__( 5) mtpOmSlStatsDurUnavailFailed
-- |  |  |  |     |__( 6) mtpOmSlStatsDurUnavailRpo
-- |  |  |  |     |__( 7) mtpOmSlStatsSibsSent
-- |  |  |  |     |__( 8) mtpOmSlStatsTranSioSifOctets
-- |  |  |  |     |__( 9) mtpOmSlStatsRetransOctets
-- |  |  |  |     |__(10) mtpOmSlStatsTranMsus
-- |  |  |  |     |__(11) mtpOmSlStatsRecvSioSifOctets
-- |  |  |  |     |__(12) mtpOmSlStatsRecvMsus
-- |  |  |  |     |__(13) mtpOmSlStatsCongOnsetInd0
-- |  |  |  |     |__(14) mtpOmSlStatsCongOnsetInd1
-- |  |  |  |     |__(15) mtpOmSlStatsCongOnsetInd2
-- |  |  |  |     |__(16) mtpOmSlStatsCongOnsetInd3
-- |  |  |  |     |__(17) mtpOmSlStatsDurCongStatus0
-- |  |  |  |     |__(18) mtpOmSlStatsDurCongStatus1
-- |  |  |  |     |__(19) mtpOmSlStatsDurCongStatus2
-- |  |  |  |     |__(20) mtpOmSlStatsDurCongStatus3
-- |  |  |  |     |__(21) mtpOmSlStatsCongDiscdInd0
-- |  |  |  |     |__(22) mtpOmSlStatsCongDiscdInd1
-- |  |  |  |     |__(23) mtpOmSlStatsCongDiscdInd2
-- |  |  |  |     |__(24) mtpOmSlStatsCongDiscdInd3
-- |  |  |  |
-- |  |  |  |__( 2) mtpOmSlL3Table
-- |  |  |  |  |__( 1) mtpOmSlL3Entry
-- |  |  |  |     |__( 1) mtpOmSlL3ValidIntervals
-- |  |  |  |     |__( 2) mtpOmSlL3TimeDiscontinuity
-- |  |  |  |     |__( 3) mtpOmSlL3SlUnavailabilityDuration
-- |  |  |  |     |__( 4) mtpOmSlL3SlLocalInhibition
-- |  |  |  |     |__( 5) mtpOmSlL3SlRemoteInhibition
-- |  |  |  |     |__( 6) mtpOmSlL3SlFailed
-- |  |  |  |     |__( 7) mtpOmSlL3SlRemoteProcOutage
-- |  |  |  |     |__( 8) mtpOmSlL3LocalMgmtInhibit
-- |  |  |  |     |__( 9) mtpOmSlL3LocalMgmtUninhibit
-- |  |  |  |     |__(10) mtpOmSlL3LocalBusy
-- |  |  |  |     |__(11) mtpOmSlL3SlCongestedStarts
-- |  |  |  |     |__(12) mtpOmSlL3SlCongestedDuration
-- |  |  |  |     |__(13) mtpOmSlL3SlCongestionStops
-- |  |  |  |     |__(14) mtpOmSlL3DiscardedMSUs
-- |  |  |  |     |__(15) mtpOmSlL3CongestionEventsMSULoss
-- |  |  |  |     |__(16) mtpOmSlL3Changeovers
-- |  |  |  |     |__(17) mtpOmSlL3Changebacks
-- |  |  |  |     |__(18) mtpOmSlL3Restorations
-- |  |  |  |
-- |  |  |  |__( 3) mtpOmSlL3Int5minTable
-- |  |  |  |  |__( 1) mtpOmSlL3Int5minEntry
-- |  |  |  |     |__( 1) mtpOmSlL3Int5minInterval
-- |  |  |  |     |__( 2) mtpOmSlL3Int5minTimeStamp
-- |  |  |  |     |__( 3) mtpOmSlL3Int5minSlUnavailabilityDuration
-- |  |  |  |     |__( 4) mtpOmSlL3Int5minSlLocalInhibition
-- |  |  |  |     |__( 5) mtpOmSlL3Int5minSlRemoteInhibition
-- |  |  |  |     |__( 6) mtpOmSlL3Int5minSlFailed
-- |  |  |  |     |__( 7) mtpOmSlL3Int5minSlRemoteProcOutage
-- |  |  |  |     |__( 8) mtpOmSlL3Int5minLocalMgmtInhibit
-- |  |  |  |     |__( 9) mtpOmSlL3Int5minLocalMgmtUninhibit
-- |  |  |  |     |__(10) mtpOmSlL3Int5minLocalBusy
-- |  |  |  |     |__(11) mtpOmSlL3Int5minSlCongestedStarts
-- |  |  |  |     |__(12) mtpOmSlL3Int5minSlCongestedDuration
-- |  |  |  |     |__(13) mtpOmSlL3Int5minSlCongestionStops
-- |  |  |  |     |__(14) mtpOmSlL3Int5minDiscardedMSUs
-- |  |  |  |     |__(15) mtpOmSlL3Int5minCongestionEventsMSULoss
-- |  |  |  |     |__(16) mtpOmSlL3Int5minChangeovers
-- |  |  |  |     |__(17) mtpOmSlL3Int5minChangebacks
-- |  |  |  |     |__(18) mtpOmSlL3Int5minRestorations
-- |  |  |  |
-- |  |  |  |__( 4) mtpOmSlL3Int15minTable
-- |  |  |  |  |__( 1) mtpOmSlL3Int15minEntry
-- |  |  |  |     |__( 1) mtpOmSlL3Int15minInterval
-- |  |  |  |     |__( 2) mtpOmSlL3Int15minTimeStamp
-- |  |  |  |     |__( 3) mtpOmSlL3Int15minSlUnavailabilityDuration
-- |  |  |  |     |__( 4) mtpOmSlL3Int15minSlLocalInhibition
-- |  |  |  |     |__( 5) mtpOmSlL3Int15minSlRemoteInhibition
-- |  |  |  |     |__( 6) mtpOmSlL3Int15minSlFailed
-- |  |  |  |     |__( 7) mtpOmSlL3Int15minSlRemoteProcOutage
-- |  |  |  |     |__( 8) mtpOmSlL3Int15minLocalMgmtInhibit
-- |  |  |  |     |__( 9) mtpOmSlL3Int15minLocalMgmtUninhibit
-- |  |  |  |     |__(10) mtpOmSlL3Int15minLocalBusy
-- |  |  |  |     |__(11) mtpOmSlL3Int15minSlCongestedStarts
-- |  |  |  |     |__(12) mtpOmSlL3Int15minSlCongestedDuration
-- |  |  |  |     |__(13) mtpOmSlL3Int15minSlCongestionStops
-- |  |  |  |     |__(14) mtpOmSlL3Int15minDiscardedMSUs
-- |  |  |  |     |__(15) mtpOmSlL3Int15minCongestionEventsMSULoss
-- |  |  |  |     |__(16) mtpOmSlL3Int15minChangeovers
-- |  |  |  |     |__(17) mtpOmSlL3Int15minChangebacks
-- |  |  |  |     |__(18) mtpOmSlL3Int15minRestorations
-- |  |  |  |
-- |  |  |  |__( 5) mtpOmSlL2Table
-- |  |  |  |  |__( 1) mtpOmSlL2Entry
-- |  |  |  |     |__( 1) mtpOmSlL2ValidIntervals
-- |  |  |  |     |__( 2) mtpOmSlL2TimeDiscontinuity
-- |  |  |  |     |__( 3) mtpOmSlL2SlInServiceDuration
-- |  |  |  |     |__( 4) mtpOmSlL2SlAlignment
-- |  |  |  |     |__( 5) mtpOmSlL2SignUnitsReceived
-- |  |  |  |     |__( 6) mtpOmSlL2NegAckReceived
-- |  |  |  |     |__( 7) mtpOmSlL2TransmittedOctetsSIFSIO
-- |  |  |  |     |__( 8) mtpOmSlL2RetransmittedOctets
-- |  |  |  |     |__( 9) mtpOmSlL2TransmittedMSUs
-- |  |  |  |     |__(10) mtpOmSlL2ReceivedOctetsSIFSIO
-- |  |  |  |     |__(11) mtpOmSlL2ReceivedMSUs
-- |  |  |  |
-- |  |  |  |__( 6) mtpOmSlL2Int5minTable
-- |  |  |  |  |__( 1) mtpOmSlL2Int5minEntry
-- |  |  |  |     |__( 1) mtpOmSlL2Int5minInterval
-- |  |  |  |     |__( 2) mtpOmSlL2Int5minTimestamp
-- |  |  |  |     |__( 3) mtpOmSlL2Int5minSlInServiceDuration
-- |  |  |  |     |__( 4) mtpOmSlL2Int5minSlAlignment
-- |  |  |  |     |__( 5) mtpOmSlL2Int5minSignUnitsReceived
-- |  |  |  |     |__( 6) mtpOmSlL2Int5minNegAckReceived
-- |  |  |  |     |__( 7) mtpOmSlL2Int5minTransmittedOctetsSIFSIO
-- |  |  |  |     |__( 8) mtpOmSlL2Int5minRetransmittedOctets
-- |  |  |  |     |__( 9) mtpOmSlL2Int5minTransmittedMSUs
-- |  |  |  |     |__(10) mtpOmSlL2Int5minReceivedOctetsSIFSIO
-- |  |  |  |     |__(11) mtpOmSlL2Int5minReceivedMSUs
-- |  |  |  |
-- |  |  |  |__( 7) mtpOmSlL2Int15minTable
-- |  |  |     |__( 1) mtpOmSlL2Int15minEntry
-- |  |  |        |__( 1) mtpOmSlL2Int15minInterval
-- |  |  |        |__( 2) mtpOmSlL2Int15minTimestamp
-- |  |  |        |__( 3) mtpOmSlL2Int15minSlInServiceDuration
-- |  |  |        |__( 4) mtpOmSlL2Int15minSlAlignment
-- |  |  |        |__( 5) mtpOmSlL2Int15minSignUnitsReceived
-- |  |  |        |__( 6) mtpOmSlL2Int15minNegAckReceived
-- |  |  |        |__( 7) mtpOmSlL2Int15minTransmittedOctetsSIFSIO
-- |  |  |        |__( 8) mtpOmSlL2Int15minRetransmittedOctets
-- |  |  |        |__( 9) mtpOmSlL2Int15minTransmittedMSUs
-- |  |  |        |__(10) mtpOmSlL2Int15minReceivedOctetsSIFSIO
-- |  |  |        |__(11) mtpOmSlL2Int15minReceivedMSUs
-- |  |  |
-- |  |  |__( 5) mtpOmOmSdtStats
-- |  |  |  |__( 1) mtpOmSdtStatsTable
-- |  |  |     |__( 1) mtpOmSdtStatsEntry
-- |  |  |        |__( 1) mtpOmSdtStatsTxBytes
-- |  |  |        |__( 2) mtpOmSdtStatsTxSus
-- |  |  |        |__( 3) mtpOmSdtStatsTxSusRepeated
-- |  |  |        |__( 4) mtpOmSdtStatsTxUnderruns
-- |  |  |        |__( 5) mtpOmSdtStatsTxAborts
-- |  |  |        |__( 6) mtpOmSdtStatsTxBufferOverflows
-- |  |  |        |__( 7) mtpOmSdtStatsTxSusInError
-- |  |  |        |__( 8) mtpOmSdtStatsRxBytes
-- |  |  |        |__( 9) mtpOmSdtStatsRxSusCompressed
-- |  |  |        |__(10) mtpOmSdtStatsRxOverruns
-- |  |  |        |__(11) mtpOmSdtStatsRxAborts
-- |  |  |        |__(12) mtpOmSdtStatsRxBufferOverflows
-- |  |  |        |__(13) mtpOmSdtStatsRxSusInError
-- |  |  |        |__(14) mtpOmSdtStatsRxSyncTransitions
-- |  |  |        |__(15) mtpOmSdtStatsRxBitsOctetCounted
-- |  |  |        |__(16) mtpOmSdtStatsRxCrcErrors
-- |  |  |        |__(17) mtpOmSdtStatsRxFrameErrors
-- |  |  |        |__(18) mtpOmSdtStatsRxFrameOverflows
-- |  |  |        |__(19) mtpOmSdtStatsRxFrameTooLong
-- |  |  |        |__(20) mtpOmSdtStatsRxFrameTooShort
-- |  |  |        |__(21) mtpOmSdtStatsRxResidueErrors
-- |  |  |        |__(22) mtpOmSdtStatsCarrierCtsLost
-- |  |  |        |__(23) mtpOmSdtStatsCarrierDcdLost
-- |  |  |        |__(24) mtpOmSdtStatsCarrierLost
-- |  |  |
-- |  |  |__( 6) mtpOmOmSdlStats
-- |  |     |__( 1) mtpOmSdlStatsTable
-- |  |        |__( 1) mtpOmSdlStatsEntry
-- |  |           |__( 1) mtpOmSdlStatsRxOctets
-- |  |           |__( 2) mtpOmSdlStatsTxOctets
-- |  |           |__( 3) mtpOmSdlStatsRXOverruns
-- |  |           |__( 4) mtpOmSdlStatsTxUnderruns
-- |  |           |__( 5) mtpOmSdlStatsRxBufferOverflows
-- |  |           |__( 6) mtpOmSdlStatsTxBufferOverflows
-- |  |           |__( 7) mtpOmSdlStatsLeadCtsLost
-- |  |           |__( 8) mtpOmSdlStatsLeadDcdLost
-- |  |           |__( 9) mtpOmSdlStatsCarrierLost
-- |  |           |__(10) mtpOmSdlStatsBipolarViolations
-- |  |
-- |  |__( 2) mtpOmScalars
-- |  |  |__( 1) mtpOm1stAndIntervalActivate
-- |  |  |__( 2) mtpOm1stAndIntervalDeactivate
-- |  |  |__( 3) mtpOm5MinActivate
-- |  |  |__( 4) mtpOm5MinDeaActivate
-- |  |  |__( 5) mtpOm15MinActivate
-- |  |  |__( 6) mtpOm15MinDeaActivate
-- |  |  |__( 7) mtpOmInterval
-- |  |  |__( 8) mtpOmDiscontinuityTime
-- |  |  |__( 9) mtpOmTimeStamp
-- |  |  |__(10) mtpOm5MinMaxIntervals
-- |  |  |__(11) mtpOm15MinMaxIntervals
-- |  |
-- |  |__( 3) mtpOmNotifs
-- |  |
-- |  |__( 4) mtpOmOids
-- |
-- |__(2) mtpOmConformance
--    |__( 1) mtpOmCompliance
--    |
--    |__( 2) mtpOmGroups
--    |
--    |__( 3) mtpOmCapabilities

-- ====================================================================
-- TABLES
-- ====================================================================

mtpOmSpTable OBJECT-TYPE
    SYNTAX	SEQUENCE OF MtpOmSpEntry
    MAX-ACCESS	not-accessible
    STATUS	current
    DESCRIPTION
	"Provides a table of signalling point current operational 
	 measurements."
    ::= { mtpOmSpStats 1 }

mtpOmSpEntry OBJECT-TYPE
    SYNTAX	MtpOmSpEntry
    MAX-ACCESS	not-accessible
    STATUS	current
    DESCRIPTION
	"Each entry in this table corresponds to the current operational 
	 measurements for on signalling point provided by the managed 
	 element."
    INDEX	{
	mtpSpId -- shared index
    }
    ::= { mtpOmSpTable 1 }

MtpOmSpEntry ::= SEQUENCE {
    mtpOmSpValidIntervals			HCPerfValidIntervals,
    mtpOmSpTimeDiscontinuity			TimeStamp,
    mtpOmSpDiscardedMSUs			Counter32, -- Q.752, 5.5
    mtpOmSpReceivedTFCstatus0			Counter32, -- Q.752, 5.8
    mtpOmSpReceivedTFCstatus1			Counter32, -- Q.752, 5.8
    mtpOmSpReceivedTFCstatus2			Counter32, -- Q.752, 5.8
    mtpOmSpOctetsXferred			Counter32
}

mtpOmSpValidIntervals OBJECT-TYPE
    SYNTAX	HCPerfValidIntervals
    MAX-ACCESS	read-only
    STATUS	current
    DESCRIPTION
	""
    ::= { mtpOmSpEntry 1 }

mtpOmSpTimeDiscontinuity OBJECT-TYPE
    SYNTAX	TimeStamp
    MAX-ACCESS	read-only
    STATUS	current
    DESCRIPTION
	""
    ::= { mtpOmSpEntry 2 }

mtpOmSpDiscardedMSUs OBJECT-TYPE
    SYNTAX	Counter32
    UNITS	"MSUs"
    MAX-ACCESS	read-only
    STATUS	current
    DESCRIPTION
	""
    REFERENCE
	"ITU-T Rec. Q.751.1 (10/95) : discardedMSUs.
	 ITU-T Rec. Q.752 (1997) : Table 5/Q.752, 5.5."
    ::= { mtpOmSpEntry 3 }

mtpOmSpReceivedTFCstatus0 OBJECT-TYPE
    SYNTAX	Counter32
    UNITS	"TFCs"
    MAX-ACCESS	read-only
    STATUS	current
    DESCRIPTION
	"This attribute represents measurement T1.116.2/5.8.

	 The number of Transfer Controlled (TFC) messages received per 
	 congestion level and signalling point collected on a first and 
	 interval basis.  This is a non-obligatory measurement that is 
	 permanently activated when available.  The measurement is used 
	 for fault detection, near real-time monitoring, and performance 
	 analysis."
    REFERENCE
	"ANSI T1.116.1D receivedTFC.
	 ANSI T1.116.1/2000 Table 5 (5.8).
	 ITU-T Rec. Q.751.1 (10/95) : receivedTFC.
	 ITU-T Rec. Q.752 (1997) : Table 5/Q.752, 5.8."
    ::= { mtpOmSpEntry 4 }

mtpOmSpReceivedTFCstatus1 OBJECT-TYPE
    SYNTAX	Counter32
    UNITS	"TFCs"
    MAX-ACCESS	read-only
    STATUS	current
    DESCRIPTION
	"This attribute represents measurement T1.116.2/5.8.

	 The number of Transfer Controlled (TFC) messages received per 
	 congestion level and signalling point collected on a first and 
	 interval basis.  This is a non-obligatory measurement that is 
	 permanently activated when available.  The measurement is used 
	 for fault detection, near real-time monitoring, and performance 
	 analysis."
    REFERENCE
	"ANSI T1.116.1D receivedTFC.
	 ANSI T1.116.1/2000 Table 5 (5.8).
	 ITU-T Rec. Q.751.1 (10/95) : receivedTFC.
	 ITU-T Rec. Q.752 (1997) : Table 5/Q.752, 5.8."
    ::= { mtpOmSpEntry 5 }

mtpOmSpReceivedTFCstatus2 OBJECT-TYPE
    SYNTAX	Counter32
    UNITS	"TFCs"
    MAX-ACCESS	read-only
    STATUS	current
    DESCRIPTION
	"This attribute represents measurement T1.116.2/5.8.

	 The number of Transfer Controlled (TFC) messages received per 
	 congestion level and signalling point collected on a first and 
	 interval basis.  This is a non-obligatory measurement that is 
	 permanently activated when available.  The measurement is used 
	 for fault detection, near real-time monitoring, and performance 
	 analysis."
    REFERENCE
	"ANSI T1.116.1D receivedTFC.
	 ANSI T1.116.1/2000 Table 5 (5.8).
	 ITU-T Rec. Q.751.1 (10/95) : receivedTFC.
	 ITU-T Rec. Q.752 (1997) : Table 5/Q.752, 5.8."
    ::= { mtpOmSpEntry 6 }

mtpOmSpOctetsXferred OBJECT-TYPE
    SYNTAX	Counter32
    UNITS	"octets"
    MAX-ACCESS	read-only
    STATUS	current
    DESCRIPTION
	""
    ::= { mtpOmSpEntry 7 }


-- ====================================================================

mtpOmSpInt5minTable OBJECT-TYPE
    SYNTAX	SEQUENCE OF MtpOmSpInt5minEntry
    MAX-ACCESS	not-accessible
    STATUS	current
    DESCRIPTION
	"Provides a table of signalling point 5-minute inteval 
	 historical operational measurements."
    ::= { mtpOmSpStats 2 }

mtpOmSpInt5minEntry OBJECT-TYPE
    SYNTAX	MtpOmSpInt5minEntry
    MAX-ACCESS	not-accessible
    STATUS	current
    DESCRIPTION
	""
    INDEX	{
	mtpSpId, -- shared index
	mtpOmSpInt5minInterval
    }
    ::= { mtpOmSpInt5minTable 1 }

MtpOmSpInt5minEntry ::= SEQUENCE {
    mtpOmSpInt5minInterval			Unsigned32,
    mtpOmSpInt5minTimeStamp			TimeStamp,
    mtpOmSpInt5minDiscardedMSUs			PerfIntervalCount, -- Q.752, 5.5
    mtpOmSpInt5minReceivedTFCstatus0		PerfIntervalCount, -- Q.752, 5.8
    mtpOmSpInt5minReceivedTFCstatus1		PerfIntervalCount, -- Q.752, 5.8
    mtpOmSpInt5minReceivedTFCstatus2		PerfIntervalCount, -- Q.752, 5.8
    mtpOmSpInt5minOctetsXferred			PerfIntervalCount
}

mtpOmSpInt5minInterval OBJECT-TYPE
    SYNTAX	Unsigned32
    MAX-ACCESS	not-accessible
    STATUS	current
    DESCRIPTION
	""
    ::= { mtpOmSpInt5minEntry 1 }

mtpOmSpInt5minTimeStamp OBJECT-TYPE
    SYNTAX	TimeStamp
    MAX-ACCESS	read-only
    STATUS	current
    DESCRIPTION
	""
    ::= { mtpOmSpInt5minEntry 2 }

mtpOmSpInt5minDiscardedMSUs OBJECT-TYPE
    SYNTAX	PerfIntervalCount
    UNITS	"MSUs"
    MAX-ACCESS	read-only
    STATUS	current
    DESCRIPTION
	""
    REFERENCE
	"ITU-T Rec. Q.751.1 (10/95) : discardedMSUs.
	 ITU-T Rec. Q.752 (1997) : Table 5/Q.752, 5.5."
    ::= { mtpOmSpInt5minEntry 3 }

mtpOmSpInt5minReceivedTFCstatus0 OBJECT-TYPE
    SYNTAX	PerfIntervalCount
    UNITS	"TFCs"
    MAX-ACCESS	read-only
    STATUS	current
    DESCRIPTION
	"This attribute represents measurement T1.116.2/5.8.

	 The number of Transfer Controlled (TFC) messages received per 
	 congestion level and signalling point collected on a first and 
	 interval basis.  This is a non-obligatory measurement that is 
	 permanently activated when available.  The measurement is used 
	 for fault detection, near real-time monitoring, and performance 
	 analysis."
    REFERENCE
	"ANSI T1.116.1D receivedTFC.
	 ANSI T1.116.1/2000 Table 5 (5.8).
	 ITU-T Rec. Q.751.1 (10/95) : receivedTFC.
	 ITU-T Rec. Q.752 (1997) : Table 5/Q.752, 5.8."
    ::= { mtpOmSpInt5minEntry 4 }

mtpOmSpInt5minReceivedTFCstatus1 OBJECT-TYPE
    SYNTAX	PerfIntervalCount
    UNITS	"TFCs"
    MAX-ACCESS	read-only
    STATUS	current
    DESCRIPTION
	"This attribute represents measurement T1.116.2/5.8.

	 The number of Transfer Controlled (TFC) messages received per 
	 congestion level and signalling point collected on a first and 
	 interval basis.  This is a non-obligatory measurement that is 
	 permanently activated when available.  The measurement is used 
	 for fault detection, near real-time monitoring, and performance 
	 analysis."
    REFERENCE
	"ANSI T1.116.1D receivedTFC.
	 ANSI T1.116.1/2000 Table 5 (5.8).
	 ITU-T Rec. Q.751.1 (10/95) : receivedTFC.
	 ITU-T Rec. Q.752 (1997) : Table 5/Q.752, 5.8."
    ::= { mtpOmSpInt5minEntry 5 }

mtpOmSpInt5minReceivedTFCstatus2 OBJECT-TYPE
    SYNTAX	PerfIntervalCount
    UNITS	"TFCs"
    MAX-ACCESS	read-only
    STATUS	current
    DESCRIPTION
	"This attribute represents measurement T1.116.2/5.8.

	 The number of Transfer Controlled (TFC) messages received per 
	 congestion level and signalling point collected on a first and 
	 interval basis.  This is a non-obligatory measurement that is 
	 permanently activated when available.  The measurement is used 
	 for fault detection, near real-time monitoring, and performance 
	 analysis."
    REFERENCE
	"ANSI T1.116.1D receivedTFC.
	 ANSI T1.116.1/2000 Table 5 (5.8).
	 ITU-T Rec. Q.751.1 (10/95) : receivedTFC.
	 ITU-T Rec. Q.752 (1997) : Table 5/Q.752, 5.8."
    ::= { mtpOmSpInt5minEntry 6 }

mtpOmSpInt5minOctetsXferred OBJECT-TYPE
    SYNTAX	PerfIntervalCount
    UNITS	"octets"
    MAX-ACCESS	read-only
    STATUS	current
    DESCRIPTION
	""
    ::= { mtpOmSpInt5minEntry 7 }


-- ====================================================================

mtpOmSpInt15minTable OBJECT-TYPE
    SYNTAX	SEQUENCE OF MtpOmSpInt15minEntry
    MAX-ACCESS	not-accessible
    STATUS	current
    DESCRIPTION
	"Provides a table of signalling point 15-minute inteval 
	 historical operational measurements."
    ::= { mtpOmSpStats 3 }

mtpOmSpInt15minEntry OBJECT-TYPE
    SYNTAX	MtpOmSpInt15minEntry
    MAX-ACCESS	not-accessible
    STATUS	current
    DESCRIPTION
	""
    INDEX	{
	mtpSpId, -- shared index
	mtpOmSpInt15minInterval
    }
    ::= { mtpOmSpInt15minTable 1 }

MtpOmSpInt15minEntry ::= SEQUENCE {
    mtpOmSpInt15minInterval			Unsigned32,
    mtpOmSpInt15minTimeStamp			TimeStamp,
    mtpOmSpInt15minDiscardedMSUs		PerfIntervalCount, -- Q.752, 5.5
    mtpOmSpInt15minReceivedTFCstatus0		PerfIntervalCount, -- Q.752, 5.8
    mtpOmSpInt15minReceivedTFCstatus1		PerfIntervalCount, -- Q.752, 5.8
    mtpOmSpInt15minReceivedTFCstatus2		PerfIntervalCount, -- Q.752, 5.8
    mtpOmSpInt15minOctetsXferred		PerfIntervalCount
}

mtpOmSpInt15minInterval OBJECT-TYPE
    SYNTAX	Unsigned32
    MAX-ACCESS	not-accessible
    STATUS	current
    DESCRIPTION
	""
    ::= { mtpOmSpInt15minEntry 1 }

mtpOmSpInt15minTimeStamp OBJECT-TYPE
    SYNTAX	TimeStamp
    MAX-ACCESS	read-only
    STATUS	current
    DESCRIPTION
	""
    ::= { mtpOmSpInt15minEntry 2 }

mtpOmSpInt15minDiscardedMSUs OBJECT-TYPE
    SYNTAX	PerfIntervalCount
    UNITS	"MSUs"
    MAX-ACCESS	read-only
    STATUS	current
    DESCRIPTION
	""
    REFERENCE
	"ITU-T Rec. Q.751.1 (10/95) : discardedMSUs.
	 ITU-T Rec. Q.752 (1997) : Table 5/Q.752, 5.5."
    ::= { mtpOmSpInt15minEntry 3 }

mtpOmSpInt15minReceivedTFCstatus0 OBJECT-TYPE
    SYNTAX	PerfIntervalCount
    UNITS	"TFCs"
    MAX-ACCESS	read-only
    STATUS	current
    DESCRIPTION
	"This attribute represents measurement T1.116.2/5.8.

	 The number of Transfer Controlled (TFC) messages received per 
	 congestion level and signalling point collected on a first and 
	 interval basis.  This is a non-obligatory measurement that is 
	 permanently activated when available.  The measurement is used 
	 for fault detection, near real-time monitoring, and performance 
	 analysis."
    REFERENCE
	"ANSI T1.116.1D receivedTFC.
	 ANSI T1.116.1/2000 Table 5 (5.8).
	 ITU-T Rec. Q.751.1 (10/95) : receivedTFC.
	 ITU-T Rec. Q.752 (1997) : Table 5/Q.752, 5.8."
    ::= { mtpOmSpInt15minEntry 4 }

mtpOmSpInt15minReceivedTFCstatus1 OBJECT-TYPE
    SYNTAX	PerfIntervalCount
    UNITS	"TFCs"
    MAX-ACCESS	read-only
    STATUS	current
    DESCRIPTION
	"This attribute represents measurement T1.116.2/5.8.

	 The number of Transfer Controlled (TFC) messages received per 
	 congestion level and signalling point collected on a first and 
	 interval basis.  This is a non-obligatory measurement that is 
	 permanently activated when available.  The measurement is used 
	 for fault detection, near real-time monitoring, and performance 
	 analysis."
    REFERENCE
	"ANSI T1.116.1D receivedTFC.
	 ANSI T1.116.1/2000 Table 5 (5.8).
	 ITU-T Rec. Q.751.1 (10/95) : receivedTFC.
	 ITU-T Rec. Q.752 (1997) : Table 5/Q.752, 5.8."
    ::= { mtpOmSpInt15minEntry 5 }

mtpOmSpInt15minReceivedTFCstatus2 OBJECT-TYPE
    SYNTAX	PerfIntervalCount
    UNITS	"TFCs"
    MAX-ACCESS	read-only
    STATUS	current
    DESCRIPTION
	"This attribute represents measurement T1.116.2/5.8.

	 The number of Transfer Controlled (TFC) messages received per 
	 congestion level and signalling point collected on a first and 
	 interval basis.  This is a non-obligatory measurement that is 
	 permanently activated when available.  The measurement is used 
	 for fault detection, near real-time monitoring, and performance 
	 analysis."
    REFERENCE
	"ANSI T1.116.1D receivedTFC.
	 ANSI T1.116.1/2000 Table 5 (5.8).
	 ITU-T Rec. Q.751.1 (10/95) : receivedTFC.
	 ITU-T Rec. Q.752 (1997) : Table 5/Q.752, 5.8."
    ::= { mtpOmSpInt15minEntry 6 }

mtpOmSpInt15minOctetsXferred OBJECT-TYPE
    SYNTAX	PerfIntervalCount
    UNITS	"octets"
    MAX-ACCESS	read-only
    STATUS	current
    DESCRIPTION
	""
    ::= { mtpOmSpInt15minEntry 7 }


-- ====================================================================

mtpOmSpSiTable OBJECT-TYPE
    SYNTAX	SEQUENCE OF MtpOmSpSiEntry
    MAX-ACCESS	not-accessible
    STATUS	current
    DESCRIPTION
	"Provides a table of optional current signalling point 
	 operational measurements broken out be SI code."
    ::= { mtpOmSpStats 4 }

mtpOmSpSiEntry OBJECT-TYPE
    SYNTAX	MtpOmSpSiEntry
    MAX-ACCESS	not-accessible
    STATUS	current
    DESCRIPTION
	""
    INDEX	{
	mtpSpId, -- shared index
	mtpOmSpSiCode
    }
    ::= { mtpOmSpSiTable 1 }

MtpOmSpSiEntry ::= SEQUENCE {
    mtpOmSpSiCode				MtpUserPart,
    mtpOmSpSiValidIntervals			HCPerfValidIntervals,
    mtpOmSpSiTimeDiscontinuity			TimeStamp,
    mtpOmSpSiTransmittedUPUnavailable		Counter32, -- Q.752, 5.6
    mtpOmSpSiReceivedUPUnavailable		Counter32, -- Q.752, 5.7
    mtpOmSpSiHandledOctetsSIO			Counter32, -- Q.752, 6.3
    mtpOmSpSiStatus				RowStatus
}

mtpOmSpSiCode OBJECT-TYPE
    SYNTAX	MtpUserPart
    MAX-ACCESS	not-accessible
    STATUS	current
    DESCRIPTION
	""
    ::= { mtpOmSpSiEntry 1 }

mtpOmSpSiValidIntervals OBJECT-TYPE
    SYNTAX	HCPerfValidIntervals
    MAX-ACCESS	read-only
    STATUS	current
    DESCRIPTION
	""
    ::= { mtpOmSpSiEntry 2 }

mtpOmSpSiTimeDiscontinuity OBJECT-TYPE
    SYNTAX	TimeStamp
    MAX-ACCESS	read-only
    STATUS	current
    DESCRIPTION
	""
    ::= { mtpOmSpSiEntry 3 }

mtpOmSpSiTransmittedUPUnavailable OBJECT-TYPE
    SYNTAX	Counter32
    UNITS	"UPUs"
    MAX-ACCESS	read-only
    STATUS	current
    DESCRIPTION
	"This attribute represents measurement T1.116.2/5.6.
	 See also Chapter T1.111.4 11.7.2.
	 
	 User Part Unavailable (UPU) MSU transmitted correlated as 
	 events per user part for each signalling point, collected on a 
	 first and interval basis.  This is a non-obligatory measurement 
	 that is permanently activated when available.  The measurement 
	 is used for fault detection, near real-time monitoring, 
	 configuration management and performance management.

	 When this measurement exceeds an implementation-dependent 
	 threshold, the management process is informed with a Quality of 
	 Service alarm indication."
    REFERENCE
	"ANSI T1.116.1D transmittedUPUnavailable.
	 ANSI T1.116.2/2000 Table 5 (5.6).
	 ANSI T1.111.4/2000 11.7.2.
	 ITU-T Rec. Q.751.1 (10/95) : transmitedUPUnavailable.
	 ITU-T Rec. Q.752 (1997) : Table 5/Q.752, 5.6."
    ::= { mtpOmSpSiEntry 4 }

mtpOmSpSiReceivedUPUnavailable OBJECT-TYPE
    SYNTAX	Counter32
    UNITS	"UPUs"
    MAX-ACCESS	read-only
    STATUS	current
    DESCRIPTION
	"This attribute represents measurement T1.116.2/5.7.
	 See also Chapter T1.111.4 11.7.2.
	 
	 User Part Unavailable (UPU) MSU received correlated as events 
	 per user part for each signalling point, collected on a first 
	 and interval basis.  This is a non-obligatory measurement that 
	 is permanently activated when available.  The measurement is 
	 used for fault-detection, near real-time monitoring, 
	 configuration management and performance management.
	 
	 When this measurement exceeds an implementation-dependent 
	 threshold, the management process is informed with a Quality of 
	 Service alarm indication.  Note that for a UPU for an 
	 unequipped MTP user results in the management process being 
	 informed immediately."
    REFERENCE
	"ANSI T1.116.1D receivedUPUnavailable.
	 ANSI T1.116.2/2000 Table 5 (5.7).
	 ANSI T1.111.4/2000 11.7.2.
	 ITU-T Rec. Q.751.1 (10/95) : receivedUPUnavailable.
	 ITU-T Rec. Q.752 (1997) : Table 5/Q.752, 5.7."
    ::= { mtpOmSpSiEntry 5 }

mtpOmSpSiHandledOctetsSIO OBJECT-TYPE
    SYNTAX	Counter32
    UNITS	"octets"
    MAX-ACCESS	read-only
    STATUS	current
    DESCRIPTION
	"This attribute represents measurement T1.116.2/6.3."
    REFERENCE
	"ANSI T1.116.1D handledOctetsSIO
	 ITU-T Rec. Q.751.1 (10/95) : handledOctetsSIO.
	 ITU-T Rec. Q.752 (1997) : Table 6/Q.752, 6.3."
    ::= { mtpOmSpSiEntry 6 }

mtpOmSpSiStatus OBJECT-TYPE
    SYNTAX	RowStatus
    MAX-ACCESS	read-create
    STATUS	current
    DESCRIPTION
	""
    REFERENCE
	"STD 58, SNMPv2-TC RowStatus."
    ::= { mtpOmSpSiEntry 7 }


-- ====================================================================

mtpOmSpSiInt5minTable OBJECT-TYPE
    SYNTAX	SEQUENCE OF MtpOmSpSiInt5minEntry
    MAX-ACCESS	not-accessible
    STATUS	current
    DESCRIPTION
	"Provides a table of optional 5-minute interval historical 
	 signalling point operational measurements broken out be SI 
	 code."
    ::= { mtpOmSpStats 5 }

mtpOmSpSiInt5minEntry OBJECT-TYPE
    SYNTAX	MtpOmSpSiInt5minEntry
    MAX-ACCESS	not-accessible
    STATUS	current
    DESCRIPTION
	""
    INDEX	{
	mtpSpId, -- shared index
	mtpOmSpSiCode,
	mtpOmSpSiInt5minInterval 
    }
    ::= { mtpOmSpSiInt5minTable 1 }

MtpOmSpSiInt5minEntry ::= SEQUENCE {
    mtpOmSpSiInt5minInterval			Unsigned32,
    mtpOmSpSiInt5minTimeStamp			TimeStamp,
    mtpOmSpSiInt5minTransmittedUPUnavailable	PerfIntervalCount, -- Q.752, 5.6
    mtpOmSpSiInt5minReceivedUPUnavailable	PerfIntervalCount, -- Q.752, 5.7
    mtpOmSpSiInt5minHandledOctetsSIO		PerfIntervalCount  -- Q.752, 6.3
}

mtpOmSpSiInt5minInterval OBJECT-TYPE
    SYNTAX	Unsigned32
    MAX-ACCESS	not-accessible
    STATUS	current
    DESCRIPTION
	""
    ::= { mtpOmSpSiInt5minEntry 1 }

mtpOmSpSiInt5minTimeStamp OBJECT-TYPE
    SYNTAX	TimeStamp
    MAX-ACCESS	read-only
    STATUS	current
    DESCRIPTION
	""
    ::= { mtpOmSpSiInt5minEntry 2 }

mtpOmSpSiInt5minTransmittedUPUnavailable OBJECT-TYPE
    SYNTAX	PerfIntervalCount
    UNITS	"UPUs"
    MAX-ACCESS	read-only
    STATUS	current
    DESCRIPTION
	"This attribute represents measurement T1.116.2/5.6.
	 See also Chapter T1.111.4 11.7.2.
	 
	 User Part Unavailable (UPU) MSU transmitted correlated as 
	 events per user part for each signalling point, collected on a 
	 first and interval basis.  This is a non-obligatory measurement 
	 that is permanently activated when available.  The measurement 
	 is used for fault detection, near real-time monitoring, 
	 configuration management and performance management.

	 When this measurement exceeds an implementation-dependent 
	 threshold, the management process is informed with a Quality of 
	 Service alarm indication."
    REFERENCE
	"ANSI T1.116.1D transmittedUPUnavailable.
	 ANSI T1.116.2/2000 Table 5 (5.6).
	 ANSI T1.111.4/2000 11.7.2.
	 ITU-T Rec. Q.751.1 (10/95) : transmitedUPUnavailable.
	 ITU-T Rec. Q.752 : Table 5/Q.752, 5.6."
    ::= { mtpOmSpSiInt5minEntry 3 }

mtpOmSpSiInt5minReceivedUPUnavailable OBJECT-TYPE
    SYNTAX	PerfIntervalCount
    UNITS	"UPUs"
    MAX-ACCESS	read-only
    STATUS	current
    DESCRIPTION
	"This attribute represents measurement T1.116.2/5.7.
	 See also Chapter T1.111.4 11.7.2.
	 
	 User Part Unavailable (UPU) MSU received correlated as events 
	 per user part for each signalling point, collected on a first 
	 and interval basis.  This is a non-obligatory measurement that 
	 is permanently activated when available.  The measurement is 
	 used for fault-detection, near real-time monitoring, 
	 configuration management and performance management.
	 
	 When this measurement exceeds an implementation-dependent 
	 threshold, the management process is informed with a Quality of 
	 Service alarm indication.  Note that for a UPU for an 
	 unequipped MTP user results in the management process being 
	 informed immediately."
    REFERENCE
	"ANSI T1.116.1D receivedUPUnavailable.
	 ANSI T1.116.2/2000 Table 5 (5.7).
	 ANSI T1.111.4/2000 11.7.2.
	 ITU-T Rec. Q.751.1 (10/95) : receivedUPUnavailable.
	 ITU-T Rec. Q.752 : Table 5/Q.752, 5.7."
    ::= { mtpOmSpSiInt5minEntry 4 }

mtpOmSpSiInt5minHandledOctetsSIO OBJECT-TYPE
    SYNTAX	PerfIntervalCount
    UNITS	"octets"
    MAX-ACCESS	read-only
    STATUS	current
    DESCRIPTION
	"This attribute represents measurement T1.116.2/6.3."
    REFERENCE
	"ANSI T1.116.1D handledOctetsSIO
	 ITU-T Rec. Q.751.1 (10/95) : handledOctetsSIO.
	 ITU-T Rec. Q.752 (1997) : Table 6/Q.752, 6.3."
    ::= { mtpOmSpSiInt5minEntry 5 }


-- ====================================================================

mtpOmSpSiInt15minTable OBJECT-TYPE
    SYNTAX	SEQUENCE OF MtpOmSpSiInt15minEntry
    MAX-ACCESS	not-accessible
    STATUS	current
    DESCRIPTION
	"Provides a table of optional 15-minute interval historical 
	 signalling point operational measurements broken out be SI 
	 code."
    ::= { mtpOmSpStats 6 }

mtpOmSpSiInt15minEntry OBJECT-TYPE
    SYNTAX	MtpOmSpSiInt15minEntry
    MAX-ACCESS	not-accessible
    STATUS	current
    DESCRIPTION
	""
    INDEX	{
	mtpSpId, -- shared index
	mtpOmSpSiCode,
	mtpOmSpSiInt15minInterval
    }
    ::= { mtpOmSpSiInt15minTable 1 }

MtpOmSpSiInt15minEntry ::= SEQUENCE {
    mtpOmSpSiInt15minInterval			Unsigned32,
    mtpOmSpSiInt15minTimeStamp			TimeStamp,
    mtpOmSpSiInt15minTransmittedUPUnavailable	PerfIntervalCount, -- Q.752, 5.6
    mtpOmSpSiInt15minReceivedUPUnavailable	PerfIntervalCount, -- Q.752, 5.7
    mtpOmSpSiInt15minHandledOctetsSIO		PerfIntervalCount  -- Q.752, 6.3
}

mtpOmSpSiInt15minInterval OBJECT-TYPE
    SYNTAX	Unsigned32
    MAX-ACCESS	not-accessible
    STATUS	current
    DESCRIPTION
	""
    ::= { mtpOmSpSiInt15minEntry 1 }

mtpOmSpSiInt15minTimeStamp OBJECT-TYPE
    SYNTAX	TimeStamp
    MAX-ACCESS	read-only
    STATUS	current
    DESCRIPTION
	""
    ::= { mtpOmSpSiInt15minEntry 2 }

mtpOmSpSiInt15minTransmittedUPUnavailable OBJECT-TYPE
    SYNTAX	PerfIntervalCount
    UNITS	"UPUs"
    MAX-ACCESS	read-only
    STATUS	current
    DESCRIPTION
	"This attribute represents measurement T1.116.2/5.6.
	 See also Chapter T1.111.4 11.7.2.
	 
	 User Part Unavailable (UPU) MSU transmitted correlated as 
	 events per user part for each signalling point, collected on a 
	 first and interval basis.  This is a non-obligatory measurement 
	 that is permanently activated when available.  The measurement 
	 is used for fault detection, near real-time monitoring, 
	 configuration management and performance management.

	 When this measurement exceeds an implementation-dependent 
	 threshold, the management process is informed with a Quality of 
	 Service alarm indication."
    REFERENCE
	"ANSI T1.116.1D transmittedUPUnavailable.
	 ANSI T1.116.2/2000 Table 5 (5.6).
	 ANSI T1.111.4/2000 11.7.2.
	 ITU-T Rec. Q.751.1 (10/95) : transmitedUPUnavailable.
	 ITU-T Rec. Q.752 : Table 5/Q.752, 5.6."
    ::= { mtpOmSpSiInt15minEntry 3 }

mtpOmSpSiInt15minReceivedUPUnavailable OBJECT-TYPE
    SYNTAX	PerfIntervalCount
    UNITS	"UPUs"
    MAX-ACCESS	read-only
    STATUS	current
    DESCRIPTION
	"This attribute represents measurement T1.116.2/5.7.
	 See also Chapter T1.111.4 11.7.2.
	 
	 User Part Unavailable (UPU) MSU received correlated as events 
	 per user part for each signalling point, collected on a first 
	 and interval basis.  This is a non-obligatory measurement that 
	 is permanently activated when available.  The measurement is 
	 used for fault-detection, near real-time monitoring, 
	 configuration management and performance management.
	 
	 When this measurement exceeds an implementation-dependent 
	 threshold, the management process is informed with a Quality of 
	 Service alarm indication.  Note that for a UPU for an 
	 unequipped MTP user results in the management process being 
	 informed immediately."
    REFERENCE
	"ANSI T1.116.1D receivedUPUnavailable.
	 ANSI T1.116.2/2000 Table 5 (5.7).
	 ANSI T1.111.4/2000 11.7.2.
	 ITU-T Rec. Q.751.1 (10/95) : receivedUPUnavailable.
	 ITU-T Rec. Q.752 : Table 5/Q.752, 5.7."
    ::= { mtpOmSpSiInt15minEntry 4 }

mtpOmSpSiInt15minHandledOctetsSIO OBJECT-TYPE
    SYNTAX	PerfIntervalCount
    UNITS	"octets"
    MAX-ACCESS	read-only
    STATUS	current
    DESCRIPTION
	"This attribute represents measurement T1.116.2/6.3."
    REFERENCE
	"ANSI T1.116.1D handledOctetsSIO
	 ITU-T Rec. Q.751.1 (10/95) : handledOctetsSIO.
	 ITU-T Rec. Q.752 (1997) : Table 6/Q.752, 6.3."
    ::= { mtpOmSpSiInt15minEntry 5 }


-- ====================================================================

mtpOmSpStudyTable OBJECT-TYPE
    SYNTAX	SEQUENCE OF MtpOmSpStudyEntry
    MAX-ACCESS	not-accessible
    STATUS	current
    DESCRIPTION
	""
    ::= { mtpOmSpStats 7 }

mtpOmSpStudyEntry OBJECT-TYPE
    SYNTAX	MtpOmSpStudyEntry
    MAX-ACCESS	not-accessible
    STATUS	current
    DESCRIPTION
	""
    INDEX	{
	mtpOmSpStudyId
    }
    ::= { mtpOmSpStudyTable 1 }

MtpOmSpStudyEntry ::= SEQUENCE {
    mtpOmSpStudyId				Unsigned32,
    mtpOmSpStudyValidIntervals			HCPerfValidIntervals,
    mtpOmSpStudyTimeDiscontinuity		TimeStamp,
    mtpOmSpStudyHandledOctetsOpcDpcSio		Counter32, -- Q.752, 6.6
    mtpOmSpStudyHandledMSUsOpcDpcSio		Counter32, -- Q.752, 6.7
    mtpOmSpStudyStatus				RowStatus
}

mtpOmSpStudyId OBJECT-TYPE
    SYNTAX	Unsigned32
    MAX-ACCESS	not-accessible
    STATUS	current
    DESCRIPTION
	"Provides a non-zero index into the signalling point study 
	 table."
    ::= { mtpOmSpStudyEntry 1 }

mtpOmSpStudyValidIntervals OBJECT-TYPE
    SYNTAX	HCPerfValidIntervals
    MAX-ACCESS	read-only
    STATUS	current
    DESCRIPTION
	""
    ::= { mtpOmSpStudyEntry 2 }

mtpOmSpStudyTimeDiscontinuity OBJECT-TYPE
    SYNTAX	TimeStamp
    MAX-ACCESS	read-only
    STATUS	current
    DESCRIPTION
	""
    ::= { mtpOmSpStudyEntry 3 }

mtpOmSpStudyHandledOctetsOpcDpcSio OBJECT-TYPE
    SYNTAX	Counter32
    UNITS	"octets"
    MAX-ACCESS	read-only
    STATUS	current
    DESCRIPTION
	"This attribute represents measurement T1.116.2/6.6.
	 
	 Number of SIF and SIO octets handled with given OPC, DPC and 
	 SIO in units of number of MSUs per OPC, DPC and SIO combination 
	 collected over a 5- or 30-minute interval.  This operational 
	 measurement is non-obligatory.  This measurement may be used 
	 for performance managment, accounting management, and network 
	 administration and planning."
    REFERENCE
	"ANSI T1.116.1D handledOctetsOpcDpcSio.
	 ANSI T1.116.2/2000 Table 6 (6.6).
	 ITU-T Rec. Q.751.1 (10/95) : handledOctetsOpcDpcSio.
	 ITU-T Rec. Q.752 (1997) : Table 6/Q.752, 6.6."
    ::= { mtpOmSpStudyEntry 4 }

mtpOmSpStudyHandledMSUsOpcDpcSio OBJECT-TYPE
    SYNTAX	Counter32
    UNITS	"MSUs"
    MAX-ACCESS	read-only
    STATUS	current
    DESCRIPTION
	"This attribute represents measurement T1.116.2/6.7.

	 This measurement measures the number of handled MSU for a given 
	 Signalling Point where the count is broken out on the basis of 
	 the DPC, OPC and SIO fields of the MTP header contained in the 
	 MSU."
    REFERENCE
	"ANSI T1.116.2/2000 Clause 6.7.
	 ANSI T1.116.1D handledMSUsOpcDpcSio.
	 ITU-T Rec. Q.751.1 (10/95) : handledMSUsOpcDpcSio.
	 ITU-T Rec. Q.752 (1997) : Table 6/Q.752, 6.7."
    ::= { mtpOmSpStudyEntry 5 }

mtpOmSpStudyStatus OBJECT-TYPE
    SYNTAX	RowStatus
    MAX-ACCESS	read-create
    STATUS	current
    DESCRIPTION
	""
    REFERENCE
	"STD 58, SNMPv2-TC RowStatus."
    ::= { mtpOmSpStudyEntry 6 }


-- ====================================================================

mtpOmSpStudyInt5minTable OBJECT-TYPE
    SYNTAX	SEQUENCE OF MtpOmSpStudyInt5minEntry
    MAX-ACCESS	not-accessible
    STATUS	current
    DESCRIPTION
	""
    ::= { mtpOmSpStats 8 }

mtpOmSpStudyInt5minEntry OBJECT-TYPE
    SYNTAX	MtpOmSpStudyInt5minEntry
    MAX-ACCESS	not-accessible
    STATUS	current
    DESCRIPTION
	""
    INDEX	{
	mtpOmSpStudyId,
	mtpOmSpStudyInt5minInterval
    }
    ::= { mtpOmSpStudyInt5minTable 1 }

MtpOmSpStudyInt5minEntry ::= SEQUENCE {
    mtpOmSpStudyInt5minInterval			Unsigned32,
    mtpOmSpStudyInt5minTimeStamp		TimeStamp,
    mtpOmSpStudyInt5minHandledOctetsOpcDpcSio	PerfIntervalCount, -- Q.752, 6.6
    mtpOmSpStudyInt5minHandledMSUsOpcDpcSio	PerfIntervalCount  -- Q.752, 6.7
}

mtpOmSpStudyInt5minInterval OBJECT-TYPE
    SYNTAX	Unsigned32
    MAX-ACCESS	not-accessible
    STATUS	current
    DESCRIPTION
	""
    ::= { mtpOmSpStudyInt5minEntry 1 }

mtpOmSpStudyInt5minTimeStamp OBJECT-TYPE
    SYNTAX	TimeStamp
    MAX-ACCESS	read-only
    STATUS	current
    DESCRIPTION
	""
    ::= { mtpOmSpStudyInt5minEntry 2 }

mtpOmSpStudyInt5minHandledOctetsOpcDpcSio OBJECT-TYPE
    SYNTAX	PerfIntervalCount
    UNITS	"octets"
    MAX-ACCESS	read-only
    STATUS	current
    DESCRIPTION
	"This attribute represents measurement T1.116.2/6.6.
	 
	 Number of SIF and SIO octets handled with given OPC, DPC and 
	 SIO in units of number of MSUs per OPC, DPC and SIO combination 
	 collected over a 5- or 30-minute interval.  This operational 
	 measurement is non-obligatory.  This measurement may be used 
	 for performance managment, accounting management, and network 
	 administration and planning."
    REFERENCE
	"ANSI T1.116.1D handledOctetsOpcDpcSio.
	 ANSI T1.116.2/2000 Table 6 (6.6).
	 ITU-T Rec. Q.751.1 (10/95) : handledOctetsOpcDpcSio.
	 ITU-T Rec. Q.752 (1997) : Table 6/Q.752, 6.6."
    ::= { mtpOmSpStudyInt5minEntry 3 }

mtpOmSpStudyInt5minHandledMSUsOpcDpcSio OBJECT-TYPE
    SYNTAX	PerfIntervalCount
    UNITS	"MSUs"
    MAX-ACCESS	read-only
    STATUS	current
    DESCRIPTION
	"This attribute represents measurement T1.116.2/6.7.

	 This measurement measures the number of handled MSU for a given 
	 Signalling Point where the count is broken out on the basis of 
	 the DPC, OPC and SIO fields of the MTP header contained in the 
	 MSU."
    REFERENCE
	"ANSI T1.116.2/2000 Clause 6.7.
	 ANSI T1.116.1D handledMSUsOpcDpcSio.
	 ITU-T Rec. Q.751.1 (10/95) : handledMSUsOpcDpcSio.
	 ITU-T Rec. Q.752 (1997) : Table 6/Q.752, 6.7."
    ::= { mtpOmSpStudyInt5minEntry 4 }


-- ====================================================================

mtpOmSpStudyInt15minTable OBJECT-TYPE
    SYNTAX	SEQUENCE OF MtpOmSpStudyInt15minEntry
    MAX-ACCESS	not-accessible
    STATUS	current
    DESCRIPTION
	""
    ::= { mtpOmSpStats 9 }

mtpOmSpStudyInt15minEntry OBJECT-TYPE
    SYNTAX	MtpOmSpStudyInt15minEntry
    MAX-ACCESS	not-accessible
    STATUS	current
    DESCRIPTION
	""
    INDEX	{
	mtpOmSpStudyId,
	mtpOmSpStudyInt15minInterval
    }
    ::= { mtpOmSpStudyInt15minTable 1 }

MtpOmSpStudyInt15minEntry ::= SEQUENCE {
    mtpOmSpStudyInt15minInterval		Unsigned32,
    mtpOmSpStudyInt15minTimeStamp		TimeStamp,
    mtpOmSpStudyInt15minHandledOctetsOpcDpcSio	PerfIntervalCount, -- Q.752, 6.6
    mtpOmSpStudyInt15minHandledMSUsOpcDpcSio	PerfIntervalCount  -- Q.752, 6.7
}

mtpOmSpStudyInt15minInterval OBJECT-TYPE
    SYNTAX	Unsigned32
    MAX-ACCESS	not-accessible
    STATUS	current
    DESCRIPTION
	""
    ::= { mtpOmSpStudyInt15minEntry 1 }

mtpOmSpStudyInt15minTimeStamp OBJECT-TYPE
    SYNTAX	TimeStamp
    MAX-ACCESS	read-only
    STATUS	current
    DESCRIPTION
	""
    ::= { mtpOmSpStudyInt15minEntry 2 }

mtpOmSpStudyInt15minHandledOctetsOpcDpcSio OBJECT-TYPE
    SYNTAX	PerfIntervalCount
    UNITS	"octets"
    MAX-ACCESS	read-only
    STATUS	current
    DESCRIPTION
	"This attribute represents measurement T1.116.2/6.6.
	 
	 Number of SIF and SIO octets handled with given OPC, DPC and 
	 SIO in units of number of MSUs per OPC, DPC and SIO combination 
	 collected over a 5- or 30-minute interval.  This operational 
	 measurement is non-obligatory.  This measurement may be used 
	 for performance managment, accounting management, and network 
	 administration and planning."
    REFERENCE
	"ANSI T1.116.1D handledOctetsOpcDpcSio.
	 ANSI T1.116.2/2000 Table 6 (6.6).
	 ITU-T Rec. Q.751.1 (10/95) : handledOctetsOpcDpcSio.
	 ITU-T Rec. Q.752 (1997) : Table 6/Q.752, 6.6."
    ::= { mtpOmSpStudyInt15minEntry 3 }

mtpOmSpStudyInt15minHandledMSUsOpcDpcSio OBJECT-TYPE
    SYNTAX	PerfIntervalCount
    UNITS	"MSUs"
    MAX-ACCESS	read-only
    STATUS	current
    DESCRIPTION
	"This attribute represents measurement T1.116.2/6.7.

	 This measurement measures the number of handled MSU for a given 
	 Signalling Point where the count is broken out on the basis of 
	 the DPC, OPC and SIO fields of the MTP header contained in the 
	 MSU."
    REFERENCE
	"ANSI T1.116.2/2000 Clause 6.7.
	 ANSI T1.116.1D handledMSUsOpcDpcSio.
	 ITU-T Rec. Q.751.1 (10/95) : handledMSUsOpcDpcSio.
	 ITU-T Rec. Q.752 (1997) : Table 6/Q.752, 6.7."
    ::= { mtpOmSpStudyInt15minEntry 4 }


-- ====================================================================

mtpOmSpStudyMapTable OBJECT-TYPE
    SYNTAX	SEQUENCE OF MtpOmSpStudyMapEntry
    MAX-ACCESS	not-accessible
    STATUS	current
    DESCRIPTION
	""
    ::= { mtpOmSpStats 10 }

mtpOmSpStudyMapEntry OBJECT-TYPE
    SYNTAX	MtpOmSpStudyMapEntry
    MAX-ACCESS	not-accessible
    STATUS	current
    DESCRIPTION
	""
    INDEX	{
	mtpSpId, -- shared index
	mtpOmOpcRsId,	-- OPC value
	mtpOmDpcRsId,	-- DPC value
	mtpOmSpSiCode,	-- SI code
	mtpOmSpStudyId
    }
    ::= { mtpOmSpStudyMapTable 1 }

MtpOmSpStudyMapEntry ::= SEQUENCE {
    mtpOmOpcRsId				Unsigned32,
    mtpOmDpcRsId				Unsigned32,
    mtpOmSpStudyMapStatus			RowStatus
}

mtpOmOpcRsId OBJECT-TYPE
    SYNTAX	Unsigned32
    MAX-ACCESS	not-accessible
    STATUS	current
    DESCRIPTION
	"Provides an OPC index into the table.  The is the index of the 
	 originating signalling point in the route set table 
	 mtpOmRsTable.  The entry must exist or the creation of a row will 
	 be refused."
    ::= { mtpOmSpStudyMapEntry 1 }

mtpOmDpcRsId OBJECT-TYPE
    SYNTAX	Unsigned32
    MAX-ACCESS	not-accessible
    STATUS	current
    DESCRIPTION
	"Provides an DPC index into the table.  The is the index of the 
	 destination signalling point in the route set table 
	 mtpOmRsTable.  The entry must exist or the creation of a row will 
	 be refused."
    ::= { mtpOmSpStudyMapEntry 2 }

mtpOmSpStudyMapStatus OBJECT-TYPE
    SYNTAX	RowStatus
    MAX-ACCESS	read-create
    STATUS	current
    DESCRIPTION
	""
    REFERENCE
	"STD 58, SNMPv2-TC RowStatus."
    ::= { mtpOmSpStudyMapEntry 3 }


-- ====================================================================

mtpOmRsTable OBJECT-TYPE
    SYNTAX	SEQUENCE OF MtpOmRsEntry
    MAX-ACCESS	not-accessible
    STATUS	current
    DESCRIPTION
	""
    ::= { mtpOmRsStats 1 }

mtpOmRsEntry OBJECT-TYPE
    SYNTAX	MtpOmRsEntry
    MAX-ACCESS	not-accessible
    STATUS	current
    DESCRIPTION
	""
    INDEX	{
	mtpSpId,
	mtpRsId
    }
    ::= { mtpOmRsTable 1 }

MtpOmRsEntry ::= SEQUENCE {
    mtpOmRsValidIntervals			HCPerfValidIntervals,
    mtpOmRsTimeDiscontinuity			TimeStamp,
    mtpOmRsReceivedOctetsOPC			Counter32, -- Q.752, 6.1
    mtpOmRsTransmittedOctetsDPC			Counter32, -- Q.752, 6.2
    mtpOmRsReceivedMSUsOpc			Counter32,
    mtpOmRsTransmittedMSUsDpc			Counter32,
    mtpOmRsRouteSetUnavailable			Counter32, -- Q.752, 4.9
    mtpOmRsRouteSetUnavailableDuration		Counter32  -- Q.752, 4.10
}

mtpOmRsValidIntervals OBJECT-TYPE
    SYNTAX	HCPerfValidIntervals
    MAX-ACCESS	read-only
    STATUS	current
    DESCRIPTION
	""
    ::= { mtpOmRsEntry 1 }

mtpOmRsTimeDiscontinuity OBJECT-TYPE
    SYNTAX	TimeStamp
    MAX-ACCESS	read-only
    STATUS	current
    DESCRIPTION
	""
    ::= { mtpOmRsEntry 2 }

mtpOmRsReceivedOctetsOPC OBJECT-TYPE
    SYNTAX	Counter32
    UNITS	"octets"
    MAX-ACCESS	read-only
    STATUS	current
    DESCRIPTION
	"This attribute represents measurement T1.116.2/6.1.
	 
	 The number of SIF and SIO octets received with given OPC (or 
	 OPC set) collected over an interval of 15 or 30 minutes.  This 
	 is a non-obligatory measurement that may be derived (from 6.6).  
	 This measurement may be used for performance analysis, 
	 accounting management, or network administration and planning."
    REFERENCE
	"ANSI T1.116.1D receivedOctetsOPC
	 ITU-T Rec. Q.751.1 (10/95) : receivedOctetsOPC.
	 ITU-T Rec. Q.752 (1997) : Table 6/Q.752, 6.1."
    ::= { mtpOmRsEntry 3 }

mtpOmRsTransmittedOctetsDPC OBJECT-TYPE
    SYNTAX	Counter32
    UNITS	"octets"
    MAX-ACCESS	read-only
    STATUS	current
    DESCRIPTION
	"This attribute represents measurement T1.116.2/6.2."
    REFERENCE
	"ANSI T1.116.1D transmittedOctetsDPC
	 ITU-T Rec. Q.751.1 (10/95) : transmittedOctetsDPC.
	 ITU-T Rec. Q.752 (1997) : Table 6/Q.752, 6.2."
    ::= { mtpOmRsEntry 4 }

mtpOmRsReceivedMSUsOpc OBJECT-TYPE
    SYNTAX	Counter32
    UNITS	"MSUs"
    MAX-ACCESS	read-only
    STATUS	current
    DESCRIPTION
	""
    ::= { mtpOmRsEntry 5 }

mtpOmRsTransmittedMSUsDpc OBJECT-TYPE
    SYNTAX	Counter32
    UNITS	"MSUs"
    MAX-ACCESS	read-only
    STATUS	current
    DESCRIPTION
	""
    ::= { mtpOmRsEntry 6 }

mtpOmRsRouteSetUnavailable OBJECT-TYPE
    SYNTAX	Counter32
    MAX-ACCESS	read-only
    STATUS	current
    DESCRIPTION
	"This attribute represents measurement T1.116.2/4.9.
	 See also Chapter T1.111.4 11.2.2.
	 
	 These are not basic measurements and can be derived (from 4.11 
	 and 4.12).  This measurement is obligatory in international 
	 networks."
    REFERENCE
	"ANSI T1.116.1D routeSetUnavailable
	 ITU-T Rec. Q.751.1, (10/95) : routeSetUnavailable.
	 ITU-T Rec. Q.752, (1997) : Table 3/Q.752 4.9"
    ::= { mtpOmRsEntry 7 }

mtpOmRsRouteSetUnavailableDuration OBJECT-TYPE
    SYNTAX	Counter32
    UNITS	"seconds"
    MAX-ACCESS	read-only
    STATUS	current
    DESCRIPTION
	"This attribute represents measurement T1.116.2/4.10.
	 See also Chapter T1.111.4 11.2.1.
	 
	 These are not basic measurements and can be derived (from 4.11 
	 and 4.12).  This measurement is obligatory in international 
	 networks."
    REFERENCE
	"ANSI T1.116.1D routeSetUnavailableDuration
	 ITU-T Rec. Q.751.1, (10/95) : routeSetUnavailableDuration.
	 ITU-T Rec. Q.752, (1997) : Table 3/Q.752 4.10"
    ::= { mtpOmRsEntry 8 }


-- ====================================================================

mtpOmRsInt5minTable OBJECT-TYPE
    SYNTAX	SEQUENCE OF MtpOmRsInt5minEntry
    MAX-ACCESS	not-accessible
    STATUS	current
    DESCRIPTION
	""
    ::= { mtpOmRsStats 2 }

mtpOmRsInt5minEntry OBJECT-TYPE
    SYNTAX	MtpOmRsInt5minEntry
    MAX-ACCESS	not-accessible
    STATUS	current
    DESCRIPTION
	""
    INDEX	{
	mtpSpId,
	mtpRsId,
	mtpOmRsInt5minInterval
    }
    ::= { mtpOmRsInt5minTable 1 }

MtpOmRsInt5minEntry ::= SEQUENCE {
    mtpOmRsInt5minInterval			Unsigned32,
    mtpOmRsInt5minTimeStamp			TimeStamp,
    mtpOmRsInt5minReceivedOctetsOPC		PerfIntervalCount, -- Q.752, 6.1
    mtpOmRsInt5minTransmittedOctetsDPC		PerfIntervalCount, -- Q.752, 6.2
    mtpOmRsInt5minReceivedMSUsOpc		PerfIntervalCount,
    mtpOmRsInt5minTransmittedMSUsDpc		PerfIntervalCount,
    mtpOmRsInt5minRouteSetUnavailable		PerfIntervalCount, -- Q.752, 4.9
    mtpOmRsInt5minRouteSetUnavailableDuration	PerfIntervalCount  -- Q.752, 4.10
}

mtpOmRsInt5minInterval OBJECT-TYPE
    SYNTAX	Unsigned32
    MAX-ACCESS	not-accessible
    STATUS	current
    DESCRIPTION
	""
    ::= { mtpOmRsInt5minEntry 1 }

mtpOmRsInt5minTimeStamp OBJECT-TYPE
    SYNTAX	TimeStamp
    MAX-ACCESS	read-only
    STATUS	current
    DESCRIPTION
	""
    ::= { mtpOmRsInt5minEntry 2 }

mtpOmRsInt5minReceivedOctetsOPC OBJECT-TYPE
    SYNTAX	PerfIntervalCount
    UNITS	"octets"
    MAX-ACCESS	read-only
    STATUS	current
    DESCRIPTION
	"This attribute represents measurement T1.116.2/6.1.
	 
	 The number of SIF and SIO octets received with given OPC (or 
	 OPC set) collected over an interval of 15 or 30 minutes.  This 
	 is a non-obligatory measurement that may be derived (from 6.6).  
	 This measurement may be used for performance analysis, 
	 accounting management, or network administration and planning."
    REFERENCE
	"ANSI T1.116.1D receivedOctetsOPC
	 ITU-T Rec. Q.751.1 (10/95) : receivedOctetsOPC.
	 ITU-T Rec. Q.752 (1997) : Table 6/Q.752, 6.1."
    ::= { mtpOmRsInt5minEntry 3 }

mtpOmRsInt5minTransmittedOctetsDPC OBJECT-TYPE
    SYNTAX	PerfIntervalCount
    UNITS	"octets"
    MAX-ACCESS	read-only
    STATUS	current
    DESCRIPTION
	"This attribute represents measurement T1.116.2/6.2."
    REFERENCE
	"ANSI T1.116.1D transmittedOctetsDPC
	 ITU-T Rec. Q.751.1 (10/95) : transmittedOctetsDPC.
	 ITU-T Rec. Q.752 (1997) : Table 6/Q.752, 6.2."
    ::= { mtpOmRsInt5minEntry 4 }

mtpOmRsInt5minReceivedMSUsOpc OBJECT-TYPE
    SYNTAX	PerfIntervalCount
    UNITS	"MSUs"
    MAX-ACCESS	read-only
    STATUS	current
    DESCRIPTION
	""
    ::= { mtpOmRsInt5minEntry 5 }

mtpOmRsInt5minTransmittedMSUsDpc OBJECT-TYPE
    SYNTAX	PerfIntervalCount
    UNITS	"MSUs"
    MAX-ACCESS	read-only
    STATUS	current
    DESCRIPTION
	""
    ::= { mtpOmRsInt5minEntry 6 }

mtpOmRsInt5minRouteSetUnavailable OBJECT-TYPE
    SYNTAX	PerfIntervalCount
    MAX-ACCESS	read-only
    STATUS	current
    DESCRIPTION
	"This attribute represents measurement T1.116.2/4.9.
	 See also Chapter T1.111.4 11.2.2.
	 
	 These are not basic measurements and can be derived (from 4.11 
	 and 4.12).  This measurement is obligatory in international 
	 networks."
    REFERENCE
	"ANSI T1.116.1D routeSetUnavailable
	 ITU-T Rec. Q.751.1, (10/95) : routeSetUnavailable.
	 ITU-T Rec. Q.752, (1997) : Table 3/Q.752 4.9"
    ::= { mtpOmRsInt5minEntry 7 }

mtpOmRsInt5minRouteSetUnavailableDuration OBJECT-TYPE
    SYNTAX	PerfIntervalCount
    UNITS	"seconds"
    MAX-ACCESS	read-only
    STATUS	current
    DESCRIPTION
	"This attribute represents measurement T1.116.2/4.10.
	 See also Chapter T1.111.4 11.2.1.
	 
	 These are not basic measurements and can be derived (from 4.11 
	 and 4.12).  This measurement is obligatory in international 
	 networks."
    REFERENCE
	"ANSI T1.116.1D routeSetUnavailableDuration
	 ITU-T Rec. Q.751.1, (10/95) : routeSetUnavailableDuration.
	 ITU-T Rec. Q.752, (1997) : Table 3/Q.752 4.10"
    ::= { mtpOmRsInt5minEntry 8 }


-- ====================================================================

mtpOmRsInt15minTable OBJECT-TYPE
    SYNTAX	SEQUENCE OF MtpOmRsInt15minEntry
    MAX-ACCESS	not-accessible
    STATUS	current
    DESCRIPTION
	""
    ::= { mtpOmRsStats 3 }

mtpOmRsInt15minEntry OBJECT-TYPE
    SYNTAX	MtpOmRsInt15minEntry
    MAX-ACCESS	not-accessible
    STATUS	current
    DESCRIPTION
	""
    INDEX	{
	mtpSpId,
	mtpRsId,
	mtpOmRsInt15minInterval
    }
    ::= { mtpOmRsInt15minTable 1 }

MtpOmRsInt15minEntry ::= SEQUENCE {
    mtpOmRsInt15minInterval			Unsigned32,
    mtpOmRsInt15minTimeStamp			TimeStamp,
    mtpOmRsInt15minReceivedOctetsOPC		PerfIntervalCount, -- Q.752, 6.1
    mtpOmRsInt15minTransmittedOctetsDPC		PerfIntervalCount, -- Q.752, 6.2
    mtpOmRsInt15minReceivedMSUsOpc		PerfIntervalCount,
    mtpOmRsInt15minTransmittedMSUsDpc		PerfIntervalCount,
    mtpOmRsInt15minRouteSetUnavailable		PerfIntervalCount, -- Q.752, 4.9
    mtpOmRsInt15minRouteSetUnavailableDuration	PerfIntervalCount  -- Q.752, 4.10
}

mtpOmRsInt15minInterval OBJECT-TYPE
    SYNTAX	Unsigned32
    MAX-ACCESS	not-accessible
    STATUS	current
    DESCRIPTION
	""
    ::= { mtpOmRsInt15minEntry 1 }

mtpOmRsInt15minTimeStamp OBJECT-TYPE
    SYNTAX	TimeStamp
    MAX-ACCESS	read-only
    STATUS	current
    DESCRIPTION
	""
    ::= { mtpOmRsInt15minEntry 2 }

mtpOmRsInt15minReceivedOctetsOPC OBJECT-TYPE
    SYNTAX	PerfIntervalCount
    UNITS	"octets"
    MAX-ACCESS	read-only
    STATUS	current
    DESCRIPTION
	"This attribute represents measurement T1.116.2/6.1.
	 
	 The number of SIF and SIO octets received with given OPC (or 
	 OPC set) collected over an interval of 15 or 30 minutes.  This 
	 is a non-obligatory measurement that may be derived (from 6.6).  
	 This measurement may be used for performance analysis, 
	 accounting management, or network administration and planning."
    REFERENCE
	"ANSI T1.116.1D receivedOctetsOPC
	 ITU-T Rec. Q.751.1 (10/95) : receivedOctetsOPC.
	 ITU-T Rec. Q.752 (1997) : Table 6/Q.752, 6.1."
    ::= { mtpOmRsInt15minEntry 3 }

mtpOmRsInt15minTransmittedOctetsDPC OBJECT-TYPE
    SYNTAX	PerfIntervalCount
    UNITS	"octets"
    MAX-ACCESS	read-only
    STATUS	current
    DESCRIPTION
	"This attribute represents measurement T1.116.2/6.2."
    REFERENCE
	"ANSI T1.116.1D transmittedOctetsDPC
	 ITU-T Rec. Q.751.1 (10/95) : transmittedOctetsDPC.
	 ITU-T Rec. Q.752 (1997) : Table 6/Q.752, 6.2."
    ::= { mtpOmRsInt15minEntry 4 }

mtpOmRsInt15minReceivedMSUsOpc OBJECT-TYPE
    SYNTAX	PerfIntervalCount
    UNITS	"MSUs"
    MAX-ACCESS	read-only
    STATUS	current
    DESCRIPTION
	""
    ::= { mtpOmRsInt15minEntry 5 }

mtpOmRsInt15minTransmittedMSUsDpc OBJECT-TYPE
    SYNTAX	PerfIntervalCount
    UNITS	"MSUs"
    MAX-ACCESS	read-only
    STATUS	current
    DESCRIPTION
	""
    ::= { mtpOmRsInt15minEntry 6 }

mtpOmRsInt15minRouteSetUnavailable OBJECT-TYPE
    SYNTAX	PerfIntervalCount
    MAX-ACCESS	read-only
    STATUS	current
    DESCRIPTION
	"This attribute represents measurement T1.116.2/4.9.
	 See also Chapter T1.111.4 11.2.2.
	 
	 These are not basic measurements and can be derived (from 4.11 
	 and 4.12).  This measurement is obligatory in international 
	 networks."
    REFERENCE
	"ANSI T1.116.1D routeSetUnavailable
	 ITU-T Rec. Q.751.1, (10/95) : routeSetUnavailable.
	 ITU-T Rec. Q.752, (1997) : Table 3/Q.752 4.9"
    ::= { mtpOmRsInt15minEntry 7 }

mtpOmRsInt15minRouteSetUnavailableDuration OBJECT-TYPE
    SYNTAX	PerfIntervalCount
    UNITS	"seconds"
    MAX-ACCESS	read-only
    STATUS	current
    DESCRIPTION
	"This attribute represents measurement T1.116.2/4.10.
	 See also Chapter T1.111.4 11.2.1.
	 
	 These are not basic measurements and can be derived (from 4.11 
	 and 4.12).  This measurement is obligatory in international 
	 networks."
    REFERENCE
	"ANSI T1.116.1D routeSetUnavailableDuration
	 ITU-T Rec. Q.751.1, (10/95) : routeSetUnavailableDuration.
	 ITU-T Rec. Q.752, (1997) : Table 3/Q.752 4.10"
    ::= { mtpOmRsInt15minEntry 8 }


-- ====================================================================

mtpOmRsSiTable OBJECT-TYPE
    SYNTAX	SEQUENCE OF MtpOmRsSiEntry
    MAX-ACCESS	not-accessible
    STATUS	current
    DESCRIPTION
	""
    ::= { mtpOmRsStats 4 }

mtpOmRsSiEntry OBJECT-TYPE
    SYNTAX	MtpOmRsSiEntry
    MAX-ACCESS	not-accessible
    STATUS	current
    DESCRIPTION
	""
    INDEX	{
	mtpSpId,	-- shared index
	mtpRsId,	-- shared index
	mtpOmRsSiCode
    }
    ::= { mtpOmRsSiTable 1 }

MtpOmRsSiEntry ::= SEQUENCE {
    mtpOmRsSiCode				MtpUserPart,
    mtpOmRsSiValidIntervals			HCPerfValidIntervals,
    mtpOmRsSiTimeDiscontinuity			TimeStamp,
    mtpOmRsSiReceivedOctetsOpcSio		Counter32, -- Q.752, 6.4
    mtpOmRsSiTransmittedOctetsDpcSio		Counter32, -- Q.752, 6.5
    mtpOmRsSiReceivedMSUsOpcSio			Counter32,
    mtpOmRsSiTransmittedMSUsDpcSio		Counter32,
    mtpOmRsSiStatus				RowStatus
}

mtpOmRsSiCode OBJECT-TYPE
    SYNTAX	MtpUserPart
    MAX-ACCESS	not-accessible
    STATUS	current
    DESCRIPTION
	""
    ::= { mtpOmRsSiEntry 1 }

mtpOmRsSiValidIntervals OBJECT-TYPE
    SYNTAX	HCPerfValidIntervals
    MAX-ACCESS	read-create
    STATUS	current
    DESCRIPTION
	""
    ::= { mtpOmRsSiEntry 2 }

mtpOmRsSiTimeDiscontinuity OBJECT-TYPE
    SYNTAX	TimeStamp
    MAX-ACCESS	read-create
    STATUS	current
    DESCRIPTION
	""
    ::= { mtpOmRsSiEntry 3 }

mtpOmRsSiReceivedOctetsOpcSio OBJECT-TYPE
    SYNTAX	Counter32
    UNITS	"octets"
    MAX-ACCESS	read-only
    STATUS	current
    DESCRIPTION
	"This attribute represents measurement T1.116.2/6.4.
	 
	 The number of SIF and SIO octets received with given OPC and 
	 SIO collected over an interval of 15 or 30 minutes.  This a 
	 non-obligatory measurement that may be used for performance 
	 analysis, accounting management, and network administration and 
	 planning."
    REFERENCE
	"ANSI T1.116.1D receivedOctetsOpcSio
	 ITU-T Rec. Q.751.1, (10/95) : receivedOctetsOpcSio.
	 ITU-T Rec. Q.752, (1997) : Table 6/Q.752 6.4"
    ::= { mtpOmRsSiEntry 4 }

mtpOmRsSiTransmittedOctetsDpcSio OBJECT-TYPE
    SYNTAX	Counter32
    UNITS	"octets"
    MAX-ACCESS	read-only
    STATUS	current
    DESCRIPTION
	"This attribute represents measurement T1.116.2/6.5."
    REFERENCE
	"ANSI T1.116.1D transmittedOctetsDpcSio
	 ITU-T Rec. Q.751.1, (10/95) : transmittedOctetsDpcSio.
	 ITU-T Rec. Q.752, (1997) : Table 6/Q.752 6.5"
    ::= { mtpOmRsSiEntry 5 }

mtpOmRsSiReceivedMSUsOpcSio OBJECT-TYPE
    SYNTAX	Counter32
    UNITS	"MSUs"
    MAX-ACCESS	read-only
    STATUS	current
    DESCRIPTION
	""
    ::= { mtpOmRsSiEntry 6 }

mtpOmRsSiTransmittedMSUsDpcSio OBJECT-TYPE
    SYNTAX	Counter32
    UNITS	"MSUs"
    MAX-ACCESS	read-only
    STATUS	current
    DESCRIPTION
	""
    ::= { mtpOmRsSiEntry 7 }

mtpOmRsSiStatus OBJECT-TYPE
    SYNTAX	RowStatus
    MAX-ACCESS	read-only
    STATUS	current
    DESCRIPTION
	""
    REFERENCE
	"STD 58, SNMPv2-TC RowStatus."
    ::= { mtpOmRsSiEntry 8 }


-- ====================================================================

mtpOmRsSiInt5minTable OBJECT-TYPE
    SYNTAX	SEQUENCE OF MtpOmRsSiInt5minEntry
    MAX-ACCESS	not-accessible
    STATUS	current
    DESCRIPTION
	""
    ::= { mtpOmRsStats 5 }

mtpOmRsSiInt5minEntry OBJECT-TYPE
    SYNTAX	MtpOmRsSiInt5minEntry
    MAX-ACCESS	not-accessible
    STATUS	current
    DESCRIPTION
	""
    INDEX	{
	mtpSpId,	-- shared index
	mtpRsId,	-- shared index
	mtpOmRsSiCode,	-- shared index
	mtpOmRsSiInt5minInterval
    }
    ::= { mtpOmRsSiInt5minTable 1 }

MtpOmRsSiInt5minEntry ::= SEQUENCE {
    mtpOmRsSiInt5minInterval			Unsigned32,
    mtpOmRsSiInt5minTimeStamp			TimeStamp,
    mtpOmRsSiInt5minReceivedOctetsOpcSio	PerfIntervalCount, -- Q.752, 6.4
    mtpOmRsSiInt5minTransmittedOctetsDpcSio	PerfIntervalCount, -- Q.752, 6.5
    mtpOmRsSiInt5minReceivedMSUsOpcSio		PerfIntervalCount,
    mtpOmRsSiInt5minTransmittedMSUsDpcSio	PerfIntervalCount
}

mtpOmRsSiInt5minInterval OBJECT-TYPE
    SYNTAX	Unsigned32
    MAX-ACCESS	not-accessible
    STATUS	current
    DESCRIPTION
	""
    ::= { mtpOmRsSiInt5minEntry 1 }

mtpOmRsSiInt5minTimeStamp OBJECT-TYPE
    SYNTAX	TimeStamp
    MAX-ACCESS	read-only
    STATUS	current
    DESCRIPTION
	""
    ::= { mtpOmRsSiInt5minEntry 2 }

mtpOmRsSiInt5minReceivedOctetsOpcSio OBJECT-TYPE
    SYNTAX	PerfIntervalCount
    UNITS	"octets"
    MAX-ACCESS	read-only
    STATUS	current
    DESCRIPTION
	"This attribute represents measurement T1.116.2/6.4.
	 
	 The number of SIF and SIO octets received with given OPC and 
	 SIO collected over an interval of 15 or 30 minutes.  This a 
	 non-obligatory measurement that may be used for performance 
	 analysis, accounting management, and network administration and 
	 planning."
    REFERENCE
	"ANSI T1.116.1D receivedOctetsOpcSio
	 ITU-T Rec. Q.751.1, (10/95) : receivedOctetsOpcSio.
	 ITU-T Rec. Q.752, (1997) : Table 6/Q.752 6.4"
    ::= { mtpOmRsSiInt5minEntry 3 }

mtpOmRsSiInt5minTransmittedOctetsDpcSio OBJECT-TYPE
    SYNTAX	PerfIntervalCount
    UNITS	"octets"
    MAX-ACCESS	read-only
    STATUS	current
    DESCRIPTION
	"This attribute represents measurement T1.116.2/6.5."
    REFERENCE
	"ANSI T1.116.1D transmittedOctetsDpcSio
	 ITU-T Rec. Q.751.1, (10/95) : transmittedOctetsDpcSio.
	 ITU-T Rec. Q.752, (1997) : Table 6/Q.752 6.5"
    ::= { mtpOmRsSiInt5minEntry 4 }

mtpOmRsSiInt5minReceivedMSUsOpcSio OBJECT-TYPE
    SYNTAX	PerfIntervalCount
    UNITS	"MSUs"
    MAX-ACCESS	read-only
    STATUS	current
    DESCRIPTION
	""
    ::= { mtpOmRsSiInt5minEntry 5 }

mtpOmRsSiInt5minTransmittedMSUsDpcSio OBJECT-TYPE
    SYNTAX	PerfIntervalCount
    UNITS	"MSUs"
    MAX-ACCESS	read-only
    STATUS	current
    DESCRIPTION
	""
    ::= { mtpOmRsSiInt5minEntry 6 }


-- ====================================================================

mtpOmRsSiInt15minTable OBJECT-TYPE
    SYNTAX	SEQUENCE OF MtpOmRsSiInt15minEntry
    MAX-ACCESS	not-accessible
    STATUS	current
    DESCRIPTION
	""
    ::= { mtpOmRsStats 6 }

mtpOmRsSiInt15minEntry OBJECT-TYPE
    SYNTAX	MtpOmRsSiInt15minEntry
    MAX-ACCESS	not-accessible
    STATUS	current
    DESCRIPTION
	""
    INDEX	{
	mtpSpId,	-- shared index
	mtpRsId,	-- shared index
	mtpOmRsSiCode,	-- shared index
	mtpOmRsSiInt15minInterval
    }
    ::= { mtpOmRsSiInt15minTable 1 }

MtpOmRsSiInt15minEntry ::= SEQUENCE {
    mtpOmRsSiInt15minInterval			Unsigned32,
    mtpOmRsSiInt15minTimeStamp			TimeStamp,
    mtpOmRsSiInt15minReceivedOctetsOpcSio	PerfIntervalCount, -- Q.752, 6.4
    mtpOmRsSiInt15minTransmittedOctetsDpcSio	PerfIntervalCount, -- Q.752, 6.5
    mtpOmRsSiInt15minReceivedMSUsOpcSio		PerfIntervalCount,
    mtpOmRsSiInt15minTransmittedMSUsDpcSio	PerfIntervalCount
}

mtpOmRsSiInt15minInterval OBJECT-TYPE
    SYNTAX	Unsigned32
    MAX-ACCESS	not-accessible
    STATUS	current
    DESCRIPTION
	""
    ::= { mtpOmRsSiInt15minEntry 1 }

mtpOmRsSiInt15minTimeStamp OBJECT-TYPE
    SYNTAX	TimeStamp
    MAX-ACCESS	read-only
    STATUS	current
    DESCRIPTION
	""
    ::= { mtpOmRsSiInt15minEntry 2 }

mtpOmRsSiInt15minReceivedOctetsOpcSio OBJECT-TYPE
    SYNTAX	PerfIntervalCount
    UNITS	"octets"
    MAX-ACCESS	read-only
    STATUS	current
    DESCRIPTION
	"This attribute represents measurement T1.116.2/6.4.
	 
	 The number of SIF and SIO octets received with given OPC and 
	 SIO collected over an interval of 15 or 30 minutes.  This a 
	 non-obligatory measurement that may be used for performance 
	 analysis, accounting management, and network administration and 
	 planning."
    REFERENCE
	"ANSI T1.116.1D receivedOctetsOpcSio
	 ITU-T Rec. Q.751.1, (10/95) : receivedOctetsOpcSio.
	 ITU-T Rec. Q.752, (1997) : Table 6/Q.752 6.4"
    ::= { mtpOmRsSiInt15minEntry 3 }

mtpOmRsSiInt15minTransmittedOctetsDpcSio OBJECT-TYPE
    SYNTAX	PerfIntervalCount
    UNITS	"octets"
    MAX-ACCESS	read-only
    STATUS	current
    DESCRIPTION
	"This attribute represents measurement T1.116.2/6.5."
    REFERENCE
	"ANSI T1.116.1D transmittedOctetsDpcSio
	 ITU-T Rec. Q.751.1, (10/95) : transmittedOctetsDpcSio.
	 ITU-T Rec. Q.752, (1997) : Table 6/Q.752 6.5"
    ::= { mtpOmRsSiInt15minEntry 4 }

mtpOmRsSiInt15minReceivedMSUsOpcSio OBJECT-TYPE
    SYNTAX	PerfIntervalCount
    UNITS	"MSUs"
    MAX-ACCESS	read-only
    STATUS	current
    DESCRIPTION
	""
    ::= { mtpOmRsSiInt15minEntry 5 }

mtpOmRsSiInt15minTransmittedMSUsDpcSio OBJECT-TYPE
    SYNTAX	PerfIntervalCount
    UNITS	"MSUs"
    MAX-ACCESS	read-only
    STATUS	current
    DESCRIPTION
	""
    ::= { mtpOmRsSiInt15minEntry 6 }


-- ====================================================================

mtpOmLsTable OBJECT-TYPE
    SYNTAX	SEQUENCE OF MtpOmLsEntry
    MAX-ACCESS	not-accessible
    STATUS	current
    DESCRIPTION
	""
    ::= { mtpOmLsStats 1 }

mtpOmLsEntry OBJECT-TYPE
    SYNTAX	MtpOmLsEntry
    MAX-ACCESS	not-accessible
    STATUS	current
    DESCRIPTION
	""
    INDEX	{
	mtpSpId,	-- shared index
	mtpLsId		-- shared index
    }
    ::= { mtpOmLsTable 1 }

MtpOmLsEntry ::= SEQUENCE {
    mtpOmLsValidIntervals			HCPerfValidIntervals,
    mtpOmLsTimeDiscontinuity			TimeStamp,
    mtpOmLsAdjacentInaccessibleEvents		Counter32, -- Q.752, 5.1
    mtpOmLsAdjacentInaccessibleDuration		Counter32, -- Q.752, 5.2
    mtpOmLsSlsUnavailable			Counter32  -- Q.752, 4.2
}

mtpOmLsValidIntervals OBJECT-TYPE
    SYNTAX	HCPerfValidIntervals
    MAX-ACCESS	read-only
    STATUS	current
    DESCRIPTION
	""
    ::= { mtpOmLsEntry 1 }

mtpOmLsTimeDiscontinuity OBJECT-TYPE
    SYNTAX	TimeStamp
    MAX-ACCESS	read-only
    STATUS	current
    DESCRIPTION
	""
    ::= { mtpOmLsEntry 2 }

mtpOmLsAdjacentInaccessibleEvents OBJECT-TYPE
    SYNTAX	Counter32
    UNITS	"events"
    MAX-ACCESS	read-only
    STATUS	current
    DESCRIPTION
	"This attribute represents measurement T1.116.2/5.1

	 Adjacent SP inaccessible.  Events per SP. On occurence reports 
	 are obligatory and permanent and are handled by alarm events.  
	 Accumuated counts on 5 and 30 minute intervals are optional.  
	 This operational measurement can be derived from events 
	 indicating the start and stop of ajacent SP inaccessible (items 
	 5.1 and 5.4).
	 "
    REFERENCE
	"ANSI T1.116.1D adjacentInaccessibleEvents
	 ITU-T Rec. Q.751.1 (10/95) : adjacentInaccessibleEvents.
	 ITU-T Rec. Q.752 (1997) : Table 5/Q.752, 5.1."
    ::= { mtpOmLsEntry 3 }

mtpOmLsAdjacentInaccessibleDuration OBJECT-TYPE
    SYNTAX	Counter32
    UNITS	"seconds"
    MAX-ACCESS	read-only
    STATUS	current
    DESCRIPTION
	"This attribute represents measurement T1.116.2/5.2 Duration of 
	 adjacent SP inaccessible.  Seconds per SP.  Accumuated counts 
	 on 5 and 30 minute intervals are obligatory.  This operational 
	 measurement can be derived from events indicating the start and 
	 stop of ajacent SP inaccessible (items 5.1 and 5.4).
	 "
    REFERENCE
	"ANSI T1.116.1D adjacentInaccessibleDuration.
	 ANSI T1.116.2/2000 Table 5 (5.2).
	 ITU-T Rec. Q.751.1 (10/95) : adjacentInacessibleDuration.
	 ITU-T Rec. Q.752 (1997) : Table 5/Q.752, 5.2."
    ::= { mtpOmLsEntry 4 }

mtpOmLsSlsUnavailable OBJECT-TYPE
    SYNTAX	Counter32
    MAX-ACCESS	read-only
    STATUS	current
    DESCRIPTION
	"This attribute represents Measurement T1.116.2/4.2.

	 This is not a basic measurement.  It can be derived (from 4.3 
	 and 4.4)."
    REFERENCE
	"ANSI T1.116.1D slsUnavailable
	 ITU-T Rec. Q.751.1, (10/95) : slsUnavailable.
	 ITU-T Rec. Q.752, (1997) : Table 3/Q.752 4.2"
    ::= { mtpOmLsEntry 5 }


-- ====================================================================

mtpOmLsInt5minTable OBJECT-TYPE
    SYNTAX	SEQUENCE OF MtpOmLsInt5minEntry
    MAX-ACCESS	not-accessible
    STATUS	current
    DESCRIPTION
	""
    ::= { mtpOmLsStats 2 }

mtpOmLsInt5minEntry OBJECT-TYPE
    SYNTAX	MtpOmLsInt5minEntry
    MAX-ACCESS	not-accessible
    STATUS	current
    DESCRIPTION
	""
    INDEX	{
	mtpSpId,	-- shared index
	mtpLsId,	-- shared index
	mtpOmLsInt5minInterval
    }
    ::= { mtpOmLsInt5minTable 1 }

MtpOmLsInt5minEntry ::= SEQUENCE {
    mtpOmLsInt5minInterval			Unsigned32,
    mtpOmLsInt5minTimeStamp			TimeStamp,
    mtpOmLsInt5minAdjacentInaccessibleEvents	PerfIntervalCount, -- Q.752, 5.1
    mtpOmLsInt5minAdjacentInaccessibleDuration	PerfIntervalCount, -- Q.752, 5.2
    mtpOmLsInt5minSlsUnavailable		PerfIntervalCount  -- Q.752, 4.2
}

mtpOmLsInt5minInterval OBJECT-TYPE
    SYNTAX	Unsigned32
    MAX-ACCESS	not-accessible
    STATUS	current
    DESCRIPTION
	""
    ::= { mtpOmLsInt5minEntry 1 }

mtpOmLsInt5minTimeStamp OBJECT-TYPE
    SYNTAX	TimeStamp
    MAX-ACCESS	read-only
    STATUS	current
    DESCRIPTION
	""
    ::= { mtpOmLsInt5minEntry 2 }

mtpOmLsInt5minAdjacentInaccessibleEvents OBJECT-TYPE
    SYNTAX	PerfIntervalCount
    UNITS	"events"
    MAX-ACCESS	read-only
    STATUS	current
    DESCRIPTION
	"This attribute represents measurement T1.116.2/5.1

	 Adjacent SP inaccessible.  Events per SP. On occurence reports 
	 are obligatory and permanent and are handled by alarm events.  
	 Accumuated counts on 5 and 30 minute intervals are optional.  
	 This operational measurement can be derived from events 
	 indicating the start and stop of ajacent SP inaccessible (items 
	 5.1 and 5.4).
	 "
    REFERENCE
	"ANSI T1.116.1D adjacentInaccessibleEvents
	 ITU-T Rec. Q.751.1 (10/95) : adjacentInaccessibleEvents.
	 ITU-T Rec. Q.752 (1997) : Table 5/Q.752, 5.1."
    ::= { mtpOmLsInt5minEntry 3 }

mtpOmLsInt5minAdjacentInaccessibleDuration OBJECT-TYPE
    SYNTAX	PerfIntervalCount
    UNITS	"seconds"
    MAX-ACCESS	read-only
    STATUS	current
    DESCRIPTION
	"This attribute represents measurement T1.116.2/5.2 Duration of 
	 adjacent SP inaccessible.  Seconds per SP.  Accumuated counts 
	 on 5 and 30 minute intervals are obligatory.  This operational 
	 measurement can be derived from events indicating the start and 
	 stop of ajacent SP inaccessible (items 5.1 and 5.4).
	 "
    REFERENCE
	"ANSI T1.116.1D adjacentInaccessibleDuration.
	 ANSI T1.116.2/2000 Table 5 (5.2).
	 ITU-T Rec. Q.751.1 (10/95) : adjacentInacessibleDuration.
	 ITU-T Rec. Q.752 (1997) : Table 5/Q.752, 5.2."
    ::= { mtpOmLsInt5minEntry 4 }

mtpOmLsInt5minSlsUnavailable OBJECT-TYPE
    SYNTAX	PerfIntervalCount
    MAX-ACCESS	read-only
    STATUS	current
    DESCRIPTION
	"This attribute represents Measurement T1.116.2/4.2.

	 This is not a basic measurement.  It can be derived (from 4.3 
	 and 4.4)."
    REFERENCE
	"ANSI T1.116.1D slsUnavailable
	 ITU-T Rec. Q.751.1, (10/95) : slsUnavailable.
	 ITU-T Rec. Q.752, (1997) : Table 3/Q.752 4.2"
    ::= { mtpOmLsInt5minEntry 5 }


-- ====================================================================

mtpOmLsInt15minTable OBJECT-TYPE
    SYNTAX	SEQUENCE OF MtpOmLsInt15minEntry
    MAX-ACCESS	not-accessible
    STATUS	current
    DESCRIPTION
	""
    ::= { mtpOmLsStats 3 }

mtpOmLsInt15minEntry OBJECT-TYPE
    SYNTAX	MtpOmLsInt15minEntry
    MAX-ACCESS	not-accessible
    STATUS	current
    DESCRIPTION
	""
    INDEX	{
	mtpSpId,	-- shared index
	mtpLsId,	-- shared index
	mtpOmLsInt15minInterval
    }
    ::= { mtpOmLsInt15minTable 1 }

MtpOmLsInt15minEntry ::= SEQUENCE {
    mtpOmLsInt15minInterval			Unsigned32,
    mtpOmLsInt15minTimeStamp			TimeStamp,
    mtpOmLsInt15minAdjacentInaccessibleEvents	PerfIntervalCount, -- Q.752, 5.1
    mtpOmLsInt15minAdjacentInaccessibleDuration	PerfIntervalCount, -- Q.752, 5.2
    mtpOmLsInt15minSlsUnavailable		PerfIntervalCount  -- Q.752, 4.2
}

mtpOmLsInt15minInterval OBJECT-TYPE
    SYNTAX	Unsigned32
    MAX-ACCESS	not-accessible
    STATUS	current
    DESCRIPTION
	""
    ::= { mtpOmLsInt15minEntry 1 }

mtpOmLsInt15minTimeStamp OBJECT-TYPE
    SYNTAX	TimeStamp
    MAX-ACCESS	read-only
    STATUS	current
    DESCRIPTION
	""
    ::= { mtpOmLsInt15minEntry 2 }

mtpOmLsInt15minAdjacentInaccessibleEvents OBJECT-TYPE
    SYNTAX	PerfIntervalCount
    UNITS	"events"
    MAX-ACCESS	read-only
    STATUS	current
    DESCRIPTION
	"This attribute represents measurement T1.116.2/5.1

	 Adjacent SP inaccessible.  Events per SP. On occurence reports 
	 are obligatory and permanent and are handled by alarm events.  
	 Accumuated counts on 5 and 30 minute intervals are optional.  
	 This operational measurement can be derived from events 
	 indicating the start and stop of ajacent SP inaccessible (items 
	 5.1 and 5.4).
	 "
    REFERENCE
	"ANSI T1.116.1D adjacentInaccessibleEvents
	 ITU-T Rec. Q.751.1 (10/95) : adjacentInaccessibleEvents.
	 ITU-T Rec. Q.752 (1997) : Table 5/Q.752, 5.1."
    ::= { mtpOmLsInt15minEntry 3 }

mtpOmLsInt15minAdjacentInaccessibleDuration OBJECT-TYPE
    SYNTAX	PerfIntervalCount
    UNITS	"seconds"
    MAX-ACCESS	read-only
    STATUS	current
    DESCRIPTION
	"This attribute represents measurement T1.116.2/5.2 Duration of 
	 adjacent SP inaccessible.  Seconds per SP.  Accumuated counts 
	 on 5 and 30 minute intervals are obligatory.  This operational 
	 measurement can be derived from events indicating the start and 
	 stop of ajacent SP inaccessible (items 5.1 and 5.4).
	 "
    REFERENCE
	"ANSI T1.116.1D adjacentInaccessibleDuration.
	 ANSI T1.116.2/2000 Table 5 (5.2).
	 ITU-T Rec. Q.751.1 (10/95) : adjacentInacessibleDuration.
	 ITU-T Rec. Q.752 (1997) : Table 5/Q.752, 5.2."
    ::= { mtpOmLsInt15minEntry 4 }

mtpOmLsInt15minSlsUnavailable OBJECT-TYPE
    SYNTAX	PerfIntervalCount
    MAX-ACCESS	read-only
    STATUS	current
    DESCRIPTION
	"This attribute represents Measurement T1.116.2/4.2.

	 This is not a basic measurement.  It can be derived (from 4.3 
	 and 4.4)."
    REFERENCE
	"ANSI T1.116.1D slsUnavailable
	 ITU-T Rec. Q.751.1, (10/95) : slsUnavailable.
	 ITU-T Rec. Q.752, (1997) : Table 3/Q.752 4.2"
    ::= { mtpOmLsInt15minEntry 5 }


-- ====================================================================

mtpOmSlStatsTable OBJECT-TYPE
    SYNTAX	SEQUENCE OF MtpOmSlStatsEntry
    MAX-ACCESS	not-accessible
    STATUS	current
    DESCRIPTION
	"This table provides SL statistics."
    REFERENCE
	"ITU-T Rec. Q.752, ANSI T1.116.2"
    ::= { mtpOmSlStats 1 }

mtpOmSlStatsEntry OBJECT-TYPE
    SYNTAX	MtpOmSlStatsEntry
    MAX-ACCESS	not-accessible
    STATUS	current
    DESCRIPTION
	"This provides the table entry for SL statistics."
    REFERENCE
	"ITU-T Rec. Q.752, ANSI T1.116.2"
    AUGMENTS	{
	mtpSlEntry
    }
    ::= { mtpOmSlStatsTable 1 }

MtpOmSlStatsEntry ::= SEQUENCE {
    mtpOmSlStatsDurInService			Counter32,
    mtpOmSlStatsFailAlignOrProving		Counter32,
    mtpOmSlStatsNacksReceived			Counter32,
    mtpOmSlStatsDurUnavail			Counter32,
    mtpOmSlStatsDurUnavailFailed		Counter32,
    mtpOmSlStatsDurUnavailRpo			Counter32,
    mtpOmSlStatsSibsSent			Counter32,
    mtpOmSlStatsTranSioSifOctets		Counter32,
    mtpOmSlStatsRetransOctets			Counter32,
    mtpOmSlStatsTranMsus			Counter32,
    mtpOmSlStatsRecvSioSifOctets		Counter32,
    mtpOmSlStatsRecvMsus			Counter32,
    mtpOmSlStatsCongOnsetInd0			Counter32,
    mtpOmSlStatsCongOnsetInd1			Counter32,
    mtpOmSlStatsCongOnsetInd2			Counter32,
    mtpOmSlStatsCongOnsetInd3			Counter32,
    mtpOmSlStatsDurCongStatus0			Counter32,
    mtpOmSlStatsDurCongStatus1			Counter32,
    mtpOmSlStatsDurCongStatus2			Counter32,
    mtpOmSlStatsDurCongStatus3			Counter32,
    mtpOmSlStatsCongDiscdInd0			Counter32,
    mtpOmSlStatsCongDiscdInd1			Counter32,
    mtpOmSlStatsCongDiscdInd2			Counter32,
    mtpOmSlStatsCongDiscdInd3			Counter32
}

mtpOmSlStatsDurInService OBJECT-TYPE
    SYNTAX	Counter32
    UNITS	"seconds"
    MAX-ACCESS	read-only
    STATUS	current
    DESCRIPTION
	"This is a count of the duration in service for the signalling 
	 link."
    REFERENCE
	"ITU-T Rec. Q.752, ANSI T1.116.2"
    ::= { mtpOmSlStatsEntry 1 }

mtpOmSlStatsFailAlignOrProving OBJECT-TYPE
    SYNTAX	Counter32
    MAX-ACCESS	read-only
    STATUS	current
    DESCRIPTION
	""
    REFERENCE
	"ITU-T Rec. Q.752, ANSI T1.116.2"
    ::= { mtpOmSlStatsEntry 2 }

mtpOmSlStatsNacksReceived OBJECT-TYPE
    SYNTAX	Counter32
    MAX-ACCESS	read-only
    STATUS	current
    DESCRIPTION
	""
    REFERENCE
	"ITU-T Rec. Q.752, ANSI T1.116.2"
    ::= { mtpOmSlStatsEntry 3 }

mtpOmSlStatsDurUnavail OBJECT-TYPE
    SYNTAX	Counter32
    MAX-ACCESS	read-only
    STATUS	current
    DESCRIPTION
	""
    REFERENCE
	"ITU-T Rec. Q.752, ANSI T1.116.2"
    ::= { mtpOmSlStatsEntry 4 }

mtpOmSlStatsDurUnavailFailed OBJECT-TYPE
    SYNTAX	Counter32
    MAX-ACCESS	read-only
    STATUS	current
    DESCRIPTION
	""
    REFERENCE
	"ITU-T Rec. Q.752, ANSI T1.116.2"
    ::= { mtpOmSlStatsEntry 5 }

mtpOmSlStatsDurUnavailRpo OBJECT-TYPE
    SYNTAX	Counter32
    MAX-ACCESS	read-only
    STATUS	current
    DESCRIPTION
	""
    REFERENCE
	"ITU-T Rec. Q.752, ANSI T1.116.2"
    ::= { mtpOmSlStatsEntry 6 }

mtpOmSlStatsSibsSent OBJECT-TYPE
    SYNTAX	Counter32
    MAX-ACCESS	read-only
    STATUS	current
    DESCRIPTION
	""
    REFERENCE
	"ITU-T Rec. Q.752, ANSI T1.116.2"
    ::= { mtpOmSlStatsEntry 7 }

mtpOmSlStatsTranSioSifOctets OBJECT-TYPE
    SYNTAX	Counter32
    MAX-ACCESS	read-only
    STATUS	current
    DESCRIPTION
	""
    REFERENCE
	"ITU-T Rec. Q.752, ANSI T1.116.2"
    ::= { mtpOmSlStatsEntry 8 }

mtpOmSlStatsRetransOctets OBJECT-TYPE
    SYNTAX	Counter32
    MAX-ACCESS	read-only
    STATUS	current
    DESCRIPTION
	""
    REFERENCE
	"ITU-T Rec. Q.752, ANSI T1.116.2"
    ::= { mtpOmSlStatsEntry 9 }

mtpOmSlStatsTranMsus OBJECT-TYPE
    SYNTAX	Counter32
    MAX-ACCESS	read-only
    STATUS	current
    DESCRIPTION
	""
    REFERENCE
	"ITU-T Rec. Q.752, ANSI T1.116.2"
    ::= { mtpOmSlStatsEntry 10 }

mtpOmSlStatsRecvSioSifOctets OBJECT-TYPE
    SYNTAX	Counter32
    MAX-ACCESS	read-only
    STATUS	current
    DESCRIPTION
	""
    REFERENCE
	"ITU-T Rec. Q.752, ANSI T1.116.2"
    ::= { mtpOmSlStatsEntry 11 }

mtpOmSlStatsRecvMsus OBJECT-TYPE
    SYNTAX	Counter32
    MAX-ACCESS	read-only
    STATUS	current
    DESCRIPTION
	""
    REFERENCE
	"ITU-T Rec. Q.752, ANSI T1.116.2"
    ::= { mtpOmSlStatsEntry 12 }

mtpOmSlStatsCongOnsetInd0 OBJECT-TYPE
    SYNTAX	Counter32
    MAX-ACCESS	read-only
    STATUS	current
    DESCRIPTION
	""
    REFERENCE
	"ITU-T Rec. Q.752, ANSI T1.116.2"
    ::= { mtpOmSlStatsEntry 13 }

mtpOmSlStatsCongOnsetInd1 OBJECT-TYPE
    SYNTAX	Counter32
    MAX-ACCESS	read-only
    STATUS	current
    DESCRIPTION
	""
    REFERENCE
	"ITU-T Rec. Q.752, ANSI T1.116.2"
    ::= { mtpOmSlStatsEntry 14 }

mtpOmSlStatsCongOnsetInd2 OBJECT-TYPE
    SYNTAX	Counter32
    MAX-ACCESS	read-only
    STATUS	current
    DESCRIPTION
	""
    REFERENCE
	"ITU-T Rec. Q.752, ANSI T1.116.2"
    ::= { mtpOmSlStatsEntry 15 }

mtpOmSlStatsCongOnsetInd3 OBJECT-TYPE
    SYNTAX	Counter32
    MAX-ACCESS	read-only
    STATUS	current
    DESCRIPTION
	""
    REFERENCE
	"ITU-T Rec. Q.752, ANSI T1.116.2"
    ::= { mtpOmSlStatsEntry 16 }

mtpOmSlStatsDurCongStatus0 OBJECT-TYPE
    SYNTAX	Counter32
    MAX-ACCESS	read-only
    STATUS	current
    DESCRIPTION
	""
    REFERENCE
	"ITU-T Rec. Q.752, ANSI T1.116.2"
    ::= { mtpOmSlStatsEntry 17 }

mtpOmSlStatsDurCongStatus1 OBJECT-TYPE
    SYNTAX	Counter32
    MAX-ACCESS	read-only
    STATUS	current
    DESCRIPTION
	""
    REFERENCE
	"ITU-T Rec. Q.752, ANSI T1.116.2"
    ::= { mtpOmSlStatsEntry 18 }

mtpOmSlStatsDurCongStatus2 OBJECT-TYPE
    SYNTAX	Counter32
    MAX-ACCESS	read-only
    STATUS	current
    DESCRIPTION
	""
    REFERENCE
	"ITU-T Rec. Q.752, ANSI T1.116.2"
    ::= { mtpOmSlStatsEntry 19 }

mtpOmSlStatsDurCongStatus3 OBJECT-TYPE
    SYNTAX	Counter32
    MAX-ACCESS	read-only
    STATUS	current
    DESCRIPTION
	""
    REFERENCE
	"ITU-T Rec. Q.752, ANSI T1.116.2"
    ::= { mtpOmSlStatsEntry 20 }

mtpOmSlStatsCongDiscdInd0 OBJECT-TYPE
    SYNTAX	Counter32
    MAX-ACCESS	read-only
    STATUS	current
    DESCRIPTION
	""
    REFERENCE
	"ITU-T Rec. Q.752, ANSI T1.116.2"
    ::= { mtpOmSlStatsEntry 21 }

mtpOmSlStatsCongDiscdInd1 OBJECT-TYPE
    SYNTAX	Counter32
    MAX-ACCESS	read-only
    STATUS	current
    DESCRIPTION
	""
    REFERENCE
	"ITU-T Rec. Q.752, ANSI T1.116.2"
    ::= { mtpOmSlStatsEntry 22 }

mtpOmSlStatsCongDiscdInd2 OBJECT-TYPE
    SYNTAX	Counter32
    MAX-ACCESS	read-only
    STATUS	current
    DESCRIPTION
	""
    REFERENCE
	"ITU-T Rec. Q.752, ANSI T1.116.2"
    ::= { mtpOmSlStatsEntry 23 }

mtpOmSlStatsCongDiscdInd3 OBJECT-TYPE
    SYNTAX	Counter32
    MAX-ACCESS	read-only
    STATUS	current
    DESCRIPTION
	""
    REFERENCE
	"ITU-T Rec. Q.752, ANSI T1.116.2"
    ::= { mtpOmSlStatsEntry 24 }


-- ====================================================================

mtpOmSlL3Table OBJECT-TYPE
    SYNTAX	SEQUENCE OF MtpOmSlL3Entry
    MAX-ACCESS	not-accessible
    STATUS	current
    DESCRIPTION
	""
    ::= { mtpOmSlStats 2 }

mtpOmSlL3Entry OBJECT-TYPE
    SYNTAX	MtpOmSlL3Entry
    MAX-ACCESS	not-accessible
    STATUS	current
    DESCRIPTION
	""
    INDEX	{
	mtpSpId,	-- shared index
	mtpLsId,	-- shared index
	mtpSlSlCode	-- shared index
    }
    ::= { mtpOmSlL3Table 1 }

MtpOmSlL3Entry ::= SEQUENCE {
    mtpOmSlL3ValidIntervals			HCPerfValidIntervals,
    mtpOmSlL3TimeDiscontinuity			TimeStamp,
    mtpOmSlL3SlUnavailabilityDuration		Counter32, -- Q.752, 2.1
    mtpOmSlL3SlLocalInhibition			Counter32, -- Q.752, 2.5
    mtpOmSlL3SlRemoteInhibition			Counter32, -- Q.752, 2.6
    mtpOmSlL3SlFailed				Counter32, -- Q.752, 2.7
    mtpOmSlL3SlRemoteProcOutage			Counter32, -- Q.752, 2.9
    mtpOmSlL3LocalMgmtInhibit			Counter32, -- Q.752, 2.13
    mtpOmSlL3LocalMgmtUninhibit			Counter32, -- Q.752, 2.14
    mtpOmSlL3LocalBusy				Counter32, -- Q.752, 2.15
    mtpOmSlL3SlCongestedStarts			Counter32, -- Q.752, 3.6
    mtpOmSlL3SlCongestedDuration		Counter32, -- Q.752, 3.7
    mtpOmSlL3SlCongestionStops			Counter32, -- Q.752, 3.9
    mtpOmSlL3DiscardedMSUs			Counter32, -- Q.752, 3.10
    mtpOmSlL3CongestionEventsMSULoss		Counter32, -- Q.752, 3.11
    mtpOmSlL3Changeovers			Counter32, -- Q.752, 1.10
    mtpOmSlL3Changebacks			Counter32, -- Q.752, 1.11
    mtpOmSlL3Restorations			Counter32  -- Q.752, 1.12
}

mtpOmSlL3ValidIntervals OBJECT-TYPE
    SYNTAX	HCPerfValidIntervals
    MAX-ACCESS	read-only
    STATUS	current
    DESCRIPTION
	""
    ::= { mtpOmSlL3Entry 1 }

mtpOmSlL3TimeDiscontinuity OBJECT-TYPE
    SYNTAX	TimeStamp
    MAX-ACCESS	read-only
    STATUS	current
    DESCRIPTION
	""
    ::= { mtpOmSlL3Entry 2 }

mtpOmSlL3SlUnavailabilityDuration OBJECT-TYPE
    SYNTAX	Counter32
    UNITS	"seconds"
    MAX-ACCESS	read-only
    STATUS	current
    DESCRIPTION
	"This attribute represents measurement T1.116.2/2.1

	 Duration of signalling link unavailability (for any reason) in 
	 units of seconds per signalling link.  This is an obligatory 
	 operational measurement to be collected on a 30 minute basis.  
	 This operational measurement is permanently activated.  This 
	 operational measurement may be derived (from 1.2, 1.12, 2.5 and 
	 2.6).

	 This measurement can be used in calculations for the detection 
	 of increases in signalling link signalling unit error rates 
	 (ANSI T1.116.2/2000 6.2.1.4.1).  It may also be used in the 
	 calculation of signalling link utilization (ANSI T1.116.2/2000 
	 6.2.2.1).
	 "
    REFERENCE
	"ANSI T1.116.1D slUnavailabilityDuration
	 ITU-T Rec. Q.751.1, (10/95) : slUnavailabilityDuration.
	 ITU-T Rec. Q.752, (1997) : Table 2/Q.752 2.1"
    ::= { mtpOmSlL3Entry 3 }

mtpOmSlL3SlLocalInhibition OBJECT-TYPE
    SYNTAX	Counter32
    UNITS	"seconds"
    MAX-ACCESS	read-only
    STATUS	current
    DESCRIPTION
	"This attribute represents measurement T1.116.2/2.5.
	 See also 3.2.8/T1.111.4.
	 
	 Duration of signalling link inhibition due to local management 
	 actions in units of seconds per signalling link collected on a 
	 30 minute interval.  This is a non-obligatory operational 
	 measurement that may be derived (from 2.16 and 2.17 which are 
	 alarm indication and clearing events).

	 This operational measurement is used in MTP performance 
	 studies.
	 "
    REFERENCE
	"ANSI T1.116.1D slLocalInhibition.
	 ANSI T1.116.1/2000 Table 2 (2.5).
	 ANSI T1.111.4/2000 3.2.8.
	 ITU-T Rec. Q.751.1, (10/95) : slLocalInhibition
	 ITU-T Rec. Q.752, (1997) : Table 2/Q.752 2.5"
    ::= { mtpOmSlL3Entry 4 }

mtpOmSlL3SlRemoteInhibition OBJECT-TYPE
    SYNTAX	Counter32
    UNITS	"seconds"
    MAX-ACCESS	read-only
    STATUS	current
    DESCRIPTION
	"This attribute represents measurement T1.116.2/2.6.
	 See also 3.2.2/T1.111.4.

	 Duration of signalling link inhibition due to remote management 
	 actions in units of seconds per signalling link collected on a 
	 30 minute interval.  This is a non-obligatory operational 
	 measurement that may be derived (from 2.18 and 2.19 which are 
	 alarm indication and clearing events).

	 This operational measurement is used in MTP performance 
	 studies.
	 "
    REFERENCE
	"ANSI T1.116.1D slRemoteInhibition.
	 ANSI T1.116.1/2000 Table 2 (2.6).
	 ANSI T1.111.4/2000 3.2.2.
	 ITU-T Rec. Q.751.1, (10/95) : slRemoteInhibition.
	 ITU-T Rec. Q.752, (1997) : Table 2/Q.752 2.6"
    ::= { mtpOmSlL3Entry 5 }

mtpOmSlL3SlFailed OBJECT-TYPE
    SYNTAX	Counter32
    UNITS	"seconds"
    MAX-ACCESS	read-only
    STATUS	current
    DESCRIPTION
	"This attribute represents measurement T1.116.2/2.7.
	 See also 3.2.2/T1.111.4.

	 Duration of signalling link unavailability due to link failure 
	 in units of seconds per signalling link collected on a 30 
	 minute interval.  This is non-obligatory operational 
	 measurement that may be derived (from 1.2 and 1.12 which are 
	 alarm indication and clearing events).

	 This operational measurement is used in MTP performance 
	 studies.
	 "
    REFERENCE
	"ANSI T1.116.1D slFailed.
	 ANSI T1.116.1/2000 Table 2 (2.7).
	 ANSI T1.111.4/2000 3.2.2.
	 ITU-T Rec. Q.751.1, (10/95) : slFailed.
	 ITU-T Rec. Q.752, (1997) : Table 2/Q.752 2.7"
    ::= { mtpOmSlL3Entry 6 }

mtpOmSlL3SlRemoteProcOutage OBJECT-TYPE
    SYNTAX	Counter32
    UNITS	"seconds"
    MAX-ACCESS	read-only
    STATUS	current
    DESCRIPTION
	"This attribute represents measurementT1.116.2/2.9.
	 See also 3.2.6/T1.111.4.

	 Duraing of signalling link unavailability due to remote 
	 processor outage in units of seconds per siganlling link 
	 collected on a 30 minute interval.  This is a non-obligatory 
	 operational measurement that may be derived (from 2.10 and 2.11 
	 which are alarm indication and clearing events).

	 This operational measurement is used in MTP performance 
	 studies.
	 "
    REFERENCE
	"ANSI T1.116.1D slRemoteProcOutage.
	 ANSI T1.111.4/3.2.6.
	 ITU-T Rec. Q.751.1, (10/95) : slRemoteProcOutage.
	 ITU-T Rec. Q.752, (1997) : Table 2/Q.752 2.9"
    ::= { mtpOmSlL3Entry 7 }

mtpOmSlL3LocalMgmtInhibit OBJECT-TYPE
    SYNTAX	Counter32
    UNITS	"seconds"
    MAX-ACCESS	read-only
    STATUS	current
    DESCRIPTION
	"This attribute represents measurement T1.116.2/2.13.
	 See also 10.2/T1.111.4.
	 
	 Local management inhibit in number of events per signalling 
	 link collected on a 5 or 30 minute interval.  This is a 
	 non-obligatory measurement that may be derived (from 2.16 which 
	 is a alarm indication event)."
    REFERENCE
	"ANSI T1.116.1D localMgntInhibit.
	 ANSI T1.116.2/2000 Table 2 (2.13).
	 ANSI T1.111.4/2000 10.2.
	 ITU-T Rec. Q.751.1, (10/95) : localMgmtInhibit.
	 ITU-T Rec. Q.752, (1997) : Table 2/Q.752 2.13"
    ::= { mtpOmSlL3Entry 8 }

mtpOmSlL3LocalMgmtUninhibit OBJECT-TYPE
    SYNTAX	Counter32
    UNITS	"seconds"
    MAX-ACCESS	read-only
    STATUS	current
    DESCRIPTION
	"This attribute represents measurement T1.116.2/2.14.
	 See also 10.3/T1.111.4.

	 Local management unininhibit in number of events per signalling 
	 link collected on a 5 or 30 minute interval.  This is a 
	 non-obligatory measurement that may be derived (from 2.17 and 
	 2.19 which are alarm clearing events)."
    REFERENCE
	"ANSI T1.116.1D localMgntUninhibit.
	 ANSI T1.116.2/2000 Table 2 (2.14).
	 ANSI T1.111.4/2000 10.3.
	 ITU-T Rec. Q.751.1, (10/95) : localMgmtUninhibit.
	 ITU-T Rec. Q.752, (1997) : Table 2/Q.752 2.14"
    ::= { mtpOmSlL3Entry 9 }

mtpOmSlL3LocalBusy OBJECT-TYPE
    SYNTAX	Counter32
    UNITS	"SIBs sent"
    MAX-ACCESS	read-only
    STATUS	current
    DESCRIPTION
	"This attribute represents measurement T1.116.2/2.15.
	 See also 9.3/T1.111.4.
	 
	 Duration of local busy in SIBs per signalling link collected 
	 over a 5 or 30 minute interval.  This is a non-obligatory 
	 measurement.  The measurement is used for near-real-time fault 
	 detection, general fault detection, and  MTP performance 
	 studies."
    REFERENCE
	"ANSI T1.116.1D localBusy.
	 ANSI T1.116.2/2000 Table 2 (2.15).
	 ANSI T1.111.4/2000 9.3.
	 ITU-T Rec. Q.751.1, (10/95) : localBusy.
	 ITU-T Rec. Q.752, (1997) : Table 2/Q.752 2.15"
    ::= { mtpOmSlL3Entry 10 }

mtpOmSlL3SlCongestedStarts OBJECT-TYPE
    SYNTAX	Counter32
    UNITS	"events"
    MAX-ACCESS	read-only
    STATUS	current
    DESCRIPTION
	"This attribute represents measurement T1.116.2/3.6.
	 See also 3.8/T1.111.4.
	 
	 Signalling link congestion indications per signalling link 
	 collected on a first and interval basis, or over a 5 or 30 
	 minute interval.  This measurement is non-obligatory and may be 
	 used for fault detection, near real-time monitoring, 
	 performance analysis and network administration and planning.
	 
	 The signalling link congestion refers to link status 
	 'congested' at Level 3.  A link is marked at Level 3 as 
	 congested when a congestion threshold is reached at the 
	 transmit side.  Measurements should be kept for thresholds 1, 2 
	 and 3 separately if that national option is selected.
	 
	 The reporting of this item on occurence should be considered 
	 carefully, since there might be many events in a short 
	 interval.  This might occur for example if the congestion onset 
	 and abatement thresholds were close together, or if the 
	 transmission/retransmission buffer size were significantly 
	 greater than the reception buffer at the other end of the link, 
	 and congestion occurred."
    REFERENCE
	"ANSI T1.116.1D slCongestedStarts.
	 ANSI T1.116.2/2000 Table 3 (3.6).
	 ANSI T1.114.1/2000 3.8.
	 ITU-T Q.752 (1997) Table 3 (3.6).
	 ITU-T Q.752 (1997) 2.4.6.
	 ITU-T Q.704 (1993) 3.6 and 11.
	 ITU-T Rec. Q.751.1, (10/95) : slCongestedStarts.
	 ITU-T Rec. Q.752, (1997) : Table 3/Q.752 3.6"
    ::= { mtpOmSlL3Entry 11 }

mtpOmSlL3SlCongestedDuration OBJECT-TYPE
    SYNTAX	Counter32
    UNITS	"seconds"
    MAX-ACCESS	read-only
    STATUS	current
    DESCRIPTION
	""
    REFERENCE
	"ITU-T Rec. Q.751.1, (10/95) : slCongestedDuration.
	 ITU-T Rec. Q.752, (1997) : Table 3/Q.752 3.7"
    ::= { mtpOmSlL3Entry 12 }

mtpOmSlL3SlCongestionStops OBJECT-TYPE
    SYNTAX	Counter32
    UNITS	"events"
    MAX-ACCESS	read-only
    STATUS	current
    DESCRIPTION
	"This attribute represents measurement T1.116.2/3.9.
	 See also 3.8/T1.111.4.
	 
	 Stop of signalling link congestion events per signalling link 
	 collected on a first and interval basis.  This measurement is 
	 non-obligatory and may be used for fault detection and 
	 performance analysis.

	 Stop of signalling link congestion occurs for a link at Level 3 
	 when the buffer occupancy has dropped below the congestion 
	 abatement threshold.  If a number of thresholds is used, the 
	 event is marked separately for each threshold.
	 
	 The reporting of this item on occurence should be considered 
	 carefully, since there might be many events in a short 
	 interval.  This might occur for example if the congestion onset 
	 and abatement thresholds were close together, or if the 
	 transmission/retransmission buffer size were significantly 
	 greater than the reception buffer at the other end of the link, 
	 and congestion occurred."
    REFERENCE
	"ANSI T1.116.1D slCongestionStops
	 ITU-T Rec. Q.751.1, (10/95) : slCongestionStops.
	 ITU-T Rec. Q.752, (1997) : Table 3/Q.752 3.9"
    ::= { mtpOmSlL3Entry 13 }

mtpOmSlL3DiscardedMSUs OBJECT-TYPE
    SYNTAX	Counter32
    UNITS	"MSUs"
    MAX-ACCESS	read-only
    STATUS	current
    DESCRIPTION
	"This attribute represents measurement T1.116.1/3.10

	 The number of MSUs discarded due to signalling link congestion.  
	 The significance and method of measuring this item depends upon 
	 the method of congestion handling employed in the newtork.  The 
	 three congestion handling methods are:

	 a) single congestion level without priority; or
	 b) national option of multiple levels without message 
	    priorities; or
	 c) the national option of multiple congestion levels with 
	    message priorities.

	 For cases a) and b), messages are discarded by the MTP only 
	 under extreme overload.  Thus the count indicates, if greater 
	 than zero, an extreme congestion.  It indicates the 
	 effectiveness of flow control procedures.  For case c), 
	 messages with priority less thatn the discard level are 
	 discarded in the MTP.  For this case, the MSUs discarded due to 
	 SL congestion (thresholds 1, 2 and 3 separately) are counted 
	 based on the greatest congestion discard threshold in effect on 
	 the link.  For example, if the congestion on a link has 
	 exceeded congestion discard threshold 2, and therefore MSUs 
	 with priority 0 and 1 are being discarded, a MSU discarded with 
	 priority 0 is counted in the threshould 2 count.
	 "
    REFERENCE
	"ANSI T1.116.1D discardedMSUs
	 ITU-T Rec. Q.751.1, (10/95) : discardedMSUs.
	 ITU-T Rec. Q.752, (1997) : Table 3/Q.752 3.10"
    ::= { mtpOmSlL3Entry 14 }

mtpOmSlL3CongestionEventsMSULoss OBJECT-TYPE
    SYNTAX	Counter32
    UNITS	"events"
    MAX-ACCESS	read-only
    STATUS	current
    DESCRIPTION
	"This attribute represents measurement T1.116.2/3.11
	 
	 The number of congestion events resulting in loss of MSUs per 
	 signalling link collected on a first and interval basis, or 
	 over a 5 or 30 minute interval.  This measurement is 
	 non-obligatory and may be used for fault detection, near 
	 real-time monitoring, performance analysis and network 
	 administration and planning.

	 This measurement is per congestion level.  For the national 
	 option of multiple congestion levels with message priorities, a 
	 congestion event that may result in the loss of MSUs for 
	 threshold 'n' begins when congestion discard threshold 'n' is 
	 exceeded.  A new congestion event that may result in the loss 
	 of MSUs for threshold 'n' cannot begin until the congestion 
	 level falls below congestion abatement threshold 'n'.  Only one 
	 congestion event which may result in the loss of MSUs can be in 
	 effect at one time, this being the greatest numbered threshold.  
	 Therefore, the congestion even that may result in the loss of 
	 MSUs for threshold 'n' is suspended (not stopped) when 
	 congestion discard threshod 'n+1' is exceeded, and resumed (not 
	 a new one started) when the congestion level falls below 
	 congestion abatement threshold 'n+1'."
    REFERENCE
	"ANSI T1.116.1D congestionEventsMSULoss.
	 ANSI T1.116.2/2000 Table 3 (3.11).
	 ITU-T Q.752 (1997) Table 3 (3.11).
	 ITU-T Q.752 (1997) 2.4.10.
	 ITU-T Rec. Q.751.1, (10/95) : congestionEventsMSULoss.
	 ITU-T Rec. Q.752, (1997) : Table 3/Q.752 3.11"
    ::= { mtpOmSlL3Entry 15 }

mtpOmSlL3Changeovers OBJECT-TYPE
    SYNTAX	Counter32
    MAX-ACCESS	read-only
    STATUS	current
    DESCRIPTION
	""
    REFERENCE
	"Q.752, 1.10"
    ::= { mtpOmSlL3Entry 16 }

mtpOmSlL3Changebacks OBJECT-TYPE
    SYNTAX	Counter32
    MAX-ACCESS	read-only
    STATUS	current
    DESCRIPTION
	""
    REFERENCE
	"Q.752, 1.11"
    ::= { mtpOmSlL3Entry 17 }

mtpOmSlL3Restorations OBJECT-TYPE
    SYNTAX	Counter32
    MAX-ACCESS	read-only
    STATUS	current
    DESCRIPTION
	""
    REFERENCE
	"Q.752, 1.12"
    ::= { mtpOmSlL3Entry 18 }


-- ====================================================================

mtpOmSlL3Int5minTable OBJECT-TYPE
    SYNTAX	SEQUENCE OF MtpOmSlL3Int5minEntry
    MAX-ACCESS	not-accessible
    STATUS	current
    DESCRIPTION
	""
    ::= { mtpOmSlStats 3 }

mtpOmSlL3Int5minEntry OBJECT-TYPE
    SYNTAX	MtpOmSlL3Int5minEntry
    MAX-ACCESS	not-accessible
    STATUS	current
    DESCRIPTION
	""
    INDEX	{
	mtpSpId,	-- shared index
	mtpLsId,	-- shared index
	mtpSlSlCode,	-- shared index
	mtpOmSlL3Int5minInterval
    }
    ::= { mtpOmSlL3Int5minTable 1 }

MtpOmSlL3Int5minEntry ::= SEQUENCE {
    mtpOmSlL3Int5minInterval			Unsigned32,
    mtpOmSlL3Int5minTimeStamp			TimeStamp,
    mtpOmSlL3Int5minSlUnavailabilityDuration	PerfIntervalCount, -- Q.752, 2.1
    mtpOmSlL3Int5minSlLocalInhibition		PerfIntervalCount, -- Q.752, 2.5
    mtpOmSlL3Int5minSlRemoteInhibition		PerfIntervalCount, -- Q.752, 2.6
    mtpOmSlL3Int5minSlFailed			PerfIntervalCount, -- Q.752, 2.7
    mtpOmSlL3Int5minSlRemoteProcOutage		PerfIntervalCount, -- Q.752, 2.9
    mtpOmSlL3Int5minLocalMgmtInhibit		PerfIntervalCount, -- Q.752, 2.13
    mtpOmSlL3Int5minLocalMgmtUninhibit		PerfIntervalCount, -- Q.752, 2.14
    mtpOmSlL3Int5minLocalBusy			PerfIntervalCount, -- Q.752, 2.15
    mtpOmSlL3Int5minSlCongestedStarts		PerfIntervalCount, -- Q.752, 3.6
    mtpOmSlL3Int5minSlCongestedDuration		PerfIntervalCount, -- Q.752, 3.7
    mtpOmSlL3Int5minSlCongestionStops		PerfIntervalCount, -- Q.752, 3.9
    mtpOmSlL3Int5minDiscardedMSUs		PerfIntervalCount, -- Q.752, 3.10
    mtpOmSlL3Int5minCongestionEventsMSULoss	PerfIntervalCount, -- Q.752, 3.11
    mtpOmSlL3Int5minChangeovers			PerfIntervalCount, -- Q.752, 1.10
    mtpOmSlL3Int5minChangebacks			PerfIntervalCount, -- Q.752, 1.11
    mtpOmSlL3Int5minRestorations		PerfIntervalCount  -- Q.752, 1.12
}

mtpOmSlL3Int5minInterval OBJECT-TYPE
    SYNTAX	Unsigned32
    MAX-ACCESS	not-accessible
    STATUS	current
    DESCRIPTION
	""
    ::= { mtpOmSlL3Int5minEntry 1 }

mtpOmSlL3Int5minTimeStamp OBJECT-TYPE
    SYNTAX	TimeStamp
    MAX-ACCESS	read-only
    STATUS	current
    DESCRIPTION
	""
    ::= { mtpOmSlL3Int5minEntry 2 }

mtpOmSlL3Int5minSlUnavailabilityDuration OBJECT-TYPE
    SYNTAX	PerfIntervalCount
    UNITS	"seconds"
    MAX-ACCESS	read-only
    STATUS	current
    DESCRIPTION
	"This attribute represents measurement T1.116.2/2.1

	 Duration of signalling link unavailability (for any reason) in 
	 units of seconds per signalling link.  This is an obligatory 
	 operational measurement to be collected on a 30 minute basis.  
	 This operational measurement is permanently activated.  This 
	 operational measurement may be derived (from 1.2, 1.12, 2.5 and 
	 2.6).

	 This measurement can be used in calculations for the detection 
	 of increases in signalling link signalling unit error rates 
	 (ANSI T1.116.2/2000 6.2.1.4.1).  It may also be used in the 
	 calculation of signalling link utilization (ANSI T1.116.2/2000 
	 6.2.2.1).
	 "
    REFERENCE
	"ANSI T1.116.1D slUnavailabilityDuration
	 ITU-T Rec. Q.751.1, (10/95) : slUnavailabilityDuration.
	 ITU-T Rec. Q.752, (1997) : Table 2/Q.752 2.1"
    ::= { mtpOmSlL3Int5minEntry 3 }

mtpOmSlL3Int5minSlLocalInhibition OBJECT-TYPE
    SYNTAX	PerfIntervalCount
    UNITS	"seconds"
    MAX-ACCESS	read-only
    STATUS	current
    DESCRIPTION
	"This attribute represents measurement T1.116.2/2.5.
	 See also 3.2.8/T1.111.4.
	 
	 Duration of signalling link inhibition due to local management 
	 actions in units of seconds per signalling link collected on a 
	 30 minute interval.  This is a non-obligatory operational 
	 measurement that may be derived (from 2.16 and 2.17 which are 
	 alarm indication and clearing events).

	 This operational measurement is used in MTP performance 
	 studies.
	 "
    REFERENCE
	"ANSI T1.116.1D slLocalInhibition.
	 ANSI T1.116.1/2000 Table 2 (2.5).
	 ANSI T1.111.4/2000 3.2.8.
	 ITU-T Rec. Q.751.1, (10/95) : slLocalInhibition
	 ITU-T Rec. Q.752, (1997) : Table 2/Q.752 2.5"
    ::= { mtpOmSlL3Int5minEntry 4 }

mtpOmSlL3Int5minSlRemoteInhibition OBJECT-TYPE
    SYNTAX	PerfIntervalCount
    UNITS	"seconds"
    MAX-ACCESS	read-only
    STATUS	current
    DESCRIPTION
	"This attribute represents measurement T1.116.2/2.6.
	 See also 3.2.2/T1.111.4.

	 Duration of signalling link inhibition due to remote management 
	 actions in units of seconds per signalling link collected on a 
	 30 minute interval.  This is a non-obligatory operational 
	 measurement that may be derived (from 2.18 and 2.19 which are 
	 alarm indication and clearing events).

	 This operational measurement is used in MTP performance 
	 studies.
	 "
    REFERENCE
	"ANSI T1.116.1D slRemoteInhibition.
	 ANSI T1.116.1/2000 Table 2 (2.6).
	 ANSI T1.111.4/2000 3.2.2.
	 ITU-T Rec. Q.751.1, (10/95) : slRemoteInhibition.
	 ITU-T Rec. Q.752, (1997) : Table 2/Q.752 2.6"
    ::= { mtpOmSlL3Int5minEntry 5 }

mtpOmSlL3Int5minSlFailed OBJECT-TYPE
    SYNTAX	PerfIntervalCount
    UNITS	"seconds"
    MAX-ACCESS	read-only
    STATUS	current
    DESCRIPTION
	"This attribute represents measurement T1.116.2/2.7.
	 See also 3.2.2/T1.111.4.

	 Duration of signalling link unavailability due to link failure 
	 in units of seconds per signalling link collected on a 30 
	 minute interval.  This is non-obligatory operational 
	 measurement that may be derived (from 1.2 and 1.12 which are 
	 alarm indication and clearing events).

	 This operational measurement is used in MTP performance 
	 studies.
	 "
    REFERENCE
	"ANSI T1.116.1D slFailed.
	 ANSI T1.116.1/2000 Table 2 (2.7).
	 ANSI T1.111.4/2000 3.2.2.
	 ITU-T Rec. Q.751.1, (10/95) : slFailed.
	 ITU-T Rec. Q.752, (1997) : Table 2/Q.752 2.7"
    ::= { mtpOmSlL3Int5minEntry 6 }

mtpOmSlL3Int5minSlRemoteProcOutage OBJECT-TYPE
    SYNTAX	PerfIntervalCount
    UNITS	"seconds"
    MAX-ACCESS	read-only
    STATUS	current
    DESCRIPTION
	"This attribute represents measurementT1.116.2/2.9.
	 See also 3.2.6/T1.111.4.

	 Duraing of signalling link unavailability due to remote 
	 processor outage in units of seconds per siganlling link 
	 collected on a 30 minute interval.  This is a non-obligatory 
	 operational measurement that may be derived (from 2.10 and 2.11 
	 which are alarm indication and clearing events).

	 This operational measurement is used in MTP performance 
	 studies.
	 "
    REFERENCE
	"ANSI T1.116.1D slRemoteProcOutage.
	 ANSI T1.111.4/3.2.6.
	 ITU-T Rec. Q.751.1, (10/95) : slRemoteProcOutage.
	 ITU-T Rec. Q.752, (1997) : Table 2/Q.752 2.9"
    ::= { mtpOmSlL3Int5minEntry 7 }

mtpOmSlL3Int5minLocalMgmtInhibit OBJECT-TYPE
    SYNTAX	PerfIntervalCount
    UNITS	"seconds"
    MAX-ACCESS	read-only
    STATUS	current
    DESCRIPTION
	"This attribute represents measurement T1.116.2/2.13.
	 See also 10.2/T1.111.4.
	 
	 Local management inhibit in number of events per signalling 
	 link collected on a 5 or 30 minute interval.  This is a 
	 non-obligatory measurement that may be derived (from 2.16 which 
	 is a alarm indication event)."
    REFERENCE
	"ANSI T1.116.1D localMgntInhibit.
	 ANSI T1.116.2/2000 Table 2 (2.13).
	 ANSI T1.111.4/2000 10.2.
	 ITU-T Rec. Q.751.1, (10/95) : localMgmtInhibit.
	 ITU-T Rec. Q.752, (1997) : Table 2/Q.752 2.13"
    ::= { mtpOmSlL3Int5minEntry 8 }

mtpOmSlL3Int5minLocalMgmtUninhibit OBJECT-TYPE
    SYNTAX	PerfIntervalCount
    UNITS	"seconds"
    MAX-ACCESS	read-only
    STATUS	current
    DESCRIPTION
	"This attribute represents measurement T1.116.2/2.14.
	 See also 10.3/T1.111.4.

	 Local management unininhibit in number of events per signalling 
	 link collected on a 5 or 30 minute interval.  This is a 
	 non-obligatory measurement that may be derived (from 2.17 and 
	 2.19 which are alarm clearing events)."
    REFERENCE
	"ANSI T1.116.1D localMgntUninhibit.
	 ANSI T1.116.2/2000 Table 2 (2.14).
	 ANSI T1.111.4/2000 10.3.
	 ITU-T Rec. Q.751.1, (10/95) : localMgmtUninhibit.
	 ITU-T Rec. Q.752, (1997) : Table 2/Q.752 2.14"
    ::= { mtpOmSlL3Int5minEntry 9 }

mtpOmSlL3Int5minLocalBusy OBJECT-TYPE
    SYNTAX	PerfIntervalCount
    UNITS	"SIBs sent"
    MAX-ACCESS	read-only
    STATUS	current
    DESCRIPTION
	"This attribute represents measurement T1.116.2/2.15.
	 See also 9.3/T1.111.4.
	 
	 Duration of local busy in SIBs per signalling link collected 
	 over a 5 or 30 minute interval.  This is a non-obligatory 
	 measurement.  The measurement is used for near-real-time fault 
	 detection, general fault detection, and  MTP performance 
	 studies."
    REFERENCE
	"ANSI T1.116.1D localBusy.
	 ANSI T1.116.2/2000 Table 2 (2.15).
	 ANSI T1.111.4/2000 9.3.
	 ITU-T Rec. Q.751.1, (10/95) : localBusy.
	 ITU-T Rec. Q.752, (1997) : Table 2/Q.752 2.15"
    ::= { mtpOmSlL3Int5minEntry 10 }

mtpOmSlL3Int5minSlCongestedStarts OBJECT-TYPE
    SYNTAX	PerfIntervalCount
    UNITS	"events"
    MAX-ACCESS	read-only
    STATUS	current
    DESCRIPTION
	"This attribute represents measurement T1.116.2/3.6.
	 See also 3.8/T1.111.4.
	 
	 Signalling link congestion indications per signalling link 
	 collected on a first and interval basis, or over a 5 or 30 
	 minute interval.  This measurement is non-obligatory and may be 
	 used for fault detection, near real-time monitoring, 
	 performance analysis and network administration and planning.
	 
	 The signalling link congestion refers to link status 
	 'congested' at Level 3.  A link is marked at Level 3 as 
	 congested when a congestion threshold is reached at the 
	 transmit side.  Measurements should be kept for thresholds 1, 2 
	 and 3 separately if that national option is selected.
	 
	 The reporting of this item on occurence should be considered 
	 carefully, since there might be many events in a short 
	 interval.  This might occur for example if the congestion onset 
	 and abatement thresholds were close together, or if the 
	 transmission/retransmission buffer size were significantly 
	 greater than the reception buffer at the other end of the link, 
	 and congestion occurred."
    REFERENCE
	"ANSI T1.116.1D slCongestedStarts.
	 ANSI T1.116.2/2000 Table 3 (3.6).
	 ANSI T1.114.1/2000 3.8.
	 ITU-T Q.752 (1997) Table 3 (3.6).
	 ITU-T Q.752 (1997) 2.4.6.
	 ITU-T Q.704 (1993) 3.6 and 11.
	 ITU-T Rec. Q.751.1, (10/95) : slCongestedStarts.
	 ITU-T Rec. Q.752, (1997) : Table 3/Q.752 3.6"
    ::= { mtpOmSlL3Int5minEntry 11 }

mtpOmSlL3Int5minSlCongestedDuration OBJECT-TYPE
    SYNTAX	PerfIntervalCount
    UNITS	"seconds"
    MAX-ACCESS	read-only
    STATUS	current
    DESCRIPTION
	""
    REFERENCE
	"ITU-T Rec. Q.751.1, (10/95) : slCongestedDuration.
	 ITU-T Rec. Q.752, (1997) : Table 3/Q.752 3.7"
    ::= { mtpOmSlL3Int5minEntry 12 }

mtpOmSlL3Int5minSlCongestionStops OBJECT-TYPE
    SYNTAX	PerfIntervalCount
    UNITS	"events"
    MAX-ACCESS	read-only
    STATUS	current
    DESCRIPTION
	"This attribute represents measurement T1.116.2/3.9.
	 See also 3.8/T1.111.4.
	 
	 Stop of signalling link congestion events per signalling link 
	 collected on a first and interval basis.  This measurement is 
	 non-obligatory and may be used for fault detection and 
	 performance analysis.

	 Stop of signalling link congestion occurs for a link at Level 3 
	 when the buffer occupancy has dropped below the congestion 
	 abatement threshold.  If a number of thresholds is used, the 
	 event is marked separately for each threshold.
	 
	 The reporting of this item on occurence should be considered 
	 carefully, since there might be many events in a short 
	 interval.  This might occur for example if the congestion onset 
	 and abatement thresholds were close together, or if the 
	 transmission/retransmission buffer size were significantly 
	 greater than the reception buffer at the other end of the link, 
	 and congestion occurred."
    REFERENCE
	"ANSI T1.116.1D slCongestionStops
	 ITU-T Rec. Q.751.1, (10/95) : slCongestionStops.
	 ITU-T Rec. Q.752, (1997) : Table 3/Q.752 3.9"
    ::= { mtpOmSlL3Int5minEntry 13 }

mtpOmSlL3Int5minDiscardedMSUs OBJECT-TYPE
    SYNTAX	PerfIntervalCount
    UNITS	"MSUs"
    MAX-ACCESS	read-only
    STATUS	current
    DESCRIPTION
	"This attribute represents measurement T1.116.1/3.10

	 The number of MSUs discarded due to signalling link congestion.  
	 The significance and method of measuring this item depends upon 
	 the method of congestion handling employed in the newtork.  The 
	 three congestion handling methods are:

	 a) single congestion level without priority; or
	 b) national option of multiple levels without message 
	    priorities; or
	 c) the national option of multiple congestion levels with 
	    message priorities.

	 For cases a) and b), messages are discarded by the MTP only 
	 under extreme overload.  Thus the count indicates, if greater 
	 than zero, an extreme congestion.  It indicates the 
	 effectiveness of flow control procedures.  For case c), 
	 messages with priority less thatn the discard level are 
	 discarded in the MTP.  For this case, the MSUs discarded due to 
	 SL congestion (thresholds 1, 2 and 3 separately) are counted 
	 based on the greatest congestion discard threshold in effect on 
	 the link.  For example, if the congestion on a link has 
	 exceeded congestion discard threshold 2, and therefore MSUs 
	 with priority 0 and 1 are being discarded, a MSU discarded with 
	 priority 0 is counted in the threshould 2 count.
	 "
    REFERENCE
	"ANSI T1.116.1D discardedMSUs
	 ITU-T Rec. Q.751.1, (10/95) : discardedMSUs.
	 ITU-T Rec. Q.752, (1997) : Table 3/Q.752 3.10"
    ::= { mtpOmSlL3Int5minEntry 14 }

mtpOmSlL3Int5minCongestionEventsMSULoss OBJECT-TYPE
    SYNTAX	PerfIntervalCount
    UNITS	"events"
    MAX-ACCESS	read-only
    STATUS	current
    DESCRIPTION
	"This attribute represents measurement T1.116.2/3.11
	 
	 The number of congestion events resulting in loss of MSUs per 
	 signalling link collected on a first and interval basis, or 
	 over a 5 or 30 minute interval.  This measurement is 
	 non-obligatory and may be used for fault detection, near 
	 real-time monitoring, performance analysis and network 
	 administration and planning.

	 This measurement is per congestion level.  For the national 
	 option of multiple congestion levels with message priorities, a 
	 congestion event that may result in the loss of MSUs for 
	 threshold 'n' begins when congestion discard threshold 'n' is 
	 exceeded.  A new congestion event that may result in the loss 
	 of MSUs for threshold 'n' cannot begin until the congestion 
	 level falls below congestion abatement threshold 'n'.  Only one 
	 congestion event which may result in the loss of MSUs can be in 
	 effect at one time, this being the greatest numbered threshold.  
	 Therefore, the congestion even that may result in the loss of 
	 MSUs for threshold 'n' is suspended (not stopped) when 
	 congestion discard threshod 'n+1' is exceeded, and resumed (not 
	 a new one started) when the congestion level falls below 
	 congestion abatement threshold 'n+1'."
    REFERENCE
	"ANSI T1.116.1D congestionEventsMSULoss.
	 ANSI T1.116.2/2000 Table 3 (3.11).
	 ITU-T Q.752 (1997) Table 3 (3.11).
	 ITU-T Q.752 (1997) 2.4.10.
	 ITU-T Rec. Q.751.1, (10/95) : congestionEventsMSULoss.
	 ITU-T Rec. Q.752, (1997) : Table 3/Q.752 3.11"
    ::= { mtpOmSlL3Int5minEntry 15 }

mtpOmSlL3Int5minChangeovers OBJECT-TYPE
    SYNTAX	PerfIntervalCount
    MAX-ACCESS	read-only
    STATUS	current
    DESCRIPTION
	""
    REFERENCE
	"Q.752, 1.10"
    ::= { mtpOmSlL3Int5minEntry 16 }

mtpOmSlL3Int5minChangebacks OBJECT-TYPE
    SYNTAX	PerfIntervalCount
    MAX-ACCESS	read-only
    STATUS	current
    DESCRIPTION
	""
    REFERENCE
	"Q.752, 1.11"
    ::= { mtpOmSlL3Int5minEntry 17 }

mtpOmSlL3Int5minRestorations OBJECT-TYPE
    SYNTAX	PerfIntervalCount
    MAX-ACCESS	read-only
    STATUS	current
    DESCRIPTION
	""
    REFERENCE
	"Q.752, 1.12"
    ::= { mtpOmSlL3Int5minEntry 18 }


-- ====================================================================

mtpOmSlL3Int15minTable OBJECT-TYPE
    SYNTAX	SEQUENCE OF MtpOmSlL3Int15minEntry
    MAX-ACCESS	not-accessible
    STATUS	current
    DESCRIPTION
	""
    ::= { mtpOmSlStats 4 }

mtpOmSlL3Int15minEntry OBJECT-TYPE
    SYNTAX	MtpOmSlL3Int15minEntry
    MAX-ACCESS	not-accessible
    STATUS	current
    DESCRIPTION
	""
    INDEX	{
	mtpSpId,	-- shared index
	mtpLsId,	-- shared index
	mtpSlSlCode,	-- shared index
	mtpOmSlL3Int15minInterval
    }
    ::= { mtpOmSlL3Int15minTable 1 }

MtpOmSlL3Int15minEntry ::= SEQUENCE {
    mtpOmSlL3Int15minInterval			Unsigned32,
    mtpOmSlL3Int15minTimeStamp			TimeStamp,
    mtpOmSlL3Int15minSlUnavailabilityDuration	PerfIntervalCount, -- Q.752, 2.1
    mtpOmSlL3Int15minSlLocalInhibition		PerfIntervalCount, -- Q.752, 2.5
    mtpOmSlL3Int15minSlRemoteInhibition		PerfIntervalCount, -- Q.752, 2.6
    mtpOmSlL3Int15minSlFailed			PerfIntervalCount, -- Q.752, 2.7
    mtpOmSlL3Int15minSlRemoteProcOutage		PerfIntervalCount, -- Q.752, 2.9
    mtpOmSlL3Int15minLocalMgmtInhibit		PerfIntervalCount, -- Q.752, 2.13
    mtpOmSlL3Int15minLocalMgmtUninhibit		PerfIntervalCount, -- Q.752, 2.14
    mtpOmSlL3Int15minLocalBusy			PerfIntervalCount, -- Q.752, 2.15
    mtpOmSlL3Int15minSlCongestedStarts		PerfIntervalCount, -- Q.752, 3.6
    mtpOmSlL3Int15minSlCongestedDuration	PerfIntervalCount, -- Q.752, 3.7
    mtpOmSlL3Int15minSlCongestionStops		PerfIntervalCount, -- Q.752, 3.9
    mtpOmSlL3Int15minDiscardedMSUs		PerfIntervalCount, -- Q.752, 3.10
    mtpOmSlL3Int15minCongestionEventsMSULoss	PerfIntervalCount, -- Q.752, 3.11
    mtpOmSlL3Int15minChangeovers		PerfIntervalCount, -- Q.752, 1.10
    mtpOmSlL3Int15minChangebacks		PerfIntervalCount, -- Q.752, 1.11
    mtpOmSlL3Int15minRestorations		PerfIntervalCount  -- Q.752, 1.12
}

mtpOmSlL3Int15minInterval OBJECT-TYPE
    SYNTAX	Unsigned32
    MAX-ACCESS	not-accessible
    STATUS	current
    DESCRIPTION
	""
    ::= { mtpOmSlL3Int15minEntry 1 }

mtpOmSlL3Int15minTimeStamp OBJECT-TYPE
    SYNTAX	TimeStamp
    MAX-ACCESS	read-only
    STATUS	current
    DESCRIPTION
	""
    ::= { mtpOmSlL3Int15minEntry 2 }

mtpOmSlL3Int15minSlUnavailabilityDuration OBJECT-TYPE
    SYNTAX	PerfIntervalCount
    UNITS	"seconds"
    MAX-ACCESS	read-only
    STATUS	current
    DESCRIPTION
	"This attribute represents measurement T1.116.2/2.1

	 Duration of signalling link unavailability (for any reason) in 
	 units of seconds per signalling link.  This is an obligatory 
	 operational measurement to be collected on a 30 minute basis.  
	 This operational measurement is permanently activated.  This 
	 operational measurement may be derived (from 1.2, 1.12, 2.5 and 
	 2.6).

	 This measurement can be used in calculations for the detection 
	 of increases in signalling link signalling unit error rates 
	 (ANSI T1.116.2/2000 6.2.1.4.1).  It may also be used in the 
	 calculation of signalling link utilization (ANSI T1.116.2/2000 
	 6.2.2.1).
	 "
    REFERENCE
	"ANSI T1.116.1D slUnavailabilityDuration
	 ITU-T Rec. Q.751.1, (10/95) : slUnavailabilityDuration.
	 ITU-T Rec. Q.752, (1997) : Table 2/Q.752 2.1"
    ::= { mtpOmSlL3Int15minEntry 3 }

mtpOmSlL3Int15minSlLocalInhibition OBJECT-TYPE
    SYNTAX	PerfIntervalCount
    UNITS	"seconds"
    MAX-ACCESS	read-only
    STATUS	current
    DESCRIPTION
	"This attribute represents measurement T1.116.2/2.5.
	 See also 3.2.8/T1.111.4.
	 
	 Duration of signalling link inhibition due to local management 
	 actions in units of seconds per signalling link collected on a 
	 30 minute interval.  This is a non-obligatory operational 
	 measurement that may be derived (from 2.16 and 2.17 which are 
	 alarm indication and clearing events).

	 This operational measurement is used in MTP performance 
	 studies.
	 "
    REFERENCE
	"ANSI T1.116.1D slLocalInhibition.
	 ANSI T1.116.1/2000 Table 2 (2.5).
	 ANSI T1.111.4/2000 3.2.8.
	 ITU-T Rec. Q.751.1, (10/95) : slLocalInhibition
	 ITU-T Rec. Q.752, (1997) : Table 2/Q.752 2.5"
    ::= { mtpOmSlL3Int15minEntry 4 }

mtpOmSlL3Int15minSlRemoteInhibition OBJECT-TYPE
    SYNTAX	PerfIntervalCount
    UNITS	"seconds"
    MAX-ACCESS	read-only
    STATUS	current
    DESCRIPTION
	"This attribute represents measurement T1.116.2/2.6.
	 See also 3.2.2/T1.111.4.

	 Duration of signalling link inhibition due to remote management 
	 actions in units of seconds per signalling link collected on a 
	 30 minute interval.  This is a non-obligatory operational 
	 measurement that may be derived (from 2.18 and 2.19 which are 
	 alarm indication and clearing events).

	 This operational measurement is used in MTP performance 
	 studies.
	 "
    REFERENCE
	"ANSI T1.116.1D slRemoteInhibition.
	 ANSI T1.116.1/2000 Table 2 (2.6).
	 ANSI T1.111.4/2000 3.2.2.
	 ITU-T Rec. Q.751.1, (10/95) : slRemoteInhibition.
	 ITU-T Rec. Q.752, (1997) : Table 2/Q.752 2.6"
    ::= { mtpOmSlL3Int15minEntry 5 }

mtpOmSlL3Int15minSlFailed OBJECT-TYPE
    SYNTAX	PerfIntervalCount
    UNITS	"seconds"
    MAX-ACCESS	read-only
    STATUS	current
    DESCRIPTION
	"This attribute represents measurement T1.116.2/2.7.
	 See also 3.2.2/T1.111.4.

	 Duration of signalling link unavailability due to link failure 
	 in units of seconds per signalling link collected on a 30 
	 minute interval.  This is non-obligatory operational 
	 measurement that may be derived (from 1.2 and 1.12 which are 
	 alarm indication and clearing events).

	 This operational measurement is used in MTP performance 
	 studies.
	 "
    REFERENCE
	"ANSI T1.116.1D slFailed.
	 ANSI T1.116.1/2000 Table 2 (2.7).
	 ANSI T1.111.4/2000 3.2.2.
	 ITU-T Rec. Q.751.1, (10/95) : slFailed.
	 ITU-T Rec. Q.752, (1997) : Table 2/Q.752 2.7"
    ::= { mtpOmSlL3Int15minEntry 6 }

mtpOmSlL3Int15minSlRemoteProcOutage OBJECT-TYPE
    SYNTAX	PerfIntervalCount
    UNITS	"seconds"
    MAX-ACCESS	read-only
    STATUS	current
    DESCRIPTION
	"This attribute represents measurementT1.116.2/2.9.
	 See also 3.2.6/T1.111.4.

	 Duraing of signalling link unavailability due to remote 
	 processor outage in units of seconds per siganlling link 
	 collected on a 30 minute interval.  This is a non-obligatory 
	 operational measurement that may be derived (from 2.10 and 2.11 
	 which are alarm indication and clearing events).

	 This operational measurement is used in MTP performance 
	 studies.
	 "
    REFERENCE
	"ANSI T1.116.1D slRemoteProcOutage.
	 ANSI T1.111.4/3.2.6.
	 ITU-T Rec. Q.751.1, (10/95) : slRemoteProcOutage.
	 ITU-T Rec. Q.752, (1997) : Table 2/Q.752 2.9"
    ::= { mtpOmSlL3Int15minEntry 7 }

mtpOmSlL3Int15minLocalMgmtInhibit OBJECT-TYPE
    SYNTAX	PerfIntervalCount
    UNITS	"seconds"
    MAX-ACCESS	read-only
    STATUS	current
    DESCRIPTION
	"This attribute represents measurement T1.116.2/2.13.
	 See also 10.2/T1.111.4.
	 
	 Local management inhibit in number of events per signalling 
	 link collected on a 5 or 30 minute interval.  This is a 
	 non-obligatory measurement that may be derived (from 2.16 which 
	 is a alarm indication event)."
    REFERENCE
	"ANSI T1.116.1D localMgntInhibit.
	 ANSI T1.116.2/2000 Table 2 (2.13).
	 ANSI T1.111.4/2000 10.2.
	 ITU-T Rec. Q.751.1, (10/95) : localMgmtInhibit.
	 ITU-T Rec. Q.752, (1997) : Table 2/Q.752 2.13"
    ::= { mtpOmSlL3Int15minEntry 8 }

mtpOmSlL3Int15minLocalMgmtUninhibit OBJECT-TYPE
    SYNTAX	PerfIntervalCount
    UNITS	"seconds"
    MAX-ACCESS	read-only
    STATUS	current
    DESCRIPTION
	"This attribute represents measurement T1.116.2/2.14.
	 See also 10.3/T1.111.4.

	 Local management unininhibit in number of events per signalling 
	 link collected on a 5 or 30 minute interval.  This is a 
	 non-obligatory measurement that may be derived (from 2.17 and 
	 2.19 which are alarm clearing events)."
    REFERENCE
	"ANSI T1.116.1D localMgntUninhibit.
	 ANSI T1.116.2/2000 Table 2 (2.14).
	 ANSI T1.111.4/2000 10.3.
	 ITU-T Rec. Q.751.1, (10/95) : localMgmtUninhibit.
	 ITU-T Rec. Q.752, (1997) : Table 2/Q.752 2.14"
    ::= { mtpOmSlL3Int15minEntry 9 }

mtpOmSlL3Int15minLocalBusy OBJECT-TYPE
    SYNTAX	PerfIntervalCount
    UNITS	"SIBs sent"
    MAX-ACCESS	read-only
    STATUS	current
    DESCRIPTION
	"This attribute represents measurement T1.116.2/2.15.
	 See also 9.3/T1.111.4.
	 
	 Duration of local busy in SIBs per signalling link collected 
	 over a 5 or 30 minute interval.  This is a non-obligatory 
	 measurement.  The measurement is used for near-real-time fault 
	 detection, general fault detection, and  MTP performance 
	 studies."
    REFERENCE
	"ANSI T1.116.1D localBusy.
	 ANSI T1.116.2/2000 Table 2 (2.15).
	 ANSI T1.111.4/2000 9.3.
	 ITU-T Rec. Q.751.1, (10/95) : localBusy.
	 ITU-T Rec. Q.752, (1997) : Table 2/Q.752 2.15"
    ::= { mtpOmSlL3Int15minEntry 10 }

mtpOmSlL3Int15minSlCongestedStarts OBJECT-TYPE
    SYNTAX	PerfIntervalCount
    UNITS	"events"
    MAX-ACCESS	read-only
    STATUS	current
    DESCRIPTION
	"This attribute represents measurement T1.116.2/3.6.
	 See also 3.8/T1.111.4.
	 
	 Signalling link congestion indications per signalling link 
	 collected on a first and interval basis, or over a 5 or 30 
	 minute interval.  This measurement is non-obligatory and may be 
	 used for fault detection, near real-time monitoring, 
	 performance analysis and network administration and planning.
	 
	 The signalling link congestion refers to link status 
	 'congested' at Level 3.  A link is marked at Level 3 as 
	 congested when a congestion threshold is reached at the 
	 transmit side.  Measurements should be kept for thresholds 1, 2 
	 and 3 separately if that national option is selected.
	 
	 The reporting of this item on occurence should be considered 
	 carefully, since there might be many events in a short 
	 interval.  This might occur for example if the congestion onset 
	 and abatement thresholds were close together, or if the 
	 transmission/retransmission buffer size were significantly 
	 greater than the reception buffer at the other end of the link, 
	 and congestion occurred."
    REFERENCE
	"ANSI T1.116.1D slCongestedStarts.
	 ANSI T1.116.2/2000 Table 3 (3.6).
	 ANSI T1.114.1/2000 3.8.
	 ITU-T Q.752 (1997) Table 3 (3.6).
	 ITU-T Q.752 (1997) 2.4.6.
	 ITU-T Q.704 (1993) 3.6 and 11.
	 ITU-T Rec. Q.751.1, (10/95) : slCongestedStarts.
	 ITU-T Rec. Q.752, (1997) : Table 3/Q.752 3.6"
    ::= { mtpOmSlL3Int15minEntry 11 }

mtpOmSlL3Int15minSlCongestedDuration OBJECT-TYPE
    SYNTAX	PerfIntervalCount
    UNITS	"seconds"
    MAX-ACCESS	read-only
    STATUS	current
    DESCRIPTION
	""
    REFERENCE
	"ITU-T Rec. Q.751.1, (10/95) : slCongestedDuration.
	 ITU-T Rec. Q.752, (1997) : Table 3/Q.752 3.7"
    ::= { mtpOmSlL3Int15minEntry 12 }

mtpOmSlL3Int15minSlCongestionStops OBJECT-TYPE
    SYNTAX	PerfIntervalCount
    UNITS	"events"
    MAX-ACCESS	read-only
    STATUS	current
    DESCRIPTION
	"This attribute represents measurement T1.116.2/3.9.
	 See also 3.8/T1.111.4.
	 
	 Stop of signalling link congestion events per signalling link 
	 collected on a first and interval basis.  This measurement is 
	 non-obligatory and may be used for fault detection and 
	 performance analysis.

	 Stop of signalling link congestion occurs for a link at Level 3 
	 when the buffer occupancy has dropped below the congestion 
	 abatement threshold.  If a number of thresholds is used, the 
	 event is marked separately for each threshold.
	 
	 The reporting of this item on occurence should be considered 
	 carefully, since there might be many events in a short 
	 interval.  This might occur for example if the congestion onset 
	 and abatement thresholds were close together, or if the 
	 transmission/retransmission buffer size were significantly 
	 greater than the reception buffer at the other end of the link, 
	 and congestion occurred."
    REFERENCE
	"ANSI T1.116.1D slCongestionStops
	 ITU-T Rec. Q.751.1, (10/95) : slCongestionStops.
	 ITU-T Rec. Q.752, (1997) : Table 3/Q.752 3.9"
    ::= { mtpOmSlL3Int15minEntry 13 }

mtpOmSlL3Int15minDiscardedMSUs OBJECT-TYPE
    SYNTAX	PerfIntervalCount
    UNITS	"MSUs"
    MAX-ACCESS	read-only
    STATUS	current
    DESCRIPTION
	"This attribute represents measurement T1.116.1/3.10

	 The number of MSUs discarded due to signalling link congestion.  
	 The significance and method of measuring this item depends upon 
	 the method of congestion handling employed in the newtork.  The 
	 three congestion handling methods are:

	 a) single congestion level without priority; or
	 b) national option of multiple levels without message 
	    priorities; or
	 c) the national option of multiple congestion levels with 
	    message priorities.

	 For cases a) and b), messages are discarded by the MTP only 
	 under extreme overload.  Thus the count indicates, if greater 
	 than zero, an extreme congestion.  It indicates the 
	 effectiveness of flow control procedures.  For case c), 
	 messages with priority less thatn the discard level are 
	 discarded in the MTP.  For this case, the MSUs discarded due to 
	 SL congestion (thresholds 1, 2 and 3 separately) are counted 
	 based on the greatest congestion discard threshold in effect on 
	 the link.  For example, if the congestion on a link has 
	 exceeded congestion discard threshold 2, and therefore MSUs 
	 with priority 0 and 1 are being discarded, a MSU discarded with 
	 priority 0 is counted in the threshould 2 count.
	 "
    REFERENCE
	"ANSI T1.116.1D discardedMSUs
	 ITU-T Rec. Q.751.1, (10/95) : discardedMSUs.
	 ITU-T Rec. Q.752, (1997) : Table 3/Q.752 3.10"
    ::= { mtpOmSlL3Int15minEntry 14 }

mtpOmSlL3Int15minCongestionEventsMSULoss OBJECT-TYPE
    SYNTAX	PerfIntervalCount
    UNITS	"events"
    MAX-ACCESS	read-only
    STATUS	current
    DESCRIPTION
	"This attribute represents measurement T1.116.2/3.11
	 
	 The number of congestion events resulting in loss of MSUs per 
	 signalling link collected on a first and interval basis, or 
	 over a 5 or 30 minute interval.  This measurement is 
	 non-obligatory and may be used for fault detection, near 
	 real-time monitoring, performance analysis and network 
	 administration and planning.

	 This measurement is per congestion level.  For the national 
	 option of multiple congestion levels with message priorities, a 
	 congestion event that may result in the loss of MSUs for 
	 threshold 'n' begins when congestion discard threshold 'n' is 
	 exceeded.  A new congestion event that may result in the loss 
	 of MSUs for threshold 'n' cannot begin until the congestion 
	 level falls below congestion abatement threshold 'n'.  Only one 
	 congestion event which may result in the loss of MSUs can be in 
	 effect at one time, this being the greatest numbered threshold.  
	 Therefore, the congestion even that may result in the loss of 
	 MSUs for threshold 'n' is suspended (not stopped) when 
	 congestion discard threshod 'n+1' is exceeded, and resumed (not 
	 a new one started) when the congestion level falls below 
	 congestion abatement threshold 'n+1'."
    REFERENCE
	"ANSI T1.116.1D congestionEventsMSULoss.
	 ANSI T1.116.2/2000 Table 3 (3.11).
	 ITU-T Q.752 (1997) Table 3 (3.11).
	 ITU-T Q.752 (1997) 2.4.10.
	 ITU-T Rec. Q.751.1, (10/95) : congestionEventsMSULoss.
	 ITU-T Rec. Q.752, (1997) : Table 3/Q.752 3.11"
    ::= { mtpOmSlL3Int15minEntry 15 }

mtpOmSlL3Int15minChangeovers OBJECT-TYPE
    SYNTAX	PerfIntervalCount
    MAX-ACCESS	read-only
    STATUS	current
    DESCRIPTION
	""
    REFERENCE
	"Q.752, 1.10"
    ::= { mtpOmSlL3Int15minEntry 16 }

mtpOmSlL3Int15minChangebacks OBJECT-TYPE
    SYNTAX	PerfIntervalCount
    MAX-ACCESS	read-only
    STATUS	current
    DESCRIPTION
	""
    REFERENCE
	"Q.752, 1.11"
    ::= { mtpOmSlL3Int15minEntry 17 }

mtpOmSlL3Int15minRestorations OBJECT-TYPE
    SYNTAX	PerfIntervalCount
    MAX-ACCESS	read-only
    STATUS	current
    DESCRIPTION
	""
    REFERENCE
	"Q.752, 1.12"
    ::= { mtpOmSlL3Int15minEntry 18 }


-- ====================================================================

mtpOmSlL2Table OBJECT-TYPE
    SYNTAX	SEQUENCE OF MtpOmSlL2Entry
    MAX-ACCESS	not-accessible
    STATUS	current
    DESCRIPTION
	""
    ::= { mtpOmSlStats 5 }

mtpOmSlL2Entry OBJECT-TYPE
    SYNTAX	MtpOmSlL2Entry
    MAX-ACCESS	not-accessible
    STATUS	current
    DESCRIPTION
	""
    INDEX	{
	mtpSpId,	-- shared index
	mtpLsId,	-- shared index
	mtpSlSlCode	-- shared index
    }
    ::= { mtpOmSlL2Table 1 }

MtpOmSlL2Entry ::= SEQUENCE {
    mtpOmSlL2ValidIntervals			HCPerfValidIntervals,
    mtpOmSlL2TimeDiscontinuity			TimeStamp,
    mtpOmSlL2SlInServiceDuration		Counter32, -- Q.752, 1.1
    mtpOmSlL2SlAlignment			Counter32, -- Q.752, 1.7
    mtpOmSlL2SignUnitsReceived			Counter32, -- Q.752, 1.8
    mtpOmSlL2NegAckReceived			Counter32, -- Q.752, 1.9
    mtpOmSlL2TransmittedOctetsSIFSIO		Counter32, -- Q.752, 3.1
    mtpOmSlL2RetransmittedOctets		Counter32, -- Q.752, 3.2
    mtpOmSlL2TransmittedMSUs			Counter32, -- Q.752, 3.3
    mtpOmSlL2ReceivedOctetsSIFSIO		Counter32, -- Q.752, 3.4
    mtpOmSlL2ReceivedMSUs			Counter32  -- Q.752, 3.5
}

mtpOmSlL2ValidIntervals OBJECT-TYPE
    SYNTAX	HCPerfValidIntervals
    MAX-ACCESS	read-only
    STATUS	current
    DESCRIPTION
	""
    ::= { mtpOmSlL2Entry 1 }

mtpOmSlL2TimeDiscontinuity OBJECT-TYPE
    SYNTAX	TimeStamp
    MAX-ACCESS	read-only
    STATUS	current
    DESCRIPTION
	""
    ::= { mtpOmSlL2Entry 2 }

mtpOmSlL2SlInServiceDuration OBJECT-TYPE
    SYNTAX	Counter32
    MAX-ACCESS	read-only
    STATUS	current
    DESCRIPTION
	"This attribute represents measurement T1.116.2/1.1

	 Duration of link in the in-service state in units of seconds 
	 per signalling link.  This is an obligatory operational 
	 measurement to be collected on a 30 minute basis.  This 
	 operational measurement is permanently activated.  This 
	 operational measurement may be derived (from 1.2 and 1.12, 
	 which are alarm and alarm clearing events).

	 This measurement can be used in calculations for the detection 
	 of increases in signalling link signalling unit error rates 
	 (ANSI T1.116.2/2000 6.2.1.4.1).  It may also be used in the 
	 calculation of signalling link utilization (ANSI T1.116.2/2000 
	 6.2.2.1).
	 "
    REFERENCE
	"ANSI T1.116.1D slInServiceDuration.
	 ANSI T1.116.1/2000 Table 1 (1.1).
	 ITU-T Rec. Q.752, (1997) : Table 1/Q.752 1.1
	 ITU-T Rec. Q.751.1, (10/95) : slInServiceDuration."
    ::= { mtpOmSlL2Entry 3 }

mtpOmSlL2SlAlignment OBJECT-TYPE
    SYNTAX	Counter32
    MAX-ACCESS	read-only
    STATUS	current
    DESCRIPTION
	"This attribute represents Measurement T1.116.2/1.7.
	 
	 Indicates a signalling data link fault that prevents the 
	 signalling data link from moving into service."
    REFERENCE
	"ANSI T1.116.1D slAlignment
	 ITU-T Rec. Q.752, (1997) : Table 1/Q.752 1.7
	 ITU-T Rec. Q.751.1 (10/95) : slAlignment."
    ::= { mtpOmSlL2Entry 4 }

mtpOmSlL2SignUnitsReceived OBJECT-TYPE
    SYNTAX	Counter32
    MAX-ACCESS	read-only
    STATUS	current
    DESCRIPTION
	"This attribute represents measurement T1.116.2/1.8.
	 See also 4/T1.111.4.
	 
	 Indicates the incoming message error rate."
    REFERENCE
	"ANSI T1.116.1D signUnitsReceived
	 ITU-T Rec. Q.752, (1997) : Table 1/Q.752 1.8
	 ITU-T Rec. Q.751.1 (10/95) : signUnitsReceived."
    ::= { mtpOmSlL2Entry 5 }

mtpOmSlL2NegAckReceived OBJECT-TYPE
    SYNTAX	Counter32
    MAX-ACCESS	read-only
    STATUS	current
    DESCRIPTION
	"This attribute represents measurement T1.116.2/1.9
	 
	 Indicates the outgoing message error rate."
    REFERENCE
	"ANSI T1.116.1D negAckReceived
	 ITU-T Rec. Q.752, (1997) : Table 1/Q.752 1.9
	 ITU-T Rec. Q.751.1 (10/95) : negAckReceived."
    ::= { mtpOmSlL2Entry 6 }

mtpOmSlL2TransmittedOctetsSIFSIO OBJECT-TYPE
    SYNTAX	Counter32
    MAX-ACCESS	read-only
    STATUS	current
    DESCRIPTION
	"This attribute represents measurement T1.116.2/3.1.
	 See also 2.3.8/T1.111.4.
	 
	 The number of SIF and SIO octets transmitted does not include 
	 SIF and SIO octets that are retransmitted."
    REFERENCE
	"ANSI T1.116.1D transmittedOctetsSIFSIO
	 ITU-T Rec. Q.752, (1997) : Table 3/Q.752 3.1
	 ITU-T Rec. Q.751.1 (10/95) : transmittedOctetsSIFSIO."
    ::= { mtpOmSlL2Entry 7 }

mtpOmSlL2RetransmittedOctets OBJECT-TYPE
    SYNTAX	Counter32
    MAX-ACCESS	read-only
    STATUS	current
    DESCRIPTION
	"This attribute represents measurement T1.116.2/3.2.
	 See also 5/T1.111.4.
	 
	 The opening flag and the check bits are included in the count."
    REFERENCE
	"ANSI T1.116.1D retransmittedOctets
	 ITU-T Rec. Q.752, (1997) : Table 3/Q.752 3.2
	 ITU-T Rec. Q.751.1 (10/95) : retransmittedOctets."
    ::= { mtpOmSlL2Entry 8 }

mtpOmSlL2TransmittedMSUs OBJECT-TYPE
    SYNTAX	Counter32
    MAX-ACCESS	read-only
    STATUS	current
    DESCRIPTION
	"This attribute represents measurement T1.116.2/3.3
	 
	 The number of message signal units transmitted does not include 
	 message signal units that are retransmitted."
    REFERENCE
	"ANSI T1.116.1D transmittedMSUs
	 ITU-T Rec. Q.752, (1997) : Table 3/Q.752 3.3
	 ITU-T Rec. Q.751.1 (10/95) : transmittedMSUs."
    ::= { mtpOmSlL2Entry 9 }

mtpOmSlL2ReceivedOctetsSIFSIO OBJECT-TYPE
    SYNTAX	Counter32
    MAX-ACCESS	read-only
    STATUS	current
    DESCRIPTION
	"This attribute represents measurement T1.116.1/3.4"
    REFERENCE
	"ANSI T1.116.1D receivedOctetsSIFSIO
	 ITU-T Rec. Q.752, (1997) : Table 3/Q.752 3.4
	 ITU-T Rec. Q.751.1 (10/95) : receivedOctetsSIFSIO."
    ::= { mtpOmSlL2Entry 10 }

mtpOmSlL2ReceivedMSUs OBJECT-TYPE
    SYNTAX	Counter32
    MAX-ACCESS	read-only
    STATUS	current
    DESCRIPTION
	"This attribute represents measurement T1.116.1/3.5,

	 The number of message signal units received consists of all 
	 message signal units that are passed to Level 3 for processing."
    REFERENCE
	"ANSI T1.116.1D receivedMSUs
	 ITU-T Rec. Q.752, (1997) : Table 3/Q.752 3.5
	 ITU-T Rec. Q.751.1 (10/95) : receivedMSUs."
    ::= { mtpOmSlL2Entry 11 }


-- ====================================================================

mtpOmSlL2Int5minTable OBJECT-TYPE
    SYNTAX	SEQUENCE OF MtpOmSlL2Int5minEntry
    MAX-ACCESS	not-accessible
    STATUS	current
    DESCRIPTION
	"Provides a 5 minute interval table for MTP Level 2 statistics."
    ::= { mtpOmSlStats 6 }

mtpOmSlL2Int5minEntry OBJECT-TYPE
    SYNTAX	MtpOmSlL2Int5minEntry
    MAX-ACCESS	not-accessible
    STATUS	current
    DESCRIPTION
	"Each entry in the table represents statistics collected for one 
	 5 minute interval.  The first interval in the table is the most 
	 recent 5 minute interval, beginning with 1."
    INDEX	{
	mtpSpId,	-- shared index
	mtpLsId,	-- shared index
	mtpSlSlCode,	-- shared index
	mtpOmSlL2Int5minInterval
    }
    ::= { mtpOmSlL2Int5minTable 1 }

MtpOmSlL2Int5minEntry ::= SEQUENCE {
    mtpOmSlL2Int5minInterval			Unsigned32,
    mtpOmSlL2Int5minTimestamp			TimeStamp,
    mtpOmSlL2Int5minSlInServiceDuration		PerfIntervalCount, -- Q.752, 1.1
    mtpOmSlL2Int5minSlAlignment			PerfIntervalCount, -- Q.752, 1.7
    mtpOmSlL2Int5minSignUnitsReceived		PerfIntervalCount, -- Q.752, 1.8
    mtpOmSlL2Int5minNegAckReceived		PerfIntervalCount, -- Q.752, 1.9
    mtpOmSlL2Int5minTransmittedOctetsSIFSIO	PerfIntervalCount, -- Q.752, 3.1
    mtpOmSlL2Int5minRetransmittedOctets		PerfIntervalCount, -- Q.752, 3.2
    mtpOmSlL2Int5minTransmittedMSUs		PerfIntervalCount, -- Q.752, 3.3
    mtpOmSlL2Int5minReceivedOctetsSIFSIO	PerfIntervalCount, -- Q.752, 3.4
    mtpOmSlL2Int5minReceivedMSUs		PerfIntervalCount  -- Q.752, 3.5
}

mtpOmSlL2Int5minInterval OBJECT-TYPE
    SYNTAX	Unsigned32
    MAX-ACCESS	not-accessible
    STATUS	current
    DESCRIPTION
	""
    ::= { mtpOmSlL2Int5minEntry 1 }

mtpOmSlL2Int5minTimestamp OBJECT-TYPE
    SYNTAX	TimeStamp
    MAX-ACCESS	read-only
    STATUS	current
    DESCRIPTION
	""
    ::= { mtpOmSlL2Int5minEntry 2 }

mtpOmSlL2Int5minSlInServiceDuration OBJECT-TYPE
    SYNTAX	PerfIntervalCount
    MAX-ACCESS	read-only
    STATUS	current
    DESCRIPTION
	"This attribute represents measurement T1.116.2/1.1

	 Duration of link in the in-service state in units of seconds 
	 per signalling link.  This is an obligatory operational 
	 measurement to be collected on a 30 minute basis.  This 
	 operational measurement is permanently activated.  This 
	 operational measurement may be derived (from 1.2 and 1.12, 
	 which are alarm and alarm clearing events).

	 This measurement can be used in calculations for the detection 
	 of increases in signalling link signalling unit error rates 
	 (ANSI T1.116.2/2000 6.2.1.4.1).  It may also be used in the 
	 calculation of signalling link utilization (ANSI T1.116.2/2000 
	 6.2.2.1).
	 "
    REFERENCE
	"ANSI T1.116.1D slInServiceDuration.
	 ANSI T1.116.1/2000 Table 1 (1.1).
	 ITU-T Rec. Q.752, (1997) : Table 1/Q.752 1.1
	 ITU-T Rec. Q.751.1, (10/95) : slInServiceDuration."
    ::= { mtpOmSlL2Int5minEntry 3 }

mtpOmSlL2Int5minSlAlignment OBJECT-TYPE
    SYNTAX	PerfIntervalCount
    MAX-ACCESS	read-only
    STATUS	current
    DESCRIPTION
	"This attribute represents Measurement T1.116.2/1.7.
	 
	 Indicates a signalling data link fault that prevents the 
	 signalling data link from moving into service."
    REFERENCE
	"ANSI T1.116.1D slAlignment
	 ITU-T Rec. Q.752, (1997) : Table 1/Q.752 1.7
	 ITU-T Rec. Q.751.1 (10/95) : slAlignment."
    ::= { mtpOmSlL2Int5minEntry 4 }

mtpOmSlL2Int5minSignUnitsReceived OBJECT-TYPE
    SYNTAX	PerfIntervalCount
    MAX-ACCESS	read-only
    STATUS	current
    DESCRIPTION
	"This attribute represents measurement T1.116.2/1.8.
	 See also 4/T1.111.4.
	 
	 Indicates the incoming message error rate."
    REFERENCE
	"ANSI T1.116.1D signUnitsReceived
	 ITU-T Rec. Q.752, (1997) : Table 1/Q.752 1.8
	 ITU-T Rec. Q.751.1 (10/95) : signUnitsReceived."
    ::= { mtpOmSlL2Int5minEntry 5 }

mtpOmSlL2Int5minNegAckReceived OBJECT-TYPE
    SYNTAX	PerfIntervalCount
    MAX-ACCESS	read-only
    STATUS	current
    DESCRIPTION
	"This attribute represents measurement T1.116.2/1.9
	 
	 Indicates the outgoing message error rate."
    REFERENCE
	"ANSI T1.116.1D negAckReceived
	 ITU-T Rec. Q.752, (1997) : Table 1/Q.752 1.9
	 ITU-T Rec. Q.751.1 (10/95) : negAckReceived."
    ::= { mtpOmSlL2Int5minEntry 6 }

mtpOmSlL2Int5minTransmittedOctetsSIFSIO OBJECT-TYPE
    SYNTAX	PerfIntervalCount
    MAX-ACCESS	read-only
    STATUS	current
    DESCRIPTION
	"This attribute represents measurement T1.116.2/3.1.
	 See also 2.3.8/T1.111.4.
	 
	 The number of SIF and SIO octets transmitted does not include 
	 SIF and SIO octets that are retransmitted."
    REFERENCE
	"ANSI T1.116.1D transmittedOctetsSIFSIO
	 ITU-T Rec. Q.752, (1997) : Table 3/Q.752 3.1
	 ITU-T Rec. Q.751.1 (10/95) : transmittedOctetsSIFSIO."
    ::= { mtpOmSlL2Int5minEntry 7 }

mtpOmSlL2Int5minRetransmittedOctets OBJECT-TYPE
    SYNTAX	PerfIntervalCount
    MAX-ACCESS	read-only
    STATUS	current
    DESCRIPTION
	"This attribute represents measurement T1.116.2/3.2.
	 See also 5/T1.111.4.
	 
	 The opening flag and the check bits are included in the count."
    REFERENCE
	"ANSI T1.116.1D retransmittedOctets
	 ITU-T Rec. Q.752, (1997) : Table 3/Q.752 3.2
	 ITU-T Rec. Q.751.1 (10/95) : retransmittedOctets."
    ::= { mtpOmSlL2Int5minEntry 8 }

mtpOmSlL2Int5minTransmittedMSUs OBJECT-TYPE
    SYNTAX	PerfIntervalCount
    MAX-ACCESS	read-only
    STATUS	current
    DESCRIPTION
	"This attribute represents measurement T1.116.2/3.3
	 
	 The number of message signal units transmitted does not include 
	 message signal units that are retransmitted."
    REFERENCE
	"ANSI T1.116.1D transmittedMSUs
	 ITU-T Rec. Q.752, (1997) : Table 3/Q.752 3.3
	 ITU-T Rec. Q.751.1 (10/95) : transmittedMSUs."
    ::= { mtpOmSlL2Int5minEntry 9 }

mtpOmSlL2Int5minReceivedOctetsSIFSIO OBJECT-TYPE
    SYNTAX	PerfIntervalCount
    MAX-ACCESS	read-only
    STATUS	current
    DESCRIPTION
	"This attribute represents measurement T1.116.1/3.4"
    REFERENCE
	"ANSI T1.116.1D receivedOctetsSIFSIO
	 ITU-T Rec. Q.752, (1997) : Table 3/Q.752 3.4
	 ITU-T Rec. Q.751.1 (10/95) : receivedOctetsSIFSIO."
    ::= { mtpOmSlL2Int5minEntry 10 }

mtpOmSlL2Int5minReceivedMSUs OBJECT-TYPE
    SYNTAX	PerfIntervalCount
    MAX-ACCESS	read-only
    STATUS	current
    DESCRIPTION
	"This attribute represents measurement T1.116.1/3.5,

	 The number of message signal units received consists of all 
	 message signal units that are passed to Level 3 for processing."
    REFERENCE
	"ANSI T1.116.1D receivedMSUs
	 ITU-T Rec. Q.752, (1997) : Table 3/Q.752 3.5
	 ITU-T Rec. Q.751.1 (10/95) : receivedMSUs."
    ::= { mtpOmSlL2Int5minEntry 11 }


-- ====================================================================

mtpOmSlL2Int15minTable OBJECT-TYPE
    SYNTAX	SEQUENCE OF MtpOmSlL2Int15minEntry
    MAX-ACCESS	not-accessible
    STATUS	current
    DESCRIPTION
	"Provides a 15 minute interval table for MTP Level 2 
	 statistics."
    ::= { mtpOmSlStats 7 }

mtpOmSlL2Int15minEntry OBJECT-TYPE
    SYNTAX	MtpOmSlL2Int15minEntry
    MAX-ACCESS	not-accessible
    STATUS	current
    DESCRIPTION
	"Each entry in the table represents statistics collected for one 
	 15 minute interval.  The first interval in the table is the 
	 most recent 15 minute interval, beginning with 1."
    INDEX	{
	mtpSpId,	-- shared index
	mtpLsId,	-- shared index
	mtpSlSlCode,	-- shared index
	mtpOmSlL2Int15minInterval
    }
    ::= { mtpOmSlL2Int15minTable 1 }

MtpOmSlL2Int15minEntry ::= SEQUENCE {
    mtpOmSlL2Int15minInterval			Unsigned32,
    mtpOmSlL2Int15minTimestamp			TimeStamp,
    mtpOmSlL2Int15minSlInServiceDuration	PerfIntervalCount, -- Q.752, 1.1
    mtpOmSlL2Int15minSlAlignment		PerfIntervalCount, -- Q.752, 1.7
    mtpOmSlL2Int15minSignUnitsReceived		PerfIntervalCount, -- Q.752, 1.8
    mtpOmSlL2Int15minNegAckReceived		PerfIntervalCount, -- Q.752, 1.9
    mtpOmSlL2Int15minTransmittedOctetsSIFSIO	PerfIntervalCount, -- Q.752, 3.1
    mtpOmSlL2Int15minRetransmittedOctets	PerfIntervalCount, -- Q.752, 3.2
    mtpOmSlL2Int15minTransmittedMSUs		PerfIntervalCount, -- Q.752, 3.3
    mtpOmSlL2Int15minReceivedOctetsSIFSIO	PerfIntervalCount, -- Q.752, 3.4
    mtpOmSlL2Int15minReceivedMSUs		PerfIntervalCount  -- Q.752, 3.5
}

mtpOmSlL2Int15minInterval OBJECT-TYPE
    SYNTAX	Unsigned32
    MAX-ACCESS	not-accessible
    STATUS	current
    DESCRIPTION
	""
    ::= { mtpOmSlL2Int15minEntry 1 }

mtpOmSlL2Int15minTimestamp OBJECT-TYPE
    SYNTAX	TimeStamp
    MAX-ACCESS	read-only
    STATUS	current
    DESCRIPTION
	""
    ::= { mtpOmSlL2Int15minEntry 2 }

mtpOmSlL2Int15minSlInServiceDuration OBJECT-TYPE
    SYNTAX	PerfIntervalCount
    MAX-ACCESS	read-only
    STATUS	current
    DESCRIPTION
	"This attribute represents measurement T1.116.2/1.1

	 Duration of link in the in-service state in units of seconds 
	 per signalling link.  This is an obligatory operational 
	 measurement to be collected on a 30 minute basis.  This 
	 operational measurement is permanently activated.  This 
	 operational measurement may be derived (from 1.2 and 1.12, 
	 which are alarm and alarm clearing events).

	 This measurement can be used in calculations for the detection 
	 of increases in signalling link signalling unit error rates 
	 (ANSI T1.116.2/2000 6.2.1.4.1).  It may also be used in the 
	 calculation of signalling link utilization (ANSI T1.116.2/2000 
	 6.2.2.1).
	 "
    REFERENCE
	"ANSI T1.116.1D slInServiceDuration.
	 ANSI T1.116.1/2000 Table 1 (1.1).
	 ITU-T Rec. Q.752, (1997) : Table 1/Q.752 1.1
	 ITU-T Rec. Q.751.1, (10/95) : slInServiceDuration."
    ::= { mtpOmSlL2Int15minEntry 3 }

mtpOmSlL2Int15minSlAlignment OBJECT-TYPE
    SYNTAX	PerfIntervalCount
    MAX-ACCESS	read-only
    STATUS	current
    DESCRIPTION
	"This attribute represents Measurement T1.116.2/1.7.
	 
	 Indicates a signalling data link fault that prevents the 
	 signalling data link from moving into service."
    REFERENCE
	"ANSI T1.116.1D slAlignment
	 ITU-T Rec. Q.752, (1997) : Table 1/Q.752 1.7
	 ITU-T Rec. Q.751.1 (10/95) : slAlignment."
    ::= { mtpOmSlL2Int15minEntry 4 }

mtpOmSlL2Int15minSignUnitsReceived OBJECT-TYPE
    SYNTAX	PerfIntervalCount
    MAX-ACCESS	read-only
    STATUS	current
    DESCRIPTION
	"This attribute represents measurement T1.116.2/1.8.
	 See also 4/T1.111.4.
	 
	 Indicates the incoming message error rate."
    REFERENCE
	"ANSI T1.116.1D signUnitsReceived
	 ITU-T Rec. Q.752, (1997) : Table 1/Q.752 1.8
	 ITU-T Rec. Q.751.1 (10/95) : signUnitsReceived."
    ::= { mtpOmSlL2Int15minEntry 5 }

mtpOmSlL2Int15minNegAckReceived OBJECT-TYPE
    SYNTAX	PerfIntervalCount
    MAX-ACCESS	read-only
    STATUS	current
    DESCRIPTION
	"This attribute represents measurement T1.116.2/1.9
	 
	 Indicates the outgoing message error rate."
    REFERENCE
	"ANSI T1.116.1D negAckReceived
	 ITU-T Rec. Q.752, (1997) : Table 1/Q.752 1.9
	 ITU-T Rec. Q.751.1 (10/95) : negAckReceived."
    ::= { mtpOmSlL2Int15minEntry 6 }

mtpOmSlL2Int15minTransmittedOctetsSIFSIO OBJECT-TYPE
    SYNTAX	PerfIntervalCount
    MAX-ACCESS	read-only
    STATUS	current
    DESCRIPTION
	"This attribute represents measurement T1.116.2/3.1.
	 See also 2.3.8/T1.111.4.
	 
	 The number of SIF and SIO octets transmitted does not include 
	 SIF and SIO octets that are retransmitted."
    REFERENCE
	"ANSI T1.116.1D transmittedOctetsSIFSIO
	 ITU-T Rec. Q.752, (1997) : Table 3/Q.752 3.1
	 ITU-T Rec. Q.751.1 (10/95) : transmittedOctetsSIFSIO."
    ::= { mtpOmSlL2Int15minEntry 7 }

mtpOmSlL2Int15minRetransmittedOctets OBJECT-TYPE
    SYNTAX	PerfIntervalCount
    MAX-ACCESS	read-only
    STATUS	current
    DESCRIPTION
	"This attribute represents measurement T1.116.2/3.2.
	 See also 5/T1.111.4.
	 
	 The opening flag and the check bits are included in the count."
    REFERENCE
	"ANSI T1.116.1D retransmittedOctets
	 ITU-T Rec. Q.752, (1997) : Table 3/Q.752 3.2
	 ITU-T Rec. Q.751.1 (10/95) : retransmittedOctets."
    ::= { mtpOmSlL2Int15minEntry 8 }

mtpOmSlL2Int15minTransmittedMSUs OBJECT-TYPE
    SYNTAX	PerfIntervalCount
    MAX-ACCESS	read-only
    STATUS	current
    DESCRIPTION
	"This attribute represents measurement T1.116.2/3.3
	 
	 The number of message signal units transmitted does not include 
	 message signal units that are retransmitted."
    REFERENCE
	"ANSI T1.116.1D transmittedMSUs
	 ITU-T Rec. Q.752, (1997) : Table 3/Q.752 3.3
	 ITU-T Rec. Q.751.1 (10/95) : transmittedMSUs."
    ::= { mtpOmSlL2Int15minEntry 9 }

mtpOmSlL2Int15minReceivedOctetsSIFSIO OBJECT-TYPE
    SYNTAX	PerfIntervalCount
    MAX-ACCESS	read-only
    STATUS	current
    DESCRIPTION
	"This attribute represents measurement T1.116.1/3.4"
    REFERENCE
	"ANSI T1.116.1D receivedOctetsSIFSIO
	 ITU-T Rec. Q.752, (1997) : Table 3/Q.752 3.4
	 ITU-T Rec. Q.751.1 (10/95) : receivedOctetsSIFSIO."
    ::= { mtpOmSlL2Int15minEntry 10 }

mtpOmSlL2Int15minReceivedMSUs OBJECT-TYPE
    SYNTAX	PerfIntervalCount
    MAX-ACCESS	read-only
    STATUS	current
    DESCRIPTION
	"This attribute represents measurement T1.116.1/3.5,

	 The number of message signal units received consists of all 
	 message signal units that are passed to Level 3 for processing."
    REFERENCE
	"ANSI T1.116.1D receivedMSUs
	 ITU-T Rec. Q.752, (1997) : Table 3/Q.752 3.5
	 ITU-T Rec. Q.751.1 (10/95) : receivedMSUs."
    ::= { mtpOmSlL2Int15minEntry 11 }


-- ====================================================================

mtpOmSdtStatsTable OBJECT-TYPE
    SYNTAX	SEQUENCE OF MtpOmSdtStatsEntry
    MAX-ACCESS	not-accessible
    STATUS	current
    DESCRIPTION
	"This is the SDT statistics table.  It provides statistics 
	 associated with signalling terminals."
    ::= { mtpOmSdtStats 1 }

mtpOmSdtStatsEntry OBJECT-TYPE
    SYNTAX	MtpOmSdtStatsEntry
    MAX-ACCESS	not-accessible
    STATUS	current
    DESCRIPTION
	"This is an entry in the SDT statistics table.  Each entry 
	 contains statistics associated with a single signalling 
	 terminal.  The entries are indexed using the same index as is 
	 used for the signalling terminal configuration and state table, 
	 and the statistics are corelated with the signalling terminal 
	 using that index.  Whenever a row exists in the signalling 
	 terminal table, a corresponding row with the same index exists 
	 in this table.
	 
	 A management station may continually walk this table, repeating 
	 every second or so, to collect near real-time statistics on the 
	 OpenSS7 implementations.  Note, however, that for general SS7 
	 implementations, statistics should be collected not more 
	 rapidly than on five minute intervals.  Notifications are 
	 provided for significant events to preclude the need for 
	 polling these tables.."
    AUGMENTS	{
	mtpSdtEntry
    }
    ::= { mtpOmSdtStatsTable 1 }

MtpOmSdtStatsEntry ::= SEQUENCE {
    mtpOmSdtStatsTxBytes			Counter32,
    mtpOmSdtStatsTxSus				Counter32,
    mtpOmSdtStatsTxSusRepeated			Counter32,
    mtpOmSdtStatsTxUnderruns			Counter32,
    mtpOmSdtStatsTxAborts			Counter32,
    mtpOmSdtStatsTxBufferOverflows		Counter32,
    mtpOmSdtStatsTxSusInError			Counter32,
    mtpOmSdtStatsRxBytes			Counter32,
    mtpOmSdtStatsRxSusCompressed		Counter32,
    mtpOmSdtStatsRxOverruns			Counter32,
    mtpOmSdtStatsRxAborts			Counter32,
    mtpOmSdtStatsRxBufferOverflows		Counter32,
    mtpOmSdtStatsRxSusInError			Counter32,
    mtpOmSdtStatsRxSyncTransitions		Counter32,
    mtpOmSdtStatsRxBitsOctetCounted		Counter32,
    mtpOmSdtStatsRxCrcErrors			Counter32,
    mtpOmSdtStatsRxFrameErrors			Counter32,
    mtpOmSdtStatsRxFrameOverflows		Counter32,
    mtpOmSdtStatsRxFrameTooLong			Counter32,
    mtpOmSdtStatsRxFrameTooShort		Counter32,
    mtpOmSdtStatsRxResidueErrors		Counter32,
    mtpOmSdtStatsCarrierCtsLost			Counter32,
    mtpOmSdtStatsCarrierDcdLost			Counter32,
    mtpOmSdtStatsCarrierLost			Counter32
}

mtpOmSdtStatsTxBytes OBJECT-TYPE
    SYNTAX	Counter32
    UNITS	"Octets"
    MAX-ACCESS	read-only
    STATUS	current
    DESCRIPTION
	"This is the count of the number of octets transmitted by the 
	 signalling terminal.  This count should increase rapidly during 
	 normal operation.  When this count does not increase, it means 
	 that the transmitters are not transmitting data."
    DEFVAL { 0 }
    ::= { mtpOmSdtStatsEntry 1 }

mtpOmSdtStatsTxSus OBJECT-TYPE
    SYNTAX	Counter32
    UNITS	"Signal Units"
    MAX-ACCESS	read-only
    STATUS	current
    DESCRIPTION
	"This is the number of signal units transmitted by the 
	 signalling terminal, it includes repeated SUs.  This count 
	 should increase rapidly during normal operation.  When this 
	 count does not increase, it means that the signalling terminal 
	 is not transmitting SUs."
    DEFVAL { 0 }
    ::= { mtpOmSdtStatsEntry 2 }

mtpOmSdtStatsTxSusRepeated OBJECT-TYPE
    SYNTAX	Counter32
    UNITS	"Signal Units"
    MAX-ACCESS	read-only
    STATUS	current
    DESCRIPTION
	"This is the count of the number of signal units repeated.  A 
	 signal unit is repeated when there is no additional signal unit 
	 waiting to be transmitted so the signalling terminal generates 
	 another copy of an LSSU or FISU, or if the last frame 
	 transmitted was an MSUs, a FISU is generated from the MSU 
	 previously sent.  This count should increase rapidly while idle 
	 (e.g. idling FISUs) during normal operation.  It is also normal 
	 for this count to not increase when the line is busy (activiely 
	 carrying a significant traffic load of MSUs."
    DEFVAL { 0 }
    ::= { mtpOmSdtStatsEntry 3 }

mtpOmSdtStatsTxUnderruns OBJECT-TYPE
    SYNTAX	Counter32
    UNITS	"Events"
    MAX-ACCESS	read-only
    STATUS	current
    DESCRIPTION
	"This is the count of the number of transmitter underrun events.  
	 A transmitter underrun event occurs when an unsufficient number 
	 of bits where provided to the signalling data link when the 
	 time came to transmit bits on the wire.  This count should not 
	 increase past possibly a small number when the link  is 
	 initialized for the first time.  Large counts here represent a 
	 significant problem."
    DEFVAL { 0 }
    ::= { mtpOmSdtStatsEntry 4 }

mtpOmSdtStatsTxAborts OBJECT-TYPE
    SYNTAX	Counter32
    UNITS	"Events"
    MAX-ACCESS	read-only
    STATUS	current
    DESCRIPTION
	"This is the count of the number of aborts transmitted.  The 
	 drivers do not normally transmit aborts (unless specifically 
	 requested to for test purposes).  This count should be low or 
	 zero.  A significant number here represents a heavy testing or 
	 a significant problem."
    DEFVAL { 0 }
    ::= { mtpOmSdtStatsEntry 5 }

mtpOmSdtStatsTxBufferOverflows OBJECT-TYPE
    SYNTAX	Counter32
    UNITS	"Events"
    MAX-ACCESS	read-only
    STATUS	current
    DESCRIPTION
	"This is the count of the number of transmit buffer overflow 
	 events.  A transmit  overflow event occurs when the signalling 
	 terminal goes to acquire a buffer to transmit data bits to the 
	 signalling data link and cannot immediately acquire a buffer, 
	 resulting in data loss.  The drivers recycle recieve buffers 
	 into transmit buffers from and to the signalling data link.  
	 There should be no counts in this item.  A significant number 
	 here would represent a significant problem."
    DEFVAL { 0 }
    ::= { mtpOmSdtStatsEntry 6 }

mtpOmSdtStatsTxSusInError OBJECT-TYPE
    SYNTAX	Counter32
    UNITS	"Signal Units"
    MAX-ACCESS	read-only
    STATUS	current
    DESCRIPTION
	"This is the count of signal units transmitted in error.  The 
	 drivers do not normally transmit signal units in error, unless 
	 requested to do so for testing purposes.  This count should be 
	 low or zero.  A significant number here reflects heavy testing 
	 or a significant error."
    DEFVAL { 0 }
    ::= { mtpOmSdtStatsEntry 7 }

mtpOmSdtStatsRxBytes OBJECT-TYPE
    SYNTAX	Counter32
    UNITS	"Octets"
    MAX-ACCESS	read-only
    STATUS	current
    DESCRIPTION
	"This count is the number of octets received by the signalling 
	 terminal from the signalling data link.  This number should 
	 increase rapidly under normal operation."
    DEFVAL { 0 }
    ::= { mtpOmSdtStatsEntry 8 }

mtpOmSdtStatsRxSusCompressed OBJECT-TYPE
    SYNTAX	Counter32
    UNITS	"Signal Units"
    MAX-ACCESS	read-only
    STATUS	current
    DESCRIPTION
	"This count is the number of signal units that were compressed 
	 on input.  Each signal unit that would otherwise have been 
	 delivered but was suppressed due to the SU compression 
	 algorithm is counted in this count.  This number should 
	 increase rapidly during normal operation when the line is idle 
	 (e.g. it is idling FISUs)."
    DEFVAL { 0 }
    ::= { mtpOmSdtStatsEntry 9 }

mtpOmSdtStatsRxOverruns OBJECT-TYPE
    SYNTAX	Counter32
    UNITS	"Events"
    MAX-ACCESS	read-only
    STATUS	current
    DESCRIPTION
	"This count is the number of receive buffer overruns that have 
	 occurred.  A receive buffer overrun occurs when the signalling 
	 terminal goes to allocate a buffer to deliver an SU to the 
	 signalling link and a buffer is not immediately available.  The 
	 drivers recycle singalling data link receive buffers into 
	 signalling data link transmit buffers and the signalling data 
	 link does the opposite (recycles transmit buffers to receive 
	 buffers).  This number should be low or zero and should not 
	 increase after the first initialization of the siganalling 
	 link.  A significant number here would represent a significant 
	 problem."
    DEFVAL { 0 }
    ::= { mtpOmSdtStatsEntry 10 }

mtpOmSdtStatsRxAborts OBJECT-TYPE
    SYNTAX	Counter32
    UNITS	"Events"
    MAX-ACCESS	read-only
    STATUS	current
    DESCRIPTION
	"This count is the number of aborts that were received in the 
	 incoming bit stream from the signalling data link.  Signalling 
	 data terminals do not normally send aborts.  A significant 
	 number here indicates that either the signalling data link is 
	 experiencing a fault or the remote signalling terminal is 
	 experiencing difficulties.  When a T1 or E1 span is losing 
	 synchronization, it is not uncommon to see this count rise.  If 
	 there are no group synchronization problems with the signalling 
	 link an increasing count here represends a problem with the 
	 facility or a problem with the remote signalling terminal."
    DEFVAL { 0 }
    ::= { mtpOmSdtStatsEntry 11 }

mtpOmSdtStatsRxBufferOverflows OBJECT-TYPE
    SYNTAX	Counter32
    UNITS	"Events"
    MAX-ACCESS	read-only
    STATUS	current
    DESCRIPTION
	"This count is the number of receive buffer overflow conditions.  
	 A receive buffer overflow condition occurs when, on the receive 
	 side, the siganlling terminal attempts to allocate a buffer to 
	 transmit data to a signalling link and a buffer is not 
	 immediately available.  Signalling link drivers typically 
	 recycle their buffers from receive to transmit and the 
	 signalling terminal recycles its buffers from transmit to 
	 receive.  Therefore, it is unlikely that a buffer overflow will 
	 occur.  An increasing number here represents a serious 
	 problem."
    DEFVAL { 0 }
    ::= { mtpOmSdtStatsEntry 12 }

mtpOmSdtStatsRxSusInError OBJECT-TYPE
    SYNTAX	Counter32
    UNITS	"Signal Units"
    MAX-ACCESS	read-only
    STATUS	current
    DESCRIPTION
	"This count is the count of the number of signal units received 
	 in error.  If this number is increasing it is either because 
	 the signalling link is noisy (due to, for example, loss of 
	 synchronization on the group carrier), or the remote signalling 
	 terminal is experiencing difficulties sending correct SUs.  A 
	 significant number here represents a significant problem with 
	 the signalling data link or with the remote signalling 
	 terminal."
    REFERENCE
	"Q.751.1, ANSI T1.116.1, Table 1/1.8"
    DEFVAL { 0 }
    ::= { mtpOmSdtStatsEntry 13 }

mtpOmSdtStatsRxSyncTransitions OBJECT-TYPE
    SYNTAX	Counter32
    UNITS	"Events"
    MAX-ACCESS	read-only
    STATUS	current
    DESCRIPTION
	"This count is the count of the number of synchronization 
	 transitions on the receive bitstream.  Syncrhonization 
	 transitions occur when the signalling terminal begins hunting 
	 for flags because a flag does not exist where expected and when 
	 the signalling terminal locks on flags and begins to frame 
	 proper HDLC frames.  Both the transition from flag and frame 
	 lock to flag hunting and the transition from flag hunting to 
	 flag and frame lock are counted.  A significant or increasing 
	 number of transitions here normally indicates that the group 
	 carrier providing the signalling link is experiencing 
	 syncrhonization problems (i.e. it is slipping).  For a clean 
	 facility, an increasing number here would indicate a difficulty 
	 with the remote signalling terminal."
    DEFVAL { 0 }
    ::= { mtpOmSdtStatsEntry 14 }

mtpOmSdtStatsRxBitsOctetCounted OBJECT-TYPE
    SYNTAX	Counter32
    UNITS	"Bits"
    MAX-ACCESS	read-only
    STATUS	current
    DESCRIPTION
	"This count is the number of bits (not bytes) octet counted.  
	 While the signalling terminal is hunting for flags, it counts 
	 the bits that it receives which do not contain a valid flag.  
	 These bits are used to count octets and every 16 octets are 
	 considered to be an SU in error for error monitoring purposes.  
	 An increasing number here indicates that the signalling 
	 terminal is hunting for flags and not finding them.  This can 
	 either be caused by a failed facility or by a serious problem 
	 with the remote signalling terminal."
    DEFVAL { 0 }
    ::= { mtpOmSdtStatsEntry 15 }

mtpOmSdtStatsRxCrcErrors OBJECT-TYPE
    SYNTAX	Counter32
    UNITS	"Events"
    MAX-ACCESS	read-only
    STATUS	current
    DESCRIPTION
	"This is the count of the number of CRC errors detected in the 
	 received bit stream.  This number should be small.  An 
	 excessive number of CRC errors either indicates that the 
	 signalling data link facility is noisy and is experiencing bit 
	 errors.  This would not normally result from a syncrhonization 
	 problem (framing would likely be lost and octet counting 
	 entered).  CRC errors result from random bit errors that are 
	 unlikely to affect flags.  A increasing or significant number 
	 here indicates a noisy signalling data link."
    DEFVAL { 0 }
    ::= { mtpOmSdtStatsEntry 16 }

mtpOmSdtStatsRxFrameErrors OBJECT-TYPE
    SYNTAX	Counter32
    UNITS	"Events"
    MAX-ACCESS	read-only
    STATUS	current
    DESCRIPTION
	"This is the count of the number of frame errors in the received 
	 bit stream."
    DEFVAL { 0 }
    ::= { mtpOmSdtStatsEntry 17 }

mtpOmSdtStatsRxFrameOverflows OBJECT-TYPE
    SYNTAX	Counter32
    UNITS	"Events"
    MAX-ACCESS	read-only
    STATUS	current
    DESCRIPTION
	""
    DEFVAL { 0 }
    ::= { mtpOmSdtStatsEntry 18 }

mtpOmSdtStatsRxFrameTooLong OBJECT-TYPE
    SYNTAX	Counter32
    UNITS	"Frames"
    MAX-ACCESS	read-only
    STATUS	current
    DESCRIPTION
	"This is the count of the number of frames that were too long 
	 (they had a number of octets between flags and CRC of greater 
	 than the maximum SIF length) in the receive bitstream.  This 
	 number should be zero or very small.  A significant count in 
	 this field indicates a loss of syncrhonization on the carrier 
	 hosting the signalling data link, a noisy signalilng data link, 
	 or a serious problem with the remote signalling terminal."
    DEFVAL { 0 }
    ::= { mtpOmSdtStatsEntry 19 }

mtpOmSdtStatsRxFrameTooShort OBJECT-TYPE
    SYNTAX	Counter32
    UNITS	"Frames"
    MAX-ACCESS	read-only
    STATUS	current
    DESCRIPTION
	"This is the count of the number of frames that were too short 
	 (they were shorter than a FISU) in the receive bitstream.  This 
	 number should be zero or very small.  A significant number in 
	 this field indicates a loss of syncrhonization on the carrier 
	 hosting the signalling data link, a noisy signalling data link 
	 or a serious problem with the remote signalling terminal."
    DEFVAL { 0 }
    ::= { mtpOmSdtStatsEntry 20 }

mtpOmSdtStatsRxResidueErrors OBJECT-TYPE
    SYNTAX	Counter32
    UNITS	"Frames"
    MAX-ACCESS	read-only
    STATUS	current
    DESCRIPTION
	"This is the count of frames with residue errors (a non-octet 
	 aligned number of bits) in the receive bitstream.  This number 
	 should be zero or small.  A significant or increasing number in 
	 this column indicates a loss of syncrhonization of the group 
	 carrier containing the signalling data link, a noisy signalling 
	 data link, or a serious problem with the remote signalling 
	 terminal."
    DEFVAL { 0 }
    ::= { mtpOmSdtStatsEntry 21 }

mtpOmSdtStatsCarrierCtsLost OBJECT-TYPE
    SYNTAX	Counter32
    UNITS	"Events"
    MAX-ACCESS	read-only
    STATUS	current
    DESCRIPTION
	"This is the count of the number of times that the CTS (Clear To 
	 Send) lead was lost (deasserted) on a V.35 interface.  A 
	 significant number in this column indicates a problem with the 
	 modem or channel bank providing access to the signalling data 
	 link over the V.35 interface."
    DEFVAL { 0 }
    ::= { mtpOmSdtStatsEntry 22 }

mtpOmSdtStatsCarrierDcdLost OBJECT-TYPE
    SYNTAX	Counter32
    UNITS	"Events"
    MAX-ACCESS	read-only
    STATUS	current
    DESCRIPTION
	"This is the count of the number of times that the DCD (Data 
	 Carrier Detect) lead was lost (deasserted) on a V.35 interface.  
	 A significant number in this column indicates a problemw tih 
	 the modem or channel bank providing access to the signalling 
	 data link over the V.35 interface."
    DEFVAL { 0 }
    ::= { mtpOmSdtStatsEntry 23 }

mtpOmSdtStatsCarrierLost OBJECT-TYPE
    SYNTAX	Counter32
    UNITS	"Events"
    MAX-ACCESS	read-only
    STATUS	current
    DESCRIPTION
	"This is the count of the number of times that the carrier was 
	 lost on a DS0/DS1 interface.  A significant number in this 
	 field indicates that there is a problem with syncrhonization of 
	 the group carrier containing the signalling data link."
    DEFVAL { 0 }
    ::= { mtpOmSdtStatsEntry 24 }


-- ====================================================================

mtpOmSdlStatsTable OBJECT-TYPE
    SYNTAX	SEQUENCE OF MtpOmSdlStatsEntry
    MAX-ACCESS	not-accessible
    STATUS	current
    DESCRIPTION
	"This is the SDL ststistics table.  It provides statistics 
	 associated with signalling data links."
    ::= { mtpOmSdlStats 1 }

mtpOmSdlStatsEntry OBJECT-TYPE
    SYNTAX	MtpOmSdlStatsEntry
    MAX-ACCESS	not-accessible
    STATUS	current
    DESCRIPTION
	"This is an entry in the SDL statistics table.  Each entry 
	 contains statistics associated with a single signalling data 
	 link.  The entries are indexed using the same index as is used 
	 for the signalling data link configuration and state table, and 
	 the statistics are corelated with the signalling data link 
	 using that index.  Whenever a row exists in the signalling data 
	 link table, a corresponding row with the same index exists in 
	 this table.
	 
	 A management station may continually walk this table, repeating 
	 every second or so, to collect near real-time statistics on the 
	 OpenSS7 implementations.  Note, however, that for general SS7 
	 implementations, statistics should not be collected more 
	 frequently than on five minute intervals.  Notifications are 
	 provided for significant events to preclude the need for 
	 polling these tables."
    AUGMENTS	{
	mtpSdlEntry
    }
    ::= { mtpOmSdlStatsTable 1 }

MtpOmSdlStatsEntry ::= SEQUENCE {
    mtpOmSdlStatsRxOctets			Counter32,
    mtpOmSdlStatsTxOctets			Counter32,
    mtpOmSdlStatsRXOverruns			Counter32,
    mtpOmSdlStatsTxUnderruns			Counter32,
    mtpOmSdlStatsRxBufferOverflows		Counter32,
    mtpOmSdlStatsTxBufferOverflows		Counter32,
    mtpOmSdlStatsLeadCtsLost			Counter32,
    mtpOmSdlStatsLeadDcdLost			Counter32,
    mtpOmSdlStatsCarrierLost			Counter32,
    mtpOmSdlStatsBipolarViolations		Counter32
}

mtpOmSdlStatsRxOctets OBJECT-TYPE
    SYNTAX	Counter32
    UNITS	"Octets"
    MAX-ACCESS	read-only
    STATUS	current
    DESCRIPTION
	"This is the count of the number of octets received by the 
	 signalling data link from the line.  This count should increase 
	 rapidly during normal operation.  When this count does not 
	 increase, it means that the receivers are not receiving data.  
	 Monitoring this column over a short period of time is a way of 
	 verifying the bit rate of the signalling data link.  During 
	 normal operation, this column should increase at a fixe rate 
	 equal to the bit rate of the signalling data link."
    ::= { mtpOmSdlStatsEntry 1 }

mtpOmSdlStatsTxOctets OBJECT-TYPE
    SYNTAX	Counter32
    UNITS	"Octets"
    MAX-ACCESS	read-only
    STATUS	current
    DESCRIPTION
	"This is the count of the number of octets transmitted by the 
	 signalling data link to the line.  This count should increase 
	 rapidly during normal operation.  When this count does not 
	 increase, it means that the transmittters are not transmitting 
	 data.  Monitoring this column over a short period of time is a 
	 way of verifying the transmission rate of the signalling data 
	 link.  During normal operation, this column should increase at 
	 a fixed rate equal to the bit rate of the signalling data 
	 link."
    ::= { mtpOmSdlStatsEntry 2 }

mtpOmSdlStatsRXOverruns OBJECT-TYPE
    SYNTAX	Counter32
    UNITS	"Occurences"
    MAX-ACCESS	read-only
    STATUS	current
    DESCRIPTION
	"Receive overruns are counted on the receiver between the line 
	 and the signalling data link terminating device.  This occurs 
	 whenever bits were able to be retrieved from the line, but the 
	 driver was too slow in accepting the previously received bit 
	 from the line, and the signalling data link receivers were 
	 forced to drop bits.  This should not occur in normal operation 
	 and this number should be low or zero and not increase after 
	 the first initialization of the signalling data link.  If this 
	 number is increasing, it indicates that there are significant 
	 latencies in some device driver which is performing too many 
	 functions with interrupts suppressed.  (Or the CPU is just too 
	 slow.)"
    ::= { mtpOmSdlStatsEntry 3 }

mtpOmSdlStatsTxUnderruns OBJECT-TYPE
    SYNTAX	Counter32
    UNITS	"Occurences"
    MAX-ACCESS	read-only
    STATUS	current
    DESCRIPTION
	"Transmit underruns are counted on the transmitter between the 
	 signalling data link and the line.  This occrus whenever bits 
	 were required to be transmitted on the wire and the signalling 
	 data link driver did not supply a sufficient number of bits to 
	 satisfy the requirement.  This should not occur in normal 
	 operation and this number should be low or zero and not 
	 increase after the first initialization of the signalling data 
	 link.  If this number is increasing, it indicates that there 
	 are significant latencies in some device driver which is 
	 performing too many functions with interrupts suppressed.  (Or 
	 the CPU is just too slow.)"
    ::= { mtpOmSdlStatsEntry 4 }

mtpOmSdlStatsRxBufferOverflows OBJECT-TYPE
    SYNTAX	Counter32
    UNITS	"Occurences"
    MAX-ACCESS	read-only
    STATUS	current
    DESCRIPTION
	"Receive buffer overflows occur between the signalling data link 
	 and the signalling terminal.  When the signalling data link 
	 driver goes to deliver data to the signalling terminal and a 
	 buffer to contain the data is not immediately available, a 
	 receive buffer overflow condition ensues.  Becuase of buffer 
	 recycling, this number should be low or zero and should not 
	 increase after the first initialization of the signalling data 
	 link.  If this number is increasing, it indicates that there 
	 are significant buffer or memory pressure issued or that there 
	 are significant latencies in some device driver which is 
	 performing too many functions with interrupts diabled.  (Or the 
	 CPU is just too slow.)"
    ::= { mtpOmSdlStatsEntry 5 }

mtpOmSdlStatsTxBufferOverflows OBJECT-TYPE
    SYNTAX	Counter32
    UNITS	"Occurences"
    MAX-ACCESS	read-only
    STATUS	current
    DESCRIPTION
	""
    ::= { mtpOmSdlStatsEntry 6 }

mtpOmSdlStatsLeadCtsLost OBJECT-TYPE
    SYNTAX	Counter32
    UNITS	"Occurences"
    MAX-ACCESS	read-only
    STATUS	current
    DESCRIPTION
	"This is the count of the number of times that the CTS (Clear To 
	 Send) lead was lost (deasserted) on a V.35 interface.  A 
	 significant number in this column indicates a problem with the 
	 modem or channel bank providing access to the signalling data 
	 link over the V.35 interface."
    ::= { mtpOmSdlStatsEntry 7 }

mtpOmSdlStatsLeadDcdLost OBJECT-TYPE
    SYNTAX	Counter32
    UNITS	"Occurences"
    MAX-ACCESS	read-only
    STATUS	current
    DESCRIPTION
	"This is the count of the number of times that the DCD (Data 
	 Carrier Detect) lead was lost (deasserted) on a V.35 interface.  
	 A significant number in this column indicates a problemw tih 
	 the modem or channel bank providing access to the signalling 
	 data link over the V.35 interface."
    ::= { mtpOmSdlStatsEntry 8 }

mtpOmSdlStatsCarrierLost OBJECT-TYPE
    SYNTAX	Counter32
    UNITS	"Occurences"
    MAX-ACCESS	read-only
    STATUS	current
    DESCRIPTION
	"This is the count of the number of times that the carrier was 
	 lost on a DS0/DS1 interface.  A significant number in this 
	 field indicates that there is a problem with syncrhonization of 
	 the group carrier containing the signalling data link."
    ::= { mtpOmSdlStatsEntry 9 }

mtpOmSdlStatsBipolarViolations OBJECT-TYPE
    SYNTAX	Counter32
    UNITS	"Occurences"
    MAX-ACCESS	read-only
    STATUS	current
    DESCRIPTION
	"This is the count of the number of bipolar violations received 
	 on a T1, J1 or E1 carrier."
    ::= { mtpOmSdlStatsEntry 10 }

-- ==========================================================================
-- SCALARS
-- ==========================================================================

mtpOm1stAndIntervalActivate OBJECT-TYPE
    SYNTAX InstancePointer
    MAX-ACCESS write-only
    STATUS current
    DESCRIPTION
	"Some measurements in this MIB that are to be collected on a 
	 first-and-interval basis are marked as obligatory but requiring 
	 activation.  Writing the instance pointer of the columnar 
	 object corresponding to the Counter32 for the measurement will 
	 activate the first-and-interval measurement if not already 
	 activated.  When the object cannot be activated, an SNMP error 
	 will be returned.
	 
	 The activation state of a measurement can be determined by 
	 attempting to read its PerfValue.  This is because these 
	 texutal conventions will return an error ('wrong value') if the 
	 particular columnar object is not activated (the data collected 
	 is invalid or missing).
	 
	 Activating first-and-interval for a given measurement causes 
	 ss7OnOccurEvent notifications to be issued for the first event 
	 within the interval that occurs for the corresponding measure.  
	 However, it has no effect on the communicationsAlarm or 
	 qualityOfServiceAalarm notifications that are generated for 
	 maintenance purposes."
    REFERENCE
	""
    ::= { mtpOmScalars 1 }

mtpOm1stAndIntervalDeactivate OBJECT-TYPE
    SYNTAX InstancePointer
    MAX-ACCESS write-only
    STATUS current
    DESCRIPTION
	"Some measurements in this MIB that are to be collected on a 
	 first-and-interval basis are marked as obligatory but requiring 
	 activation.  Writing the instance pointer of the columnar 
	 object corresponding to the Counter32 for the measurement will 
	 deactivate the first-and-interval measurement if not already 
	 activated.  When the object cannot be deactivated, an SNMP 
	 error will be returned.
	 
	 The activation state of a measurement can be determined by 
	 attempting to read its PerfValue.  This is because these 
	 texutal conventions will return an error if they particular 
	 columnar object is not activated (the data collected is invalid 
	 or missing).
	 
	 Activating first-and-interval for a given measurement causes 
	 ss7OnOccurEvent notifications to be issued for the first event 
	 within the interval that occurs for the corresponding measure.  
	 However, it has no effect on the communicationsAlarm or 
	 qualityOfServiceAalarm notifications that are generated for 
	 maintenance purposes."
    REFERENCE
	""
    ::= { mtpOmScalars 2 }

mtpOm5MinActivate OBJECT-TYPE
    SYNTAX InstancePointer
    MAX-ACCESS write-only
    STATUS current
    DESCRIPTION
	"Some measurements in this MIB that are to be collected on a 
	 5-minute basis are marked as obligatory by requiring 
	 activation.  Writing the instance pointer of the columnar 
	 object coresponding to the Counter32 for the measurement will 
	 activate the 5-minute measurement if not already activated.  
	 When the object cannot be activated, an SNMP error will be 
	 returned.
	 
	 The activation state of a measurement can be determined by 
	 attempting to read its PerfValue.  This is because these 
	 texutal conventions will return an error if they particular 
	 columnar object is not activated (the data collected is invalid 
	 or missing)."
    REFERENCE
	""
    ::= { mtpOmScalars 3 }

mtpOm5MinDeaActivate OBJECT-TYPE
    SYNTAX InstancePointer
    MAX-ACCESS write-only
    STATUS current
    DESCRIPTION
	"Some measurements in this MIB that are to be collected on a 
	 5-minute basis are marked as obligatory by requiring 
	 activation.  Writing the instance pointer of the columnar 
	 object coresponding to the Counter32 for the measurement will 
	 deactivate the 5-minute measurement if not already deactivated.  
	 When the object cannot be deactivated, an SNMP error will be 
	 returned.

	 The activation state of a measurement can be determined by 
	 attempting to read its PerfValue.  This is because these 
	 texutal conventions will return an error if they particular 
	 columnar object is not activated (the data collected is invalid 
	 or missing)."
    REFERENCE
	""
    ::= { mtpOmScalars 4 }

mtpOm15MinActivate OBJECT-TYPE
    SYNTAX InstancePointer
    MAX-ACCESS write-only
    STATUS current
    DESCRIPTION
	"Some measurements in this MIB that are to be collected on a 
	 15-minute basis are marked as obligatory by requiring 
	 activation.  Writing the instance pointer of the columnar 
	 object coresponding to the Counter32 for the measurement will 
	 activate the 15-minute measurement if not already activated.  
	 When the object cannot be activated, an SNMP error will be 
	 returned.
	 
	 The activation state of a measurement can be determined by 
	 attempting to read its PerfValue.  This is because these 
	 texutal conventions will return an error if they particular 
	 columnar object is not activated (the data collected is invalid 
	 or missing)."
    REFERENCE
	""
    ::= { mtpOmScalars 5 }

mtpOm15MinDeaActivate OBJECT-TYPE
    SYNTAX InstancePointer
    MAX-ACCESS write-only
    STATUS current
    DESCRIPTION
	"Some measurements in this MIB that are to be collected on a 
	 15-minute basis are marked as obligatory by requiring 
	 activation.  Writing the instance pointer of the columnar 
	 object coresponding to the Counter32 for the measurement will 
	 deactivate the 15-minute measurement if not already 
	 deactivated.  When the object cannot be deactivated, an SNMP 
	 error will be returned.
	 
	 The activation state of a measurement can be determined by 
	 attempting to read its PerfValue.  This is because these 
	 texutal conventions will return an error if they particular 
	 columnar object is not activated (the data collected is invalid 
	 or missing)."
    REFERENCE
	""
    ::= { mtpOmScalars 6 }

mtpOmInterval OBJECT-TYPE
    SYNTAX Integer32 (1..672)
    MAX-ACCESS not-accessible
    STATUS current
    DESCRIPTION
	"A historical data collection interval for use as an index.  
	 Specifies the historical data collection interval as a 
	 time-sequence with the lowest ordinal value '1' representing 
	 the newest data collected and the highest ordinal value 
	 (typically '96') being the oldest data collected."
    ::= { mtpOmScalars 7 }

mtpOmDiscontinuityTime OBJECT-TYPE
    SYNTAX TimeStamp
    MAX-ACCESS read-only
    STATUS current
    DESCRIPTION
	"The time of the last discontinuity."
    ::= { mtpOmScalars 8 }

mtpOmTimeStamp OBJECT-TYPE
    SYNTAX TimeStamp
    MAX-ACCESS read-only
    STATUS current
    DESCRIPTION
	"The time stamp of the beggining of the last completed 15-minute 
	 time interval when read, the beginning of an interval report 
	 for notifications."
    ::= { mtpOmScalars 9 }

mtpOm5MinMaxIntervals OBJECT-TYPE
    SYNTAX Unsigned32 (0..288)
    MAX-ACCESS read-write
    STATUS current
    DESCRIPTION
	"Indicates the maximum number of historical 5-minute intervals 
	 that will be collected.  This is in the range from zero (0), no 
	 historical data collected, to 288, 1 day of historical 5-minute 
	 data collected.  Some implementations may support longer 
	 periods of time, or some, a more restricted range.  The default 
	 value that should be supported by all managed systems by 
	 element configuration is 96, or 8 hours of historical 5-minute 
	 data.
	 
	 Increasing or decreasing this value may increase or descrease 
	 respectively the local storage demands of the agent.  
	 Decreasing this value may or may not cause historical interval 
	 data beyond the maximum to be discarded.  Increasing this value 
	 might not restore valid intervals beyond the point to which 
	 this maximum was previously decreased.
	 
	 Therefore, the setting of this value must be retained in 
	 permanent storage and should be altered only infrequently, if 
	 at all, by management stations."
    DEFVAL { 96 }
    ::= { mtpOmScalars 10 }

mtpOm15MinMaxIntervals OBJECT-TYPE
    SYNTAX Unsigned32 (0..672)
    MAX-ACCESS read-write
    STATUS current
    DESCRIPTION
	"Indicates and specifies the maximum number of historical 
	 15-minute intervals that will be collected.  This is in the 
	 range from zero (0), no historical data collected, to 672, 7 
	 days of historical 15-minute data collected.  Some 
	 implementations may support longer periods of time, or a some, 
	 a more restricted range.  The default value that should be 
	 supported by all managed systems by element configuration is 
	 96, or 24 hours of historical 15-minute data.
	 
	 Increasing or decreasing this value may increase or descrease 
	 respectively the local storage demands of the agent.  
	 Decreasing this value may or may not cause historical interval 
	 data beyond the maximum to be discarded.  Increasing this value 
	 might not restore valid intervals beyond the point to which 
	 this maximum was previously decreased.
	 
	 Therefore, the setting of this value must be retained in 
	 permanent storage and should be altered only infrequently, if 
	 at all, by management stations."
    DEFVAL { 96 }
    ::= { mtpOmScalars 11 }

END -- OPENSS7-MTP-OM-MIB2 module

-- vim: ft=mib comments=\f\:\",\b\:\-\-,\:\-\-,\f\b\:- fo+=tcqlornw tw=72 nocin nosi sts=4 sw=4
