-- vim: ft=mib comments=\f\:\",\b\:\-\-,\:\-\-,\f\b\:- fo+=tcqlornw tw=72 nocin nosi sts=4 sw=4
-- =============================================================================
-- 
-- @(#) $RCSfile: OPENSS7-MTP-MIB3.mib,v $ $Name: OpenSS7-0_9_2 $($Revision: 0.9.2.6 $) $Date: 2008-12-24 13:08:28 $
--
-- -----------------------------------------------------------------------------
--
-- Copyright (c) 2001-2008  OpenSS7 Corporation <http://www.openss7.com/>
-- Copyright (c) 1997-2000  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2008-12-24 13:08:28 $ by $Author: brian $
--
-- -----------------------------------------------------------------------------
--
-- $Log: OPENSS7-MTP-MIB3.mib,v $
-- Revision 0.9.2.6  2008-12-24 13:08:28  brian
-- - building ss7confd
--
-- Revision 0.9.2.5  2008-12-20 12:55:43  brian
-- - add new mibs and agents
--
-- Revision 0.9.2.4  2008-12-14 12:55:56  brian
-- - working up mibs
--
-- Revision 0.9.2.3  2008-10-11 04:34:39  brian
-- - cleanup MIBs
--
-- Revision 0.9.2.2  2008/04/29 07:11:22  brian
-- - updating headers for release
--
-- Revision 0.9.2.1  2008/01/24 17:43:03  brian
-- - added new mibs
--
-- =============================================================================

OPENSS7-MTP-MIB DEFINITIONS ::= BEGIN

IMPORTS
    MODULE-IDENTITY, OBJECT-IDENTITY, OBJECT-TYPE, NOTIFICATION-TYPE, 
    Integer32, Unsigned32, Counter32, Gauge32, zeroDotZero
	FROM SNMPv2-SMI

    TEXTUAL-CONVENTION, AutonomousType, RowPointer, RowStatus, 
    TimeInterval, TimeStamp, TruthValue
	FROM SNMPv2-TC

    SnmpAdminString
	FROM SNMP-FRAMEWORK-MIB

    MODULE-COMPLIANCE, NOTIFICATION-GROUP, OBJECT-GROUP
	FROM SNMPv2-CONF

    PerfCurrentCount, PerfIntervalCount
	FROM PerfHist-TC-MIB

    HCPerfIntervalThreshold, HCPerfValidIntervals
	FROM HC-PerfHist-TC-MIB

    Ss7ProtocolVariant
	FROM OPENSS7-SS7-MIB

    AdministrativeState, AvailabilityStatus, OperationalState, 
    ProceduralStatus, SimpleNameType, UsageState, AlarmStatus, 
    tmnObjectInstance, tmnPerceivedSeverity, tmnProbableCause, 
    attributeValueChangeNotificationPackage, communicationsAlarmPackage,  
    createDeleteNotificationsPackage
	FROM OPENSS7-SMI-MIB

    CircuitCode, CircuitIdentificationCode, MilliSeconds, 
    CommonLanguageName
	FROM OPENSS7-TC

    openss7, openss7Q, openss7Q751
	FROM OPENSS7-SMI;

mtpMIB MODULE-IDENTITY
    LAST-UPDATED "200812201153Z"
    ORGANIZATION "The OpenSS7 Project"
    CONTACT-INFO
	"Brian Bidulock
	 OpenSS7 Corporation
	 1469 Jefferys Crescent
	 Edmonton, Alberta  T6L 6T1
	 CANADA
	 Tel: +1 780 490 1141
	 Fax: +1 780 490 1241
	 Mob: +1 780 953 0557
	 mailto:bidulock@openss7.org"
    DESCRIPTION
	"MIB Module for SS7 MTP management.
	 
	 This MIB is based heavily on TMN (ITU-T Rec. X.721 (1992)) and 
	 the SS7 GDMOs (ITU-T Rec. Q.751.1 (1997) and ANSI T1.116.1 
	 (2000)).  It also includes statistics, alarms, notifications 
	 and operational measurements per ITU-T Rec. Q.752 (1997) and 
	 ANSI T1.116.2 (2000).
	 
	 The MIB uses the following relationships:
	 
	  - A network contains zero or more signalling points.
	 
	  - All objects other than a network and a signalling point are 
	    contained at some level within a signalling point.
	 
	  - A signalling data link is associated with a piece of 
	    physical equipment.  Signalling data links are described in 
	    the mtpSdlTable.
	 
	  - A signalling terminal is associated with a piece of physical 
	    equipment or software.  Signalling terminals are not 
	    normally independent from signalling data links, but may be.  
	    Signalling terminals are described in the mtpSdtTable.
	 
	  - A signalling link is a collection of a signalling data link 
	    providing the facility and a signalling terminal providing 
	    the access to the signalling data link media.  Signalling 
	    terminals may be permanently associated with a signalling 
	    data link or trace termination point for media and the 
	    signalling data link may be sufficient to identify the 
	    signalling terminal.  Signalling links are described in the 
	    mtpSlTable.
	 
	    Signalling links have two groups of protocol profiles:
	 
	    One profile is the MTP Level 3 profile for the signalling 
	    link and is much the same for most signalling links.  This 
	    profile is contained in the mtpSlL3ProfileTable.
	 
	    Another is the MTP Level 2 profile for the signalling link 
	    and is much the same for most signalling links of the same 
	    transmission speed, but varies from one transmission speed 
	    to another.  This protocol profile is contained in the 
	    mtpSlL2ProfileTable.
	 
	    Lastly the signalling terminal and data link has a protocol 
	    profile that depends both on the transmission rate as well 
	    as the precise nature of the data link (narrowband, ATM 
	    SAAL, or SIGTRAN).  This protocol profile is contained in 
	    the mtpL2NbTable, mtpL2SaalTable and mtpL2M2paTable 
	    depending on the nature of the data link.
	 
	    Signalling links are described in the mtpSlTable and have 
	    protocol profiles described in the mtpSlL3ProfileTable, 
	    mtpSlL2ProfileTable and the corresponding mtpNbTable, 
	    mtpSaalTable or mtpM2paTable.
	 
	  - A link set is a collection of signalling links whose remote 
	    termination points terminate on the same adjacent signalling 
	    point code.  Signalling link sets are described in the 
	    mtpLsTable and have protocol profiles described in the 
	    mtpLsProfileTable.
	 
	  - A combined link set is a collection of signalling link sets 
	    (normally one or two) over which traffic destined for a 
	    destination point code or set of destination point codes is 
	    load shared.  Combined link sets are not specified 
	    separately from route sets and there is no table for them.
	 
	  - A route is a signalling link set that has been allocated to 
	    a destination.  A route is a path to a remote or adjacent 
	    signalling point code via a link set to (possibly another) 
	    signalling point code.  Routes are described in the 
	    mtpRtTable and have protocol profiles described in the 
	    mtpRtProfileTable.
	 
	  - A route list is a collection of signalling routes to the 
	    same destination that have the same priority within a route 
	    set.  Route lists are not specified separately from routes 
	    and there is no table for them.
	 
	  - A route set is a collection of routes for the same 
	    destination.  Routes in a route set that have the same 
	    priority are candidates for loadsharing.  A route set is 
	    contained directly within a signalling point.  A route can 
	    be to a remote signalling point or can be to an adjacent 
	    signalling point, or can be to a signalling point cluster.  
	    Adjacent signalling points must have a type provided by the 
	    MtpSpType textual convention.  Route sets are described in 
	    the mtpRsTable and have protocol profiles described in the 
	    mtpRsProfileTable.
	 
	 This is a MIB providing management information is accordance 
	 with ITU-T Rec. Q.751.1, ITU-T Rec. Q.2751.1, ANSI T1.116.1.
	 
	 Notes:
	 
	  1. ITU-T Rec. Q.751.1 (1997) and ANSI T1.116.1 (2000) derive 
	     and contain managed objects against ITU-T Rec. M.3100 
	     managed objects.  This is largely a matter of alarms and 
	     performance measures.  This MIB assumes that the 
	     capabilities provided by ITU-T Rec. M.3100 are provided by 
	     an intermediate manager.  That is, alarm aggregation and 
	     summary, and performance measure analysis.  Therefore, 
	     there is no managedSwitchingElement MOC represented in this 
	     MIB.  The managedElementId to which alarms and measures 
	     correspond are implied by the SNMP host and community 
	     string.
	 
	  2. ITU-T Rec. Q.751.1 (1997) and ANSI T.116.1 (2000) do not 
	     provide a management model that accomodates having multiple 
	     protocol stack variants running on the same managed 
	     switching element under multiple network appearances, such 
	     as the international gateway SSP or STP illustrated in 
	     ITU-T Rec. Q.705 and ANSI T1.111.5.  This MIB adds a 
	     network appearance managed object class to accomodate that.
	 
	  3. ITU-T Rec. Q.2751.1 provides add-on support for MTP3b SAAL.  
	     The corresponding managed objects have been included in 
	     this MIB.
	 
	  4. ITU-T Rec. Q.751.1 Annex E and ITU-T Rec. ANSI T1.116.1 
	     Appendix D provide performance measurements in accordance 
	     with ITU-T Rec. Q.752 and ANSI T1.116.2.  However, the 
	     model of the performance measures are not ammeniable to 
	     SNMP and have been regrouped and simplified.
	 
	  5. ITU-T Rec. Q.752 and ANSI T1.116.2 only require a 5-minute 
	     collection interval for near-real-time performance measures 
	     and a 30-minute collection interval for longer term 
	     performance measures.  Nevertheless, it states that the 
	     objective is for 15-minute intervals for longer term 
	     performance measures.  Since these specifications are quite 
	     old and most systems are easily capable of 15-minute 
	     collection intervals, all 5-minute and 30-minute measures 
	     have been converted to 5-minute or 15-minute measures.
	 
	  6. The gateway screening provided in ITU-T Rec. Q.705 and ANSI 
	     T1.111.5 Clause 8 is a very simplified approach.  Three 
	     advances in the industry have occurred since then: enhanced 
	     gateway screening, border gateway screening, and full 
	     mediation.  Also, at the time that SS7 was developed, 
	     platforms were not very capable in this regard: current 
	     implemetnations should be able to perform a full access 
	     control list rule set on all message attributes.  This MIB 
	     has been updated to accomodate.
	 
	  7. Q.751.1, Q.2751.1 and ANSI T1.116.1 do not provide for RFC 
	     4165 M2PA (SIGTRAN) signalling links.  This MIB provides 
	     additional MOC definitions for signalling links that rely 
	     on M2PA to provide the underlying signalling link.  An 
	     attempt was made to do this consistent with the approach of 
	     Q.2751.1.
	 
	  8. Q.751.1 and T1.116.1 do not provide for Q.703 Annex A or 
	     ANSI T1.111.3 Appendix A operation (so-called high-speed 
	     signalling links at full T1 and E1 rates).  This MIB was 
	     enhanced to provide for Q.703 Annex A signalling links.
	 
	  9. Q.751.1 does not provide for management of many of the 
	     optional features found in Q.704 and ANSI T1.111.4.  Also, 
	     ANSI T1.116.1 does not provide management of timers 
	     specific to ANSI!  Additional attributes were added to 
	     managed object classes to accomodate this.
	"
    REVISION "200812201153Z"
    DESCRIPTION
	"Additional work."
    REVISION "200812161101Z"
    DESCRIPTION
	"Major rework of organization."
    REVISION "200801171900Z"
    DESCRIPTION
	"First release of this module."
    ::= { openss7Q751 1 }

 -- top level organization of the MIB

mtpNotifications	OBJECT IDENTIFIER ::= { mtpMIB		 0 }
mtpObjects		OBJECT IDENTIFIER ::= { mtpMIB		 1 }
mtpConformance		OBJECT IDENTIFIER ::= { mtpMIB		 2 }

mtpTables		OBJECT IDENTIFIER ::= { mtpObjects	 1 }
mtpScalars		OBJECT IDENTIFIER ::= { mtpObjects	 2 }
mtpNotifs		OBJECT IDENTIFIER ::= { mtpObjects	 3 }
mtpOids			OBJECT IDENTIFIER ::= { mtpObjects	 4 }

mtpCompliance		OBJECT IDENTIFIER ::= { mtpConformance	 1 }
mtpGroups		OBJECT IDENTIFIER ::= { mtpConformance	 2 }

mtpDefaults		OBJECT IDENTIFIER ::= { mtpScalars	 1 }

mtpProtocols		OBJECT IDENTIFIER ::= { mtpOids		 1 }
mtpProbableCauses	OBJECT IDENTIFIER ::= { mtpOids		 2 }
mtpSpecificProblems	OBJECT IDENTIFIER ::= { mtpOids		 3 }
mtpExtensions		OBJECT IDENTIFIER ::= { mtpOids		 4 }

mtpSap			OBJECT IDENTIFIER ::= { mtpTables	 1 }
mtpMs			OBJECT IDENTIFIER ::= { mtpTables	 2 }
mtpNa			OBJECT IDENTIFIER ::= { mtpTables	 3 }
mtpGs			OBJECT IDENTIFIER ::= { mtpTables	 4 }
mtpSp			OBJECT IDENTIFIER ::= { mtpTables	 5 }
mtpL3			OBJECT IDENTIFIER ::= { mtpTables	 6 }
mtpRs			OBJECT IDENTIFIER ::= { mtpTables	 7 }
mtpRt			OBJECT IDENTIFIER ::= { mtpTables	 8 }
mtpLs			OBJECT IDENTIFIER ::= { mtpTables	 9 }
mtpSl			OBJECT IDENTIFIER ::= { mtpTables	10 }
mtpSdt			OBJECT IDENTIFIER ::= { mtpTables	11 }
mtpSdl			OBJECT IDENTIFIER ::= { mtpTables	12 }

-- ====================================================================

-- (1.3.6.1.4.1.29591.17.751.1) mtpMIB
-- |__(0) mtpNotifications
-- |  |__( 1) mtpRestarting
-- |  |__( 2) ss7OnOccEvent
-- |  |__( 3) sdlEventLostSync
-- |  |__( 4) sdlEventSuError
-- |  |__( 5) sdlEventTxFail
-- |  |__( 6) sdlEventRxFail
-- |  |__( 7) sdtEventLostSync
-- |  |__( 8) sdtEventSuError
-- |  |__( 9) sdtEventTxFail
-- |  |__(10) sdtEventRxFail
-- |  |__(11) sdtEventCarrier
-- |  |__(12) slEventFailureAllReasons
-- |  |__(13) slEventFailureAbnormalBsnrFibr
-- |  |__(14) slEventFailureExcessiveDelayOfAck
-- |  |__(15) slEventFailureExcessiveErrorRate
-- |  |__(16) slEventFailureExcessiveDurationCongestion
-- |  |__(17) slEventLocalAutomaticChangeover
-- |  |__(18) slEventLocalAutomaticChangeback
-- |  |__(19) slEventRestoration
-- |  |__(10) slEventRpoStartEvent
-- |  |__(21) slEventRpoStopEvent
-- |  |__(22) slEventLocalInhibitionStart
-- |  |__(23) slEventLocalInhibitionStop
-- |  |__(24) slEventRemoteInhibitionStart
-- |  |__(25) slEventRemoteInhibitionStop
-- |  |__(26) slEventCongestionStart
-- |  |__(27) slEventCongestionStop
-- |  |__(28) slEventCongestionLoss
-- |  |__(29) lkEventFailureStart
-- |  |__(30) lkEventFailureStop
-- |  |__(31) lkEventSendTFP
-- |  |__(32) lkEventSendTFA
-- |  |__(33) rsEventUnavailableStart
-- |  |__(34) rsEventUnavailableStop
-- |  |__(35) rsEventAdjSpLinkSetChange
-- |  |__(36) rsEventAdjSPInaccessibleStart
-- |  |__(37) rsEventAdjSpInaccessibleStop
-- |  |__(38) rsEventRecvTFC
-- |  |__(39) spEventMsuDiscard
-- |  |__(40) spEventUpuSent
-- |  |__(41) spEventUpuRecv
-- |
-- |__( 1) mtpObjects
-- |  |__( 1) mtpTables
-- |  |  |__( 1) mtpSap
-- |  |  |  |__( 1) mtpSapTable
-- |  |  |     |__( 1) mtpSapEntry
-- |  |  |        |__( 1) mtpSapId
-- |  |  |        |__( 2) mtpSap2Address
-- |  |  |        |__( 3) mtpSapUserPart
-- |  |  |        |__( 4) mtpSapUserPartStatus
-- |  |  |        |__( 5) mtpSapUserEntityNames
-- |  |  |        |__( 6) mtpSapProviderEntityNames
-- |  |  |        |__( 7) mtpSapUsageState
-- |  |  |        |__( 8) mtpSapAsaProfilePointer
-- |  |  |        |__( 9) mtpSapName
-- |  |  |        |__(10) mtpSapLongMessageSupported
-- |  |  |        |__(11) mtpSapRowStatus
-- |  |  |
-- |  |  |__( 2) mtpMs
-- |  |  |  |__( 1) mtpMsTable
-- |  |  |     |__( 1) mtpMsEntry
-- |  |  |        |__( 1) mtpMsId
-- |  |  |        |__( 2) mtpMsName
-- |  |  |        |__( 3) mtpMsAlarmStatus
-- |  |  |        |__( 4) mtpMsOperationalState
-- |  |  |        |__( 5) mtpMsUsageState
-- |  |  |        |__( 6) mtpMsManagedElementType
-- |  |  |        |__( 7) mtpMsModelCode
-- |  |  |        |__( 8) mtpMsVendorName
-- |  |  |        |__( 9) mtpMsUserLabel
-- |  |  |        |__(10) mtpMsVersion
-- |  |  |        |__(11) mtpMsAsaProfilePointer
-- |  |  |        |__(12) mtpMsNetworkElementAliases
-- |  |  |        |__(13) mtpMsStatus
-- |  |  |
-- |  |  |__( 3) mtpNa
-- |  |  |  |__( 1) mtpNaTable
-- |  |  |     |__( 1) mtpNaEntry
-- |  |  |        |__( 1) mtpNaId
-- |  |  |        |__( 2) mtpNaProtocolVariant
-- |  |  |        |__( 3) mtpNaProtocolYear
-- |  |  |        |__( 4) mtpNaProtocolOptions
-- |  |  |        |__( 5) mtpNaNetworkIndicator
-- |  |  |        |__( 6) mtpNaPointCodeFormat
-- |  |  |        |__( 7) mtpNaSlsLength
-- |  |  |        |__( 8) mtpNaSpDefault
-- |  |  |        |__( 9) mtpNaName
-- |  |  |        |__(10) mtpNaRowStatus
-- |  |  |
-- |  |  |__( 4) mtpGs
-- |  |  |  |__( 1) mtpGsTable
-- |  |  |  |  |__( 1) mtpGsEntry
-- |  |  |  |     |__( 1) mtpGsId
-- |  |  |  |     |__( 2) mtpGsAdministrativeState
-- |  |  |  |     |__( 3) mtpGsTreatmentOfOutsideRanges
-- |  |  |  |     |__( 4) mtpGsListMode
-- |  |  |  |     |__( 5) mtpGsScreeningByLinkSetOrByOpc
-- |  |  |  |     |__( 6) mtpGsGetScreenedOpcsOrLinkSetsByDpc
-- |  |  |  |     |__( 7) mtpGsName
-- |  |  |  |     |__( 8) mtpGsRowStatus
-- |  |  |  |
-- |  |  |  |__( 2) mtpGsLineTable
-- |  |  |  |  |__( 1) mtpGsLineEntry
-- |  |  |  |     |__( 1) mtpGsLineId
-- |  |  |  |     |__( 2) mtpGsLineObject
-- |  |  |  |     |__( 3) mtpGsLineContent
-- |  |  |  |     |__( 4) mtpGsLineRowStatus
-- |  |  |  |
-- |  |  |  |__( 3) mtpGsLineContentTable
-- |  |  |     |__( 1) mtpGsLineContentEntry
-- |  |  |        |__( 1) mtpGsLineContentId
-- |  |  |        |__( 2) mtpGsLineContentDesignatedDPCFirst
-- |  |  |        |__( 3) mtpGsLineContentDesignatedDPCLast
-- |  |  |        |__( 4) mtpGsLineContentSiMask
-- |  |  |        |__( 5) mtpGsLineContentMessageTreatment
-- |  |  |        |__( 6) mtpGsLineContentComment
-- |  |  |        |__( 7) mtpGsLineContentRowStatus
-- |  |  |
-- |  |  |__( 5) mtpSp
-- |  |  |  |__( 1) mtpSpProfileTable
-- |  |  |  |  |__( 1) mtpSpProfileEntry
-- |  |  |  |     |__( 1) mtpSpProfileId
-- |  |  |  |     |__( 2) mtpSpProfileTimerT1R
-- |  |  |  |     |__( 3) mtpSpProfileTimerT2
-- |  |  |  |     |__( 4) mtpSpProfileTimerT4
-- |  |  |  |     |__( 5) mtpSpProfileTimerT5
-- |  |  |  |     |__( 6) mtpSpProfileTimerT7
-- |  |  |  |     |__( 7) mtpSpProfileTimerT11
-- |  |  |  |     |__( 8) mtpSpProfileTimerT12
-- |  |  |  |     |__( 9) mtpSpProfileTimerT13
-- |  |  |  |     |__(10) mtpSpProfileTimerT14
-- |  |  |  |     |__(11) mtpSpProfileTimerT15
-- |  |  |  |     |__(12) mtpSpProfileTimerT16
-- |  |  |  |     |__(13) mtpSpProfileTimerT18I
-- |  |  |  |     |__(14) mtpSpProfileTimerT19I
-- |  |  |  |     |__(15) mtpSpProfileTimerT20I
-- |  |  |  |     |__(16) mtpSpProfileTimerT21I
-- |  |  |  |     |__(17) mtpSpProfileTimerT22I
-- |  |  |  |     |__(18) mtpSpProfileTimerT23I
-- |  |  |  |     |__(19) mtpSpProfileTimerT20A
-- |  |  |  |     |__(20) mtpSpProfileTimerT21A
-- |  |  |  |     |__(21) mtpSpProfileTimerT22A
-- |  |  |  |     |__(22) mtpSpProfileTimerT23A
-- |  |  |  |     |__(23) mtpSpProfileTimerT24A
-- |  |  |  |     |__(24) mtpSpProfileTimerT26A
-- |  |  |  |     |__(25) mtpSpProfileTimerT27A
-- |  |  |  |     |__(26) mtpSpProfileTimerT1T
-- |  |  |  |     |__(27) mtpSpProfileTimerT2T
-- |  |  |  |     |__(28) mtpSpProfileName
-- |  |  |  |     |__(29) mtpSpRsDefault
-- |  |  |  |     |__(30) mtpSpLsDefault
-- |  |  |  |     |__(31) mtpSpProfileRowStatus
-- |  |  |  |
-- |  |  |  |__( 2) mtpSpTable
-- |  |  |  |  |__( 1) mtpSpEntry
-- |  |  |  |     |__( 1) mtpSpId
-- |  |  |  |     |__( 2) mtpSpPointCode
-- |  |  |  |     |__( 3) mtpSpType
-- |  |  |  |     |__( 4) mtpSpOperationalState
-- |  |  |  |     |__( 5) mtpSpProceduralStatus
-- |  |  |  |     |__( 6) mtpSpAvailabilityStatus
-- |  |  |  |     |__( 7) mtpSpVersion
-- |  |  |  |     |__( 8) mtpSpNetworkIndicator
-- |  |  |  |     |__( 9) mtpSpName
-- |  |  |  |     |__(10) mtpSpMtpT1
-- |  |  |  |     |__(11) mtpSpMtpT2
-- |  |  |  |     |__(12) mtpSpMtpT3
-- |  |  |  |     |__(13) mtpSpMtpT4
-- |  |  |  |     |__(14) mtpSpMtpT5
-- |  |  |  |     |__(15) mtpSpMtpT6
-- |  |  |  |     |__(16) mtpSpMtpT7
-- |  |  |  |     |__(17) mtpSpMtpT8
-- |  |  |  |     |__(18) mtpSpMtpT10
-- |  |  |  |     |__(19) mtpSpMtpT11
-- |  |  |  |     |__(20) mtpSpMtpT12
-- |  |  |  |     |__(21) mtpSpMtpT13
-- |  |  |  |     |__(22) mtpSpMtpT14
-- |  |  |  |     |__(23) mtpSpMtpT15
-- |  |  |  |     |__(24) mtpSpMtpT16
-- |  |  |  |     |__(25) mtpSpMtpT17
-- |  |  |  |     |__(26) mtpSpMtpT19A
-- |  |  |  |     |__(27) mtpSpMtpT31A
-- |  |  |  |     |__(28) mtpSpMtpT32A
-- |  |  |  |     |__(29) mtpSpMtpT33A
-- |  |  |  |     |__(30) mtpSpMtpT34A
-- |  |  |  |     |__(31) mtpSpMtpT18I
-- |  |  |  |     |__(32) mtpSpMtpT19I
-- |  |  |  |     |__(33) mtpSpMtpT20I
-- |  |  |  |     |__(34) mtpSpMtpT21I
-- |  |  |  |     |__(35) mtpSpMtpT22I
-- |  |  |  |     |__(36) mtpSpMtpT23I
-- |  |  |  |     |__(37) mtpSpMtpT20A
-- |  |  |  |     |__(38) mtpSpMtpT21A
-- |  |  |  |     |__(39) mtpSpMtpT24I
-- |  |  |  |     |__(40) mtpSpMtpT1T
-- |  |  |  |     |__(41) mtpSpMtpT2T
-- |  |  |  |     |__(42) mtpSpMtpT1S
-- |  |  |  |     |__(43) mtpSpProfilePointer
-- |  |  |  |     |__(44) mtpSpNaPointer
-- |  |  |  |     |__(45) mtpSpFlags
-- |  |  |  |     |__(46) mtpSpUsers
-- |  |  |  |     |__(47) mtpSpAlarmStatus
-- |  |  |  |     |__(48) mtpSpRowStatus
-- |  |  |  |
-- |  |  |  |__( 3) mtpSpStatsTable
-- |  |  |  |  |__( 1) mtpSpStatsEntry
-- |  |  |  |     |__( 1) mtpSpStatsRowStatus
-- |  |  |  |
-- |  |  |  |__( 4) mtpSpCurrentTable
-- |  |  |  |  |__( 1) mtpSpCurrentEntry
-- |  |  |  |     |__( 1) mtpSpCurrentValidIntervals
-- |  |  |  |     |__( 2) mtpSpCurrentTimeDiscontinuity
-- |  |  |  |     |__( 3) mtpSpCurrentDiscardedMSUs
-- |  |  |  |     |__( 4) mtpSpCurrentReceivedTFCstatus0
-- |  |  |  |     |__( 5) mtpSpCurrentReceivedTFCstatus1
-- |  |  |  |     |__( 6) mtpSpCurrentReceivedTFCstatus2
-- |  |  |  |     |__( 7) mtpSpCurrentOctetsXferred
-- |  |  |  |
-- |  |  |  |__( 5) mtpSpInt5minTable
-- |  |  |  |  |__( 1) mtpSpInt5minEntry
-- |  |  |  |     |__( 1) mtpSpInt5minInterval
-- |  |  |  |     |__( 2) mtpSpInt5minTimeStamp
-- |  |  |  |     |__( 3) mtpSpInt5minDiscardedMSUs
-- |  |  |  |     |__( 4) mtpSpInt5minReceivedTFCstatus0
-- |  |  |  |     |__( 5) mtpSpInt5minReceivedTFCstatus1
-- |  |  |  |     |__( 6) mtpSpInt5minReceivedTFCstatus2
-- |  |  |  |     |__( 7) mtpSpInt5minOctetsXferred
-- |  |  |  |
-- |  |  |  |__( 6) mtpSpInt15minTable
-- |  |  |  |  |__( 1) mtpSpInt15minEntry
-- |  |  |  |     |__( 1) mtpSpInt15minInterval
-- |  |  |  |     |__( 2) mtpSpInt15minTimeStamp
-- |  |  |  |     |__( 3) mtpSpInt15minDiscardedMSUs
-- |  |  |  |     |__( 4) mtpSpInt15minReceivedTFCstatus0
-- |  |  |  |     |__( 5) mtpSpInt15minReceivedTFCstatus1
-- |  |  |  |     |__( 6) mtpSpInt15minReceivedTFCstatus2
-- |  |  |  |     |__( 7) mtpSpInt15minOctetsXferred
-- |  |  |  |
-- |  |  |  |__( 7) mtpSpSiTable
-- |  |  |  |  |__( 1) mtpSpSiEntry
-- |  |  |  |     |__( 1) mtpSpSiCode
-- |  |  |  |     |__( 2) mtpSpSiValidIntervals
-- |  |  |  |     |__( 3) mtpSpSiTimeDiscontinuity
-- |  |  |  |     |__( 4) mtpSpSiTransmittedUPUnavailable
-- |  |  |  |     |__( 5) mtpSpSiReceivedUPUnavailable
-- |  |  |  |     |__( 6) mtpSpSiHandledOctetsSIO
-- |  |  |  |     |__( 7) mtpSpSiStatus
-- |  |  |  |
-- |  |  |  |__( 8) mtpSpSiInt5minTable
-- |  |  |  |  |__( 1) mtpSpSiInt5minEntry
-- |  |  |  |     |__( 1) mtpSpSiInt5minInterval
-- |  |  |  |     |__( 2) mtpSpSiInt5minTimeStamp
-- |  |  |  |     |__( 3) mtpSpSiInt5minTransmittedUPUnavailable
-- |  |  |  |     |__( 4) mtpSpSiInt5minReceivedUPUnavailable
-- |  |  |  |     |__( 5) mtpSpSiInt5minHandledOctetsSIO
-- |  |  |  |
-- |  |  |  |__( 9) mtpSpSiInt15minTable
-- |  |  |  |  |__( 1) mtpSpSiInt15minEntry
-- |  |  |  |     |__( 1) mtpSpSiInt15minInterval
-- |  |  |  |     |__( 2) mtpSpSiInt15minTimeStamp
-- |  |  |  |     |__( 3) mtpSpSiInt15minTransmittedUPUnavailable
-- |  |  |  |     |__( 4) mtpSpSiInt15minReceivedUPUnavailable
-- |  |  |  |     |__( 5) mtpSpSiInt15minHandledOctetsSIO
-- |  |  |  |
-- |  |  |  |__(10) mtpSpStudyTable
-- |  |  |  |  |__( 1) mtpSpStudyEntry
-- |  |  |  |     |__( 1) mtpSpStudyId
-- |  |  |  |     |__( 2) mtpSpStudyValidIntervals
-- |  |  |  |     |__( 3) mtpSpStudyTimeDiscontinuity
-- |  |  |  |     |__( 4) mtpSpStudyHandledOctetsOpcDpcSio
-- |  |  |  |     |__( 5) mtpSpStudyHandledMSUsOpcDpcSio
-- |  |  |  |     |__( 6) mtpSpStudyStatus
-- |  |  |  |
-- |  |  |  |__(11) mtpSpStudyInt5minTable
-- |  |  |  |  |__( 1) mtpSpStudyInt5minEntry
-- |  |  |  |     |__( 1) mtpSpStudyInt5minInterval
-- |  |  |  |     |__( 2) mtpSpStudyInt5minTimeStamp
-- |  |  |  |     |__( 3) mtpSpStudyInt5minHandledOctetsOpcDpcSio
-- |  |  |  |     |__( 4) mtpSpStudyInt5minHandledMSUsOpcDpcSio
-- |  |  |  |
-- |  |  |  |__(12) mtpSpStudyInt15minTable
-- |  |  |  |  |__( 1) mtpSpStudyInt15minEntry
-- |  |  |  |     |__( 1) mtpSpStudyInt15minInterval
-- |  |  |  |     |__( 2) mtpSpStudyInt15minTimeStamp
-- |  |  |  |     |__( 3) mtpSpStudyInt15minHandledOctetsOpcDpcSio
-- |  |  |  |     |__( 4) mtpSpStudyInt15minHandledMSUsOpcDpcSio
-- |  |  |  |
-- |  |  |  |__(13) mtpSpStudyMapTable
-- |  |  |     |__( 1) mtpSpStudyMapEntry
-- |  |  |        |__( 1) mtpSpStudyMapStatus
-- |  |  |
-- |  |  |__( 6) mtpL3
-- |  |  |  |__( 1) mtpL3Table
-- |  |  |     |__( 1) mtpL3Entry
-- |  |  |        |__( 1) mtpL3Id
-- |  |  |        |__( 2) mtpL3AdministrativeState
-- |  |  |        |__( 3) mtpL3OperationalState
-- |  |  |        |__( 4) mtpL3UsageState
-- |  |  |        |__( 5) mtpL3ProceduralStatus
-- |  |  |        |__( 6) mtpL3AsaProfilePointer
-- |  |  |        |__( 7) mtpL3Name
-- |  |  |        |__( 8) mtpL3RowStatus
-- |  |  |
-- |  |  |__( 7) mtpRs
-- |  |  |  |__( 1) mtpRsProfileTable
-- |  |  |  |  |__( 1) mtpRsProfileEntry
-- |  |  |  |     |__( 1) mtpRsProfileId
-- |  |  |  |     |__( 2) mtpRsProfileName
-- |  |  |  |     |__( 3) mtpRsProfileTimerT8
-- |  |  |  |     |__( 4) mtpRsProfileTimerT11
-- |  |  |  |     |__( 5) mtpRsProfileTimerT15
-- |  |  |  |     |__( 6) mtpRsProfileTimerT16
-- |  |  |  |     |__( 7) mtpRsProfileTimerT18A
-- |  |  |  |     |__( 8) mtpRsProfileRtDefault
-- |  |  |  |     |__( 9) mtpRsProfileRowStatus
-- |  |  |  |
-- |  |  |  |__( 2) mtpRsTable
-- |  |  |  |  |__( 1) mtpRsEntry
-- |  |  |  |     |__( 1) mtpRsId
-- |  |  |  |     |__( 2) mtpRsDest
-- |  |  |  |     |__( 3) mtpRsFlags
-- |  |  |  |     |__( 4) mtpRsAdministrativeState
-- |  |  |  |     |__( 5) mtpRsOperationalState
-- |  |  |  |     |__( 6) mtpRsAsaProfilePointer
-- |  |  |  |     |__( 7) mtpRsCongestedState
-- |  |  |  |     |__( 8) mtpRsCongestionLevel
-- |  |  |  |     |__( 9) mtpRsLoadsharingInformation
-- |  |  |  |     |__(10) mtpRsLoadsharingObject
-- |  |  |  |     |__(11) mtpRsRemoteExchangeLabel
-- |  |  |  |     |__(12) mtpRsName
-- |  |  |  |     |__(13) mtpRsProfile
-- |  |  |  |     |__(14) mtpRsAlarmStatus
-- |  |  |  |     |__(15) mtpRsRowStatus
-- |  |  |  |
-- |  |  |  |__( 3) mtpRsStatsTable
-- |  |  |  |  |__( 1) mtpRsStatsEntry
-- |  |  |  |     |__( 1) mtpRsStatsStatus
-- |  |  |  |
-- |  |  |  |__( 4) mtpRsCurrentTable
-- |  |  |  |  |__( 1) mtpRsCurrentEntry
-- |  |  |  |     |__( 1) mtpRsCurrentValidIntervals
-- |  |  |  |     |__( 2) mtpRsCurrentTimeDiscontinuity
-- |  |  |  |     |__( 3) mtpRsCurrentReceivedOctetsOPC
-- |  |  |  |     |__( 4) mtpRsCurrentTransmittedOctetsDPC
-- |  |  |  |     |__( 5) mtpRsCurrentReceivedMSUsOpc
-- |  |  |  |     |__( 6) mtpRsCurrentTransmittedMSUsDpc
-- |  |  |  |     |__( 7) mtpRsCurrentRouteSetUnavailable
-- |  |  |  |     |__( 8) mtpRsCurrentRouteSetUnavailableDuration
-- |  |  |  |
-- |  |  |  |__( 5) mtpRsInt5minTable
-- |  |  |  |  |__( 1) mtpRsInt5minEntry
-- |  |  |  |     |__( 1) mtpRsInt5minInterval
-- |  |  |  |     |__( 2) mtpRsInt5minTimeStamp
-- |  |  |  |     |__( 3) mtpRsInt5minReceivedOctetsOPC
-- |  |  |  |     |__( 4) mtpRsInt5minTransmittedOctetsDPC
-- |  |  |  |     |__( 5) mtpRsInt5minReceivedMSUsOpc
-- |  |  |  |     |__( 6) mtpRsInt5minTransmittedMSUsDpc
-- |  |  |  |     |__( 7) mtpRsInt5minRouteSetUnavailable
-- |  |  |  |     |__( 8) mtpRsInt5minRouteSetUnavailableDuration
-- |  |  |  |
-- |  |  |  |__( 6) mtpRsInt15minTable
-- |  |  |  |  |__( 1) mtpRsInt15minEntry
-- |  |  |  |     |__( 1) mtpRsInt15minInterval
-- |  |  |  |     |__( 2) mtpRsInt15minTimeStamp
-- |  |  |  |     |__( 3) mtpRsInt15minReceivedOctetsOPC
-- |  |  |  |     |__( 4) mtpRsInt15minTransmittedOctetsDPC
-- |  |  |  |     |__( 5) mtpRsInt15minReceivedMSUsOpc
-- |  |  |  |     |__( 6) mtpRsInt15minTransmittedMSUsDpc
-- |  |  |  |     |__( 7) mtpRsInt15minRouteSetUnavailable
-- |  |  |  |     |__( 8) mtpRsInt15minRouteSetUnavailableDuration
-- |  |  |  |
-- |  |  |  |__( 7) mtpRsSiTable
-- |  |  |  |  |__( 1) mtpRsSiEntry
-- |  |  |  |     |__( 1) mtpRsSiCode
-- |  |  |  |     |__( 2) mtpRsSiValidIntervals
-- |  |  |  |     |__( 3) mtpRsSiTimeDiscontinuity
-- |  |  |  |     |__( 4) mtpRsSiReceivedOctetsOpcSio
-- |  |  |  |     |__( 5) mtpRsSiTransmittedOctetsDpcSio
-- |  |  |  |     |__( 6) mtpRsSiReceivedMSUsOpcSio
-- |  |  |  |     |__( 7) mtpRsSiTransmittedMSUsDpcSio
-- |  |  |  |     |__( 8) mtpRsSiStatus
-- |  |  |  |
-- |  |  |  |__( 8) mtpRsSiInt5minTable
-- |  |  |  |  |__( 1) mtpRsSiInt5minEntry
-- |  |  |  |     |__( 1) mtpRsSiInt5minInterval
-- |  |  |  |     |__( 2) mtpRsSiInt5minTimeStamp
-- |  |  |  |     |__( 3) mtpRsSiInt5minReceivedOctetsOpcSio
-- |  |  |  |     |__( 4) mtpRsSiInt5minTransmittedOctetsDpcSio
-- |  |  |  |     |__( 5) mtpRsSiInt5minReceivedMSUsOpcSio
-- |  |  |  |     |__( 6) mtpRsSiInt5minTransmittedMSUsDpcSio
-- |  |  |  |
-- |  |  |  |__( 9) mtpRsSiInt15minTable
-- |  |  |     |__( 1) mtpRsSiInt15minEntry
-- |  |  |        |__( 1) mtpRsSiInt15minInterval
-- |  |  |        |__( 2) mtpRsSiInt15minTimeStamp
-- |  |  |        |__( 3) mtpRsSiInt15minReceivedOctetsOpcSio
-- |  |  |        |__( 4) mtpRsSiInt15minTransmittedOctetsDpcSio
-- |  |  |        |__( 5) mtpRsSiInt15minReceivedMSUsOpcSio
-- |  |  |        |__( 6) mtpRsSiInt15minTransmittedMSUsDpcSio
-- |  |  |
-- |  |  |__( 8) mtpRt
-- |  |  |  |__( 1) mtpRtProfileTable
-- |  |  |  |  |__( 1) mtpRtProfileEntry
-- |  |  |  |     |__( 1) mtpRtProfileId
-- |  |  |  |     |__( 2) mtpRtProfileTimerT6
-- |  |  |  |     |__( 3) mtpRtProfileTimerT10
-- |  |  |  |     |__( 4) mtpRtProfileRowStatus
-- |  |  |  |
-- |  |  |  |__( 2) mtpRtTable
-- |  |  |  |  |__( 1) mtpRtEntry
-- |  |  |  |     |__( 1) mtpRtId
-- |  |  |  |     |__( 2) mtpRtLsPointer
-- |  |  |  |     |__( 3) mtpRtAdministrativeState
-- |  |  |  |     |__( 4) mtpRtOperationalState
-- |  |  |  |     |__( 5) mtpRtAvailabilityStatus
-- |  |  |  |     |__( 6) mtpRtInClsLoadsharingAlgorithm
-- |  |  |  |     |__( 7) mtpRtFixedPriority
-- |  |  |  |     |__( 8) mtpRtFlexiblePriority
-- |  |  |  |     |__( 9) mtpRtPriorityMode
-- |  |  |  |     |__(10) mtpRtLoadsharingInformation
-- |  |  |  |     |__(11) mtpRtLoadsharingObject
-- |  |  |  |     |__(12) mtpRtName
-- |  |  |  |     |__(13) mtpRtSlsList
-- |  |  |  |     |__(14) mtpRtUsageState
-- |  |  |  |     |__(15) mtpRtRlSlot
-- |  |  |  |     |__(16) mtpRtProfile
-- |  |  |  |     |__(17) mtpRtRowStatus
-- |  |  |  |
-- |  |  |  |__( 3) mtpRtLsaTable
-- |  |  |     |__( 2) mtpRtLsaEntry
-- |  |  |        |__( 1) mtpRtLsaSlsCode
-- |  |  |        |__( 2) mtpRtLsaNormalSlCode
-- |  |  |        |__( 3) mtpRtLsaAlternativeSlCodeList
-- |  |  |
-- |  |  |__( 9) mtpLs
-- |  |  |  |__( 1) mtpLsProfileTable
-- |  |  |  |  |__( 1) mtpLsProfileEntry
-- |  |  |  |     |__( 1) mtpLsProfileId
-- |  |  |  |     |__( 2) mtpLsProfileTimerT6
-- |  |  |  |     |__( 3) mtpLsProfileTimerT8
-- |  |  |  |     |__( 4) mtpLsProfileTimerT10
-- |  |  |  |     |__( 5) mtpLsProfileTimerT7
-- |  |  |  |     |__( 6) mtpLsProfileTimerT19I
-- |  |  |  |     |__( 7) mtpLsProfileTimerT21I
-- |  |  |  |     |__( 8) mtpLsProfileTimerT25A
-- |  |  |  |     |__( 9) mtpLsProfileTimerT28A
-- |  |  |  |     |__(10) mtpLsProfileTimerT29A
-- |  |  |  |     |__(11) mtpLsProfileTimerT30A
-- |  |  |  |     |__(12) mtpLsProfileName
-- |  |  |  |     |__(13) mtpLsProfileSlDefault
-- |  |  |  |     |__(14) mtpLsProfileRowStatus
-- |  |  |  |
-- |  |  |  |__( 2) mtpLsTable
-- |  |  |  |  |__( 1) mtpLsEntry
-- |  |  |  |     |__( 1) mtpLsId
-- |  |  |  |     |__( 2) mtpLsAdjPc
-- |  |  |  |     |__( 3) mtpLsRsId
-- |  |  |  |     |__( 4) mtpLsMaxCapacity
-- |  |  |  |     |__( 5) mtpLsCurrentCapacity
-- |  |  |  |     |__( 6) mtpLsCongestionControlMethod
-- |  |  |  |     |__( 7) mtpLsUsageState
-- |  |  |  |     |__( 8) mtpLsOperationalState
-- |  |  |  |     |__( 9) mtpLsAvailabilityStatus
-- |  |  |  |     |__(10) mtpLsPeriodicLinkTestFlag
-- |  |  |  |     |__(11) mtpLsPeriodicLinkTestFail
-- |  |  |  |     |__(12) mtpLsAdministrativeState
-- |  |  |  |     |__(13) mtpLsInLsLoadShareAlgorithm
-- |  |  |  |     |__(14) mtpLsProfilePointer
-- |  |  |  |     |__(15) mtpLsNumberOfNormallyActiveSignLinks
-- |  |  |  |     |__(16) mtpLsName
-- |  |  |  |     |__(17) mtpLsAsaProfilePointer
-- |  |  |  |     |__(18) mtpLsAlarmStatus
-- |  |  |  |     |__(19) mtpLsRowStatus
-- |  |  |  |
-- |  |  |  |__( 3) mtpLsStatsTable
-- |  |  |  |  |__( 1) mtpLsStatsEntry
-- |  |  |  |     |__( 1) mtpLsStatsStatus
-- |  |  |  |
-- |  |  |  |__( 4) mtpLsCurrentTable
-- |  |  |  |  |__( 1) mtpLsCurrentEntry
-- |  |  |  |     |__( 1) mtpLsCurrentValidIntervals
-- |  |  |  |     |__( 2) mtpLsCurrentTimeDiscontinuity
-- |  |  |  |     |__( 3) mtpLsCurrentAdjacentInaccessibleEvents
-- |  |  |  |     |__( 4) mtpLsCurrentAdjacentInaccessibleDuration
-- |  |  |  |     |__( 5) mtpLsCurrentSlsUnavailable
-- |  |  |  |
-- |  |  |  |__( 5) mtpLsInt5minTable
-- |  |  |  |  |__( 1) mtpLsInt5minEntry
-- |  |  |  |     |__( 1) mtpLsInt5minInterval
-- |  |  |  |     |__( 2) mtpLsInt5minTimeStamp
-- |  |  |  |     |__( 3) mtpLsInt5minAdjacentInaccessibleEvents
-- |  |  |  |     |__( 4) mtpLsInt5minAdjacentInaccessibleDuration
-- |  |  |  |     |__( 5) mtpLsInt5minSlsUnavailable
-- |  |  |  |
-- |  |  |  |__( 6) mtpLsInt15minTable
-- |  |  |     |__( 1) mtpLsInt15minEntry
-- |  |  |        |__( 1) mtpLsInt15minInterval
-- |  |  |        |__( 2) mtpLsInt15minTimeStamp
-- |  |  |        |__( 3) mtpLsInt15minAdjacentInaccessibleEvents
-- |  |  |        |__( 4) mtpLsInt15minAdjacentInaccessibleDuration
-- |  |  |        |__( 5) mtpLsInt15minSlsUnavailable
-- |  |  |
-- |  |  |__(10) mtpSl
-- |  |  |  |__( 1) mtpSlL3ProfileTable
-- |  |  |  |  |__( 1) mtpSlL3ProfileEntry
-- |  |  |  |     |__( 1) mtpSlL3ProfileId
-- |  |  |  |     |__( 2) mtpSlL3ProfileTimerT1
-- |  |  |  |     |__( 3) mtpSlL3ProfileTimerT3
-- |  |  |  |     |__( 4) mtpSlL3ProfileTimerT17
-- |  |  |  |     |__( 5) mtpSlL3ProfileTimerT24I
-- |  |  |  |     |__( 6) mtpSlL3ProfileName
-- |  |  |  |     |__( 7) mtpSlL3ProfileTimerT2
-- |  |  |  |     |__( 8) mtpSlL3ProfileTimerT4
-- |  |  |  |     |__( 9) mtpSlL3ProfileTimerT5
-- |  |  |  |     |__(10) mtpSlL3ProfileTimerT12
-- |  |  |  |     |__(11) mtpSlL3ProfileTimerT13
-- |  |  |  |     |__(12) mtpSlL3ProfileTimerT14
-- |  |  |  |     |__(13) mtpSlL3ProfileTimerT19A
-- |  |  |  |     |__(14) mtpSlL3ProfileTimerT20A
-- |  |  |  |     |__(15) mtpSlL3ProfileTimerT21A
-- |  |  |  |     |__(16) mtpSlL3ProfileTimerT22I
-- |  |  |  |     |__(17) mtpSlL3ProfileTimerT23I
-- |  |  |  |     |__(18) mtpSlL3ProfileTimerT31A
-- |  |  |  |     |__(19) mtpSlL3ProfileTimerT32A
-- |  |  |  |     |__(20) mtpSlL3ProfileTimerT33A
-- |  |  |  |     |__(21) mtpSlL3ProfileTimerT34A
-- |  |  |  |     |__(22) mtpSlL3ProfileTimerT1T
-- |  |  |  |     |__(23) mtpSlL3ProfileTimerT2T
-- |  |  |  |     |__(24) mtpSlL3ProfileTimerT1S
-- |  |  |  |     |__(25) mtpSlL3ProfileL2Default
-- |  |  |  |     |__(26) mtpSlL3ProfileRowStatus
-- |  |  |  |
-- |  |  |  |__( 2) mtpSlL2ProfileTable
-- |  |  |  |  |__( 1) mtpSlL2ProfileEntry
-- |  |  |  |     |__( 1) mtpSlL2ProfileId
-- |  |  |  |     |__( 2) mtpSlL2ProfileErrorCorrectionMethod
-- |  |  |  |     |__( 3) mtpSlL2ProfileTransmissionRate
-- |  |  |  |     |__( 4) mtpSlL2ProfileTimerT1
-- |  |  |  |     |__( 5) mtpSlL2ProfileTimerT2
-- |  |  |  |     |__( 6) mtpSlL2ProfileTimerT2L
-- |  |  |  |     |__( 7) mtpSlL2ProfileTimerT2H
-- |  |  |  |     |__( 8) mtpSlL2ProfileTimerT3
-- |  |  |  |     |__( 9) mtpSlL2ProfileTimerT4N
-- |  |  |  |     |__(10) mtpSlL2ProfileTimerT4E
-- |  |  |  |     |__(11) mtpSlL2ProfileTimerT5
-- |  |  |  |     |__(12) mtpSlL2ProfileTimerT6
-- |  |  |  |     |__(13) mtpSlL2ProfileTimerT7
-- |  |  |  |     |__(14) mtpSlL2ProfileTbOnset1
-- |  |  |  |     |__(15) mtpSlL2ProfileTbAbate1
-- |  |  |  |     |__(16) mtpSlL2ProfileNumberOfThresholdLevels
-- |  |  |  |     |__(17) mtpSlL2ProfileCongestionCounting
-- |  |  |  |     |__(18) mtpSlL2ProfileCongestionReportingBaseObject
-- |  |  |  |     |__(19) mtpSlL2ProfileLoopDelay
-- |  |  |  |     |__(20) mtpSlL2ProfileName
-- |  |  |  |     |__(21) mtpSlL2ProfileTbOnset2
-- |  |  |  |     |__(22) mtpSlL2ProfileTbAbate2
-- |  |  |  |     |__(23) mtpSlL2ProfileTbOnset3
-- |  |  |  |     |__(24) mtpSlL2ProfileTbAbate3
-- |  |  |  |     |__(25) mtpSlL2ProfileTbDiscard1
-- |  |  |  |     |__(26) mtpSlL2ProfileTbDiscard2
-- |  |  |  |     |__(27) mtpSlL2ProfileTbDiscard3
-- |  |  |  |     |__(28) mtpSlL2ProfileTimerTx
-- |  |  |  |     |__(29) mtpSlL2ProfileTimerTy
-- |  |  |  |     |__(30) mtpSlL2ProfileNumberOfCongestionStates
-- |  |  |  |     |__(31) mtpSlL2ProfileInitialLevelOfCongestion
-- |  |  |  |     |__(32) mtpSlL2ProfileMaxMSUsRetransN1
-- |  |  |  |     |__(33) mtpSlL2ProfileMaxOctRetransN2
-- |  |  |  |     |__(34) mtpSlL2ProfileReceiveCongestionThresholdOnset
-- |  |  |  |     |__(35) mtpSlL2ProfileReceiveCongestionThresholdAbate
-- |  |  |  |     |__(36) mtpSlL2ProfileReceiveCongestionThresholdDiscard
-- |  |  |  |     |__(37) mtpSlL2ProfileM
-- |  |  |  |     |__(38) mtpSlL2ProfileRowStatus
-- |  |  |  |
-- |  |  |  |__( 3) mtpSlTable
-- |  |  |  |  |__( 1) mtpSlEntry
-- |  |  |  |     |__( 1) mtpSlSlCode
-- |  |  |  |     |__( 2) mtpSlSlsCodeCurrentList
-- |  |  |  |     |__( 3) mtpSlMaxCapacitySL
-- |  |  |  |     |__( 4) mtpSlCurrentCapacitySL
-- |  |  |  |     |__( 5) mtpSlLinkTpStatus
-- |  |  |  |     |__( 6) mtpSlAdministrativeState
-- |  |  |  |     |__( 7) mtpSlOperationalState
-- |  |  |  |     |__( 8) mtpSlUsageState
-- |  |  |  |     |__( 9) mtpSlProceduralStatus
-- |  |  |  |     |__(10) mtpSlMtpL2ProtocolProfilePointer
-- |  |  |  |     |__(11) mtpSlSignTermPointer
-- |  |  |  |     |__(12) mtpSlSignDataLinkTpPointer
-- |  |  |  |     |__(13) mtpSlLocalInhibit
-- |  |  |  |     |__(14) mtpSlLocalUninhibit
-- |  |  |  |     |__(15) mtpSlReplaceSt
-- |  |  |  |     |__(16) mtpSlAsaProfilePointer
-- |  |  |  |     |__(17) mtpSlCongestionLevel
-- |  |  |  |     |__(18) mtpSlRelatedLinkGroupNumber
-- |  |  |  |     |__(19) mtpSlSdlList
-- |  |  |  |     |__(20) mtpSlTest
-- |  |  |  |     |__(21) mtpSlName
-- |  |  |  |     |__(22) mtpSlSdtList
-- |  |  |  |     |__(23) mtpSlSlsCodeNormalList
-- |  |  |  |     |__(24) mtpSlL3ProfilePointer
-- |  |  |  |     |__(25) mtpSlAlarmStatus
-- |  |  |  |     |__(26) mtpSlRowStatus
-- |  |  |  |
-- |  |  |  |__( 4) mtpSlSdlListTable
-- |  |  |  |  |__( 1) mtpSlSdlListEntry
-- |  |  |  |     |__( 1) mtpSlSdlListId
-- |  |  |  |     |__( 2) mtpSlSdlListPointer
-- |  |  |  |     |__( 3) mtpSlSdlListRowStatus
-- |  |  |  |
-- |  |  |  |__( 5) mtpSlSdtListTable
-- |  |  |  |  |__( 1) mtpSlSdtListEntry
-- |  |  |  |     |__( 1) mtpSlSdtListId
-- |  |  |  |     |__( 2) mtpSlSdtListPointer
-- |  |  |  |     |__( 3) mtpSlSdtListRowStatus
-- |  |  |  |
-- |  |  |  |__( 6) mtpSlStatsTable
-- |  |  |  |  |__( 1) mtpSlStatsEntry
-- |  |  |  |     |__( 1) mtpSlStatsDurInService
-- |  |  |  |     |__( 2) mtpSlStatsFailAlignOrProving
-- |  |  |  |     |__( 3) mtpSlStatsNacksReceived
-- |  |  |  |     |__( 4) mtpSlStatsDurUnavail
-- |  |  |  |     |__( 5) mtpSlStatsDurUnavailFailed
-- |  |  |  |     |__( 6) mtpSlStatsDurUnavailRpo
-- |  |  |  |     |__( 7) mtpSlStatsSibsSent
-- |  |  |  |     |__( 8) mtpSlStatsTranSioSifOctets
-- |  |  |  |     |__( 9) mtpSlStatsRetransOctets
-- |  |  |  |     |__(10) mtpSlStatsTranMsus
-- |  |  |  |     |__(11) mtpSlStatsRecvSioSifOctets
-- |  |  |  |     |__(12) mtpSlStatsRecvMsus
-- |  |  |  |     |__(13) mtpSlStatsCongOnsetInd0
-- |  |  |  |     |__(14) mtpSlStatsCongOnsetInd1
-- |  |  |  |     |__(15) mtpSlStatsCongOnsetInd2
-- |  |  |  |     |__(16) mtpSlStatsCongOnsetInd3
-- |  |  |  |     |__(17) mtpSlStatsDurCongStatus0
-- |  |  |  |     |__(18) mtpSlStatsDurCongStatus1
-- |  |  |  |     |__(19) mtpSlStatsDurCongStatus2
-- |  |  |  |     |__(20) mtpSlStatsDurCongStatus3
-- |  |  |  |     |__(21) mtpSlStatsCongDiscdInd0
-- |  |  |  |     |__(22) mtpSlStatsCongDiscdInd1
-- |  |  |  |     |__(23) mtpSlStatsCongDiscdInd2
-- |  |  |  |     |__(24) mtpSlStatsCongDiscdInd3
-- |  |  |  |
-- |  |  |  |__( 7) mtpSlL3CurrentTable
-- |  |  |  |  |__( 1) mtpSlL3CurrentEntry
-- |  |  |  |     |__( 1) mtpSlL3CurrentValidIntervals
-- |  |  |  |     |__( 2) mtpSlL3CurrentTimeDiscontinuity
-- |  |  |  |     |__( 3) mtpSlL3CurrentSlUnavailabilityDuration
-- |  |  |  |     |__( 4) mtpSlL3CurrentSlLocalInhibition
-- |  |  |  |     |__( 5) mtpSlL3CurrentSlRemoteInhibition
-- |  |  |  |     |__( 6) mtpSlL3CurrentSlFailed
-- |  |  |  |     |__( 7) mtpSlL3CurrentSlRemoteProcOutage
-- |  |  |  |     |__( 8) mtpSlL3CurrentLocalMgmtInhibit
-- |  |  |  |     |__( 9) mtpSlL3CurrentLocalMgmtUninhibit
-- |  |  |  |     |__(10) mtpSlL3CurrentLocalBusy
-- |  |  |  |     |__(11) mtpSlL3CurrentSlCongestedStarts
-- |  |  |  |     |__(12) mtpSlL3CurrentSlCongestedDuration
-- |  |  |  |     |__(13) mtpSlL3CurrentSlCongestionStops
-- |  |  |  |     |__(14) mtpSlL3CurrentDiscardedMSUs
-- |  |  |  |     |__(15) mtpSlL3CurrentCongestionEventsMSULoss
-- |  |  |  |     |__(16) mtpSlL3CurrentChangeovers
-- |  |  |  |     |__(17) mtpSlL3CurrentChangebacks
-- |  |  |  |     |__(18) mtpSlL3CurrentRestorations
-- |  |  |  |
-- |  |  |  |__( 8) mtpSlL3Int5minTable
-- |  |  |  |  |__( 1) mtpSlL3Int5minEntry
-- |  |  |  |     |__( 1) mtpSlL3Int5minInterval
-- |  |  |  |     |__( 2) mtpSlL3Int5minTimeStamp
-- |  |  |  |     |__( 3) mtpSlL3Int5minSlUnavailabilityDuration
-- |  |  |  |     |__( 4) mtpSlL3Int5minSlLocalInhibition
-- |  |  |  |     |__( 5) mtpSlL3Int5minSlRemoteInhibition
-- |  |  |  |     |__( 6) mtpSlL3Int5minSlFailed
-- |  |  |  |     |__( 7) mtpSlL3Int5minSlRemoteProcOutage
-- |  |  |  |     |__( 8) mtpSlL3Int5minLocalMgmtInhibit
-- |  |  |  |     |__( 9) mtpSlL3Int5minLocalMgmtUninhibit
-- |  |  |  |     |__(10) mtpSlL3Int5minLocalBusy
-- |  |  |  |     |__(11) mtpSlL3Int5minSlCongestedStarts
-- |  |  |  |     |__(12) mtpSlL3Int5minSlCongestedDuration
-- |  |  |  |     |__(13) mtpSlL3Int5minSlCongestionStops
-- |  |  |  |     |__(14) mtpSlL3Int5minDiscardedMSUs
-- |  |  |  |     |__(15) mtpSlL3Int5minCongestionEventsMSULoss
-- |  |  |  |     |__(16) mtpSlL3Int5minChangeovers
-- |  |  |  |     |__(17) mtpSlL3Int5minChangebacks
-- |  |  |  |     |__(18) mtpSlL3Int5minRestorations
-- |  |  |  |
-- |  |  |  |__( 9) mtpSlL3Int15minTable
-- |  |  |  |  |__( 1) mtpSlL3Int15minEntry
-- |  |  |  |     |__( 1) mtpSlL3Int15minInterval
-- |  |  |  |     |__( 2) mtpSlL3Int15minTimeStamp
-- |  |  |  |     |__( 3) mtpSlL3Int15minSlUnavailabilityDuration
-- |  |  |  |     |__( 4) mtpSlL3Int15minSlLocalInhibition
-- |  |  |  |     |__( 5) mtpSlL3Int15minSlRemoteInhibition
-- |  |  |  |     |__( 6) mtpSlL3Int15minSlFailed
-- |  |  |  |     |__( 7) mtpSlL3Int15minSlRemoteProcOutage
-- |  |  |  |     |__( 8) mtpSlL3Int15minLocalMgmtInhibit
-- |  |  |  |     |__( 9) mtpSlL3Int15minLocalMgmtUninhibit
-- |  |  |  |     |__(10) mtpSlL3Int15minLocalBusy
-- |  |  |  |     |__(11) mtpSlL3Int15minSlCongestedStarts
-- |  |  |  |     |__(12) mtpSlL3Int15minSlCongestedDuration
-- |  |  |  |     |__(13) mtpSlL3Int15minSlCongestionStops
-- |  |  |  |     |__(14) mtpSlL3Int15minDiscardedMSUs
-- |  |  |  |     |__(15) mtpSlL3Int15minCongestionEventsMSULoss
-- |  |  |  |     |__(16) mtpSlL3Int15minChangeovers
-- |  |  |  |     |__(17) mtpSlL3Int15minChangebacks
-- |  |  |  |     |__(18) mtpSlL3Int15minRestorations
-- |  |  |  |
-- |  |  |  |__(10) mtpSlL2CurrentTable
-- |  |  |  |  |__( 1) mtpSlL2CurrentEntry
-- |  |  |  |     |__( 1) mtpSlL2CurrentValidIntervals
-- |  |  |  |     |__( 2) mtpSlL2CurrentTimeDiscontinuity
-- |  |  |  |     |__( 3) mtpSlL2CurrentSlInServiceDuration
-- |  |  |  |     |__( 4) mtpSlL2CurrentSlAlignment
-- |  |  |  |     |__( 5) mtpSlL2CurrentSignUnitsReceived
-- |  |  |  |     |__( 6) mtpSlL2CurrentNegAckReceived
-- |  |  |  |     |__( 7) mtpSlL2CurrentTransmittedOctetsSIFSIO
-- |  |  |  |     |__( 8) mtpSlL2CurrentRetransmittedOctets
-- |  |  |  |     |__( 9) mtpSlL2CurrentTransmittedMSUs
-- |  |  |  |     |__(10) mtpSlL2CurrentReceivedOctetsSIFSIO
-- |  |  |  |     |__(11) mtpSlL2CurrentReceivedMSUs
-- |  |  |  |
-- |  |  |  |__(11) mtpSlL2Int5minTable
-- |  |  |  |  |__( 1) mtpSlL2Int5minEntry
-- |  |  |  |     |__( 1) mtpSlL2Int5minInterval
-- |  |  |  |     |__( 2) mtpSlL2Int5minTimestamp
-- |  |  |  |     |__( 3) mtpSlL2Int5minSlInServiceDuration
-- |  |  |  |     |__( 4) mtpSlL2Int5minSlAlignment
-- |  |  |  |     |__( 5) mtpSlL2Int5minSignUnitsReceived
-- |  |  |  |     |__( 6) mtpSlL2Int5minNegAckReceived
-- |  |  |  |     |__( 7) mtpSlL2Int5minTransmittedOctetsSIFSIO
-- |  |  |  |     |__( 8) mtpSlL2Int5minRetransmittedOctets
-- |  |  |  |     |__( 9) mtpSlL2Int5minTransmittedMSUs
-- |  |  |  |     |__(10) mtpSlL2Int5minReceivedOctetsSIFSIO
-- |  |  |  |     |__(11) mtpSlL2Int5minReceivedMSUs
-- |  |  |  |
-- |  |  |  |__(12) mtpSlL2Int15minTable
-- |  |  |     |__( 1) mtpSlL2Int15minEntry
-- |  |  |        |__( 1) mtpSlL2Int15minInterval
-- |  |  |        |__( 2) mtpSlL2Int15minTimestamp
-- |  |  |        |__( 3) mtpSlL2Int15minSlInServiceDuration
-- |  |  |        |__( 4) mtpSlL2Int15minSlAlignment
-- |  |  |        |__( 5) mtpSlL2Int15minSignUnitsReceived
-- |  |  |        |__( 6) mtpSlL2Int15minNegAckReceived
-- |  |  |        |__( 7) mtpSlL2Int15minTransmittedOctetsSIFSIO
-- |  |  |        |__( 8) mtpSlL2Int15minRetransmittedOctets
-- |  |  |        |__( 9) mtpSlL2Int15minTransmittedMSUs
-- |  |  |        |__(10) mtpSlL2Int15minReceivedOctetsSIFSIO
-- |  |  |        |__(11) mtpSlL2Int15minReceivedMSUs
-- |  |  |
-- |  |  |__(11) mtpSdt
-- |  |  |  |__( 1) mtpNbTable
-- |  |  |  |  |__( 1) mtpNbEntry
-- |  |  |  |     |__( 1) mtpSdtProfileId
-- |  |  |  |     |__( 2) mtpNbTransmissionRate
-- |  |  |  |     |__( 3) mtpNbTimerT8
-- |  |  |  |     |__( 4) mtpNbTin
-- |  |  |  |     |__( 5) mtpNbTie
-- |  |  |  |     |__( 6) mtpNbT
-- |  |  |  |     |__( 7) mtpNbD
-- |  |  |  |     |__( 8) mtpNbTe
-- |  |  |  |     |__( 9) mtpNbDe
-- |  |  |  |     |__(10) mtpNbUe
-- |  |  |  |     |__(11) mtpNbN
-- |  |  |  |     |__(12) mtpNbm
-- |  |  |  |     |__(13) mtpNbb
-- |  |  |  |     |__(14) mtpNbf
-- |  |  |  |     |__(15) mtpNbRowStatus
-- |  |  |  |
-- |  |  |  |__( 2) mtpSaalTable
-- |  |  |  |  |__( 1) mtpSaalEntry
-- |  |  |  |     |__( 1) mtpSaalBufferRelease
-- |  |  |  |     |__( 2) mtpSaalMaxCc
-- |  |  |  |     |__( 3) mtpSaalMaxNrp
-- |  |  |  |     |__( 4) mtpSaalMaxInformationFieldLength
-- |  |  |  |     |__( 5) mtpSaalMaxLengthSscopUuField
-- |  |  |  |     |__( 6) mtpSaalMaxPd
-- |  |  |  |     |__( 7) mtpSaalMaxSscopCreditToPeer
-- |  |  |  |     |__( 8) mtpSaalMaxStat
-- |  |  |  |     |__( 9) mtpSaalN1
-- |  |  |  |     |__(10) mtpSaalNniLayerManagementProvingState
-- |  |  |  |     |__(11) mtpSaalNniLayerManagementTimerNoCredit
-- |  |  |  |     |__(12) mtpSaalNniLayerManagementTimerRepeatSrec
-- |  |  |  |     |__(13) mtpSaalNniTimerT1
-- |  |  |  |     |__(14) mtpSaalNniTimerT2
-- |  |  |  |     |__(15) mtpSaalNniTimerT3
-- |  |  |  |     |__(16) mtpSaalSscopTimerCc
-- |  |  |  |     |__(17) mtpSaalSscopTimerIdle
-- |  |  |  |     |__(18) mtpSaalSscopTimerKeepAlive
-- |  |  |  |     |__(19) mtpSaalSscopTimerNoResponse
-- |  |  |  |     |__(20) mtpSaalSscopTimerPoll
-- |  |  |  |     |__(21) mtpSaalTransmissionRateIntervalLower
-- |  |  |  |     |__(22) mtpSaalTransmissionRateIntervalUpper
-- |  |  |  |     |__(23) mtpSaalEgressTransmissionRateIntervalLower
-- |  |  |  |     |__(24) mtpSaalEgressTransmissionRateIntervalUpper
-- |  |  |  |     |__(25) mtpSaalPollAfterRetransmission
-- |  |  |  |     |__(26) mtpSaalRowStatus
-- |  |  |  |
-- |  |  |  |__( 3) mtpM2paTable
-- |  |  |  |  |__( 1) mtpM2paEntry
-- |  |  |  |     |__( 1) mtpM2paN1
-- |  |  |  |     |__( 2) mtpM2paProving
-- |  |  |  |     |__( 3) mtpM2paManagementProvingState
-- |  |  |  |     |__( 4) mtpM2paLoopDelayLower
-- |  |  |  |     |__( 5) mtpM2paLoopDelayUpper
-- |  |  |  |     |__( 6) mtpM2paTransmissionRateIntervalLower
-- |  |  |  |     |__( 7) mtpM2paTransmissionRateIntervalUpper
-- |  |  |  |     |__( 8) mtpM2paSctpNoDelay
-- |  |  |  |     |__( 9) mtpM2paSctpMaxseg
-- |  |  |  |     |__(10) mtpM2paSctpHeartbeatItvl
-- |  |  |  |     |__(11) mtpM2paSctpHeartbeat
-- |  |  |  |     |__(12) mtpM2paSctpRtoInitial
-- |  |  |  |     |__(13) mtpM2paSctpRtoMin
-- |  |  |  |     |__(14) mtpM2paSctpRtoMax
-- |  |  |  |     |__(15) mtpM2paSctpPathMaxRetrans
-- |  |  |  |     |__(16) mtpM2paSctpCookieLife
-- |  |  |  |     |__(17) mtpM2paSctpCookieInc
-- |  |  |  |     |__(18) mtpM2paSctpMaxInitRetries
-- |  |  |  |     |__(19) mtpM2paSctpMaxBurst
-- |  |  |  |     |__(20) mtpM2paSctpAssocMaxRetrans
-- |  |  |  |     |__(21) mtpM2paSctpSackDelay
-- |  |  |  |     |__(22) mtpM2paSctpLifetime
-- |  |  |  |     |__(23) mtpM2paProvingAttempts
-- |  |  |  |     |__(24) mtpM2paRowStatus
-- |  |  |  |
-- |  |  |  |__( 4) mtpSdtTable
-- |  |  |  |  |__( 1) mtpSdtEntry
-- |  |  |  |     |__( 1) mtpSdtId
-- |  |  |  |     |__( 2) mtpSdtAdministrativeState
-- |  |  |  |     |__( 3) mtpSdtOperationalState
-- |  |  |  |     |__( 4) mtpSdtUsageState
-- |  |  |  |     |__( 5) mtpSdtProceduralStatus
-- |  |  |  |     |__( 6) mtpSdtAvailabilityStatus
-- |  |  |  |     |__( 7) mtpSdtEquipmentPointer
-- |  |  |  |     |__( 8) mtpSdtName
-- |  |  |  |     |__( 9) mtpSdtProfilePointer
-- |  |  |  |     |__(10) mtpSdtRowStatus
-- |  |  |  |
-- |  |  |  |__( 5) mtpSdtStatsTable
-- |  |  |     |__( 1) mtpSdtStatsEntry
-- |  |  |        |__( 1) mtpSdtStatsTxBytes
-- |  |  |        |__( 2) mtpSdtStatsTxSus
-- |  |  |        |__( 3) mtpSdtStatsTxSusRepeated
-- |  |  |        |__( 4) mtpSdtStatsTxUnderruns
-- |  |  |        |__( 5) mtpSdtStatsTxAborts
-- |  |  |        |__( 6) mtpSdtStatsTxBufferOverflows
-- |  |  |        |__( 7) mtpSdtStatsTxSusInError
-- |  |  |        |__( 8) mtpSdtStatsRxBytes
-- |  |  |        |__( 9) mtpSdtStatsRxSusCompressed
-- |  |  |        |__(10) mtpSdtStatsRxOverruns
-- |  |  |        |__(11) mtpSdtStatsRxAborts
-- |  |  |        |__(12) mtpSdtStatsRxBufferOverflows
-- |  |  |        |__(13) mtpSdtStatsRxSusInError
-- |  |  |        |__(14) mtpSdtStatsRxSyncTransitions
-- |  |  |        |__(15) mtpSdtStatsRxBitsOctetCounted
-- |  |  |        |__(16) mtpSdtStatsRxCrcErrors
-- |  |  |        |__(17) mtpSdtStatsRxFrameErrors
-- |  |  |        |__(18) mtpSdtStatsRxFrameOverflows
-- |  |  |        |__(19) mtpSdtStatsRxFrameTooLong
-- |  |  |        |__(20) mtpSdtStatsRxFrameTooShort
-- |  |  |        |__(21) mtpSdtStatsRxResidueErrors
-- |  |  |        |__(22) mtpSdtStatsCarrierCtsLost
-- |  |  |        |__(23) mtpSdtStatsCarrierDcdLost
-- |  |  |        |__(24) mtpSdtStatsCarrierLost
-- |  |  |
-- |  |  |__(12) mtpSdl
-- |  |     |__( 1) mtpSdlTable
-- |  |     |  |__( 1) mtpSdlEntry
-- |  |     |     |__( 1) mtpSdlId
-- |  |     |     |__( 2) mtpSdlAdjPc
-- |  |     |     |__( 3) mtpSdlTransmissionRate
-- |  |     |     |__( 4) mtpSdlLoopDelay
-- |  |     |     |__( 5) mtpSdlOperationalState
-- |  |     |     |__( 6) mtpSdlEquipmentPointer
-- |  |     |     |__( 7) mtpSdlCIC
-- |  |     |     |__( 8) mtpSdlName
-- |  |     |     |__( 9) mtpSdlStmChannel
-- |  |     |     |__(10) mtpSdlVcTTpPointer
-- |  |     |     |__(11) mtpSdlRowStatus
-- |  |     |
-- |  |     |__( 2) mtpSdlStatsTable
-- |  |        |__( 1) mtpSdlStatsEntry
-- |  |           |__( 1) mtpSdlStatsRxOctets
-- |  |           |__( 2) mtpSdlStatsTxOctets
-- |  |           |__( 3) mtpSdlStatsRXOverruns
-- |  |           |__( 4) mtpSdlStatsTxUnderruns
-- |  |           |__( 5) mtpSdlStatsRxBufferOverflows
-- |  |           |__( 6) mtpSdlStatsTxBufferOverflows
-- |  |           |__( 7) mtpSdlStatsLeadCtsLost
-- |  |           |__( 8) mtpSdlStatsLeadDcdLost
-- |  |           |__( 9) mtpSdlStatsCarrierLost
-- |  |           |__(10) mtpSdlStatsBipolarViolations
-- |  |
-- |  |__( 2) mtpScalars
-- |  |  |__( 1) mtpDefaults
-- |  |     |__( 1) mtpM2paDefaultSctpNoDelay
-- |  |     |__( 2) mtpM2paDefaultSctpMaxseg
-- |  |     |__( 3) mtpM2paDefaultSctpHeartbeatItvl
-- |  |     |__( 4) mtpM2paDefaultSctpHeartbeat
-- |  |     |__( 5) mtpM2paDefaultSctpRtoInitial
-- |  |     |__( 6) mtpM2paDefaultSctpRtoMin
-- |  |     |__( 7) mtpM2paDefaultSctpRtoMax
-- |  |     |__( 8) mtpM2paDefaultSctpPathMaxRetrans
-- |  |     |__( 9) mtpM2paDefaultSctpCookieLife
-- |  |     |__(10) mtpM2paDefaultSctpCookieInc
-- |  |     |__(11) mtpM2paDefaultSctpMaxInitRetries
-- |  |     |__(12) mtpM2paDefaultSctpMaxBurst
-- |  |     |__(13) mtpM2paDefaultSctpAssocMaxRetrans
-- |  |     |__(14) mtpM2paDefaultSctpSackDelay
-- |  |     |__(15) mtpM2paDefaultSctpLifetime
-- |  |
-- |  |__( 3) mtpNotifs
-- |  |  |__( 1) changeInLsToAdjSp
-- |  |  |__( 2) oldLs
-- |  |  |__( 3) newLs
-- |  |  |__( 4) inaccessibleSp
-- |  |  |__( 5) remoteUnavailableUserPart
-- |  |  |__( 6) congestionStatus
-- |  |  |__( 7) networkPointCode
-- |  |  |__( 8) userPart
-- |  |  |__( 9) userPartStatus
-- |  |  |__(10) linkFailureReason
-- |  |
-- |  |__( 4) mtpOids
-- |     |__( 1) mtpProtocols
-- |     |  |__( 1) mtpProtocolItut
-- |     |  |__( 2) mtpProtocolEtsi
-- |     |  |__( 3) mtpProtocolAnsi
-- |     |  |__( 4) mtpProtocolJttc
-- |     |  |__( 5) mtpProtocolChin
-- |     |  |__( 6) mtpProtocolPnoc
-- |     |  |__( 7) mtpProtocolSing
-- |     |  |__( 8) mtpProtocolSpan
-- |     |
-- |     |__( 2) mtpProbableCauses
-- |     |  |__(  1) localUserPartUnavailable
-- |     |  |__(  2) remoteUserPartUnavailable
-- |     |  |__(102) slFailure
-- |     |  |__(110) localAutomaticChange
-- |     |  |__(210) remoteProcOutage
-- |     |  |__(216) localInhibition
-- |     |  |__(218) remoteInhibition
-- |     |  |__(306) linkCongestionIndications
-- |     |  |__(311) linkCongestionDiscard
-- |     |  |__(403) linkSetFailure
-- |     |  |__(405) linkSetFailureTFPBroadcast
-- |     |  |__(411) routesetUnavailability
-- |     |  |__(413) linksetAdjSpChange
-- |     |  |__(501) adjSpInaccessibility
-- |     |  |__(505) routingDataError
-- |     |  |__(506) userPartUnavailableSent
-- |     |  |__(507) userPartUnavailableReceived
-- |     |  |__(508) transferControlledReceived
-- |     |
-- |     |__( 3) mtpSpecificProblems
-- |     |  |__(  3) abnormalFIBRorBSNR
-- |     |  |__(  4) excessiveAckDelay
-- |     |  |__(  5) excessiveErrorRate
-- |     |  |__(  6) excessiveCongDuration
-- |     |  |__(  7) remoteUPUnknown
-- |     |  |__(  8) remoteUPUnequipped
-- |     |  |__(  9) remoteUPInaccessible
-- |     |
-- |     |__( 4) mtpExtensions
-- |        |__(  1) defaultInLsLoadShareAlgorithm
-- |
-- |__( 2) mtpConformance
--    |__( 1) mtpCompliance
--    |  |__( 1) mtpLsProfileCompliance
--    |  |__( 2) mtpSapCompliance
--    |  |__( 3) mtpL2ProfocolProfileCompliance
--    |  |__( 4) mtpNbProfileCompliance
--    |  |__( 5) mtpSaalProfileCompliance
--    |  |__( 6) mtpM2paProfileCompliance
--    |  |__( 7) mtpL3Compliacne
--    |  |__( 8) mtpSpCompliance
--    |  |__( 9) mtpSdlCompliance
--    |  |__(10) mtpLsCompliance
--    |  |__(11) mtpSlCompliance
--    |  |__(12) mtpSlL3ProfileCompliance
--    |  |__(13) mtpSpProfileCompliance
--    |  |__(14) mtpRtCompliance
--    |  |__(15) mtpSignRouteSetNetPartCompliance
--    |  |__(16) mtpStCompliance
--    |  |__(17) mtpGsCompliance
--    |  |__(18) mtpGsLineCompliance
--    |
--    |__( 2) mtpGroups
--       |__( 1) mtpLsProfilePackage
--       |__( 2) managedSwitchingElementPackage
--       |__( 3) mtpSapPkg
--       |__( 4) mtpSlL2ProfilePkg
--       |__( 5) mtpL3Package
--       |__( 6) mtpSpPackage
--       |__( 7) mtpSdlPackage
--       |__( 8) mtpLsPackage
--       |__( 9) mtpSlPackage
--       |__(10) mtpSlL3ProfilePackage
--       |__(11) mtpSpProfilePackage
--       |__(12) mtpRtPackage
--       |__(13) mtpRsPackage
--       |__(14) mtpStPackage
--       |__(15) mtpGsPkg
--       |__(16) mtpGsLinePkg
--       |__(17) administrativeStatePackage
--       |__(18) bufferMechanismPackage
--       |__(19) cICPackage
--       |__(20) clsLoadsharingInformationPackage
--       |__(21) congestedStatePackage
--       |__(22) congestionHandlingPackage
--       |__(23) congestionLevelPackage
--       |__(24) getScreenedOpcsOrLinkSetsByDpcActionPackage
--       |__(25) fixedRouteNePartPriorityPackage
--       |__(26) flexibleRouteNePartPriorityPackage
--       |__(27) inLsLoadShareAlgorithmPackage
--       |__(28) linkCongestionLevelPackage
--       |__(29) loadsharingInformationRouteNePartPackage
--       |__(30) loadsharingInformationRouteSetNePartPackage
--       |__(31) loopDelayPackage
--       |__(32) mtpLsProfileNamePackage
--       |__(33) mtpLsProfilePointerPackage
--       |__(34) managedSwitchingElementNamePackage
--       |__(35) mtpSapNamePackage
--       |__(36) mtpSlL2ProfileNamePackage
--       |__(37) mtpL3NamePackage
--       |__(38) mtpLoadsharingObjectForRouteNePartPointerPackage
--       |__(39) mtpLoadsharingObjectForRouteSetNePartPointerPackage
--       |__(40) mtpSpNamePackage
--       |__(41) multipleTransmissionCongestionLevelsPackage
--       |__(42) multipleTransmissionCongestionLevelsWithPrioPackage
--       |__(43) multipleTransmissionCongestionStatesPackage
--       |__(44) noBasicLinkAllocationPackage
--       |__(45) pCRPackage
--       |__(46) receiveCongestionLevelsPackage
--       |__(47) relatedLinkGroupNumberPackage
--       |__(48) remoteExchangeLabelPackage
--       |__(49) mtpSdlListPackage
--       |__(50) mtpSdlNamePackage
--       |__(51) mtpLsNamePackage
--       |__(52) mtpSignLinkTestPackage
--       |__(53) mtpSlNamePackage
--       |__(54) mtpRtNamePackage
--       |__(55) mtpRsNamePackage
--       |__(56) mtpStListPackage
--       |__(57) mtpStNamePackage
--       |__(58) slsCodeNormalListPackage
--       |__(59) slsListPackage
--       |__(60) mtpSlL3ProfileNamePackage
--       |__(61) mtpSlL3ProfilePointerPackage
--       |__(62) mtpRestartingNotification
--       |__(63) mtpSpTimersPackage
--       |__(64) mtpSpProfileNamePackage
--       |__(65) mtpSpProfilePointerPackage
--       |__(66) ss7OnOccEventPackage
--       |__(67) stmChannelPackage
--       |__(68) mtpGsNamePackage
--       |__(69) usageStatePackage
--       |__(70) adjPcPackage
--       |__(71) broadbandSpecificPackage
--       |__(72) egressTransmissionRateIntervalPackage
--       |__(73) longMessageSupportedPackage
--       |__(74) narrowbandSpecificPackage
--       |__(75) pollAfterRetransmissionPackage
--       |__(76) mtpSaalProfilePackage
--       |__(77) saalSdlPackage
--       |__(78) saalSlPackage
--       |__(79) m2paSctpDefaultsPackage
--       |__(80) mtpM2paProfilePkg
--       |__(81) m2paProvingPackage
--       |__(82) providerEntityNamesPackage
--       |__(83) mtpRestartingParameters
--       |__(84) ss7OnOccEventParameters
--       |__(85) mtpSapAsaPointerPackage
--       |__(86) mtpL3AsaPointerPackage
--       |__(87) mtpSlAsaPointerPackage
--       |__(88) mtpRsAsaPointerPackage
--       |__(89) mtpLsAsaPointerPackage


-- ====================================================================
-- TEXTUAL CONVENTIONS
-- ====================================================================

VisibleString ::= TEXTUAL-CONVENTION
    STATUS current
    DESCRIPTION
	"The VisibleString of ASN.1."
    SYNTAX OCTET STRING

GraphicString ::= TEXTUAL-CONVENTION
    STATUS current
    DESCRIPTION
	"The GraphicString of ASN.1."
    SYNTAX OCTET STRING

Ss7LoadShareAlgorithm ::= TEXTUAL-CONVENTION
    STATUS current
    DESCRIPTION
	"This is a SS7 load sharing algorithm as identified by the SS7 
	 MTP GDMOs."
    REFERENCE
	"ITU-T Rec. Q.751.1 (1997)"
    SYNTAX OBJECT IDENTIFIER

SlsList ::= TEXTUAL-CONVENTION
    DISPLAY-HINT "1d,"
    STATUS current
    DESCRIPTION
	"This is a way of specifying a list of SLS values.  Because SLS 
	 values can be 4, 5 or 8 bits, depending on the protocol 
	 variant, issue year,  and options, one octet is used to 
	 represent one SLS value.  If 4 bit SLSs apply, each octet is 
	 set to a value constrained to the range (0..15) and the size of 
	 the string is constrained to SIZE(0..16); 5-bits, (0..31), 
	 SIZE(0..32); and 8-bits (0..255), SIZE(0..256).  No SLS value 
	 can be repeated in the list.  What we really want is a SET OF 
	 Sls here, but SNMP won't have it."
    REFERENCE
	"ITU-T Rec. Q.751.1 (1997) : slsList ATTRIBUTE"
    SYNTAX OCTET STRING (SIZE(0..256))

SlsCodeList ::= TEXTUAL-CONVENTION
    STATUS current
    DESCRIPTION
	"Provides a specification of a list of signalling link codes.  
	 Each octet in the string has the value (0..15) for ITU-T based 
	 protocol variants (4-bit SLC), and (0..31) for ANSI based 
	 protocol variants (5-bit SLC), and represents one signalling 
	 link code in the list.  Values are only allowed to occur once 
	 in the list; therefore, the maximum length of the list is 
	 SIZE(0..16) for ITU-T based protocol variants, and SIZE(0..31) 
	 for ANSI based protocol variants."
    SYNTAX OCTET STRING (SIZE(0..31))

MtpGsTreatment ::= TEXTUAL-CONVENTION
    STATUS current
    DESCRIPTION
	"Provides a treatment result for rules in the gateway screening 
	 tables.  Objects with a SYNTAX clause containing this textual 
	 convention are single-valued and may have one of the following 
	 values:
	 
	  - normal(0), the message will be processed as normal.
	 
	  - discard(1), the message will be discarded with no further 
	    action.
	 
	  - prohibit(2), the message will be treated as a message to a 
	    prohibited destination: that is, the message will illicit a 
	    transfer-prohibited response for the destination point code 
	    in the message and then the message is discarded.
	 
	  - unequipped(3), when the message has an SI value that 
	    corresponds to an MTP user part, the message will be treated 
	    as a message to an unequipped user: that is, the message 
	    will illicit a user-part-unavailable message for an 
	    unequipped user and then the message is discarded.
	 
	  - inaccessible(4), when the message has an SI value that 
	    corresponds to an MTP user part, the message will be treated 
	    as a message to an inaccessible user: that is, the message 
	    will illicit a user-part-unavailable message for an 
	    inaccessible user and then the message is discarded.
	 
	  - congest(5), the message will be treated as a message to a 
	    congested destination: that is, the message will illicit a 
	    transfer-controlled response for the destination point code 
	    and at the priority of the message and then the message is 
	    discarded.

	 Note that application of values other than normal(0) or 
	 discard(1) will not conform to ITU-T Recommendation Q.705 
	 Clause 8.
	"
    SYNTAX INTEGER {
	normal(0), discard(1), prohibit(2), unequipped(3), 
	inaccessible(4), congest(5) }

MtpPointCodeFormat ::= TEXTUAL-CONVENTION
    DISPLAY-HINT "1d-"
    STATUS current
    DESCRIPTION
	"This textual convention describes an MTP point code format.  It 
	 contains three octets.  The first octet contains the number of 
	 bits in the first sub-field of the point code (network part), 
	 the second octet, the number in the second sub-field (cluster 
	 part), the third, the third sub-field (member part).  The sum 
	 of the bits is the total number of bits in the point code.  
	 Popular values are 3-8-3 (ITU-T and ETSI 14-bit point code) and 
	 8-8-8 (ANSI 24-bit point code)."
    SYNTAX OCTET STRING (SIZE(3))

MtpNetworkIndicator ::= TEXTUAL-CONVENTION
    STATUS current
    DESCRIPTION
	"This type specifies the SS7 MTP network indicator.
	 
	  - internationalNetwork1(0), network indicator for the 
	    international network;
	  - internationalNetwork2(1), reserved network indicator for the 
	    international network;
	  - nationalNetwork1(2), network indicator for the national 
	    network; and,
	  - nationalNetwork2(3), reserved network indicator for the 
	    national network.
	 "
    REFERENCE
	"ITU-T Rec. Q.751.1 (1997), ANSI T1.116.1 (2000) : 
	     MTPDefinedTypesModule.NetworkIndicator."
    SYNTAX INTEGER {
	internationalNetwork1(0), internationalNetwork2(1), 
	nationalNetwork1(2), nationalNetwork2(3) }

MtpSpType ::= TEXTUAL-CONVENTION
    STATUS current
    DESCRIPTION
	"This textual covention describes the type of signalling point.  
	 One of the of the major reasons for understanding this 
	 information is so that the MTP Restart procedures can be 
	 properly performed against an adjacent signalling point.  When:
	 
	  - sep(0), it indicates that the signalling point is a 
	    signalling end point that is not equipped with the transfer 
	    function; when
	  - step (1), it indicates that the signalling point is both a 
	    signalling end point (it has user parts) and a signalling 
	    transfer point (it has the transfer function); or,
	  - stp(2), the signalling point is has the transfer function 
	    but does not have user parts.
	"
    REFERENCE
	"ITU-T Rec. Q.751.1 (1997), ANSI T1.116.1 (2000) : 
	     MTPDefinedTypesModule.SpType."
    SYNTAX INTEGER {
	sep(0), step(1), stp(2) }

MtpResultOfAction ::= TEXTUAL-CONVENTION
    STATUS current
    DESCRIPTION
	"Provides the result of action on read and invokes the action on 
	 write.  Objects with this textual convention in their SYNTAX 
	 clause should have a MAX-ACCESS clause of read-write or 
	 read-create.  When any value is written to the object, the 
	 action is invoked.  When the object is read, the result of 
	 the action is returned as follows:
	 
	  - success(0), the last action was successful;
	 
	  - unsuccessful(1), the last action was unsuccessful;
	 
	  - notPerformed(2), the last action was not performed;
	 
	  - linkAlreadyInhibited(3), the last localInhibit action was 
	    attempted on an already locally inhibited link;
	 
	  - linkNotInhibited(4), the last localUninhibit action was 
	    attempted on an already locally uninihibited link;
	 
	  - wrongClassReferenced(5), the action was attempted on a class 
	    not supoprting the action;
	 
	  - signTermNonExisting(6), the last replaceSignTerm action was 
	    attempted with a non-existent signalling terminal;
	 
	  - signTermAlreadyReferenced(7), the last replaceSignTerm 
	    action was attempted with a signalling terminal already 
	    referenced;
	 
	  - wrongSignLinkTpStatus(8), the last action was attempted on a 
	    signalling link in the wrong state.
	"
    SYNTAX INTEGER {
	success(0), unsuccessful(1), notPerformed(2), 
	linkAlreadyInhibited(3), linkNotInhibited(4), 
	wrongClassReferenced(5), signTermNonExisting(6), 
	signTermAlreadyReferenced(7), wrongSignLinkTpStatus(8) }

MtpCongestedState ::= TEXTUAL-CONVENTION
    STATUS current
    DESCRIPTION
	"This type specifies an SS7 MTP congestion state.  Columnar 
	 objects folowing this textual convention are used to reflect 
	 route set congestion when multiple congestion levels are not 
	 in effect.
	 
	  - notCongested(0), the corresponding route set is not 
	    congested;
	  - congested(1), the corresponding route set is congested.
	 
	 The value may be changed by the managed system and objects with 
	 this textual convention in their SYNTAX clause should have a 
	 MAX-ACCESS clause of read-only.
	 
	 In the case where multiple congestion levels are used, the 
	 level of congestion is indicated by a column following the 
	 MtpCongestionLevel textual convention and columnar objects 
	 following this textual convention are not present.
	"
    REFERENCE
	"ITU-T Rec. Q.751.1 (1997), ANSI T1.116.1 (2000) : 
	     MTPDefinedTypesModule.CongestedState."
    SYNTAX INTEGER {
	notCongested(0), congested(1) }

MtpCongestionLevel ::= TEXTUAL-CONVENTION
    STATUS current
    DESCRIPTION
	"This type specifies an SS7 MTP congestion level.  Columnar 
	 object following this textual convention are used to reflect 
	 route set or signalling link congestion when multiple 
	 congestion levels are in effect.
	 
	  - none(0), the corresponding route set or signalling link is 
	    not congested;
	  - congestionLevel1(1), the corresponding route set or 
	    signalling link is congested at congestion level 1;
	  - congestionLevel2(2), the corresponding route set or 
	    signalling link is congested at congestion level 2;
	  - congestionLevel3(3), the corresponding route set or 
	    signalling link is congested at congestion level 3.
	 
	 The value may be changed by the managed system and objects with 
	 this textual convention in their SYNTAX clause should have a 
	 MAX-ACCESS clause of read-only.
	 
	 When multiple congestion levels are not in effect, the 
	 congestion state is indicated by a column following the 
	 MtpCongestedState textual convention and columnar objects 
	 following this textual convention are not present.
	"
    REFERENCE
	"ITU-T Rec. Q.751.1 (1997), ANSI T1.116.1 (2000) : 
	     MTPDefinedTypesModule.CongestionLevel."
    SYNTAX INTEGER {
	none(0), congestionLevel1(1), congestionLevel2(2), 
	congestionLevel3(3) }

NetworkPointCode ::= TEXTUAL-CONVENTION
    DISPLAY-HINT "1d:1d-"
    STATUS current
    DESCRIPTION
	"This is a network referenced signalling point code that 
	 uniquely identifies both the national or international SS7 
	 network (point code numbering space) to which the point code 
	 belongs as well as the point code within the network.  The 
	 first octet is a network identifier that identifies the larger 
	 national or international SS7 network; the second octet is the 
	 'network' portion of the signalling point code as defined in 
	 Q.704; the third, the 'cluster'; and, the fourth and last, the 
	 'member'.  This is displayed with a colon separating the 
	 network number and the normal numbers and dashes notation for 
	 the signalling point code: e.g. 1:5-1-1.  Note that an ITU-T 
	 signalling point code is unpacked by network, cluster and 
	 member into separate octets.  Also note that when the first 
	 octet is zero (0) it does not specify a global larger network 
	 and thus the network point code applies only to a locally 
	 defined network."
    SYNTAX OCTET STRING (SIZE(4))

MtpUserPart ::= TEXTUAL-CONVENTION
    STATUS current
    DESCRIPTION
	"Provides a specification of an MTP user part.  This textual 
	 convention provides an enumerated user part value that 
	 corresponds to the MTP SI value for the user part.  SI values 
	 snmm(0), sntm(1) and snsm(2) are reserved for MTP management 
	 messages; other values may be assigned to user parts.
	 
	  - snmm(0), signalling network management messages;
	  - sntm(1), signalling network test messages;
	  - snsm(2), signalling network special test messages;
	  - sccp(3), signalling connection control part;
	  - tup(4), telephone user part;
	  - isup(5), integrated services digital network user part;
	  - dup1(6), data user part 1;
	  - dup2(7), data user part 2;
	  - mtup(8), MTP test user part;
	  - bisup(9), broadband integrated services digital network user 
	    part;
	  - siup(10), user part;
	  - user11(11), user part 11;
	  - user12(12), user part 12;
	  - user13(13), user part 13;
	  - user14(14), user part 14;
	  - user15(15), user part 15.
	"
    SYNTAX INTEGER {
	snmm(0), sntm(1), snsm(2), sccp(3), tup(4), isup(5), dup1(6), 
	dup2(7), mtup(8), bisup(9), siup(10), user11(11), user12(12), 
	user13(13), user14(14), user15(15) }

MtpSiMask ::= TEXTUAL-CONVENTION
    STATUS current
    DESCRIPTION
	"Provides a set-valued attribute that specifies a set of MTP SI 
	 codes or User parts.  This textual convention is normally used 
	 to specify a set of user parts that are equipped or unequipped.  
	 It can contain any of the following:
	 
	  - snmm(0), signalling network management messages;
	  - sntm(1), signalling network test messages;
	  - snsm(2), signalling network special test messages;
	  - sccp(3), signalling connection control part;
	  - tup(4), telephone user part;
	  - isup(5), integrated services digital network user part;
	  - dup1(6), data user part 1;
	  - dup2(7), data user part 2;
	  - mtup(8), MTP test user part;
	  - bisup(9), broadband integrated services digital network user 
	    part;
	  - siup(10), user part;
	  - user11(11), user part 11;
	  - user12(12), user part 12;
	  - user13(13), user part 13;
	  - user14(14), user part 14;
	  - user15(15), user part 15.
	 
	 Objects that have a SYNTAX clause with this textual convention 
	 normally have a MAX-ACCESS clause of read-write or read-create.
	"
    SYNTAX BITS {
	snmm(0), sntm(1), snsm(2), sccp(3), tup(4), isup(5), dup1(6), 
	dup2(7), mtup(8), bisup(9), siup(10), user11(11), user12(12), 
	user13(13), user14(14), user15(15) }

MtpUserPartStatus ::= TEXTUAL-CONVENTION
    STATUS current
    DESCRIPTION
	"This textual convention can be used for reporting the 
	 availability of MTP user parts as well as providing a mechanism 
	 for controlling the availability of user parts.

	  - unknown(0) means that the availabilty of the user part is 
	    unknown;
	  - inaccessible(1) means that the user part is present but 
	    currently inaccessible;
	  - unequipped(2) means that the user part is not present.
	"
    SYNTAX INTEGER {
	unknown(0), inaccessible(1), unequipped(2) }

MtpAvailabilityStatus ::= TEXTUAL-CONVENTION
    STATUS current
    DESCRIPTION
	"This textual convention provides the status of an MTP entity, 
	 such as a route set, route or signalling point.  When:
	 
	  - inactive(0), the route set is inactive and does not carry 
	    user traffic;
	  - blocked(1), configured and able to carry traffic but blocked 
	    by transport;
	  - inhibited(2), management inhibited, but able to carry 
	    traffic;
	  - prohibited(3), prohibited by relay;
	  - restart(4), relay or endpoint restarting;
	  - restricted(5), restricted by relay;
	  - congested(6), endpoint congested;
	  - danger(7), in danger of congestion;
	  - allowed(8), allowed to to destination.
	 
	 Where the MTP managed object whose status is represented 
	 contains other managed objects with an MTP status, the MTP 
	 status of the managed object is the set-union (logical OR) of 
	 the contained managed objects."
    REFERENCE
	"ITU-T Rec. Q.704 (1997), ANSI T1.111.4/2000, ETSI ETS 
	     300 008-1"
    SYNTAX BITS {
	inactive(0), blocked(1), inhibited(2), prohibited(3), 
	restart(4), restricted(5), congested(6), danger(7), allowed(8) }

MtpOptions ::= TEXTUAL-CONVENTION
    STATUS current
    DESCRIPTION
	"This textual convention provides options for use with MTP and 
	 MTP users.  Not all options are applicable to all managed 
	 objects in all circumstances.  Options that are not applicable 
	 are ignored.  The DESCRIPTION clause of the OBJECT-TYPE must 
	 specify which options are applicable.
	 
	  - cluster(0), the MTP signalling point supports cluster 
	    routing, or the route or route set is a cluster route or 
	    route set;
	  - transferFunction(1), the MTP signalling point provides the 
	    transfer function (i.e. mtpSpType is step(1) or stp(2));
	  - adjacent(2), the MTP route set is to an adjacent signalling 
	    point;
	  - security(3), the MTP signalling point has the gateway 
	    screening function;
	    applied;
	  - linkOscillationA(4), the MTP signalling point has signalling 
	    links that support link oscillation procedure A by default;
	  - linkOscillationB(5), the MTP signalling point has signalling 
	    links that support link oscillation procedure B by default.
	 
	 Not all combinations of the options are valid.  Not all valid 
	 combinations of the flags are acceptable to all protocol 
	 variants.
	"
    SYNTAX BITS {
	cluster(0), transferFunction(1), adjacent(2), security(3), 
	linkOscillationA(4), linkOscillationB(5) }

MtpLinkStatus ::= TEXTUAL-CONVENTION
    STATUS current
    DESCRIPTION
	"This type specifes an SS7 MTP Level 2 Link protocol status.
	 
	 The linkTpStatus contains the SS No. 7 functional statuses as 
	 described in Recommendation Q.704. Possible states indicated 
	 are local blocked, remote blocked, local inhibited, remote 
	 inhibited, failed and deactivated.  Attributes following this 
	 textual convention are set-valued and may contain the following 
	 values:
	 
	  - localBlocked(0), the signalling link is locally blocked.  
	    Signalling links are locally blocked when experiencing local 
	    processor outage.
	 
	  - remoteBlocked(1), the signalling link is remotely blocked.  
	    Signalling links are remotely blocked when experiencing 
	    remote processor outage.
	 
	  - localInhibited(2), the signalling link is locally inhibited.  
	    Signalling links are locally inhibited when locally 
	    inhibited by MTP management.
	 
	  - remoteInhibited(3), the signalling link is remotely 
	    inhibited.  Signalling links are remotely inhibited when 
	    inhibited by the remote MTP management.
	 
	  - failed(4), the signalling link is failed.  Signalling links 
	    are failed when they were previously active and are inactive 
	    due to a failure rather than a management action.
	 
	  - deactivated(5), the signalling link is deactivated.  
	    Signalling links are deactivated when inactive due to 
	    management action.
	 
	 The value may be changed by the managed system and objects with 
	 this textual convention in their SYNTAX clause should have a 
	 MAX-ACCESS clause of read-only.
	 "
    REFERENCE
	"ITU-T Rec. Q.751.1 (1997), ANSI T1.116.1 (2000) : 
	     MTPDefinedTypesModule.LinkTpStatus."
    SYNTAX BITS {
	localBlocked(0), remoteBlocked(1), localInhibited(2), 
	remoteInhibited(3), failed(4), deactivated(5) }

MtpLinkFailureReason ::= TEXTUAL-CONVENTION
    STATUS current
    DESCRIPTION
	"This is the detailed reason for a link failure.  It has the 
	 following enumeration:
	 
	  - unspecified(0), the reason for failure is unknown or none of 
	    the other failure reasons apply;
	  - contTimeout(1), T6 timeout;
	  - ackTimeout(2), T7 timeout;
	  - abnormalBsnr(3), receipt of excessive abnormal BSNs;
	  - abnormalFibr(4), receipt of excessive abnormal FIBs;
	  - suermEim(5), error rate monitor exceeded the threshold;
	  - alignmentNotPossible(6), alignment failed;
	  - receivedSio(7), an unexpected SIO was received;
	  - receivedSin(8), an unexpected SIN was received;
	  - receivedSie(9) an unexpected SIE was received;
	  - receivedSios(10), the link was shut down by the other side;
	  - t1Timeout(11), T1 timeout.
	 
	 The value is set by the managed system and objects with this 
	 textual convention in thier SYNTAX clause have a MAX-ACCESS 
	 clause of read-only.
	"
    REFERENCE
	"ITU-T Recommendation Q.703 (1996)"
    SYNTAX INTEGER {
	unspecified(0), congTimeout(1), ackTimeout(2), abnormalBsnr(3), 
	abnormalFibr(4), suermEim(5), alignmentNotPossible(6), 
	receivedSio(7), receivedSin(8), receivedSie(9), 
	receivedSios(10), t1Timeout(11) }

MtpTransmissionRate ::= TEXTUAL-CONVENTION
    STATUS current
    DESCRIPTION
	"This type describes an applicable narrowband transmission rate.  
	 This can be 4800, 56000, 64000, 1536000 or 1984000, which 
	 corresponds to modem, DS0-A, DS0, T1/J1 or E1.  It also implies 
	 the transmission type: 56, 64, 1544 and 2048 kbis implies 
	 digital transmission; 4.8 kbits implies analog transmission.
	 
	  - kbits4point8(0), the transmission rate is for modem (4800 baud);
	  - kbits56(1), the transmission rate is for DS0-A (56kbps);
	  - kbits64(2), the transmission rate is for DS0 (64kbps);
	  - kbits1544(3), the transmission rate is for T1 (1536kbps);
	  - kbits2048(4), the transmission rate is for E1 (1984kbps).
	 
	 Objects with this textual convention in thier SYNTAX clause 
	 normally have a MAX-ACCESS clause of read-write or read-create.
	"
    SYNTAX INTEGER {
	kbits4point8(0), kbits56(1), kbits64(2), kbits1544(3), 
	kbits2048(4) }

-- ====================================================================

-- Protocols


mtpProtocolItut OBJECT-IDENTITY
    STATUS current
    DESCRIPTION
	"Provides an autonomous type for ITU-T and ITU-T  based MTP 
	 protocols."
    ::= { mtpProtocols 1 }

mtpProtocolEtsi OBJECT-IDENTITY
    STATUS current
    DESCRIPTION
	"Provides an autonomous type for ETSI and ETSI based MTP 
	 protocols."
    ::= { mtpProtocols 2 }

mtpProtocolAnsi OBJECT-IDENTITY
    STATUS current
    DESCRIPTION
	"Provides an autonomous type for ANSI and ANSI based protocols."
    ::= { mtpProtocols 3 }

mtpProtocolJttc OBJECT-IDENTITY
    STATUS current
    DESCRIPTION
	"Provides an autonomous type for JTTC and JTTC based protocols."
    ::= { mtpProtocols 4 }

mtpProtocolChin OBJECT-IDENTITY
    STATUS current
    DESCRIPTION
	"Provides an autonomous type for China and China based 
	 protocols."
    ::= { mtpProtocols 5 }

mtpProtocolPnoc OBJECT-IDENTITY
    STATUS current
    DESCRIPTION
	"Provides an autonomous type for PNOC and PNOC based protocols."
    ::= { mtpProtocols 6 }

mtpProtocolSing OBJECT-IDENTITY
    STATUS current
    DESCRIPTION
	"Provides an autonomous type for Singapore and Singapore based 
	 protocols."
    ::= { mtpProtocols 7 }

mtpProtocolSpan OBJECT-IDENTITY
    STATUS current
    DESCRIPTION
	"Provides an autonomous type for Spain and Spain based 
	 protocols."
    ::= { mtpProtocols 8 }


-- ====================================================================
-- MTP SPECIFIC PROBLEMS
-- ====================================================================

abnormalFIBRorBSNR OBJECT-IDENTITY
    STATUS current
    DESCRIPTION
	"SpecificProblems.  This object identity is used with 
	 specificProblems when the probableCause = 102 (slFailure).  It 
	 identifies the specific cause of the failure which was receipt 
	 of an abnormal FIB or BSN.
	  
	 Whenever the managed element issues a notification of 
	 signalling link failure with probable cause slFailure, and the 
	 specific problem was the receipt of an abnormal FIB or BSN, 
	 this object identity should be placed in the specificProblems 
	 field in the notification."
    REFERENCE
	"ITU-T Rec. Q.751.1 (1996), ANSI T1.116.1 (2000),
	     MTPDefinedTypesModule.abnormalFIBRorBSNR.
	 ITU-T Rec. Q.752 (1997) : Table 1/Q.752, 1.2 and 1.3."
    ::= { mtpSpecificProblems 3 }

excessiveAckDelay OBJECT-IDENTITY
    STATUS current
    DESCRIPTION
	"SpecificProblems.  This object identity is used with 
	 specificProblems when the probableCause = 102 (slFailure).  It 
	 identifies the specific cause of the failure which was 
	 excessive delay of acknowledgement (i.e. Timer T7 timeout).
	  
	 Whenever the managed element issues a notification of 
	 signalling link failure with probable cause slFailure, and the 
	 specific problem was excessive delay of acknowlegement or timer 
	 T7 timeout, this object identity should be placed in the 
	 specificProblems field of the notification."
    REFERENCE
	"ITU-T Rec. Q.751.1 (1996), ANSI T1.116.1 (2000), 
	     MTPDefinedTypesModule.excessiveAckDelay.
	 ITU-T Rec. Q.752 (1997) : Table 1/Q.752, 1.2 and 1.4."
    ::= { mtpSpecificProblems 4 }

excessiveErrorRate OBJECT-IDENTITY
    STATUS current
    DESCRIPTION
	"SpecificProblems.  This object identity is used with 
	 specificProblems when the probableCause = 102 (slFailure).  It 
	 identifies the specific cause of the failure which was 
	 excessive error rate (i.e. SUERM or EIM driven failure).
	  
	 Whenever the managed element issues a notification of 
	 signalling link failure with probable cause slFailure, and the 
	 specific problem was excessive error rate, this object identity 
	 should be placed in the specificProblems field of the 
	 notification."
    REFERENCE
	"ITU-T Rec. Q.751.1 (1997), ANSI T1.116.1 (2000), 
	     MTPDefinedTypesModule.excessiveErrorRate.
	 ITU-T Rec. Q.752 (1997) : Table 1/Q.752, 1.2 and 1.5"
    ::= { mtpSpecificProblems 5 }

excessiveCongDuration OBJECT-IDENTITY
    STATUS current
    DESCRIPTION
	"SpecificProblems.  This object identity is used with 
	 specificProblems when the probableCause = 102 (slFailure).  It 
	 identifies the specific cause of the failure which was 
	 excessive congestion duration (i.e. Timer T6 timeout).
	 
	 Whenver the managed element issues a notification of signalling 
	 link failure with probable cause slFailure,  and the specific 
	 problem was excessive duration of congestion, this object 
	 identity should be placed in the specificProblems field of the 
	 notification."
    REFERENCE
	"ITU-T Rec. Q.751.1 (1997), ANSI T1.116.1 (2000), 
	     MTPDefinedTypesModule.excessiveCongDuration.
	 ITU-T Rec. Q.752 (1997) : Table 1/Q.752, 1.2 and 1.6"
    ::= { mtpSpecificProblems 6 }

remoteUPUnknown OBJECT-IDENTITY
    STATUS current
    DESCRIPTION
	"SpecificProblems.  This object identity is used with 
	 specificProblems when probableCause = 2 
	 (remoteUserPartUnavailable).  It identifies the specific cause 
	 of the notification which in this case is that the remote user 
	 part is unknown."
    REFERENCE
	"ITU-T Rec. Q.751.1 (1997), ANSI T1.116.1 (2000), 
	     MTPDefinedTypesModule.remoteUPUnknown."
    ::= { mtpSpecificProblems 7 }

remoteUPUnequipped OBJECT-IDENTITY
    STATUS current
    DESCRIPTION
	"SpecificProblems.  This object identity is used with 
	 specificProblems when probableCause = 2 
	 (remoteUserPartUnavailable).  It identifies the specific cause 
	 of the notification which in this case is that the remote user 
	 part is unequipped."
    REFERENCE
	"ITU-T Rec. Q.751.1 (1997), ANSI T1.116.1 (2000), 
	     MTPDefinedTypesModule.remoteUPUnequipped."
    ::= { mtpSpecificProblems 8 }

remoteUPInaccessible OBJECT-IDENTITY
    STATUS current
    DESCRIPTION
	"SpecificProblems.  This object identity is used with 
	 specificProblems when probableCause = 2 
	 (remoteUserPartUnavailable).  It identifies the specific cause 
	 of the notification which in this case is that the remote user 
	 part is inaccessible."
    REFERENCE
	"ITU-T Rec. Q.751.1 (1997), ANSI T1.116.1 (2000), 
	     MTPDefinedTypesModule.remoteUPInaccessible."
    ::= { mtpSpecificProblems 9 }

-- ====================================================================
-- MTP LOAD SHARING ALGORITHMS
-- ====================================================================

defaultInLsLoadShareAlgorithm OBJECT-IDENTITY
    STATUS current
    DESCRIPTION
	""
    ::= { mtpExtensions 1 }

-- ====================================================================
-- MTP PROBABLE CAUSES
-- ====================================================================

localUserPartUnavailable OBJECT-IDENTITY
    STATUS current
    DESCRIPTION
	"ProbableCause.  This object identity is used with 
	 probableCause."
    REFERENCE
	"ITU-T Rec. Q.751.1 (1997), ANSI T1.116.1 (2000), 
	     MTPDefinedTypesModule.localUserPartUnavailable."
    ::= { mtpProbableCauses 1 }

remoteUserPartUnavailable OBJECT-IDENTITY
    STATUS current
    DESCRIPTION
	"ProbableCause"
    REFERENCE
	"ITU-T Rec. Q.751.1 (1997), ANSI T1.116.1 (2000), 
	     MTPDefinedTypesModule.remoteUserPartUnavailable."
    ::= { mtpProbableCauses 2 }

-- NOTE: ANSI T1.116.1/2000 takes a somewhat different approach to 
-- notifications than does ITU-T Q.751.1: Whereas ITU-T defines an 
-- ss7OnOccEvent notification that has the same parameteres as a 
-- communicationsAlarm notification with some additional parameters for 
-- on occurence events not covered by communicationsAlarm, ANSI uses the 
-- communicationsAlarm for all events that can be accomodated by the 
-- alarm and uses ss7OnOccEvent only for those notifications that cannot 
-- be represented by a communicationsAlarm.  It is the view of the 
-- OpenSS7 Project that the ANSI approach is somewhat superior in that 
-- all communicationsAlarms are better integrated into a single 
-- mechanism.

-- q752Item1p02 OBJECT IDENTIFIER
--     ::= { mtpProbableCauses 102 }
-- 
-- q752Item1p10 OBJECT IDENTIFIER
--     ::= { mtpProbableCauses 110 }
-- 
-- q752Item2p10 OBJECT IDENTIFIER
--     ::= { mtpProbableCauses 210 }
-- 
-- q752Item2p16 OBJECT IDENTIFIER
--     ::= { mtpProbableCauses 216 }
-- 
-- q752Item2p18 OBJECT IDENTIFIER
--     ::= { mtpProbableCauses 218 }
-- 
-- q752Item3p06 OBJECT IDENTIFIER
--     ::= { mtpProbableCauses 306 }
-- 
-- q752Item3p11 OBJECT IDENTIFIER
--     ::= { mtpProbableCauses 311 }
-- 
-- q752Item4p03 OBJECT IDENTIFIER
--     ::= { mtpProbableCauses 403 }
-- 
-- q752Item4p05 OBJECT IDENTIFIER
--     ::= { mtpProbableCauses 405 }
-- 
-- q752Item4p11 OBJECT IDENTIFIER
--     ::= { mtpProbableCauses 411 }
-- 
-- q752Item4p13 OBJECT IDENTIFIER
--     ::= { mtpProbableCauses 413 }
-- 
-- q752Item5p01 OBJECT IDENTIFIER
--     ::= { mtpProbableCauses 501 }
-- 
-- q752Item5p05 OBJECT IDENTIFIER
--     ::= { mtpProbableCauses 505 }
-- 
-- q752Item5p06 OBJECT IDENTIFIER
--     ::= { mtpProbableCauses 506 }
-- 
-- q752Item5p07 OBJECT IDENTIFIER
--     ::= { mtpProbableCauses 507 }
-- 
-- q752Item5p08 OBJECT IDENTIFIER
--     ::= { mtpProbableCauses 508 }

q752Item1p02 OBJECT IDENTIFIER ::= { mtpProbableCauses 102 }

slFailure OBJECT-IDENTITY
    STATUS current
    DESCRIPTION
	"ProbableCause.  This object identity is used with 
	 probableCause.  Probable Cause = 102 (slFailure) which 
	 represents measurement Q.752/1.2 measurement Q.752/1.6 
	 (specificProblems = 003 abnormalFIBRorBSNR, 004 
	 excessiveAckDelay, 005 excessiveErrorRate, 006 excessiveCong 
	 Duration) and Q.752/1.12 (Perceived Severity = Cleared).
	 
	 When a signalling link failure occurs, an ss7OnOccEvent 
	 notification is generated with this object as the probableCause 
	 and the failed signalling link as the objectInstance.  The 
	 specificProblems object identifier is included in the message 
	 which indicates the reason for the failure, as follows:
	 
	  - When the signalling link failed due to receipt of an 
	    abnormal FIB or BSN, the abnormalFIBRorBSNR object identity 
	    will be placed in the specific problem.  In this case the 
	    notification corresponds to a Table 1/Q.752 1.2 (SL failure 
	    - All reasons) and 1.3 (SL failure - Abnormal FIBR/BSNR) on 
	    occurrence notifiction.
	 
	  - When the signalling link failed due to excessive delay of 
	    acknowledgement, or T7 timeout, the excessiveAckDelay object 
	    identity will be placed in the specific problem.  In this 
	    case the notification corresponds to a Table 1/Q.752 1.2 (SL 
	    failure - All reasons) and 1.4 (SL failure - Excessive delay 
	    of ack) on occurence notification.
	 
	  - When the signalling link failed due to excessive error rate, 
	    or the error count surpassing the threshold in the SUERM or 
	    EIM, the excessiveErrorRate object identity will be placed 
	    in the specific problem.  In this case the notification 
	    corresponds to a Table 1/Q.752 1.2 (SL failure - All 
	    reasons) and 1.5 (SL failure - Excessive error rate) on 
	    ocurence notification.
	 
	  - When the signalling link failed due to excessive duration of 
	    congestion (i.e, Timer T6 expiry), the excessiveCongDuration 
	    object identity will be placed in the specific problem.  In 
	    this case the notification corresponds to a Table 1/Q.752 
	    1.2 (SL failure - All reasons) and 1.6 (SL failure - 
	    Excessive duration of congestion) on occurrence 
	    notification.
	 
	  - When the signalling link failed due to a reason other than 
	    the above, or the reason cannot be determined, no object 
	    identity is placed in the specific problems.  In this case, 
	    the notification corresponds to a Table 1/Q.752 1.2 (SL 
	    failure - All reasons) on occurence notification.
	 
	  - When the signalling link is restored (versus intialized) 
	    this proabable cause with the perceived severity of 
	    cleared(5) will be issued complete with the objectPointer 
	    identifying the restored link.  In this case the 
	    notification corresponds to Table 1/Q.752 1.12 (SL 
	    restoration).
	 
	 For signalling link failures, the perceivedSeverity included in 
	 the message is warning(1), minor(2), major(3) or critical(4).  
	 The failure of a signalling link is considered a minor alarm 
	 event.  If the loss of the signalling link results in the 
	 failure of a link set, or other failures such as route set 
	 failures, a separate major(3) alarm will be generated for the 
	 correlated failure.  Additional information that must be placed 
	 in the alarm assertion is the objectPointer of the signalling 
	 link in question."
    REFERENCE
	"ITU-T Rec. Q.751.1 (1996) : q752Item1p02,
	 ITU-T Rec. Q.752 (1997) : Table 1/Q.752 1.2, 1.3, 1.4, 
	     1.5, 1.6, 1.12"
    ::= { mtpProbableCauses 102 }

q752Item1p10 OBJECT IDENTIFIER ::= { mtpProbableCauses 110 }

localAutomaticChange OBJECT-IDENTITY
    STATUS current
    DESCRIPTION
	"ProbableCause.  This object identity is used with probableCause 
	 in the ss7OnOccEvent or communicationsAlarm notification.  It 
	 is used for notification of local automatic changeover of a 
	 signalling link and local automatic changeback of a signalilng 
	 link in accordance with Table 1/Q.752 1.10 (Local automatic 
	 changeover) and 1.11 (Local automatic changeback).
	 
	  - When used to indicate local automatic changeover, 
	    perceivedSeverity will have values warning(1), minor(2), 
	    major(3) or critical(4).  In this case the notification 
	    corresponds to Table 1/Q.752 1.10 or Table 1/T1.116.1 1.10 
	    (Local automatic changeover).
	 
	  - When used to indicate local automatic changeback, 
	    perceivedSeverity will contain cleared(5).  In this case the 
	    notification corresponds to Table 1/Q.752 1.11 or Table 
	    1/T1.116.1 1.11 (Local automatic changeback).
	 
	 For automatic link changeovers, the perceivedSeverity included 
	 in the message is warning(1), minor(2), major(3) or 
	 critical(4).  The automatic changeover of a signalling link is 
	 considered a minor alarm event as it derives directly from from 
	 a signalling link failure, also considered a minor event.  The 
	 fact that an automatic changeover has occurred just means that 
	 the signalling links was carrying traffic when it failed, or 
	 that a remote processour outage was of a long duration."
    REFERENCE
	"ITU-T Rec. Q.751.1 (1996) : q752Item1p10,
	 ITU-T Rec. Q.752 (1997) : Table 1, 1.10 and 1.11,
	 ANSI T1.116.1 (2000D) : Table 1, 1.10 and 1.11"
    ::= { mtpProbableCauses 110 }

q752Item2p10 OBJECT IDENTIFIER ::= { mtpProbableCauses 210 }

remoteProcOutage OBJECT-IDENTITY
    STATUS current
    DESCRIPTION
	"ProbableCause.  This object identity is used with probableCause 
	 in the ss7OnOccEvent or communicationsAlarm notification.  It 
	 is used for notification of the start or stop of remote 
	 processor outage condition for a signalling link in accordance 
	 with Table 2/Q.752 2.10 (Start of remote processor outage) and 
	 2.11 (Stop of remote processor outage).
	 
	 communicationsAlarm notifications that use this object identity 
	 as a probableCause will populate the objectInstance with the 
	 identity of the
	 signalling link which has experienced or recovered from 
	 processor outage condition in accordance with the 
	 objectInstance texutal convention.
	 
	  - When used to indicate start of remote processor outage, 
	    perceivedSeverity will have values warning(1), minor(2), 
	    major(3) or critical(4).  In this case the notification 
	    corresponds to Table 1/Q.752 2.10 or Table 1/T1.116.1 2.10 
	    (Start of remote processor outage).
	 
	  - When used to indicate stop of remote processor outage, 
	    perceivedSeverity will have the value cleared(5).  In this 
	    case, the notification corresponds to Table 1/Q.752 2.11 or 
	    Table 1/T1.116.1 2.11 (Stop of remote proceessor outage).
	 
	 For start of remote processor outage and stop of remote 
	 processor outage, the specificProblems parameter is not 
	 expected to be present.
	 
	 For start of remote processor outage indications, the 
	 perceivedSeverity included in the mssage is warning(1), 
	 minor(2), major(3) or critical(4).  THe blockage of a 
	 signalling link is considered a minor event."
    REFERENCE
	"ITU-T Rec. Q.751.1 (1996) : q752Item2p10,
	 ITU-T Rec. Q.752 (1997) : Table 1/Q.752 2.10, 2.11,
	 ANSI T1.116.1 Table 1/T1.116.1 2.10, 2.11"
    ::= { mtpProbableCauses 210 }

q752Item2p16 OBJECT IDENTIFIER ::= { mtpProbableCauses 216 }

localInhibition OBJECT-IDENTITY
    STATUS current
    DESCRIPTION
	"ProbableCause.  This object identity is used with probableCause 
	 in the ss7OnOccEvent or communicationsAlarm notification.  It 
	 is used for notification of the start or stop of local 
	 inhibition in accordance with Table 2/Q.752 or Table 2/T1.116.2 
	 2.16 (Start of local inhibition) or 2.17 (Stop of local 
	 inhibition).
	 
	 comunicationsAlarm notifications that use this object identity 
	 as a probableCause will populate the objectInstance with the 
	 identity of the signalling link which has entered or exited 
	 local inhibition, in accordance with the objectInstance textual 
	 convention.
	 
	  - When used to indicate start of local inhibition, 
	    perceivedSeverity will have values warning(1), minor(2), 
	    major(3) or critical(4).  In this case, the notification 
	    corresponds to Table 2/Q.752 2.16 or Table 2/T1.116.2 2.16 
	    (Start of local inhibition).
	 
	  - When used to indicate stop of local inhibition, 
	    perceivedSeverity will have the value cleared(5).  In this 
	    case, the notification corresponds to Table 2/Q.752 2.17 or 
	    Table 2/T1.116.2 2.17 (Stop of local inhibition).
	 
	 For start or stop of local inhibition notifications, the 
	 specificProblems parameter is not expected to be present.
	 
	 For start of local inhibition notifications, the 
	 perceivedSeverity included in the notification is warning(1), 
	 minor(2), major(3) or critical(4).  The inhibition of a 
	 signalling link will be removed automatically in the event a 
	 requirement to use the signalling link and the the event is 
	 considered a warning level event.  The unmapped value for 
	 perceivedSeverity will be warning(1)."
    REFERENCE
	"ITU-T Rec. Q.751.1 (1996) : q752Item2p16"
    ::= { mtpProbableCauses 216 }

q752Item2p18 OBJECT IDENTIFIER ::= { mtpProbableCauses 218 }

remoteInhibition OBJECT-IDENTITY
    STATUS current
    DESCRIPTION
	"ProbableCause.  This object identity is used with probableCause 
	 in the ss7OnOccEvent or communicationsAlarm notification.  It 
	 is used for notification of the start or stop of remote 
	 inhibitition in accordance with Table 2/Q.752 2.18 (Start of 
	 remote inhibition) and 2.19 (Stop of remote inhibition).
	 
	 communicationsAlarm notifications that use this object identity 
	 as a probableCause will populate the objectInstance with the 
	 identity of the signalling link which has entered or exited 
	 remote inhibition, in accordance with the objectInstance 
	 textual convention.
	 
	  - When used to indicate start of remote inhibition, 
	    perceivedSeverity will have values warning(1), minor(2), 
	    major(3) or critical(4).  In this case, the notification 
	    corresponds to Table 2/Q.752 2.18 or Table 2/T1.116.2 2.18 
	    (Start of remote inhibition).
	 
	  - When used to indicate stop of remote inhibition, 
	    perceivedSeverity will have the value cleared(5).  In this 
	    case, the notification corresponds to Table 2/Q.752 2.19 or 
	    Table 2/T1.116.2 2.19 (Stop of remote inhibition).
	 
	 For start or stop of remote inhibition notifications, the 
	 specificProblems parameter is not expected to be present.
	 
	 For start of remote inhibition notifications, the 
	 perceivedSeverity included in the message is warning(1), 
	 minor(2), major(3) or critical(4).  The inhibition of a 
	 signalling link will be removed automatically in the event of a 
	 requirement to use the signalling link and the event is 
	 considered a warning level event.  The unmapped value for 
	 perceivedSeverity will be warning(1)."
    REFERENCE
	"ITU-T Rec. Q.751.1 (1996) : q752Item2p18"
    ::= { mtpProbableCauses 218 }

q752Item3p06 OBJECT IDENTIFIER ::= { mtpProbableCauses 306 }

linkCongestionIndications OBJECT-IDENTITY
    STATUS current
    DESCRIPTION
	"ProbableCause.  This object identity is used with probableCause 
	 in the ss7OnOccEvent or communicationsAlarm notification.  It 
	 is used for notification of signalling link congestion 
	 indications in accordance with Table 3/Q.752 and Table 
	 3/T1.116.2 3.6 (SL congestion indications).
	 
	 communicationsAlarm notifications that use this object identity 
	 as a proabableCause will populate the objectInstance with the 
	 identity of the signalling link which has experienced onset, 
	 discard or abatement of a congesetion level.  In addition, it 
	 will contain the congestionStatus parameter indicating the 
	 level of congestion which has reached the onset threshold or 
	 which has abated.
	 
	  - When used to indicate onset of congestion at level N, 
	    perceivedSeverity will have values warning(1), minor(2), 
	    major(3) or critical(4).  In this case, the notification 
	    corresponds to Table 3/Q.752 or Table 3/T1.116.2 3.6 (SL 
	    congestion indications).
	 
	  - When used to indicate abatement of congestion at level N, 
	    perceivedSeverity will have the value cleared(5).
	 
	 For onset indications at congestion level 0, the perceived 
	 Severity wil have an unmapped value of minor(2).  For onset 
	 indications at congestion level 1 and 2, the perceivedSeverity 
	 will have an unmapped value of major(3).  Abatement at each 
	 congestion level will have the perceivedSeverity value of 
	 cleared(5).
	 
	 This probableCause, therefore, represents three alarm 
	 conditions and three alarm clearing conditions, onset and 
	 abatement for each congestion level."
    REFERENCE
	"ITU-T Rec. Q.751.1 (1996) : q752Item3p06,
	 ANSI T1.116.2/2000 : q752Item3p06"
    ::= { mtpProbableCauses 306 }

q752Item3p11 OBJECT IDENTIFIER ::= { mtpProbableCauses 311 }

linkCongestionDiscard OBJECT-IDENTITY
    STATUS current
    DESCRIPTION
	"ProbableCause.  This object identity is used with probableCause 
	 in the ss7OnOccEvent or communicationsAlarm notification.  It 
	 is used for notification of signalling link congestion 
	 resulting in the discard of MSUs in accordance with Table 
	 3/Q.752 and Table 3/T1.116.2 3.11 (Number of congestion events 
	 resulting in loss of MSUs).
	 
	 communicationsAlarm notifications that use this object identity 
	 as a probableCause will populate the objectInstance with the 
	 identity of the signalling link which has experienced discard 
	 or abatement of a congestion level.  In addition, it will 
	 contain the congestionStatus parameter indicating the level of 
	 congestion which has reached the discard threshold or which has 
	 abated.
	 
	  - When used to indicate discard congestion at level N, 
	    perceivedSeverity will have values warning(1), minor(2), 
	    major(3) or critical(4).  In this case, the notification 
	    corresponds to Table 3/Q.752 or Table 3/T1.116.2 3.11 
	    (Number of congestion events resulting in loss of MSUs).
	 
	  - When used to indicate abatement of congestion at level N, 
	    perceivedSeverity will have the value cleared(5).
	 
	 For discard indications at congestion level 0 and above, the 
	 perceivedSeverity will have an unmapped value of major(3).  
	 Abatement at each congestion level will have the 
	 perceivedSeverity value of cleared(5).
	 
	 This probableCause, therefore, represents three alarm 
	 conditions and three alarm clearing conditions, discard and 
	 abatement for each congestion level."
    REFERENCE
	"ITU-T Rec. Q.751.1 (1996) : q752Item3p11,
	 ANSI T1.116.2/2000 : q752Item3p11"
    ::= { mtpProbableCauses 311 }

q752Item4p03 OBJECT IDENTIFIER ::= { mtpProbableCauses 403 }

linkSetFailure OBJECT-IDENTITY
    STATUS current
    DESCRIPTION
	"ProbableCause.  This object identity is used with 
	 probableCause.  A PerceivedSeverity=Maj/Min/War represents 
	 Table 4, Item 4.3, PerceivedSeverity=Cleared represents Table 
	 4, Item 4.4.
	 
	 This object identity is used with probableCause in the 
	 ss7OnOccEvent or communicationsAlarm notification.  It is used 
	 for notification of the start or stop of link set failure for a 
	 link set in accordance with Table 4/Q.752 or Table 4/T1.116.2 
	 4.3 (Start of link set failure) and 4.4 (Stop of link set 
	 failure).
	 
	 communicationsAlarm notifications that use this object identity 
	 as a probableCause will populate the objectInstance with the 
	 identity of the signalling link set (direct link set) which has 
	 experienced or recovered from the failure condition in 
	 accordance with the objectInstance textual convention.
	 
	  - When used to indicate link set failure, perceivedSeverity 
	    will have the values warning(1), minor(2), major(3) or 
	    critical(4).  In this case, the notification corresponds to 
	    Table 4/Q.752 4.3 or Table 4/T1.116.1 4.3 (Start of link set 
	    failure).
	 
	  - When used to indicate link set recovery, perceivedSeverity 
	    will have the value cleared(5).  In this case, the 
	    notification corresponds to Table 4/Q.752 4.4 or Table 
	    4/T1.116.1 4.4 (Stop of link set failure).
	 
	 For start of link set failure and stop of link set failure, the 
	 specificProblems parameter is not expected to be present in the 
	 ss7OnOccEvent notification.
	 
	 For start of link set failure indications, the 
	 perceivedSeverity included in the message is warning(1), 
	 minor(2), major(3) or critical(4).  The blockage of a 
	 signalling link set is considered a major event and the 
	 unmapped value of the perceivedSeverity associated with alarm 
	 notifications will be major(3)."
    REFERENCE
	"ITU-T Rec. Q.751.1 (1996) : q752Item4p03"
    ::= { mtpProbableCauses 403 }

q752Item4p05 OBJECT IDENTIFIER ::= { mtpProbableCauses 405 }

linkSetFailureTFPBroadcast OBJECT-IDENTITY
    STATUS current
    DESCRIPTION
	"ProbableCause.  This object identity is used with 
	 probableCause.  A PerceivedSeverity=Maj/Min/War represents 
	 Table 4, Item 4.5, PerceivedSeverity=Cleared represents Table 
	 4, Item 4.6.
	 
	 This object identity is used with probableCause in the 
	 ss7OnOccEvent or communicationsAlarm notification.  It is used 
	 for notification of the initiation of broadcast of TFP or TFA 
	 due to failure or recovery of a measured link set in accordance 
	 with Table 4/Q.752 4.5 (Init. Of Broadcast TFP due to failure 
	 of measured link set) and 4.6 (Init. of Broadcast TFA for 
	 recovery of a measured link set).
	 
	 communicationsAlarm notifications that use this object 
	 indentity as a probableCause will populate the objectInstance 
	 with the identity of the signalling link set (direct link set) 
	 which has initiated broadcast in accordance with the 
	 objectInstance textual convention.
	 
	  - When used to indicate the initiation of broadcast TFP due to 
	    failure of a measured link set, perceivedSeverity will have 
	    the values warning(1), minor(2), major(3) or critical(4).  
	    In this case, the notification corresponds to Table 4/Q.752 
	    4.5 (Init.  of Broadcast TFP due to failure of a measured 
	    link set).
	 
	  - When used to indicate the initiation of broadcast TFA due to 
	    recovery of a measured link set, perceivedSeverity will have 
	    the value cleared(5).  In this case, the notification 
	    corresponds to Table 4/Q.752 4.6 (Init. of Broadcast TFA due 
	    to failure of a measured link set).
	 
	 For initiation of broadcast TFP or TFA, the specificProblems 
	 parameter is not expecte to be present in the ss7OnOccEvent 
	 notification.  For both, the present of the objectInstance 
	 parameter identifying the failed link set is required.
	 
	 For initiation of broadcast TFP due to failure of a measured 
	 link set, the perceivedSeverity is warning(1), minor(2), 
	 major(3) or critical(4).  THe broadcast of TFP due to failure 
	 of a meassured link set is considered a major event."
    REFERENCE
	"ITU-T Rec. Q.751.1 (1996) : q752Item4p05"
    ::= { mtpProbableCauses 405 }

q752Item4p11 OBJECT IDENTIFIER ::= { mtpProbableCauses 411 }

routesetUnavailability OBJECT-IDENTITY
    STATUS current
    DESCRIPTION
	"ProbableCause.  This object identity is used with probableCause 
	 in the ss7OnOccEvent or communicationsAlarm notification.  It 
	 is use for notification of the start or stop of unavailability 
	 of a route set to a given destination or destinationss in 
	 accordance with Table 4/Q.752 4.11 (Start of unavailability of 
	 route set to a given destination or set of destinations) and 
	 4.12 (Stop of unavailability of route set to a given 
	 desintation or set of destinations).
	 
	 communicationsAlarm notifications that use this object identity 
	 as a probableCause will populate the objectInstance with the 
	 identity of the signalling route set (destination) which has 
	 become unavailable or available in accordance with the 
	 objectInstance textual convention.
	 
	  - When used to indicate the start of unavailability of a route 
	    set to a given destination or set of destinations, 
	    perceivedSeverity will has the values warning(1), minor(2), 
	    major(3) or critical(4).  In this case, the notification 
	    corresponds to Table 4/Q.752 4.11 (Start of unavailability 
	    of route set to a given destination or set of destinations).
	 
	  - When used to indicate the stop of unavailability of a route 
	    set to a given destination or set of destinations, 
	    perceivedSeverity will have the value cleared(5).  In this 
	    case, the notification corresponds to Table 4/Q.752 4.12 
	    (Stop of unavailability of route set to a given destination 
	    or set of destinations).
	 
	 For start or stop of unavailablity of a route set to a 
	 destination or destinations, the specificProblems parameter is 
	 not expected to be preseent in the ss7OnOccEvent notification.  
	 For both, the presence of the objectInstance parameter 
	 identifying the failed routeset is required.
	 
	 For start of unavailability of a route set to a destination or 
	 set of destinations, the perceivedSeverity is warning(1), 
	 minor(2), major(3) or critical(4).  The start of unavailabiltiy 
	 of a route set to a destination considered a major event; to a 
	 set of destinations (i.e. a cluster), is considered a critical 
	 event."
    REFERENCE
	"ITU-T Rec. Q.751.1 (1996) : q752Item4p11"
    ::= { mtpProbableCauses 411 }

q752Item4p13 OBJECT IDENTIFIER ::= { mtpProbableCauses 413 }

linksetAdjSpChange OBJECT-IDENTITY
    STATUS current
    DESCRIPTION
	"ProbableCause.  This object identity is used with probableCause 
	 in the ss7OnOccEvent or communicationsAlarm notification.  It 
	 is used for notification of the change in link set used to an 
	 adjacent SP, in accordance with Table 4/Q.752 4.13 (Change in 
	 link set used to adjacent SP).
	 
	 communicationsAlarm notifications that use this object identity 
	 as a probableCause will populate the objectInstance with the 
	 identity of the signalling route set (adjacent destination) 
	 which has changed link set used and will include a second 
	 occurence of the objectInstance providing the identity of the 
	 link set currently used to the adjacent signalling point, both 
	 in accordance to the objectInstance textual convention.
	 
	  - When used to indicate the start of use of an alternate 
	    (non-direct link set) to an adjacent signalling point code, 
	    the perceivedSeverity will have the values warning(1), 
	    minor(2), major(3) and critical(4).  In this case, the 
	    notification corresponds to Table 4/Q.752 4.13 (Change in 
	    link set used to adjacent SP).
	 
	  - When used to indicate the start of use of the normal (direct 
	    link set) to an adjacent signalling point code, the 
	    perceivedSeverity will have the value cleared(5).  In this 
	    case, the notification corresponds to Table 4/Q.752 4.13 
	    (Change in link set used to adjacent SP).
	 
	 For change of use of link set to an ajacent SP, the 
	 specificProblems parameter is not expected to be present in the 
	 ss7OnOccEvent notification.  For this event, the presenCe of 
	 the objectInstance parameter identifying the affected route set 
	 and the current link set is required.
	 
	 For change of use of link set to an adjacent SP from a direct 
	 link set to a non-direct link set, the peceivedSeverity is 
	 warning(1), minor(2), major(3) or critical(4).  The change from 
	 a direct link set to an indirect link set can be considered a 
	 major event."
    REFERENCE
	"ITU-T Rec. Q.751.1 (1996) : q752Item4p13"
    ::= { mtpProbableCauses 413 }

q752Item5p01 OBJECT IDENTIFIER ::= { mtpProbableCauses 501 }

adjSpInaccessibility OBJECT-IDENTITY
    STATUS current
    DESCRIPTION
	"ProbableCause.  This object identity is used with probableCause 
	 in the ss7OnOccEvent or or communicationsAlarm notification.  
	 It is used for notification of the inaccessibility or 
	 accessibility of an adjacent signalling point in accordance 
	 with Table 5/Q.752 or T1.116.2 5.1 (Adjacent SP inaccessible).
	 
	 communicationsAlarm notifications that use this object identity 
	 as a probableCause will populate the objectInstance with the 
	 identity of the signalling route set (adjacent destination) 
	 which has become inaccesible or accessbile in accordance with 
	 the ObjectInstance textual convention.
	 
	  - When used to indicate the inaccessibility of an adjacent 
	    signalling point, the perceivedSeverity will have the value 
	    warning(1), minor(2), major(3) or critical(4).  In this 
	    case, the notification corresponds to Table 5/Q.752 or 
	    T1.116.2 5.1 (Adjacent SP inaccessible).
	 
	  - When used to indicate the accessibility of an adjacent 
	    signalling point, the perceivedSeverity will have the value 
	    cleared(5).  In this case, the notification corresponds to 
	    Table 5/Q.752 or T1.116.2 5.4 (Stop of adjacent SP 
	    inaccessible).
	 
	 For inaccessibility or accessibility of an adjacent SP, the 
	 specificProblems parameter is not expected to be present in the 
	 notification.
	 
	 For inaccessibility of an adjacent signalling point, the 
	 initial unmapped value of the perceivedSeverity will be 
	 major(3)."
    REFERENCE
	"ITU-T Rec. Q.751.1 (1996) : q752Item5p01"
    ::= { mtpProbableCauses 501 }

q752Item5p05 OBJECT IDENTIFIER ::= { mtpProbableCauses 505 }

routingDataError OBJECT-IDENTITY
    STATUS current
    DESCRIPTION
	"ProbableCause.  This object identity is used with probableCause 
	 in the ss7OnOccEvent or communicationsAlarm notification.  It 
	 is used to indicate MSUs discarded due to a routing data error 
	 in accordance with Table 5/Q.752 or T1.116.2 5.5 (MSUs 
	 discarded due to a routing data error).  This is a first and 
	 delta notification.
	 
	 commnunicationsAlarm notifications that use this object 
	 identity as a probableCause will populate the objectInstance 
	 with the identity of the signalling point receiving the MSU in 
	 accordance with the ObjectInstance textual convention.  In 
	 addition, the two NetworkPointCode parameters will be populated 
	 indicating the source and destination of the MSU.  The MSU 
	 itself should populate an additionalText and 
	 additionalInformation parameter.
	 
	  - When used to indicate a discarded MSU, which is a first and 
	    delta notification, the perceivedSeverity will be 
	    warning(1), minor(2), major(3) or critical(4).  This 
	    corresponds to Table 5/Q.752 or T1.116.2 5.5 (MSUs discarded 
	    due to a routing data error).
	 
	  - When used to indicate a period in which no additional 
	    indication was received, the perceivedSeverity will have the 
	    value cleared(5).
	 
	 For routing data error MSUs discarded, the intial unmapped 
	 value of the perceivedSeverity will be major(3).
	 
	 Note that it might be necessary to also raise an 
	 operationalViolation security alarm as this normally occurs 
	 when an operator is trying to probe the routing and screening 
	 tables of another operator's STP."
    REFERENCE
	"ITU-T Rec. Q.751.1 (1996) : q752Item5p05"
    ::= { mtpProbableCauses 505 }

q752Item5p06 OBJECT IDENTIFIER ::= { mtpProbableCauses 506 }

userPartUnavailableSent OBJECT-IDENTITY
    STATUS current
    DESCRIPTION
	"ProbableCause.  This object identity is used with probableCause 
	 in the ss7OnOccEvent or communicationsAlarm notification.  It 
	 is used to indicate the transmission of a user part unavailable 
	 message in accordance with Table 5/Q.752 or T1.116.2 5.6 (User 
	 Part Unavailable MSU transmitted).  This is a first and delta 
	 notification.
	 
	 communicationsAlarm notifications that use this object identity 
	 as a probableCause will populate the objectInstance with the 
	 identity of the signalling point transmitting the UPU in 
	 accordance with the ObjectInstance textual convention.  In 
	 addition, one networkPointCode parameter will be populated 
	 indicating the source of the MSU that triggered the sending of 
	 the UPU.  One userPart parameter will be populated indicating 
	 the user part for which the UPU was sent and the status of the 
	 user part reported.  The additionalText and 
	 additionalInformation parameters will be populated with the MSU 
	 that triggered the UPU to be sent.
	 
	  - When used to indicate a sent UPU, which is a first and delta 
	    notification, the perceivedSeverity will be warning(1), 
	    minor(2), major(3) or critical(4).  This corresponds to 
	    Table 5/Q.752 or T1.116.2 5.6 (User Part Unavailable MSU 
	    transmitted).
	 
	  - When used to indicate a period in which no additional 
	    indication was received for the indicated user part, the 
	    perceivedSeverity will have the value cleared(5).
	 
	 For transmission of UPU that have the inaccessible indication, 
	 the initial unmapped perceivedSeverity will be minor(2).  For 
	 transmission of UPU that have the unequipped indication, the 
	 intial unmapped perceivedSeverity will be major(3).
	 
	 Note that it might also be necessary to raise an 
	 operationalViolation security alarm as this normally occurs 
	 when an operator is trying to probe the routing and screening 
	 tables of another operator's STP or SEP."
    REFERENCE
	"ITU-T Rec. Q.751.1 (1996) : q752Item5p06"
    ::= { mtpProbableCauses 506 }

q752Item5p07 OBJECT IDENTIFIER ::= { mtpProbableCauses 507 }

userPartUnavailableReceived OBJECT-IDENTITY
    STATUS current
    DESCRIPTION
	"ProbableCause.  This object identity is used with probableCause 
	 in the ss7OnOccEvent or communicationsAlaram notification.  It 
	 is used to indicate the reception of a user part unavailable 
	 message in accordance with Table 5/Q.752 or T1.116.2 5.7 (User 
	 Part Unavailable received).  This is a first and delta 
	 notification.
	 
	 communicationsAlarm notifications that use this object identity 
	 as a probableCause will populate the objectInstance with the 
	 identity of the signalling point receiving the UPU in 
	 accordance with the ObjectInstance textual convention.  In 
	 addition, one networkPointCode parameter will be populated 
	 indicating the source of the UPU.  One userPart parameter will 
	 be populated indicating the user part for which the UPU was 
	 sent and the status of the user part reported.
	 
	  - When used to indicate a received UPU, which is a first and 
	    delta notification, the perceivedSeverity will be 
	    warning(1), minor(2), major(3) or critical(4).  This 
	    corresponds to Table 5/Q.752 or T1.116.2 (User Part 
	    Unavailable MSU received).
	 
	  - When used to indicate a period in which no additional 
	    indication was received for the indicated user part, the 
	    perceivedSeverity will have the value cleared(5).
	 
	 For reception of UPU that have the inaccessible indication, the 
	 initial unmapped value perceivedSeverity will be minor(2).  For 
	 reception of UPU that have the unequipped indication, the 
	 intiial unmapped perceivedSeverity will be major(3)."
    REFERENCE
	"ITU-T Rec. Q.751.1 (1996) : q752Item5p07"
    ::= { mtpProbableCauses 507 }

q752Item5p08 OBJECT IDENTIFIER ::= { mtpProbableCauses 508 }

transferControlledReceived OBJECT-IDENTITY
    STATUS current
    DESCRIPTION
	"ProbableCause.  This object identity is used with probableCause 
	 in the ss7OnOccEvent or communicationsAlarm notification.  It 
	 is used to indicate the reception of a transfer controlled 
	 message in accordance with Table 5/Q.752 or T1.116.2 5.8 (TFC 
	 received).  This is a first and delta notification.
	 
	 communicationsAlarm notifications that use this object identity 
	 as a probableCause will populate the objectInstance with the 
	 identity of the signalling point receiving the TFC in 
	 accordance with the ObjectInstance textual convention.  In 
	 addition, one networkPointCode parameter will be populated 
	 indicating the source of the TFC.  One congestionStatus 
	 parameter wll be populated indicating the congestion level of 
	 the message.
	 
	  - When used to indicate reception of a TFC, which is a first 
	    and delta notification, the perceivedSeverity will be 
	    warning(1), minor(2), major(3) or critical(4).  This 
	    corresponds to Table 5/Q.752 or T1.116.2 5.8 (TFC received).
	 
	  - When used to indicate a period in which no additional 
	    indication was received for the indicated point code and 
	    congestion level, the perceivedSeverity will have the value 
	    cleared(5).
	 
	 For reception of TFC that indicate congestion level 0, the 
	 initial unmapped perceivedSeverity will be minor(2).  For 
	 reception of TFC at a higher level, the initial unmapped 
	 perceivedSeverity will be major(3)."
    REFERENCE
	"ITU-T Rec. Q.751.1 (1996) : q752Item5p08"
    ::= { mtpProbableCauses 508 }

-- ====================================================================
-- NOTIFICATIONS
-- ====================================================================
-- Most of the notifications defined here are for reporting first and 
-- occurrence or on-occurrence events for Q.752 usage reporting and 
-- performance monitoring.  Some of these notifications overlap with 
-- communications alarms.

-- Notification objects (scalars) for use in notifications.

-- The TMN (Q.751.1) way of providing on-occurrence events from Q.752 
-- notifications is to provide a special ss7OnOccEvent notification 
-- which performs double duty as a communicationsAlarm (that is, it 
-- contains the same information as a communications alarm).  That 
-- approach is duplicated here to limit the number of unique 
-- notifications necessary to represent all of the events to one, which 
-- also provides alarms.

-- ITU-T Rec. Q.751.1 mtpSpecificExtensions
-- mtpSpecificExtensions OBJECT IDENTIFIER
--     ::= { mtpMIB 3 }
--    ::= { ccitt(0) recommendation(0) q(17) omap(751) mtp(1) 
--    informationModel(0) specificExtensions(0) }

mtpRestarting NOTIFICATION-TYPE
    OBJECTS {
	tmnObjectInstance, 
	mtpSpPointCode 
    }
    STATUS current
    DESCRIPTION
	""
    ::= { mtpNotifications 1 }

ss7OnOccEvent NOTIFICATION-TYPE
    OBJECTS {
	tmnObjectInstance, 
	tmnProbableCause, 
	tmnPerceivedSeverity 
    }
    STATUS current
    DESCRIPTION
	"This notification is used to report the Q.752 on-occurrence 
	 measurement results and other MTP events, which are not 
	 reported as a communication alarm.
	 
	 This notification is sent when an SS7 on-occurence event (as 
	 defined by cited references) transpires.  These event 
	 notifications represent both usage and performance measurement 
	 conditions, as well as alarm indications.  The form of the 
	 notification takes the same general form as a 
	 communicationsAlarm notification and should contain similar 
	 pertinent information.
	 
	 tmnObjectInstance is a pointer to an object instance using the 
	 RowPointer textual convention that identifies the primary 
	 object responsible for generation of the event.  This may be a 
	 signalling link, a direct link set, a route set or a signalling 
	 point as defined by the probable cause values for this 
	 notification."
    REFERENCE
	"ITU-T Rec. Q.751.1, ANSI T1.116.1"
    ::= { mtpNotifications 2 }

sdlEventLostSync NOTIFICATION-TYPE
    OBJECTS { tmnObjectInstance }
    STATUS current
    DESCRIPTION
	"This notification is sent when a frame-based interface 
	 (channel) group loses frame synchronization on the line."
    ::= { mtpNotifications 3 }

sdlEventSuError NOTIFICATION-TYPE
    OBJECTS { tmnObjectInstance }
    STATUS current
    DESCRIPTION
	"This notification is sent when a frame-based interface 
	 (channel) group receices an SU in Error."
    ::= { mtpNotifications 4 }

sdlEventTxFail NOTIFICATION-TYPE
    OBJECTS { tmnObjectInstance }
    STATUS current
    DESCRIPTION
	"This notification is sent when the transmit section of the 
	 interface fails."
    ::= { mtpNotifications 5 }

sdlEventRxFail NOTIFICATION-TYPE
    OBJECTS { tmnObjectInstance }
    STATUS current
    DESCRIPTION
	"This notification is sent when the receive section of the 
	 interface fails."
    ::= { mtpNotifications 6 }

sdtEventLostSync NOTIFICATION-TYPE
    OBJECTS { tmnObjectInstance }
    STATUS current
    DESCRIPTION
	"This notification is sent when the signalling terminal loses 
	 HLDC framing in the channel and the terminal enters octet 
	 counting mode and hunts for flags."
    ::= { mtpNotifications 7 }

sdtEventSuError NOTIFICATION-TYPE
    OBJECTS { tmnObjectInstance }
    STATUS current
    DESCRIPTION
	"This notification is sent when a singal unit is received in 
	 error."
    ::= { mtpNotifications 8 }

sdtEventTxFail NOTIFICATION-TYPE
    OBJECTS { tmnObjectInstance }
    STATUS current
    DESCRIPTION
	"This notification is sent if the transmitters fail and the 
	 management agent detects the failure."
    ::= { mtpNotifications 9 }

sdtEventRxFail NOTIFICATION-TYPE
    OBJECTS { tmnObjectInstance }
    STATUS current
    DESCRIPTION
	"This notification is sent if the receivers fail and the 
	 management agent detects the failure."
    ::= { mtpNotifications 10 }

sdtEventCarrier NOTIFICATION-TYPE
    OBJECTS { tmnObjectInstance }
    STATUS current
    DESCRIPTION
	"This notification is sent if group carrier is lost and the 
	 management agent detects the loss of carrier."
    ::= { mtpNotifications 11 }

slEventFailureAllReasons NOTIFICATION-TYPE
    OBJECTS { tmnObjectInstance }
    STATUS current
    DESCRIPTION
	"This notification is issued on occurrence of link failure for 
	 any reason."
    REFERENCE
	"ITU-T Rec. Q.752/ANSI T1.116 Table 2/1.2"
    ::= { mtpNotifications 12 }

slEventFailureAbnormalBsnrFibr NOTIFICATION-TYPE
    OBJECTS { tmnObjectInstance }
    STATUS current
    DESCRIPTION
	"This notification is issued on occurence of link failure due to 
	 abonormal BSNR or link failure due to abnormal FIBR.
	 
	 This notification indicates complex failure in transmission or 
	 an intermittent hardware fault or even a design error."
    REFERENCE
	"ITU-T Rec. Q.752/ANSI T1.116 Table 2/1.3"
    ::= { mtpNotifications 13 }

slEventFailureExcessiveDelayOfAck NOTIFICATION-TYPE
    OBJECTS { tmnObjectInstance }
    STATUS current
    DESCRIPTION
	"This notification is issued on occurence of link failure dues 
	 to excessive delay of acknowledgement (i.e. Timer T7 expiry).
	 
	 May indicate serious disturbance or an interruption of the 
	 signalling data link (SDL)."
    REFERENCE
	"ITU-T Rec. Q.752/ANSI T1.116 Table 2/1.4"
    ::= { mtpNotifications 14 }

slEventFailureExcessiveErrorRate NOTIFICATION-TYPE
    OBJECTS { tmnObjectInstance }
    STATUS current
    DESCRIPTION
	"Indicates a noisy link."
    REFERENCE
	"ITU-T Rec. Q.752/ANSI T1.116 Table 2/1.5"
    ::= { mtpNotifications 15 }

slEventFailureExcessiveDurationCongestion NOTIFICATION-TYPE
    OBJECTS { tmnObjectInstance }
    STATUS current
    DESCRIPTION
	"Failure due to excessive duration of congestion is when the 
	 signalling link fails to to T6 expiry while receiving SIB from 
	 the far side.  This means that the far end is experiencing 
	 receive congestion and that it has waited too long to 
	 acknowledge even while running T6.  This may indicate serious 
	 congestion problems at the remote end of the signalling link."
    REFERENCE
	"ITU-T Rec. Q.752/ANSI T1.116 Table 2/1.6"
    ::= { mtpNotifications 16 }

slEventLocalAutomaticChangeover NOTIFICATION-TYPE
    OBJECTS { tmnObjectInstance }
    STATUS current
    DESCRIPTION
	"This measurment can be deduced from 1.2 and 1.12."
    REFERENCE
	"ITU-T Rec. Q.752/ANSI T1.116 Table 2/1.10"
    ::= { mtpNotifications 17 }

slEventLocalAutomaticChangeback NOTIFICATION-TYPE
    OBJECTS { tmnObjectInstance }
    STATUS current
    DESCRIPTION
	"This measurment can be deduced from 1.2 and 1.12."
    REFERENCE
	"ITU-T Rec. Q.752/ANSI T1.116 Table 2/1.11"
    ::= { mtpNotifications 18 }

slEventRestoration NOTIFICATION-TYPE
    OBJECTS { tmnObjectInstance }
    STATUS current
    DESCRIPTION
	""
    REFERENCE
	"ITU-T Rec. Q.752/ANSI T1.116 Table 2/1.12"
    ::= { mtpNotifications 19 }

slEventRpoStartEvent NOTIFICATION-TYPE
    OBJECTS { tmnObjectInstance }
    STATUS current
    DESCRIPTION
	"This notification is issued whenever a signalling link enters 
	 remote processor outage.  The parameters are the signalling 
	 link index and its name.
	 
	 This and 2.11 indicate a problem and its cessation at the other 
	 end of the link, this problem could be one between level 2 and 
	 3."
    REFERENCE
	"ITU-T Rec. Q.752/ANSI T1.116 Table 2/2.10"
    ::= { mtpNotifications 20 }

slEventRpoStopEvent NOTIFICATION-TYPE
    OBJECTS { tmnObjectInstance }
    STATUS current
    DESCRIPTION
	"This notification is issued whenever a signalling link leaves 
	 remote processor outage.  The parameters are the signalling 
	 link index and its name.
	 
	 This and 2.10 indicate a problem and its cessation at the other 
	 end of the link, this problem could be one between level 2 and 
	 3."
    REFERENCE
	"ITU-T Rec. Q.752/ANSI T1.116 Table 2/2.11"
    ::= { mtpNotifications 21 }

slEventLocalInhibitionStart NOTIFICATION-TYPE
    OBJECTS { tmnObjectInstance }
    STATUS current
    DESCRIPTION
	"This notification is issued whenever a signalling link becomes 
	 locally inhibited.  The parameters are the signalling link 
	 index and its name."
    REFERENCE
	"ITU-T Rec. Q.752/ANSI T1.116 Table 2/2.16"
    ::= { mtpNotifications 22 }

slEventLocalInhibitionStop NOTIFICATION-TYPE
    OBJECTS { tmnObjectInstance }
    STATUS current
    DESCRIPTION
	""
    REFERENCE
	"ITU-T Rec. Q.752/ANSI T1.116 Table 2/2.17"
    ::= { mtpNotifications 23 }

slEventRemoteInhibitionStart NOTIFICATION-TYPE
    OBJECTS { tmnObjectInstance }
    STATUS current
    DESCRIPTION
	""
    REFERENCE
	"ITU-T Rec. Q.752/ANSI T1.116 Table 2/2.18"
    ::= { mtpNotifications 24 }

slEventRemoteInhibitionStop NOTIFICATION-TYPE
    OBJECTS { tmnObjectInstance }
    STATUS current
    DESCRIPTION
	""
    REFERENCE
	"ITU-T Rec. Q.752/ANSI T1.116 Table 2/2.19"
    ::= { mtpNotifications 25 }

slEventCongestionStart NOTIFICATION-TYPE
    OBJECTS { tmnObjectInstance }
    STATUS current
    DESCRIPTION
	"The nuber of signalling link congestion indications, first and 
	 delta.
	 
	 The signalling link congestion refers to link status congested 
	 at level 3.  A link is marked at level 3 as congested when a 
	 congestion threshold is reacehd at the transmit side (see 
	 3.6/T1.111.4 on Signalling Newtork Congestion cluase 11 on 
	 Signalling Traffic Flow Control).  Measurements should be kept 
	 for thresholds 1, 2, and 3 separately if that national option 
	 is selected.  NOTE - The reporting of this item on occurrent 
	 should be considered carefully, since there might be many 
	 events in a short interval.  This might occur for example if 
	 the congestion onset and abatement thresholds were close 
	 together, or if the transmission/retransmission buffer size 
	 were significantly greater than the reception buffer at the 
	 other end of the link, and congestion occurred."
    REFERENCE
	"ITU-T Rec. Q.752/ANSI T1.116 Table 2/3.6"
    ::= { mtpNotifications 26 }

slEventCongestionStop NOTIFICATION-TYPE
    OBJECTS { tmnObjectInstance }
    STATUS current
    DESCRIPTION
	"Stop of signalling link congestion (first and delta).
	 
	 The stop of signalling link congestion occurs for a link at 
	 level 3 when the buffer occupancy has dropped below the 
	 congestion abatement threshold.  If a number of thresholds is 
	 used, the event is marked separately for each threshold.  See 
	 also the Note to slCongestionStart above."
    REFERENCE
	"ITU-T Rec. Q.752/ANSI T1.116 Table 2/3.9"
    ::= { mtpNotifications 27 }

slEventCongestionLoss NOTIFICATION-TYPE
    OBJECTS { tmnObjectInstance }
    STATUS current
    DESCRIPTION
	"First and delta: the number of congestion events resulting in 
	 loss of MSUs."
    REFERENCE
	"ITU-T Rec. Q.752/ANSI T1.116 Table 2/3.11"
    ::= { mtpNotifications 28 }

lkEventFailureStart NOTIFICATION-TYPE
    OBJECTS { tmnObjectInstance }
    STATUS current
    DESCRIPTION
	"This notification is issued on occurrence.
	 
	 This is the notification of a link set failure.  A link set 
	 fails when the last link in the direct link set to the adjacent 
	 signalling point fails."
    REFERENCE
	"ITU-T Rec. Q.752/ANSI T1.116 Table 2/4.3"
    ::= { mtpNotifications 29 }

lkEventFailureStop NOTIFICATION-TYPE
    OBJECTS { tmnObjectInstance }
    STATUS current
    DESCRIPTION
	"This notification is issued on occurrence."
    REFERENCE
	"ITU-T Rec. Q.752/ANSI T1.116 Table 2/4.4"
    ::= { mtpNotifications 30 }

lkEventSendTFP NOTIFICATION-TYPE
    OBJECTS { tmnObjectInstance }
    STATUS current
    DESCRIPTION
	""
    REFERENCE
	"ITU-T Rec. Q.752/ANSI T1.116 Table 2/4.5"
    ::= { mtpNotifications 31 }

lkEventSendTFA NOTIFICATION-TYPE
    OBJECTS { tmnObjectInstance }
    STATUS current
    DESCRIPTION
	""
    REFERENCE
	"ITU-T Rec. Q.752/ANSI T1.116 Table 2/4.6"
    ::= { mtpNotifications 32 }

rsEventUnavailableStart NOTIFICATION-TYPE
    OBJECTS { tmnObjectInstance }
    STATUS current
    DESCRIPTION
	""
    REFERENCE
	"ITU-T Rec. Q.752/ANSI T1.116 Table 2/4.11"
    ::= { mtpNotifications 33 }

rsEventUnavailableStop NOTIFICATION-TYPE
    OBJECTS { tmnObjectInstance }
    STATUS current
    DESCRIPTION
	""
    REFERENCE
	"ITU-T Rec. Q.752/ANSI T1.116 Table 2/4.12"
    ::= { mtpNotifications 34 }

rsEventAdjSpLinkSetChange NOTIFICATION-TYPE
    OBJECTS { tmnObjectInstance }
    STATUS current
    DESCRIPTION
	"This is an ITU-T Rec. Q.752 occurence and is issued whenever 
	 the link set used to access an adjacent SP changes."
    REFERENCE
	"ITU-T Rec. Q.752 Table 2/4.13"
    ::= { mtpNotifications 35 }

rsEventAdjSPInaccessibleStart NOTIFICATION-TYPE
    OBJECTS { tmnObjectInstance }
    STATUS current
    DESCRIPTION
	""
    REFERENCE
	"ITU-T Rec. Q.752 Table 2/5.1"
    ::= { mtpNotifications 36 }

rsEventAdjSpInaccessibleStop NOTIFICATION-TYPE
    OBJECTS { tmnObjectInstance }
    STATUS current
    DESCRIPTION
	""
    REFERENCE
	"ITU-T Rec. Q.752 Table 2/5.4"
    ::= { mtpNotifications 37 }

rsEventRecvTFC NOTIFICATION-TYPE
    OBJECTS { tmnObjectInstance }
    STATUS current
    DESCRIPTION
	"Item 5.8, TFC received, indicates congestion in the route set 
	 towards the destination (see 3.8.4/Q.704, 11.2.3/Q.704, 
	 11.2.4/Q.704 and 11.2.5/Q.704).  for the national option of 
	 multiple levels of congestion, the congestion status is 
	 included."
    REFERENCE
	"ITU-T Rec. Q.752 Table 2/5.8"
    ::= { mtpNotifications 38 }

spEventMsuDiscard NOTIFICATION-TYPE
    OBJECTS { tmnObjectInstance }
    STATUS current
    DESCRIPTION
	"Measurement 5.5, the number of MSUs discarded due to routing 
	 data error, is obligatory, and could indicate a severe problem.  
	 It indicates incorrect routing or a data error.  It could be a 
	 reason to start the MTP Route Verification Test (MRVT), 
	 described in 
	 2.2/Q.753."
    REFERENCE
	"ITU-T Rec. Q.752 Table 2/5.5"
    ::= { mtpNotifications 39 }

spEventUpuSent NOTIFICATION-TYPE
    OBJECTS { tmnObjectInstance }
    STATUS current
    DESCRIPTION
	""
    REFERENCE
	"ITU-T Rec. Q.752 Table 2/5.6"
    ::= { mtpNotifications 40 }

spEventUpuRecv NOTIFICATION-TYPE
    OBJECTS { tmnObjectInstance }
    STATUS current
    DESCRIPTION
	""
    REFERENCE
	"ITU-T Rec. Q.752 Table 2/5.7"
    ::= { mtpNotifications 41 }

-- ====================================================================
-- MTP TABLES
-- ====================================================================

mtpSapTable OBJECT-TYPE
    SYNTAX SEQUENCE OF MtpSapEntry
    MAX-ACCESS not-accessible
    STATUS current
    DESCRIPTION
	"This is an MTP-SAP table that defines the MTP SAPs (users) that 
	 are available at a signalling point."
    REFERENCE
	"ITU-T Rec. Q.751.1 (1997), ANSI T1.116.1 (2000), mtpAccessPoint 
	 MOC."
    ::= { mtpSap 1 }

mtpSapEntry OBJECT-TYPE
    SYNTAX MtpSapEntry
    MAX-ACCESS not-accessible
    STATUS current
    DESCRIPTION
	"This is an MTP-SAP entry that defines the MTP-SAPs (users) that 
	 are available at a signalling point.
	 
	 The sap2Address attribute contains the address of the 
	 mtpAccessPoint. It contains the Signalling Point Code (SPC), 
	 Service Indicator (SI) and MTP Network Identity (NI).
	 
	 The sapId attribute is used in naming instances of the 
	 mtpAccessPoint managed object class.
	 
	 The userEntityNames attribute contains the distinguished names 
	 of the managed objects that represent the user entities that 
	 are using the mtpAccessPoint, e.g. the SCCP instance.
	 
	 The providerEntityNames attribute contains the distinguished 
	 names of the managed objects that represent the provider 
	 entities that are supporting the mtpAccessPoint, i.e. the 
	 instance of the MTP.
	 
	 A mtpAccessPoint can have the MTP status: allowed, this means 
	 that the mtpAccessPoint is accessible and is functioning 
	 normally; congested, this means that the mtpAccessPoint is 
	 accessible but the path to it is heavily loaded; prohibited, 
	 this means that the mtpAccessPoint not accessible.
	 
	 If the ss7OnOccEventPackage is present, event notifications 
	 with the following probable causes can apply: Probable Cause = 
	 001 (localUserPartUnavailable)"
    REFERENCE
	"ITU-T Rec. Q.751.1 (1997), ANSI T1.116.1 (2000), mtpAccessPoint 
	 MO."
    INDEX {
	mtpSapId
    }
    ::= { mtpSapTable 1 }

MtpSapEntry ::= SEQUENCE {
    mtpSapId					Unsigned32,
    mtpSap2Address				MtpSapAddress,
    mtpSapUserPart				MtpUserPart,
    mtpSapUserPartStatus			MtpUserPartStatus,
    mtpSapUserEntityNames			RowPointer,
    mtpSapProviderEntityNames			RowPointer,
    mtpSapUsageState				UsageState,
    mtpSapAsaProfilePointer			RowPointer,
    mtpSapName					SimpleNameType,
    mtpSapLongMessageSupported			TruthValue,
    mtpSapRowStatus				RowStatus
}

mtpSapId OBJECT-TYPE
    SYNTAX Unsigned32
    MAX-ACCESS not-accessible
    STATUS current
    DESCRIPTION
	"Provides an index into the MTP-SAP table.  Provides an index 
	 relative to the MTP level 3 index, of the MTP access point."
    REFERENCE
	"ITU-T Rec. Q.751.1 (1997), ANSI T1.116.1 (2000),
	 ITU-T Rec. X.723 | ISO/IEC 10165-5, sapId attibute."
    ::= { mtpSapEntry 1 }

mtpSap2Address OBJECT-TYPE
    SYNTAX Unsigned32
    MAX-ACCESS read-only
    STATUS current
    DESCRIPTION
	"Provides the cardinal number of SAP address components that 
	 exist for this MTP access point in the mtpSap2AddressTable side 
	 table.
	 
	 The sap2Address attribute contains the address of the 
	 mtpAccessPoint. It contains the Signalling Point Code (SPC), 
	 Service Indicator (SI) and MTP Network Identity (NI).
	 
	 Provides the MTP User Part (SI value) associated with this MTP 
	 user."
    REFERENCE
	"ITU-T Rec. Q.751.1 (1997), ANSI T1.116.1 (2000),
	 ITU-T Rec. X.723 | ISO/IEC 10165-5, sap2Address attibute."
    ::= { mtpSapEntry 2 }

mtpSapUserPart OBJECT-TYPE
    SYNTAX MtpUserPart
    MAX-ACCESS read-create
    STATUS current
    DESCRIPTION
	"Provides the cardinal number of SAP address components that 
	 exist for this MTP access point in the mtpSap2AddressTable side 
	 table.
	 
	 The sap2Address attribute contains the address of the 
	 mtpAccessPoint. It contains the Signalling Point Code (SPC), 
	 Service Indicator (SI) and MTP Network Identity (NI).
	 
	 Provides the MTP User Part (SI value) associated with this MTP 
	 user."
    REFERENCE
	"ITU-T Rec. Q.751.1 (1997), ANSI T1.116.1 (2000),
	 ITU-T Rec. X.723 | ISO/IEC 10165-5, sap2Address attibute."
    ::= { mtpSapEntry 3 }

mtpSapUserPartStatus OBJECT-TYPE
    SYNTAX MtpUserPartStatus
    MAX-ACCESS read-create
    STATUS current
    DESCRIPTION
	"Provides, using the MtpUserPartStatus textual convention, the 
	 status of the MTP-SAP as well a allowing management stations to 
	 control the individual user part status for MTP-SAP that have 
	 no MTP User.  Values are:
	 
	  - unknown(0), the status of the user, when not present, is 
	    unknown;
	  - inaccessible(1), the user, when not present, is 
	    inaccessible;
	  - unequipped(2), the statu of the user, when not present, is 
	    unequipped.
	 
	 When the user part is present (the usage state is idle(0)), 
	 this value is inaccessible(1).  Note that management stations 
	 may only set these values for MTP-SAPs that are not in active 
	 use by an MTP-user (i.e. those for which the usage state is 
	 idle(0))."
    REFERENCE
	"mtpSapUsageState"
    ::= { mtpSapEntry 4 }

mtpSapUserEntityNames OBJECT-TYPE
    SYNTAX RowPointer
    MAX-ACCESS read-only
    STATUS current
    DESCRIPTION
	"Provides the user entity name that exists for the MTP access 
	 point."
    REFERENCE
	"ITU-T Rec. Q.751.1 (1997), ANSI T1.116.1 (2000),
	 ITU-T Rec. X.723 | ISO/IEC 10165-5, userEntityNames attibute."
    ::= { mtpSapEntry 5 }

mtpSapProviderEntityNames OBJECT-TYPE
    SYNTAX RowPointer
    MAX-ACCESS read-create
    STATUS current
    DESCRIPTION
	"Provides the provider entity name that exists for the MTP 
	 access point."
    REFERENCE
	"ITU-T Rec. Q.751.1 (1997), ANSI T1.116.1 (2000),
	 ITU-T Rec. X.723 | ISO/IEC 10165-5, providerEntityNames 
	 attibute."
    ::= { mtpSapEntry 6 }

mtpSapUsageState OBJECT-TYPE
    SYNTAX UsageState
    MAX-ACCESS read-only
    STATUS current
    DESCRIPTION
	"Provides the usage state of the MTP service access point 
	 following the UsageState textual convention and ITU-T Rec. 
	 X.721 | ISO/IEC 10165-2.
	 
	  - idle(0), no user part is attached to the MTP-SAP (note that 
	    management stations may set the MTP user part status in this 
	    state);
	  - active(1), a user part exists and is attached to the 
	    MTP-SAP;
	  - busy(2), a user part exists and is passing traffic but 
	    congesetion exists in the path toward the MTP user.
	   
	 Note that management stations may set values for the MTP user 
	 part status when this value is idle(0)."
    REFERENCE
	"ITU-T Rec. X.721 | ISO/IEC 10165-2 usageState attribute."
    ::= { mtpSapEntry 7 }

mtpSapAsaProfilePointer OBJECT-TYPE
    SYNTAX RowPointer
    MAX-ACCESS read-create
    STATUS current
    DESCRIPTION
	"Provides a pointer to a row in another table that contains the 
	 alarm severity assignment profile, or zeroDotZero when no alarm 
	 severity assignment profile has been specified."
    REFERENCE
	"ITU-T Rec. Q.751.1 (1997), ANSI T1.116.1 (2000),
	 ITU-T Rec. M.3100, alarmSeverityAssignmentProfilePointer 
	 attibute."
    DEFVAL { { zeroDotZero } }
    ::= { mtpSapEntry 8 }

mtpSapName OBJECT-TYPE
    SYNTAX SimpleNameType
    MAX-ACCESS read-create
    STATUS current
    DESCRIPTION
	"Provides an additional administrative name for the MTP access 
	 point.
	 
	 Provides an optional administrative name for this entry in the 
	 MTP-SAP table.  MTP-SAP are typically names using, as a prefix, 
	 the common language name of the managed switching element at 
	 which they appear, concetentated with the name of the MTP User 
	 (e.g. EDTAB01DS1 ISUP)."
    REFERENCE
	"ITU-T Rec. Q.751.1 (1997), ANSI T1.116.1 (2000),
	 mtpAccessPointName attibute."
    ::= { mtpSapEntry 9 }

mtpSapLongMessageSupported OBJECT-TYPE
    SYNTAX TruthValue
    MAX-ACCESS read-create
    STATUS current
    DESCRIPTION
	"This attribute defines whether messages longer than 272 octets 
	 are supported."
    REFERENCE
	"ITU-T Rec. Q.2751.1 (1997), longMessageSupported attribute."
    ::= { mtpSapEntry 10 }

mtpSapRowStatus OBJECT-TYPE
    SYNTAX RowStatus
    MAX-ACCESS read-create
    STATUS current
    DESCRIPTION
	"Provides a mechainsm whereby management stations may create and 
	 delete entries in this table.  Rows may also be created and 
	 deleted by the managed system as a part of system operation.
	 
	 If the name package is supported: a create request with a value 
	 for the name attribute that is already used by another instance 
	 of the same object class will be rejected."
    REFERENCE
	"STD 58, SNMPv2-TC RowStatus.
	 ITU-T Rec. Q.751.1 (1997) : mtpSignPoint-mtpAccessPoint NAME 
	     BINDING."
    ::= { mtpSapEntry 11 }


-- ====================================================================

mtpMsTable OBJECT-TYPE
    SYNTAX SEQUENCE OF MtpMsEntry
    MAX-ACCESS not-accessible
    STATUS current
    DESCRIPTION
	""
    ::= { mtpMs 1 }

mtpMsEntry OBJECT-TYPE
    SYNTAX MtpMsEntry
    MAX-ACCESS not-accessible
    STATUS current
    DESCRIPTION
	""
    INDEX {
	mtpMsId
    }
    ::= { mtpMsTable 1 }

MtpMsEntry ::= SEQUENCE {
    mtpMsId					Unsigned32,
    mtpMsName					SnmpAdminString,
    mtpMsAlarmStatus				AlarmStatus,
    mtpMsOperationalState			OperationalState,
    mtpMsUsageState				UsageState,
    mtpMsManagedElementType			SnmpAdminString,
    mtpMsModelCode				SnmpAdminString,
    mtpMsVendorName				SnmpAdminString,
    mtpMsUserLabel				SnmpAdminString,
    mtpMsVersion				SnmpAdminString,
    mtpMsAsaProfilePointer			RowPointer,
    mtpMsNetworkElementAliases			SnmpAdminString,
    mtpMsStatus					RowStatus
}

mtpMsId OBJECT-TYPE
    SYNTAX Unsigned32
    MAX-ACCESS not-accessible
    STATUS current
    DESCRIPTION
	"Provides a non-zero index into the managed switching element 
	 table."
    ::= { mtpMsEntry 1 }

mtpMsName OBJECT-TYPE
    SYNTAX SnmpAdminString
    MAX-ACCESS read-create
    STATUS current
    DESCRIPTION
	"Provides an optional administrative name for this managed 
	 switching element.  It is typical to use the common language 
	 name assigned to the element (e.g. EDTNAB01DS1)."
    ::= { mtpMsEntry 2 }

mtpMsAlarmStatus OBJECT-TYPE
    SYNTAX AlarmStatus
    MAX-ACCESS read-create
    STATUS current
    DESCRIPTION
	"Provides the alarm status of the MTP managed switching element 
	 following the AlarmStatus textual convention and ITU-T Rec. 
	 X.721 (1992) | ISO/IEC 10165-2 : 1992.
	 
	  - underRepair(0),
	  - critical(1),
	  - major(2),
	  - minor(3),
	  - alarmOutstanding(4),
	"
    REFERENCE
	"ITU-T Rec. Q.751.1 (1997), ANSI T1.116.1 (2000) : alarmStatus 
	     attribute.
	 ITU-T Rec. X.721 (1992) | ISO/IEC 10165-2 : 1992, 
	     Attribute-ASN1Module.AlarmStatus.
	 ITU-T Rec. X.731 (1992) | ISO/IEC 10164-2 : 1993, 
	     Section 8.1.2.1."
    ::= { mtpMsEntry 3 }

mtpMsOperationalState OBJECT-TYPE
    SYNTAX OperationalState
    MAX-ACCESS read-only
    STATUS current
    DESCRIPTION
	"Provides the operational state of the signalling point 
	 following the OperationalState textual convention and ITU-T 
	 Rec. X.721 | ISO/IEC 10165-2.
	 
	  - disabled(0),
	  - enabled(1),
	"
    REFERENCE
	"ITU-T Rec. X.721 (1992) | ISO/IEC 10165-2 : 1992, 
	     Attribute-ASN1Module.OperationalState.
	 ITU-T Rec. X.731 (1992) | ISO/IEC 10164-2 : 1993, 
	     Section 8.1.1.1.
	 ITU-T Rec. Q.751.1 (1997), ANSI T1.116.1 (2000), 
	     operationalState attribute."
    DEFVAL { 0 } -- disabled
    ::= { mtpMsEntry 4 }

mtpMsUsageState OBJECT-TYPE
    SYNTAX UsageState
    MAX-ACCESS read-only
    STATUS current
    DESCRIPTION
	"Provides the usage state of the MTP managed switching element 
	 following the UsageState textual convention and ITU-T Rec. 
	 X.721 | ISO/IEC 10165-2.

	  - idle(0),
	  - active(1),
	  - busy(2),
	"
    REFERENCE
	"ITU-T Rec. X.721 | ISO/IEC 10165-2 usageState attribute."
    DEFVAL { 0 } -- idle
    ::= { mtpMsEntry 5 }

mtpMsManagedElementType OBJECT-TYPE
    SYNTAX SnmpAdminString
    MAX-ACCESS read-create
    STATUS current
    DESCRIPTION
	""
    ::= { mtpMsEntry 6 }

mtpMsModelCode OBJECT-TYPE
    SYNTAX SnmpAdminString
    MAX-ACCESS read-create
    STATUS current
    DESCRIPTION
	""
    ::= { mtpMsEntry 7 }

mtpMsVendorName OBJECT-TYPE
    SYNTAX SnmpAdminString
    MAX-ACCESS read-create
    STATUS current
    DESCRIPTION
	""
    ::= { mtpMsEntry 8 }

mtpMsUserLabel OBJECT-TYPE
    SYNTAX SnmpAdminString
    MAX-ACCESS read-create
    STATUS current
    DESCRIPTION
	""
    ::= { mtpMsEntry 9 }

mtpMsVersion OBJECT-TYPE
    SYNTAX SnmpAdminString
    MAX-ACCESS read-create
    STATUS current
    DESCRIPTION
	""
    ::= { mtpMsEntry 10 }

mtpMsAsaProfilePointer OBJECT-TYPE
    SYNTAX RowPointer
    MAX-ACCESS read-create
    STATUS current
    DESCRIPTION
	"Provides a pointer to an alarm severity assignment profile to 
	 be used for alarms generated by this managed switching element, 
	 or zeroDotZero."
    REFERENCE
	"ITU-T Rec. Q.751.1 (1997), ANSI T1.116.1 (2000), 
	     alarmSeverityAssignmentProfilePointer attribute."
    DEFVAL { { zeroDotZero } }
    ::= { mtpMsEntry 11 }

mtpMsNetworkElementAliases OBJECT-TYPE
    SYNTAX SnmpAdminString
    MAX-ACCESS read-create
    STATUS current
    DESCRIPTION
	""
    ::= { mtpMsEntry 12 }


mtpMsStatus OBJECT-TYPE
    SYNTAX RowStatus
    MAX-ACCESS read-create
    STATUS current
    DESCRIPTION
	""
    REFERENCE
	"STD 58, SNMPv2-TC RowStatus."
    ::= { mtpMsEntry 13 }



-- ====================================================================

mtpNaTable OBJECT-TYPE
    SYNTAX SEQUENCE OF MtpNaEntry
    MAX-ACCESS not-accessible
    STATUS current
    DESCRIPTION
	"Provides the network table which defines all of the networks 
	 known to the managed element."
    REFERENCE
	""
    ::= { mtpNa 1 }

mtpNaEntry OBJECT-TYPE
    SYNTAX MtpNaEntry
    MAX-ACCESS not-accessible
    STATUS current
    DESCRIPTION
	"Each entry in the network appearance profile table represents a 
	 unique combination of network appearance protocol parameters 
	 and options.
	 
	 Provides an entry in the network table.  Each entry provides 
	 fundamental information about the network as well as protocol 
	 profile defaults for signalling points created for operation in 
	 each network."
    REFERENCE
	""
    INDEX {
	mtpNaId
    }
    ::= { mtpNaTable 1 }

MtpNaEntry ::= SEQUENCE {
    mtpNaId					INTEGER,
    mtpNaProtocolVariant			Ss7ProtocolVariant,
    mtpNaProtocolYear				INTEGER,
    mtpNaProtocolOptions			BITS,
    mtpNaNetworkIndicator			MtpNetworkIndicator,
    mtpNaPointCodeFormat			MtpPointCodeFormat,
    mtpNaSlsLength				INTEGER,
    mtpNaSpDefault				SimpleNameType,
    mtpNaName					SnmpAdminString,
    mtpNaRowStatus				RowStatus
}

mtpNaId OBJECT-TYPE
    SYNTAX INTEGER (1..255)
    MAX-ACCESS not-accessible
    STATUS current
    DESCRIPTION
	"Provides a non-zero index for the network table.  The index is 
	 restricted in the range 1..255 because the value is also used 
	 as the first octet of a NetworkPointCode texutal convention.
	 
	 Provides an ordinal simple name type index into this table.  
	 This can be a print-formatted decimal number or a string.  Some 
	 implementations may require that this index be formatted as a 
	 print-formatted decimal number.
	 
	 Provides an index into the network profile table, mtpNaProfileTable.  
	 Rows in this table can be referred to using this index or using 
	 the RowPointer pointer.  The index valud zero (0) has special 
	 semantics: the zero index contains default default values."
    REFERENCE
	""
    ::= { mtpNaEntry 1 }

mtpNaProtocolVariant OBJECT-TYPE
    SYNTAX Ss7ProtocolVariant
    MAX-ACCESS read-create
    STATUS current
    DESCRIPTION
	"Provides the primary protocol variant used at the network 
	 appearance using the Ss7ProtocolVariant textual convention from 
	 the OPENSS7-SS7-MIB module.  This describes the major protocol 
	 variant, such as ANSI, ETSI, ITU-T, using an object-identity.  
	 All signalling points in the network appearance are expected to 
	 signal using this protocol variant.
	 
	 Provides the SS7 protocol variant by standards body and year of 
	 issue.  Years are based on the corresponding ITU-T Plenary 
	 Session year, not the actually publish date of the 
	 specification or standard.  This is an autonomous type so 
	 vendor-specific extensions or localizations are permitted.  The 
	 agent can refuse a management station SET operation for this 
	 field with an object identifier that the agent does not 
	 recognize.  The default is the current ITU-T standards 
	 specifications."
    REFERENCE
	""
    DEFVAL { { ss7ProtocolItut 0 } }
    ::= { mtpNaEntry 2 }

mtpNaProtocolYear OBJECT-TYPE
    SYNTAX INTEGER {
	current(0), y1980(1980), y1984(1984), y1988(1988), y1992(1992), 
	y1996(1996), y2000(2000), y2004(2004), y2008(2008) }
    MAX-ACCESS read-create
    STATUS current
    DESCRIPTION
	"Specifies the year of the protocol variant which corresponds to 
	 the network appearance.  All signalling points in the network 
	 appearance are expected to be compatible to this MTP signalling 
	 protocol version.  Provides a protocol issue year within the 
	 major protocol variant.  Typical values are 1988, 1992, 1996, 
	 2000, etc."
    DEFVAL { 0 } -- current
    ::= { mtpNaEntry 3 }

mtpNaProtocolOptions OBJECT-TYPE
    SYNTAX BITS {
	mtpfCongInt(0), mtpfCongLev(1), mtpfCongSta(2), mtpfTfrBasic(3), 
	mtpfTfrBcast(4), mtpfTfrResp(5), mtpfTfrCong(6), mtpfLinkOsc(7), 
	mtpfLinkOscA(8), mtpfLinkOscB(9), mtpfPcAlias(10), 
	mtpfCluster(11), mtpfSnsm(12), mtpfGws(13), mtpfEGws(14), 
	mtpfBGws(15), mtpfLinkPcr(16), mtpfLinkHsl(17), 
	mtpfLinkHslBsn(18), mtpfLinkHslEsn(19), mtpfLinkSaal(20), 
	mtpfLinkM2pa(21), mtpfLinkProving(22), mtpfLinkSdlAlloc(23), 
	mtpfLinkStAlloc(24), mtpfSntmFail(25) }
    MAX-ACCESS read-create
    STATUS current
    DESCRIPTION
	"Specifies the MTP national protocol options associated with the 
	 network appearance.  This can be used to refine ITU-T and ANSI 
	 based protocol variants.
	 
	  - mtpfCongInt(0): support for international congestion 
	    procedures (ITU-T Rec. Q.704 (07/96) Clause 3.8.1);
	 
	  - mtpfCongLev(1): support for multiple congestion levels with 
	    congestion priority (ITU-T Rec. Q.704 (07/96) Clause 
	    3.8.2.2);
	 
	  - mtpfCongSta(2): support for multiple congestion states 
	    without congestion priority (ITU-T Rec. Q.704 (07/96) Clause 
	    3.8.2.3);
	 
	  - mtpfTfrBasic(3): support of national option for 
	    transfer-restricted message and procedures (ITU-T Rec. Q.704 
	    (07/96) Clause 13.4);
	 
	  - mtpfTfrBcast(4): support of national option for the 
	    transfer-restricted broadcast procedures (ANSI T1.111.4 
	    (2000) Clause 13.4.2);
	 
	  - mtpfTfrResp(5): support of national option for the 
	    transfer-restricted responsive procedures (ANSI T1.111.4 
	    (2000) Clause 13.4.2);
	 
	  - mtpfTfrCong(6): support of national option for the 
	    transfer-restricted congestion avoidance procedures (ANSI 
	    T1.111.4 (2000) Clause 13.4.2A);
	 
	  - mtpfLinkOsc(7): support of basic link oscillation procedures 
	    (ITU-T Rec. Q.704 (06/96), ANSI T1.111.4 (1992) Clause 
	    12.2.2);
	 
	  - mtpfLinkOscA(8): support of national option for link 
	    oscillation procedure (A) (ANSI T1.111.4 (2000) Clause 
	    12.2.2 (A));
	 
	  - mtpfLinkOscB(9): support of national option for link 
	    oscillation procedure (B) (ANSI T1.111.4 (2000) Clause 
	    12.2.2 (B));
	 
	  - mtpfPcAlias(10): support of national option for alias point 
	    codes;
	 
	  - mtpfCluster(11): support of national option for cluster 
	    routing and associated cluster route management messages and 
	    procedures (ANSI T1.111.4 (2000) Clause 13.4.5A TCR);
	 
	  - mtpfSnsm(12): support of national option for the signalling 
	    network special test message (ITU-T Rec. Q.707, ANSI 
	    T1.111.7 (2000));
	 
	  - mtpfGws(13): support of national option for basic gateway 
	    screening (ITU-T Rec. Q.705, ANSI T1.111.5 (2000) : Clause 
	    8.3);
	 
	  - mtpfEGws(14): support of national option for enhanced 
	    gateway screening;
	 
	  - mtpfBGws(15): support of national option for border gateway 
	    screening;
	 
	  - mtpfLinkPcr(16): support for preventative cyclic 
	    retransmission on long delay signalling links;
	 
	  - mtpfLinkHsl(17): support of national option for high-speed 
	    signalling links (ITU-T Rec. Q.703 (07/96) Annex A);
	 
	  - mtpfLinkHslBsn(18): support of national option for 
	    non-extended sequence numbers on high-speed signalling links 
	    (ITU-T Rec.  Q.703 (07/96) Clause A.2.3.5);
	 
	  - mtpfLinkHslEsn(19): support of national option for exended 
	    sequence numbers on high-speed signalling links (ITU-T Rec. 
	    Q.703 (07/96) Clause A.2.3.5);
	 
	  - mtpfLinkSaal(20): support for MTP3b SAAL signalling links 
	    (ITU-T Rec. Q.2140);
	 
	  - mtpfLinkM2pa(21): support for M2PA SIGTRAN signalling links 
	    (RFC 
	    4165);
	 
	  - mtpfLinkProving(22): support for suppression of proving on 
	    MTP3b SAAL and M2PA signalling links;
	 
	  - mtpfLinkSdlAlloc(23): support for the automatic allocation 
	    of signalling data terminals (ITU-T Rec. Q.704 (06/96), ANSI 
	    T1.111.4 (2000) : Clause 12.4).
	 
	  - mtpfLinkStAlloc(24): support for the automatic allocation of 
	    signalling terminals (ITU-T Rec. Q.704 (06/96), ANSI 
	    T1.111.4 (2000) : Clause 12.3).
	 
	  - mtpfSntmFail(25): support of national option for failing a 
	    signalling link on routine SLTM failure (ANSI T1.111.7 
	    (2000) Clause 2.2);
	 
	 This object simply describes the capabilities and policies 
	 present at a network appearance.  It does not say anything 
	 about the capabilities of signalling points that are connected 
	 to this network.
	 
	 This is for convenience or for modifying existing standards to 
	 suit other protocol variants.  The value for existing standards 
	 can be deduced from the standard and the year.  Some 
	 implementations may provide this object with a MAX-ACCESS 
	 clause of read-only.
	 
	 When a row is created without specifying a value for this 
	 column, a suitable default based on the protocol variant and 
	 year should be completed by the agent."
    REFERENCE
	"ITU-T Recommendation Q.703 (06/97),
	 ITU-T Recommendation Q.704 (07/96),
	 ITU-T Recommendation Q.705,
	 ITU-T Recommendation Q.707,
	 ANSI T1.111.3 (2000),
	 ANSI T1.111.4 (1992),
	 ANSI T1.111.4 (2000),
	 ANSI T1.111.5 (2000),
	 ANSI T1.111.7 (2000).
	 "
    ::= { mtpNaEntry 4 }

mtpNaNetworkIndicator OBJECT-TYPE
    SYNTAX MtpNetworkIndicator
    MAX-ACCESS read-create
    STATUS current
    DESCRIPTION
	"Specifies the normal network indicator used for the signalling 
	 network.  This is one of the following values:
	 
	  - internationalNetwork1(0): network indicator for the 
	    international network;
	  - internationalNetwork2(1): reserved network indicator for the 
	    international network;
	  - nationalNetwork1(2): network indicator for the national 
	    network;
	  - nationalNetwork2(3): reserved network indicator for the 
	    national network.
	 
	 This is for convenience or for modifying existing standards to 
	 suit other protocol variants.  The value for existing standards 
	 can be deduced from the standard and the year.  Some 
	 implementations may provide this object with a MAX-ACCESS 
	 clause of read-only.
	 
	 When a row is created without specifying this column, a 
	 suitable default based on the protocol variant and year should 
	 be completed by the agent."
    REFERENCE
	"ITU-T Rec. Q.751.1 (1997), ANSI T1.116.1 (2000) : 
	     MTPDefinedTypesModule.NetworkIndicator."
    ::= { mtpNaEntry 5 }

mtpNaPointCodeFormat OBJECT-TYPE
    SYNTAX MtpPointCodeFormat
    MAX-ACCESS read-create
    STATUS current
    DESCRIPTION
	"Provides the format of point codes used in the signalling 
	 network using the MtpPointCodeFormat textual convention.  This 
	 convention provides for a three-octet octet string that 
	 contains the size (in bits) of the network, cluster and member 
	 elements of the signalling point code.  For ITU-T, ETSI and 
	 ITU-T or ETSI-based networks, this is 3-8-3; for ANSI and 
	 ANSI-based networks, this is 8-8-8.
	 
	 This is for convenience as the value can be deduced from the 
	 protocol variant and year, so this object might be provided 
	 with a MAX-ACCESS clause of read-only by some implementations."
    REFERENCE
	""
    ::= { mtpNaEntry 6 }

mtpNaSlsLength OBJECT-TYPE
    SYNTAX INTEGER {
	sls4bits(4), sls5bits(5), sls8bits(8) }
    UNITS "bits"
    MAX-ACCESS read-create
    STATUS current
    DESCRIPTION
	"Provides the length of the signalling link selection field 
	 (SLS) in bits.  This can be one of the following values:

	  - sls4bits(4): the 4-bit signalling link selection field 
	    provided by international and ITU-T based networks;
	  - sls5bits(5): the 5-bit signalling link selection field 
	    provided by older ANSI and ANSI-based networks;
	  - sls8bits(8): the 8-bit signalling link selection field 
	    provided by more recent ANSI and ANSI-based networks.

	 This is for convenience as the value can be deduced from the 
	 protocol variant and year, so this object might be provided 
	 with a MAX-ACCESS clause of read-only by some implementations."
    ::= { mtpNaEntry 7 }

mtpNaSpDefault OBJECT-TYPE
    SYNTAX SimpleNameType
    MAX-ACCESS read-create
    STATUS current
    DESCRIPTION
	"Provides a reference to a signalling point protocol profile 
	 that will be used as a default when creating signalling points 
	 that communicate on this network.  When this value is not 
	 specified on creation, the default from the network protocol 
	 profile will be used.
	 
	 Specifies the default signalling point protocol profile that 
	 will be used when creating signalling points that appear in 
	 this network.
	 
	 When non-null, provides the name or index of a signalling point 
	 profile table entry (mtpSpProfileEntry) that contains the 
	 signalling point protocol profile to be used as a default when 
	 creating signalling points that appear in this signalling 
	 network.  Agents may refuse creation of rows that have non-null 
	 strings in this column that:
	 
	  1. does not refer to the signalling point profile table 
	     (mtpSpProfileTable);
	  2. refers to a non-existent entry in the signalling point 
	     profile table (mtpSpProfileEntry).
	 
	 When null, it specifies that a signalling point protocol 
	 profile must be specified when creating signalling points that 
	 appear in this network."
    REFERENCE
	""
    ::= { mtpNaEntry 8 }

mtpNaName OBJECT-TYPE
    SYNTAX SnmpAdminString
    MAX-ACCESS read-create
    STATUS current
    DESCRIPTION
	"Provides an optional administrative name for this network.  
	 This column is optional and will be a null string if not 
	 specified.
	 
	 Provides an administrative name for the SS7 signalling network.  
	 When non-null, this must be a unique string within this table.  
	 Agents may refuse creation of row that has a non-null 
	 administrative name that is already used by another row in the 
	 table."
    REFERENCE
	""
    ::= { mtpNaEntry 9 }

mtpNaRowStatus OBJECT-TYPE
    SYNTAX RowStatus
    MAX-ACCESS read-create
    STATUS current
    DESCRIPTION
	"Provides a mechanism whereby management stations may add an 
	 delete conceptual rows in this table.  Row entries are 
	 persistent across and agent reboot.  Before a row can be 
	 deleted from the table, there must be no signalling points that 
	 refer to it.
	 
	 Index zero (0) is special in that it provides default network 
	 characteristics when no network is specified, additional rows 
	 in this table may represent standard defaults for specific 
	 protocol variants and years.  Managed system may refuse removal 
	 of rows in this table that represents default entries.
	 
	 Requests to delete rows in this table that are referenced by a 
	 row in the signalling point table (mtpSpTable) may be refused.  
	 The agent may refuse changing columns in rows in this table for 
	 which there are active signalling points.
	 
	 Rows in this table are persistent across an agent reboot."
    REFERENCE
	"STD 58, SNMPv2-TC RowStatus."
    ::= { mtpNaEntry 10 }

-- ====================================================================

mtpGsTable OBJECT-TYPE
    SYNTAX SEQUENCE OF MtpGsEntry
    MAX-ACCESS not-accessible
    STATUS current
    DESCRIPTION
	""
    REFERENCE
	"ITU-T Rec. Q.751.1 (1997), ANSI T1.116.1 (2000), 
	 stpScreeningTable MOC."
    ::= { mtpGs 1 }

mtpGsEntry OBJECT-TYPE
    SYNTAX MtpGsEntry
    MAX-ACCESS not-accessible
    STATUS current
    DESCRIPTION
	""
    REFERENCE
	"ITU-T Rec. Q.751.1 (1997), ANSI T1.116.1 (2000), 
	 stpScreeningTable MO."
    INDEX {
	mtpSpId, -- shared index
	mtpGsId
    }
    ::= { mtpGsTable 1 }

MtpGsEntry ::= SEQUENCE {
    mtpGsId					Unsigned32,
    mtpGsAdministrativeState			AdministrativeState,
    mtpGsTreatmentOfOutsideRanges		MtpGsTreatment,
    mtpGsListMode				TruthValue,
    mtpGsScreeningByLinkSetOrByOpc		INTEGER,
    mtpGsGetScreenedOpcsOrLinkSetsByDpc		MtpResultOfAction,
    mtpGsName					SimpleNameType,
    mtpGsRowStatus				RowStatus
}

mtpGsId OBJECT-TYPE
    SYNTAX Unsigned32
    MAX-ACCESS not-accessible
    STATUS current
    DESCRIPTION
	"The STP Screening Table Id is an attribute used for naming 
	 purposes."
    REFERENCE
	"ITU-T Rec. Q.751.1 (1997), ANSI T1.116.1 (2000), 
	 stpScreeningTableId attribute."
    ::= { mtpGsEntry 1 }

mtpGsAdministrativeState OBJECT-TYPE
    SYNTAX AdministrativeState
    MAX-ACCESS read-create
    STATUS current
    DESCRIPTION
	"Provides the adminstrative state of the STP screening table 
	 following the AdministrativeState texutal convention and ITU-T 
	 Rec. X.721 | ISO/IEC 10165-2.
	 
	  - locked(0),
	  - unlocked(2),
	  - shuttingDown(3),
	 "
    REFERENCE
	"ITU-T Rec. Q.751.1 (1997), ANSI T1.116.1 (2000), 
	     administrativeState attribute."
    DEFVAL { 0 } -- locked
    ::= { mtpGsEntry 2 }

mtpGsTreatmentOfOutsideRanges OBJECT-TYPE
    SYNTAX MtpGsTreatment
    MAX-ACCESS read-create
    STATUS current
    DESCRIPTION
	"The treatmentOfOutsideRanges attribute specifies the treatment 
	 of the messages outside the designated ranges given the 
	 stpScreeningTable managed object (see 8.3/Q.705, part two).
	 
	  - normal(0), allow all STP messages outside the designated 
	    ranges
	 
	  - discard(1), discard all STP messages outside the designated 
	    ranges.
	 
	  - prohibit(2), respond with a transfer-prohibited message for 
	    the destination point code of the message before discarding 
	    all STP messages outside the designated ranges.  Note that 
	    this treatment should only be specified for DPC ranges that 
	    fall outside the designated ranges for all SI values.
	 
	  - unequipped(3), respond with a user-part-unavailable 
	    (unequipped) message for the destination point code and SI 
	    value of the message for all STP messages outside the 
	    designated ranges.
	 
	  - inaccessible(4), respond with a user-part-unavailable 
	    (inaccessible) message for the destination point code and SI 
	    value of the message for all STP messages outside the 
	    designated ranges.
	 
	  - congest(5), respond with a transfer-controlled message for 
	    the destination point code and priority of the message 
	    before discarding all STP message outside the designated 
	    ranges.  Note that this treatment should only be specified 
	    for DPC ranges that fall outside the designated ranges for 
	    all SI values.
	 
	 Note that application of values other than normal(0) or 
	 discard(1) will not conform to ITU-T Recommendation Q.705 
	 Clause 8.
	"
    REFERENCE
	"ITU-T Rec. Q.751.1 (1997), ANSI T1.116.1 (2000), 
	 treatmentOfOutsideRanges attribute."
    ::= { mtpGsEntry 3 }

mtpGsListMode OBJECT-TYPE
    SYNTAX TruthValue
    MAX-ACCESS read-create
    STATUS current
    DESCRIPTION
	"The stpScreeningTableListMode attribute indicates whether the 
	 STP access is allowed or not by the designated combinations 
	 contained in the subordinate stpScreeningTableLine's (see 
	 8.2/Q.705). TRUE: STP access allowed FALSE: STP access 
	 inhibited."
    REFERENCE
	"ITU-T Rec. Q.751.1 (1997), ANSI T1.116.1 (2000), 
	 stpScreeningTableListMode attribute."
    ::= { mtpGsEntry 4 }

mtpGsScreeningByLinkSetOrByOpc OBJECT-TYPE
    SYNTAX INTEGER {
	byOpc(0),
	byIncomingLinkset(1),
	byOutgoingLinkset(2)
    }
    MAX-ACCESS read-create
    STATUS current
    DESCRIPTION
	"This attribute defines which of the different options of 
	 8.2/Q.705 are used for identifying unauthorized SS No. 7 
	 messages.
	 
	  - byOpc(0) : ;
	  - byIncomingLinkset(1) : ;
	  - byOutgoingLinkset(2) : ;
	 
	 "
    REFERENCE
	"ITU-T Rec. Q.751.1 (1997), ANSI T1.116.1 (2000), 
	 screeningByLinkSetOrByOpc attribute."
    ::= { mtpGsEntry 5 }

mtpGsGetScreenedOpcsOrLinkSetsByDpc OBJECT-TYPE
    SYNTAX MtpResultOfAction
    MAX-ACCESS read-create
    STATUS current
    DESCRIPTION
	"This action gets all OPCs or linksets (depending on the value 
	 of the screeningByLinkSetOrByOPC attribute) together with their 
	 respective messageTreatments which are screened in combination 
	 with a specific DPC within all the 
	 stpScreeningTableLineContents of all stpScreeningTableLine's 
	 contained in the stpScreeningTable. The resulting list in the 
	 reply is empty, if no OPC or Linkset within all the 
	 stpScreeningTableLine (Contents of all stpScreeningTableLine's 
	 contained in the stpScreeningTable is screened in combination 
	 with the DPC - given in the information syntax), or if no 
	 stpScreeningTableLine contained in the stpScreeningTable does 
	 exist."
    REFERENCE
	"ITU-T Rec. Q.751.1 (1997), ANSI T1.116.1 (2000), 
	 getScreenedOpcsOrLinkSetsByDpc attribute."
    ::= { mtpGsEntry 6 }

mtpGsName OBJECT-TYPE
    SYNTAX SimpleNameType
    MAX-ACCESS read-create
    STATUS current
    DESCRIPTION
	"This attribute is an additional name for instances of the 
	 stpScreeningTable managed object class."
    REFERENCE
	"ITU-T Rec. Q.751.1 (1997), ANSI T1.116.1 (2000), 
	 stpScreeningTableName attribute."
    ::= { mtpGsEntry 7 }

mtpGsRowStatus OBJECT-TYPE
    SYNTAX RowStatus
    MAX-ACCESS read-create
    STATUS current
    DESCRIPTION
	"Provides a mechanism whereby management stations may create or 
	 delete rows in this table.
	 
	 If the name package is supported: a create request with a value 
	 for the name attribute that is already used by another instance 
	 of the same object class will be rejected.  It is only allowed 
	 to delete an instance of this object class if its 
	 administrative state equals 'locked'."
    REFERENCE
	"STD 58, SNMPv2-TC RowStatus.
	 ITU-T Rec. Q.751.1 (1997) : mtpSignPoint-stpScreeningTable NAME 
	     BINDING"
    ::= { mtpGsEntry 8 }


-- ====================================================================

mtpGsLineTable OBJECT-TYPE
    SYNTAX SEQUENCE OF MtpGsLineEntry
    MAX-ACCESS not-accessible
    STATUS current
    DESCRIPTION
	"The stpScreeningTableLine together with its superior 
	 stpScreeningTable contains all the information which are 
	 necessary for an STP to identify and to handle unauthorized SS 
	 No. 7 messages as defined in 8.2/Q.705 and 8.3/Q.705.  The 
	 total number of screened DPC's across all stpScreeningTableLine 
	 instances contained by a stpScreeningTable must be less or 
	 equal to maxNoOfScreenedDpcs."
    REFERENCE
	"ITU-T Rec. Q.751.1 (1997), ANSI T1.116.1 (2000), 
	 stpScreeningTableLine MOC."
    ::= { mtpGs 2 }

mtpGsLineEntry OBJECT-TYPE
    SYNTAX MtpGsLineEntry
    MAX-ACCESS not-accessible
    STATUS current
    DESCRIPTION
	""
    REFERENCE
	"ITU-T Rec. Q.751.1 (1997), ANSI T1.116.1 (2000), 
	 stpScreeningTableLine MO."
    INDEX {
	mtpSpId, -- shared index
	mtpGsId,
	mtpGsLineId
    }
    ::= { mtpGsLineTable 1 }

MtpGsLineEntry ::= SEQUENCE {
    mtpGsLineId					Unsigned32,
    mtpGsLineObject				RowPointer,
    mtpGsLineContent				Unsigned32,
    mtpGsLineRowStatus				RowStatus
}

mtpGsLineId OBJECT-TYPE
    SYNTAX Unsigned32
    MAX-ACCESS not-accessible
    STATUS current
    DESCRIPTION
	"Provides an ordinal index into the gateway screening rule 
	 table.
	 
	 The stpScreeningTableLineId is an attribute used for naming 
	 purposes.  Depending on the value of attribute 
	 screeningByLinkSetOrByDpc of the superior stpScreeningTable 
	 instance it represents the OPC or linkset which is designated 
	 to be screened for STP traffic."
    REFERENCE
	"ITU-T Rec. Q.751.1 (1997), ANSI T1.116.1 (2000), 
	 stpScreeningTableLineId attribute."
    ::= { mtpGsLineEntry 1 }

--
-- The stpScreeningTableLineId is an attribute used for naming purposes.  
-- Depending on the value of attribute screeningByLinkSetOrByDpc of the 
-- superior stpScreeningTable instance it represents the OPC or linkset 
-- which is designated to be screened for STP traffic.
--
mtpGsLineObject OBJECT-TYPE
    SYNTAX RowPointer
    MAX-ACCESS read-create
    STATUS current
    DESCRIPTION
	"Identifies the object used as a target for screening.  
	 Depending on the value of mtpGsScreeningByLinkSetOrByOpc for 
	 this table, this object can be one of:
	 
	  - byOpc(0), a pointer to a route set entry in the mtpRsTable 
	    corresponding to an originating point code.
	 
	  - byIncomingLinkset(1), a pointer to a combined link set in 
	    the mtpClTable corresponding to an incoming link set.
	 
	  - byOutgoingLinkset(2), a pointer to a combind link set in the 
	    mtpClTable corresponding to an outgoing link set.
	 
	  Note that a null pointer (with a value of zeroDotZero) means 
	  any originating route set, incoming link set or outgoing link 
	  set.  In this case, mtpGsScreeningByLinkSetOrByOpc value has 
	  no effect.
	"
    REFERENCE
	"ITU-T Rec. Q.751.1 (1997), ANSI T1.116.1 (2000), 
	 stpScreeningTableLineId attribute."
    DEFVAL { { zeroDotZero } }
    ::= { mtpGsLineEntry 2 }

mtpGsLineContent OBJECT-TYPE
    SYNTAX Unsigned32
    MAX-ACCESS read-create
    STATUS current
    DESCRIPTION
	"The stpScreeningTableLineContent attribute represents the 
	 content of one line of the STP ScreeningTable.  The content 
	 consists of elements indicating the designated DPCs which are 
	 to be screened in combination with the OPC or linkset given by 
	 the stpScreeningTableLineId and an indication how a message 
	 fulfilling such a combination is to be treated.
	 
	 This column provides the number of components of STP screening 
	 table line content information is available in the 
	 stpScreeningTableLineContentTable side-table for the currently 
	 indexed line."
    REFERENCE
	"ITU-T Rec. Q.751.1 (1997), ANSI T1.116.1 (2000), 
	 stpScreeningTableLineContent attribute."
    ::= { mtpGsLineEntry 3 }

mtpGsLineRowStatus OBJECT-TYPE
    SYNTAX RowStatus
    MAX-ACCESS read-create
    STATUS current
    DESCRIPTION
	"Provides a mechanism whereby management stations may create and 
	 delete rows in this table.
	 
	 If the name package is supported: a create request with a value 
	 for the name attribute that is already used by another instance 
	 of the same object class will be rejected.
	 
	 The total number of screened DPC's across all 
	 stpScreeningTableLine instances contained by an 
	 stpScreeningTable must be less or equal to maxNoOfScreenedDpcs.  
	 A respectively unallowed create request is rejected.  If one 
	 tries to create an instance with an stpScreeningTableLineId 
	 which would represent a linkset which is not contained within 
	 the same signPoint as the stpScreeningTable, the create request 
	 is rejected.  Instances of this object class can be deleted 
	 automatically if the superior stpScreeningTable is deleted."
    REFERENCE
	"STD 58, SNMPv2-TC RowStatus.
	 ITU-T Rec. Q.751.1 (1997) : 
	     stpScreeningTable-stpScreeningTableLine NAME BINDING."
    ::= { mtpGsLineEntry 4 }

-- ====================================================================

mtpGsLineContentTable OBJECT-TYPE
    SYNTAX SEQUENCE OF MtpGsLineContentEntry
    MAX-ACCESS not-accessible
    STATUS current
    DESCRIPTION
	"Provides a side table for the STP screening table line table 
	 that provides a breakout of the individual screening matches 
	 for the line."
    REFERENCE
	"ITU-T Rec. Q.751.1 (1997), ANSI T1.116.1 (2000), ASN.1 
	 StpScreeningTableLineContent."
    ::= { mtpGs 3 }

mtpGsLineContentEntry OBJECT-TYPE
    SYNTAX MtpGsLineContentEntry
    MAX-ACCESS not-accessible
    STATUS current
    DESCRIPTION
	"Id the signalling point, screening table, screening table 
	 line and then screening table source."
    REFERENCE
	"ITU-T Rec. Q.751.1 (1997), ANSI T1.116.1 (2000), ASN.1 
	 StpScreeningTableLineContent."
    INDEX {
	mtpSpId, -- shared index
	mtpGsId,
	mtpGsLineId,
	mtpGsLineContentId
    }
    ::= { mtpGsLineContentTable 1 }

MtpGsLineContentEntry ::= SEQUENCE {
    mtpGsLineContentId				Unsigned32,
    mtpGsLineContentDesignatedDPCFirst		NetworkPointCode,
    mtpGsLineContentDesignatedDPCLast		NetworkPointCode,
    mtpGsLineContentSiMask			MtpSiMask,
    mtpGsLineContentMessageTreatment		MtpGsTreatment,
    mtpGsLineContentComment			SnmpAdminString,
    mtpGsLineContentRowStatus			RowStatus
}

mtpGsLineContentId OBJECT-TYPE
    SYNTAX Unsigned32
    MAX-ACCESS not-accessible
    STATUS current
    DESCRIPTION
	"Provides an ordinal index into the gateway screening table.  
	 Rules with a lower ordinal value are applied first."
    ::= { mtpGsLineContentEntry 1 }

mtpGsLineContentDesignatedDPCFirst OBJECT-TYPE
    SYNTAX NetworkPointCode
    MAX-ACCESS read-create
    STATUS current
    DESCRIPTION
	"Provides the first DPC in a range of DPCs and also provides an 
	 index to the STP screening table line content table.
	 
	 Provides the first destination point code (DPC) in an 
	 inclusive range that is applicable to this rule.  This column 
	 is used with the mtpGsLineContentDesignatedDPCLast column to 
	 define the range.  This, the first DPC in the range, must be 
	 ordinally less that the last DPC in the range.  Both values 
	 must belong to the same network appearance.  Both values must 
	 belong to the same network appearance (that of the signalling 
	 point) and, therefore, the network appearance component of the 
	 NetworkPointCode must be zero (0), indicating the default 
	 network.  To be effective, the range should include at least 
	 one signalling point code for which the associated signalling 
	 point has a route set."
    REFERENCE
	"ITU-T Rec. Q.751.1 (1997), ANSI T1.116.1 (2000), ASN.1 
	 StpScreeningTableLineContent .StpScreeningElement 
	 .designatedDPC .dpcRange .firstDPC"
    ::= { mtpGsLineContentEntry 2 }

mtpGsLineContentDesignatedDPCLast OBJECT-TYPE
    SYNTAX NetworkPointCode
    MAX-ACCESS read-create
    STATUS current
    DESCRIPTION
	"Provides the last DPC in a range of DPCs.  If not provided when 
	 a line is created, this defaults to the same value as the 
	 mtpGsLineContentDesignatedDPCFirst index.  The designated DPCs 
	 should cover at least one DPC for which the indexed signalling 
	 point has a routeset.
	 
	 Provides the last destination point code (DPC) in an inclusive 
	 range that is applicable to this rule.  This column is used 
	 with the mtpGsLineContentDesignatedDPCFirst column to define the 
	 range.  This, the last DPC in the range, must be ordinally 
	 greater than the first DPC in the range.  Both values must 
	 belong to the same network appearance (that of the signalling 
	 point) and, therefore, the network appearance component of the 
	 NetworkPointCode must be zero (0), indicating the default 
	 network.  To be effective, the range should include at lease 
	 one signalling point code for which the associated signalling 
	 point has a route set."
    REFERENCE
	"ITU-T Rec. Q.751.1 (1997), ANSI T1.116.1 (2000), ASN.1 
	 StpScreeningTableLineContent .StpScreeningElement 
	 .designatedDPC .dpcRange .lastDPC"
    ::= { mtpGsLineContentEntry 3 }

mtpGsLineContentSiMask OBJECT-TYPE
    SYNTAX MtpSiMask
    MAX-ACCESS read-create
    STATUS current
    DESCRIPTION
	"Provides a set-valued mask of the service indicators to which 
	 this rule is applicable."
    ::= { mtpGsLineContentEntry 4 }

mtpGsLineContentMessageTreatment OBJECT-TYPE
    SYNTAX MtpGsTreatment
    MAX-ACCESS read-create
    STATUS current
    DESCRIPTION
	"Specifies the treatment for messages that match this rule 
	 component.  Only normal(0) and discard(1) are specified in 
	 ITU-T Q.705.  This attribute specifies the treatment of 
	 messages that correspond to this screening entry.  It can be 
	 one of the following values:
	 
	  - normal(0): allow all STP messages outside the designated 
	    ranges; allow the message and handle as normal;
	  - discard(1): discard all STP messages outside the designated 
	    ranges, providing no indication; discard the message, 
	    providing no indication;
	  - prohibit(2): treat the destination as though it is 
	    prohibited; treat the message as a message to a prohibited 
	    destination (that is, issue a responsive transfer-prohibited 
	    message in response);
	  - unequipped(3): treat the destination as though it is an 
	    unequipped MTP user; treat the message as a message to an 
	    unequipped user (that is, issue a user-part-unavailable 
	    (unequipped) message in response);
	  - inaccessible(4): treat the destination as though it is an 
	    inaccessible MTP user; treat the message as a message to an 
	    inaccessible user (that is, issue a user-part-unavailable 
	    (inaccessible) message in response);
	  - congest(5): treat the destination as though it is congested; 
	    treat the message as a message to a congested destination 
	    (that is, issue a transfer-controlled message, with the same 
	    congestion level as the message priority in the message, in 
	    response).
	 
	 Only values normal(0) and discard(1) conform to ITU-T Rec. 
	 Q.705 Clause 8.3.
	"
    REFERENCE
	"ITU-T Rec. Q.751.1 (1997), ANSI T1.116.1 (2000), ASN.1 
	     StpScreeningTableLineContent .StpScreeningElement 
	     .mtpGsLineContentMessageTreatment"
    ::= { mtpGsLineContentEntry 5 }

mtpGsLineContentComment OBJECT-TYPE
    SYNTAX SnmpAdminString
    MAX-ACCESS read-create
    STATUS current
    DESCRIPTION
	"Provides an optional administrative string that can be used as 
	 a free-form comment for the rule."
    ::= { mtpGsLineContentEntry 6 }

mtpGsLineContentRowStatus OBJECT-TYPE
    SYNTAX RowStatus
    MAX-ACCESS read-create
    STATUS current
    DESCRIPTION
	"Provides a mechanism whereby management stations may create and 
	 delete entries in this table.  Entries created by management 
	 stations survive an agent reboot.
	 
	 Because the order of entries in this table is important, this 
	 column has the additional feature that if an attempt is made to 
	 create a row with the index value of an existing row, the entry 
	 will be inserted rather than failing.  When insertion occurs, 
	 all entries ordinally equal to or greater than the inserted 
	 entry will be renumbered one greater."
    REFERENCE
	"STD 58, SNMPv2-TC RowStatus.
	 ITU-T Rec. Q.751.1 (1997), ANSI T1.116.1 (2000), ASN.1 
	     StpScreeningTableLineContent .StpScreeningElement 
	     .designatedDPC .dpcRange .firstDPC"
    ::= { mtpGsLineContentEntry 7 }


-- ====================================================================

mtpSpProfileTable OBJECT-TYPE
    SYNTAX SEQUENCE OF MtpSpProfileEntry
    MAX-ACCESS not-accessible
    STATUS current
    DESCRIPTION
	"Provides the signalling point profile table that defines 
	 profiles for all of the signalling points provided by the 
	 managed element."
    REFERENCE
	"ITU-T Rec. Q.751.1 (1997), ANSI T1.116.1 (2000), 
	     spTimersProfile MOC."
    ::= { mtpSp 1 }

mtpSpProfileEntry OBJECT-TYPE
    SYNTAX MtpSpProfileEntry
    MAX-ACCESS not-accessible
    STATUS current
    DESCRIPTION
	"Each entry in the signalling point profile table represents a 
	 unique combination of signalling point protocol parameters and 
	 options."
    REFERENCE
	"ITU-T Rec. Q.751.1 (1997), ANSI T1.116.1 (2000), 
	     spTimersProfile MO."
    INDEX {
	mtpSpProfileId
    }
    ::= { mtpSpProfileTable 1 }

MtpSpProfileEntry ::= SEQUENCE {
    mtpSpProfileId				SimpleNameType,
    mtpSpProfileTimerT1R			TimeInterval,
    mtpSpProfileTimerT2				TimeInterval,
    mtpSpProfileTimerT4				TimeInterval,
    mtpSpProfileTimerT5				TimeInterval,
    mtpSpProfileTimerT7				TimeInterval,
    mtpSpProfileTimerT11			TimeInterval,
    mtpSpProfileTimerT12			TimeInterval,
    mtpSpProfileTimerT13			TimeInterval,
    mtpSpProfileTimerT14			TimeInterval,
    mtpSpProfileTimerT15			TimeInterval,
    mtpSpProfileTimerT16			TimeInterval,
    mtpSpProfileTimerT18I			TimeInterval,
    mtpSpProfileTimerT19I			TimeInterval,
    mtpSpProfileTimerT20I			TimeInterval,
    mtpSpProfileTimerT21I			TimeInterval,
    mtpSpProfileTimerT22I			TimeInterval,
    mtpSpProfileTimerT23I			TimeInterval,
    mtpSpProfileTimerT20A			TimeInterval,
    mtpSpProfileTimerT21A			TimeInterval,
    mtpSpProfileTimerT22A			TimeInterval,
    mtpSpProfileTimerT23A			TimeInterval,
    mtpSpProfileTimerT24A			TimeInterval,
    mtpSpProfileTimerT26A			TimeInterval,
    mtpSpProfileTimerT27A			TimeInterval,
    mtpSpProfileTimerT1T			TimeInterval,
    mtpSpProfileTimerT2T			TimeInterval,
    mtpSpProfileName				SimpleNameType,
    mtpSpRsDefault				SimpleNameType,
    mtpSpLsDefault				SimpleNameType,
    mtpSpProfileRowStatus			RowStatus
}

mtpSpProfileId OBJECT-TYPE
    SYNTAX SimpleNameType
    MAX-ACCESS not-accessible
    STATUS current
    DESCRIPTION
	"This attribute is used for naming instances.
	 
	 Provides an index into the signalling point profile table.  
	 Rows in this table can be referred to using this index or using 
	 the RowPointer pointer.  The index valud zero (0) has special 
	 semantics: the zero index contains default default values."
    REFERENCE
	"ITU-T Rec. Q.751.1 (1997), ANSI T1.116.1 (2000), 
	     spTimersProfileId attribute."
    ::= { mtpSpProfileEntry 1 }

mtpSpProfileTimerT1R OBJECT-TYPE
    SYNTAX TimeInterval (50..120)
    UNITS "centiseconds"
    MAX-ACCESS read-create
    STATUS current
    DESCRIPTION
	"This attribute defines the initial timer value of timer T1R, 
	 MTP restart timer, defined in ITU-T Recommendation Q.704, ANSI 
	 T1.111.4, ETSI ETS 300 0080-1.  The value range is 500 to 1200 
	 milliseconds, with a minimum value of 800 milliseconds for long 
	 delay links.
	 
	 This timer value and associated procedure are applicable to 
	 both ITU-T and ANSI based protocol variants.
	 
	 This is the same as timer T1 for signalling links, but is used 
	 to determine the amount of time from the last failed signalling 
	 link until restart is required.
	 
	 When the timer expires, mark restart.  (ANSI procedures call 
	 for the extension of the MTP unavailability period by T27a so 
	 that adjacent nodes are aware of the restart condition.  Note 
	 that this is about the time of T1 + T2 which is the amount of 
	 time taken for the remote end to institute and complete 
	 changeover procedures for the restarting node.)  When the first 
	 link is in service at level 2 (and T27a is not running or 
	 expires), additional actions will be performed."
    DEFVAL { 80 }
    ::= { mtpSpProfileEntry 2 }

mtpSpProfileTimerT2 OBJECT-TYPE
    SYNTAX TimeInterval
    UNITS "centiseconds"
    MAX-ACCESS read-create
    STATUS current
    DESCRIPTION
	"This attribute defines the initial timer value of timer T2 
	 'Waiting for changeover acknowledgement' defined in 
	 Recommendation Q.704.  The value range is from 700 to 2000 ms.  
	 For routes with long propagation delays a minimum value of 1400 
	 ms is used."
    REFERENCE
	"ITU-T Rec. Q.751.1 (1997), ANSI T1.116.1 (2000), q704-t2 
	 attribute."
    ::= { mtpSpProfileEntry 3 }

mtpSpProfileTimerT4 OBJECT-TYPE
    SYNTAX TimeInterval
    MAX-ACCESS read-create
    STATUS current
    DESCRIPTION
	"This attribute defines the initial timer value of timer T4 
	 'Waiting for changeback acknowledgement (first attempt)' 
	 defined in Recommendation Q.704.  The value range is from 500 
	 to 1200 ms.  For routes with long propagation delays a minimum 
	 value of 800 ms is used."
    REFERENCE
	"ITU-T Rec. Q.751.1 (1997), ANSI T1.116.1 (2000), q704-t4 
	 attribute."
    ::= { mtpSpProfileEntry 4 }

mtpSpProfileTimerT5 OBJECT-TYPE
    SYNTAX TimeInterval
    MAX-ACCESS read-create
    STATUS current
    DESCRIPTION
	"This attribute defines the initial timer value of timer T5 
	 Waiting for changeback acknowledgement (second attempt) defined 
	 in Recommendation Q.704.  The value range is from 500 to 1200 
	 ms.  For routes with long propagation delays a minimum value of 
	 800 ms is used."
    REFERENCE
	"ITU-T Rec. Q.751.1 (1997), ANSI T1.116.1 (2000), q704-t5 
	 attribute."
    ::= { mtpSpProfileEntry 5 }

mtpSpProfileTimerT7 OBJECT-TYPE
    SYNTAX TimeInterval
    MAX-ACCESS read-create
    STATUS current
    DESCRIPTION
	"This attribute defines the initial timer value of timer T7 
	 Waiting for signalling data link connection acknowledgement 
	 defined in Recommendation Q.704.  The value range is from 1 to 
	 2 seconds."
    REFERENCE
	"ITU-T Rec. Q.751.1 (1997), ANSI T1.116.1 (2000), q704-t7 
	 attribute."
    ::= { mtpSpProfileEntry 6 }

mtpSpProfileTimerT11 OBJECT-TYPE
    SYNTAX TimeInterval
    MAX-ACCESS read-create
    STATUS current
    DESCRIPTION
	"This attribute defines the initial timer value of timer T11 
	 Transfer restricted timer defined in Recommendation Q.704.  The 
	 value range is from 30 to 90 seconds.  This is one way of 
	 implementing the function described in 
	 13.4/Q.704 and mainly intended to simplify STPs."
    REFERENCE
	"ITU-T Rec. Q.751.1 (1997), ANSI T1.116.1 (2000), q704-t11 
	 attribute."
    ::= { mtpSpProfileEntry 7 }

mtpSpProfileTimerT12 OBJECT-TYPE
    SYNTAX TimeInterval
    MAX-ACCESS read-create
    STATUS current
    DESCRIPTION
	"This attribute defines the initial timer value of timer T12 
	 Waiting for uninhibit acknowledgement defined in Recommendation 
	 Q.704.  The value range is from 800 to 
	 1500 ms."
    REFERENCE
	"ITU-T Rec. Q.751.1 (1997), ANSI T1.116.1 (2000), q704-t12 
	 attribute."
    ::= { mtpSpProfileEntry 8 }

mtpSpProfileTimerT13 OBJECT-TYPE
    SYNTAX TimeInterval
    MAX-ACCESS read-create
    STATUS current
    DESCRIPTION
	"This attribute defines the initial timer value of timer T13 
	 Waiting for force uninhibit defined in Recommendation Q.704.  
	 The value range is from 800 to 
	 1500 ms."
    REFERENCE
	"ITU-T Rec. Q.751.1 (1997), ANSI T1.116.1 (2000), q704-t13 
	 attribute."
    ::= { mtpSpProfileEntry 9 }

mtpSpProfileTimerT14 OBJECT-TYPE
    SYNTAX TimeInterval
    MAX-ACCESS read-create
    STATUS current
    DESCRIPTION
	"This attribute defines the initial timer value of timer T14 
	 Waiting for inhibition acknowledgement defined in 
	 Recommendation Q.704.  The value range is from 2 to 3 seconds."
    REFERENCE
	"ITU-T Rec. Q.751.1 (1997), ANSI T1.116.1 (2000), q704-t14 
	 attribute."
    ::= { mtpSpProfileEntry 10 }

mtpSpProfileTimerT15 OBJECT-TYPE
    SYNTAX TimeInterval
    MAX-ACCESS read-create
    STATUS current
    DESCRIPTION
	"This attribute defines the initial timer value of timer T15 
	 Waiting to start signalling route set congestion test defined 
	 in Recommendation Q.704.  The value range is from 2 to 3 
	 seconds."
    REFERENCE
	"ITU-T Rec. Q.751.1 (1997), ANSI T1.116.1 (2000), q704-t15 
	 attribute."
    ::= { mtpSpProfileEntry 11 }

mtpSpProfileTimerT16 OBJECT-TYPE
    SYNTAX TimeInterval
    MAX-ACCESS read-create
    STATUS current
    DESCRIPTION
	"This attribute defines the initial timer value of timer T16 
	 Waiting for route set congestion status update defined in 
	 Recommendation Q.704.  The value range is from 1.4 to 2 
	 seconds."
    REFERENCE
	"ITU-T Rec. Q.751.1 (1997), ANSI T1.116.1 (2000), q704-t16 
	 attribute."
    ::= { mtpSpProfileEntry 12 }

mtpSpProfileTimerT18I OBJECT-TYPE
    SYNTAX TimeInterval
    UNITS "centiseconds"
    MAX-ACCESS read-create
    STATUS current
    DESCRIPTION
	"This attribute defines the initial timer value of timer T18 
	 defined in Recommendation Q.704.  T18 is the Timer within a 
	 signalling point whose MTP restarts, for supervising link and 
	 linkset activation as well as the receipt of routing 
	 information.  The value is implementation and network 
	 dependent.  Criteria to choose T18 are given in 9.2/Q.704.
	 
	 This timer value and associated procedure are only applicable 
	 to ITU-T based signalling protocol variants.
	 
	 Timer T18 is a phase 1 restart timer and is started by a 
	 restarting signalling point with the transfer function when the 
	 first link goes into service at level 2.
	 
	 9.2.2 ... Timer T18 is implementation and network dependent, 
	   and is stopped when:
	 
	   1. sufficient links and link sets are available to carry the 
	      expected signalling traffic; and
	 
	   2. enough TRA messages (and therefore routing data) have been 
	      received to give a high level of confidence in the MTP 
	      routing tables.
	 
	   NOTE - In normal circumstances the restarting MTP should wait 
	   for TRA messages from all adjacent nodes.  There are, 
	   however, other situations where this might not be useful, 
	   e.g. for a long-term equipment failure.
	 
	   When T18 is stopped or expires, these second phase begins, 
	   which includes as a major part a broadcast of 
	   non-preventative transfer prohibited messages [i.e. those 
	   TFPs according to 13.2.2 v)] and transfer-restricted 
	   messages, taking into account signalling link sets which are 
	   not available and any TFP, TFA and TFR messages received 
	   during phase 1.  Note that timer T18 is determined such that 
	   during phase 2 the broadcast of TFP and TFR messages may be 
	   completed in normal situations."
    REFERENCE
	"ITU-T Rec. Q.751.1 (1997), ANSI T1.116.1 (2000), q704-t18 
	     attribute."
    DEFVAL { 60000 }
    ::= { mtpSpProfileEntry 13 }

mtpSpProfileTimerT19I OBJECT-TYPE
    SYNTAX TimeInterval
    MAX-ACCESS read-create
    STATUS current
    DESCRIPTION
	"This attribute defines the initial timer value of timer T19 
	 Supervision timer during MTP restart to avoid possible 
	 ping-pong of TFP, TFR and TRA messages.  defined in 
	 Recommendation Q.704.  The value range is from 67 to 69 
	 seconds."
    REFERENCE
	"ITU-T Rec. Q.751.1 (1997), ANSI T1.116.1 (2000), q704-t19 
	 attribute."
    ::= { mtpSpProfileEntry 14 }

mtpSpProfileTimerT20I OBJECT-TYPE
    SYNTAX TimeInterval (5900..6100)
    UNITS "centiseconds"
    MAX-ACCESS read-create
    STATUS current
    DESCRIPTION
	"This attribute defines the initial timer value of timer T20 
	 Overall MTP restart timer at the signalling point whose MTP 
	 restarts, defined in Recommendation Q.704.  The value range is 
	 from 59 to 61 seconds.
	 
	 This timer value and associated procedure are only applicable 
	 to ITU-T based signalling protocol variants.
	 
	 Timer T20 is an overall restart timer that is started by a 
	 restarting signalling point when the first link goes into 
	 service at level 2.
	 
	 9.2.2 ... When all TFP and TFR messages have been sent, the 
	   overall restart timer T20 is stopped and phase 2 is finished.  
	   Note that preventative TFP messages [i.e. those according to 
	   13.2.2 i)], except possibly those for highest priority 
	   routes, must have been sent before normal User traffic is 
	   carried.  This might be done during or after phase 2.
	 
	 9.2.3 If the restarting MTP has no transfer function, phase 1 
	   (see 9.2.2) but not phase 2 is present.  In this case, the 
	   whole restart time is available for phase 1.  The overall 
	   restart timer T20 is stopped when:
	 
	   1. sufficient links and link sets are available to carry the 
	      expected signalling traffic; and
	 
	   2. enough TRA messages (and therefore routing data) have been 
	      received to give a high level of confidence in the MTP 
	      routing tables.
	 
	 9.2.4  When T20 is stopped or expires, the restarting MTP of 
	   the signalling point or signalling transfer point sends 
	   traffic restart allowed messages to all adjacent signalling 
	   points via corresponding available direct link sets, and an 
	   indication of the end of MTP restart is sent to all local MTP 
	   Users showing each signalling point's accessibility or 
	   inaccessibility.  The means of doing the latter is 
	   implementation dependent.
	 
	   In addition, [to sending TRA] timer T19 is started (see 
	   9.5.2) for all signalling points to which a TRA message has 
	   just been sent.  Normal operation is then resumed.
	 
	   When T20 expires the transmission of TFP and TFR messages is 
	   stopped.  However, preventative TFP messages [i.e. those 
	   according to 13.2.2 i)] except possibly those for highest 
	   priority routes, must have been sent before MTP User traffic 
	   is restarted."
    REFERENCE
	"ITU-T Rec. Q.751.1 (1997), ANSI T1.116.1 (2000), q704-t20 
	     attribute."
    DEFVAL { 6000 }
    ::= { mtpSpProfileEntry 15 }

mtpSpProfileTimerT21I OBJECT-TYPE
    SYNTAX TimeInterval
    MAX-ACCESS read-create
    STATUS current
    DESCRIPTION
	"This attribute defines the initial timer value of timer T21 
	 Overall MTP restart timer at a signalling point adjacent to one 
	 whose MTP restarts, defined in Recommendation Q.704.  The value 
	 range is from 63 to 65 seconds."
    REFERENCE
	"ITU-T Rec. Q.751.1 (1997), ANSI T1.116.1 (2000), q704-t21 
	 attribute."
    ::= { mtpSpProfileEntry 16 }

mtpSpProfileTimerT22I OBJECT-TYPE
    SYNTAX TimeInterval
    MAX-ACCESS read-create
    STATUS current
    DESCRIPTION
	"This attribute defines the initial timer value of timer T22 
	 Local inhibit test timer defined in Recommendation Q.704.  The 
	 value range is from 3 to 6 minutes (provisional value)."
    REFERENCE
	"ITU-T Rec. Q.751.1 (1997), ANSI T1.116.1 (2000), q704-t22 
	 attribute."
    ::= { mtpSpProfileEntry 17 }

mtpSpProfileTimerT23I OBJECT-TYPE
    SYNTAX TimeInterval
    MAX-ACCESS read-create
    STATUS current
    DESCRIPTION
	"This attribute defines the initial timer value of timer T23 
	 Remote inhibit test timer defined in Recommendation Q.704.  The 
	 value range is from 3 to 6 minutes (provisional value)."
    REFERENCE
	"ITU-T Rec. Q.751.1 (1997), ANSI T1.116.1 (2000), q704-t23 
	 attribute."
    ::= { mtpSpProfileEntry 18 }

mtpSpProfileTimerT20A OBJECT-TYPE
    SYNTAX TimeInterval (9000..12000)
    UNITS "centiseconds"
    MAX-ACCESS read-create
    STATUS current
    DESCRIPTION
	"This attribute defines the initial timer value of timer T20 
	 (ANSI) local inihibit test timer defined in ANSI T1.111.4 
	 10.3A.  The value range is from 90 to 120 seconds (1.5 to 2 
	    minutes).
	 
	 Note that timer T20(ANSI) is equivalent to timer T22(ITU-T) in 
	 function but has a range from 1.5 to 2.0 minutes instead of 3 
	 to 6 minutes.
	 
	 This timer value and associated procedure is appliable only to 
	 ANSI based protocol variants.
	 
	 ANSI T1.111.4/2000 10.3A (Inhibit Test Procedure Actions).  
	 When a signalling link becomes inibited, either locally, 
	 remotely or both, the following test procedure actions take 
	 place, as appropriate:
	 
	 1. If timer T20 expires at signalling point X and the 
	    signalling link is locally inhibited at signalling point X, 
	    signalling point X transmits a local inhibit test message to 
	    the signalling point at the other end of the locally 
	    inhibited link and restarts timer T20.
	 
	 2. If timer T20 expires at signalling point X and the 
	    signalling link is no longer locally inhibited, no action is 
	    taken.
	 
	 3. If timer T21 expires at signalling point X and the 
	    signalling link is remotely inhibtied at signalling point X, 
	    signalling point X transmits a remote inhibit teset message 
	    to the signalling point at the other end of the remotely 
	    inhibited link and restarts timer T21.
	 
	 4. If timer T21 expires at signalling point X and the 
	    signalling link is no longer remotely inihibited, no action 
	    is taken.
	 
	 5. If signalling point Y receives a local inhibit test message 
	    from signalling point X and the concerned link is marked 
	    remotely inhibited, no action is taken.
	 
	 6. If signalling point Y receoves a local inhibit test message 
	    from signalling point X and the concerned link is not marked 
	    remotely inhibited, the forced uninhibiting procedure is 
	    invoked at signalling point Y, beginning with the 
	    transmission of a force uninhibit signalling link message to 
	    signalling point X.  As a result of this procedure, the 
	    local inhibit indicator is canceled at signalling point X.
	 
	 7. If signalling point Y receives a remote inhibit test message 
	    from signalling point X and the concerned link is marked 
	    locally inhibited, no action is taken.
	 
	 8. If signalling point Y receives a remote inhibit test message 
	    from signalling point X and the concerned signalling link is 
	    not marked locally inhibited, the uninhibiting procedure is 
	    invoked at signalling point Y, beginning with the 
	    transmission of an uninhibit signalling link message to 
	    signalling point X.  As a result of this procedure, the 
	    remote inhibit indicator is canceled at signalling point X.
	 
	 Note: ANSI Timer T20 is simply ITU-T Timer T22 renumbered."
    REFERENCE
	"ANSI T1.111.4/2000, Section 10.3A, Timer T20."
    DEFVAL { 10000 }
    ::= { mtpSpProfileEntry 19 }


mtpSpProfileTimerT21A OBJECT-TYPE
    SYNTAX TimeInterval (9000..12000)
    UNITS "centiseconds"
    MAX-ACCESS read-create
    STATUS current
    DESCRIPTION
	"This attribute defines the initial timer value of timer T21 
	 (ANSI) remote inhibit test timer defined in ANSI T1.111.4 
	 10.3A.  The value range is from 90 to 120 seconds (1.5 to 2 
	    minutes).
	 
	 Note that timer T21(ANSI) is equivalent to timer T23(ITU-T) in 
	 function but has a range from 1.5 to 2.0 minutes instead of 3 
	 to 6 minutes.
	 
	 This timer value and associated procedure is appliable only to 
	 ANSI based protocol variants.
	 
	 ANSI T1.111.4/2000 10.3A (Inhibit Test Procedure Actions).  
	 When a signalling link becomes inibited, either locally, 
	 remotely or both, the following test procedure actions take 
	 place, as appropriate:
	 
	 1. If timer T20 expires at signalling point X and the 
	    signalling link is locally inhibited at signalling point X, 
	    signalling point X transmits a local inhibit test message to 
	    the signalling point at the other end of the locally 
	    inhibited link and restarts timer T20.
	 
	 2. If timer T20 expires at signalling point X and the 
	    signalling link is no longer locally inhibited, no action is 
	    taken.
	 
	 3. If timer T21 expires at signalling point X and the 
	    signalling link is remotely inhibtied at signalling point X, 
	    signalling point X transmits a remote inhibit teset message 
	    to the signalling point at the other end of the remotely 
	    inhibited link and restarts timer T21.
	 
	 4. If timer T21 expires at signalling point X and the 
	    signalling link is no longer remotely inihibited, no action 
	    is taken.
	 
	 5. If signalling point Y receives a local inhibit test message 
	    from signalling point X and the concerned link is marked 
	    remotely inhibited, no action is taken.
	 
	 6. If signalling point Y receoves a local inhibit test message 
	    from signalling point X and the concerned link is not marked 
	    remotely inhibited, the forced uninhibiting procedure is 
	    invoked at signalling point Y, beginning with the 
	    transmission of a force uninhibit signalling link message to 
	    signalling point X.  As a result of this procedure, the 
	    local inhibit indicator is canceled at signalling point X.
	 
	 7. If signalling point Y receives a remote inhibit test message 
	    from signalling point X and the concerned link is marked 
	    locally inhibited, no action is taken.
	 
	 8. If signalling point Y receives a remote inhibit test message 
	    from signalling point X and the concerned signalling link is 
	    not marked locally inhibited, the uninhibiting procedure is 
	    invoked at signalling point Y, beginning with the 
	    transmission of an uninhibit signalling link message to 
	    signalling point X.  As a result of this procedure, the 
	    remote inhibit indicator is canceled at signalling point X.
	 
	 Note: ANSI Timer T21 is simply ITU-T Timer T23 renumbered."
    REFERENCE
	"ANSI T1.111.4/2000, Section 10.3A, Timer T21."
    DEFVAL { 10000 }
    ::= { mtpSpProfileEntry 20 }

mtpSpProfileTimerT22A OBJECT-TYPE
    SYNTAX TimeInterval
    UNITS "centiseconds"
    MAX-ACCESS read-create
    STATUS current
    DESCRIPTION
	"
	 The value range is implementation and network dependent.
	 
	 This timer value and associated procedure is only applicable to 
	 ANSI based signalling protocol variants.
	 
	 ANSI T1.111.4/20000 9.2 ... When the first signalling link goes 
	    into the in service state at level 2, the restarting 
	    signalling point begins taking into account any 
	    transfer-prohibited, transfer-restricted, transfer-allowed, 
	    traffic restart allowed, and traffic restart waiting 
	    messages received.  The restarting point starts timers T22 
	    and T26 either when the first signalling link goes into the 
	    in service state at level 2 or when the first signalling 
	    link becomes available at level 3.  When a traffic restart 
	    waiting message is received before user traffic is restarted 
	    on the link(s) to the point that sent the traffic restart 
	    waiting message, timer T25 is started and user traffic is 
	    not restarted on that link set until after a traffic restart 
	    allowed message is received or timer T25 expires (see 9.3).
	 
	    When the first signalling link of a signalling link set is 
	    available, MTP message traffic terminating at the far end of 
	    the signalling link set is immediately restarted (see also 
	    9.5), and a traffic restart waiting message is sent to the 
	    point at the end of the link set.
	 
	    Whenever timer T26 expires, the restarting signalling point 
	    restarts timer T26 and broadcasts a traffic restart waiting 
	    message to those adjacent signalling points connected by an 
	    available link.
	 
	    T22 is stopped when sufficient links are available to carry 
	    the expected signalling traffic: stopping T22 is a 
	    management decision that may take into account factors such 
	    as the known long term unavailability of certain signalling 
	    links because of equipment failures.
	 
	    When T22 is stopped or expires, the signalling point starts 
	    a timer T23, during which it expects to receive additional 
	    transfer-prohibited, transfer-restricted, transfer-allowed 
	    (see Section 13), traffic restart waiting, and traffic 
	    restart allowed messages.  When traffic restart allowed 
	    message have been received for all available links or the 
	    management function determines that sufficient traffic 
	    restart allowed messages have been received that the 
	    expected traffic can be handled, T23 is stopped.
	 
	 IMPLEMENTATION NOTES:- T22 is used to place an upper limit on 
	    the availability of sufficient signalling links to handle 
	    the expected load.  A good rule of thumb would be that when 
	    at least half of the signalling links in each signalling 
	    link set are available, that there are sufficient links 
	    available to handle traffic; however, this does not include 
	    the knowledge of long term failures.  Note that T22 is set 
	    to about 10 minutes, and it would be really bad if there was 
	    a signalling link set will long term link failures that kept 
	    it below the rule of thumb causing the restart to take 
	    longer than 10 minutes.  Therefore a better rule of thumb 
	    might be that half the signalling links are either active or 
	    management blocked or in link oscillation lockout.  With 
	    reference to ITU, this is still Restart Phase 1 and the next 
	    phase is also Restart Phase 1."
    DEFVAL { 60000 }
    ::= { mtpSpProfileEntry 21 }

mtpSpProfileTimerT23A OBJECT-TYPE
    SYNTAX TimeInterval
    UNITS "centiseconds"
    MAX-ACCESS read-create
    STATUS current
    DESCRIPTION
	"The value range is implementation and network dependent.
	 
	 This timer value and associated procedure is only applicable to 
	 ANSI based signalling protocol variants.
	 
	 ANSI T1.111.4/2000 9.2 ... When T23 is stopped or expires, the 
	    signalling point starts a timer T24, during which it 
	    broadcasts transfer-prohibited and transfer-restricted 
	    messages (see Section 13), taking into account signalling 
	    links which are not available and at least those transfer 
	    prohibited, transfer-restricted and transfer-allowed message 
	    that were received before T23 expired or was stopped.  
	    Before user traffic is restarted, preventative 
	    transfer-prohibited messages according to 13.2.2 (1) must be 
	    sent.  Whether these preventative transfer-prohibited 
	    messages are sent for all routes or only for alternate 
	    routes is a network option.  When the broadcast of 
	    transfer-prohibited and transfer-restricted messages is 
	    completed, timer T24 is stopped.
	 
	 IMPLEMENTATION NOTES:- In ANSI T22 and T23 are similar to ITU-T 
	    T18.  After expiry of T23 or T18, the broadcast of 
	    transfer-prohibited, transfer-restricted and 
	    transfer-allowed messages begins.  ANSI starts T24 in the 
	    same way that ITU-T (use to) starts T19.  ANSI T26 is the 
	    overall timer that is roughly equivalent to ITU T20 (T26 
	    rebroadcasts TRW during the entire restart period)."
    DEFVAL { 60000 }
    ::= { mtpSpProfileEntry 22 }

mtpSpProfileTimerT24A OBJECT-TYPE
    SYNTAX TimeInterval
    UNITS "centiseconds"
    MAX-ACCESS read-create
    STATUS current
    DESCRIPTION
	"The value range is implementation and network dependent.
	 
	 This timer value and associated procedure is only applicable to 
	 ANSI based signalling protocol variants.
	 
	 ANSI T1.111.4/2000 9.2 ... When T24 is stopped, timer T26 is 
	     also stopped, and the signalling point broadcasts traffic 
	     restart allowed message to all adjacent signalling points 
	     and restarts the remaining traffic by giving MTP-RESUME 
	     primitives to users for all accessible destinations.  It 
	     also starts timer T29 for those points to which it has sent 
	     a traffic restart allowed message.
	 
	     If T24 expires, the sending of any transfer-prohibited 
	     messages required by 13.2.2 (1) is completed, timer T26 is 
	     stopped, and the signalling point broadcasts traffic 
	     restart allowed messages to all adjacent signalling points 
	     and restarts the remaining traffic by giving MTP-RESUME 
	     primitives to users for all accessible destinations.  It 
	     also starts timer T29 for those points to which it has sent 
	     a traffic restart allowed message."
    DEFVAL { 60000 }
    ::= { mtpSpProfileEntry 23 }

mtpSpProfileTimerT26A OBJECT-TYPE
    SYNTAX TimeInterval (1200..1500)
    UNITS "centiseconds"
    MAX-ACCESS read-create
    STATUS current
    DESCRIPTION
	"The value range is 12 to 15 seconds.
	 
	 This timer value and associated procedure is only applicable to 
	 ANSI based signalling protocol variants.
	 
	 ANSI T1.111.4/20000 9.2 ... When the first signalling link goes 
	    into the in service state at level 2, the restarting 
	    signalling point begins taking into account any 
	    transfer-prohibited, transfer-restricted, transfer-allowed, 
	    traffic restart allowed, and traffic restart waiting 
	    messages received.  The restarting point starts timers T22 
	    and T26 either when the first signalling link goes into the 
	    in service state at level 2 or when the first signalling 
	    link becomes available at level 3.  When a traffic restart 
	    waiting message is received before user traffic is restarted 
	    on the link(s) to the point that sent the traffic restart 
	    waiting message, timer T25 is started and user traffic is 
	    not restarted on that link set until after a traffic restart 
	    allowed message is received or timer T25 expires (see 9.3).
	 
	    When the first signalling link of a signalling link set is 
	    available, MTP message traffic terminating at the far end of 
	    the signalling link set is immediately restarted (see also 
	    9.5), and a traffic restart waiting message is sent to the 
	    point at the end of the link set.
	 
	    Whenever timer T26 expires, the restarting signalling point 
	    restarts timer T26 and broadcasts a traffic restart waiting 
	    message to those adjacent signalling points connected by an 
	    available link."
    DEFVAL { 1350 }
    ::= { mtpSpProfileEntry 24 }

mtpSpProfileTimerT27A OBJECT-TYPE
    SYNTAX TimeInterval (200..500)
    UNITS "centiseconds"
    MAX-ACCESS read-create
    STATUS current
    DESCRIPTION
	"This timer value and associated procedure is only applicable to 
	 ANSI based signalling protocol variants.
	 
	 ANSI T1.111.4/2000 9.1 (Actions in a Signalling Point Having 
	     the Transfer Function Which Restarts.) ... If the 
	     management function determines that a full restart 
	     procedure is needed, then it ensures, for example, by using 
	     local processor outage, that the period of unavailability 
	     persists for a time of at least T27.  The purpose of 
	     remaining unavailable for time T27 is to increase the 
	     probability that adjacent points are aware of the 
	     unavailability of the restarting point and initiate the 
	     appropriate restart procedures (see 9.3).
	 
	 Timer T27:
	 Start:	    When SP becomes unavailable (SPF_RESTART_LOCKOUT flag 
		    set)
	 Stop:	    When SP restarts without requiring restart procedure 
		    (SPF_RESTART_LOCKOUT flag cleared)
	 Timeout:   Deassert local processor outage condition on 
		    signalling links that realigned during the period 
		    that T27 was running.
	 
	 Signalling links that are in restart lockout are signalling 
	 links that aligned during the T27a lockout period and were 
	 placed into local processor outage state to affect the lockout.  
	 Other options include suppressing activation of the signalling 
	 link, or stopping signalling link that was in a processor 
	 outage situation.  (Note that not all types of signalling links 
	 support processor outage.) At any rate, depending on the state 
	 of the signalling link at the time that the outage is to be 
	 cleared, the next action is determined.  The purpose is always 
	 to return the signalling link to the active state unless it is 
	 locally blocked by management."
    DEFVAL { 300 }
    ::= { mtpSpProfileEntry 25 }

mtpSpProfileTimerT1T OBJECT-TYPE
    SYNTAX TimeInterval
    MAX-ACCESS read-create
    STATUS current
    DESCRIPTION
	"This attribute defines a timer value of timer T1 which is 
	 defined in Recommendation Q.707."
    REFERENCE
	"ITU-T Rec. Q.751.1 (1997), ANSI T1.116.1 (2000), q707-t1 
	 attribute."
    ::= { mtpSpProfileEntry 26 }

mtpSpProfileTimerT2T OBJECT-TYPE
    SYNTAX TimeInterval
    MAX-ACCESS read-create
    STATUS current
    DESCRIPTION
	"This attribute defines a timer value of timer T2 which is 
	 defined in Recommendation Q.707."
    REFERENCE
	"ITU-T Rec. Q.751.1 (1997), ANSI T1.116.1 (2000), q707-t2 
	 attribute."
    ::= { mtpSpProfileEntry 27 }

mtpSpProfileName OBJECT-TYPE
    SYNTAX SimpleNameType
    MAX-ACCESS read-create
    STATUS current
    DESCRIPTION
	"Provides an optional administrative name for this signalling 
	 point protocol profile.
	 
	 This attribute is an additional name for instances of the 
	 spTimersProfile managed object class."
    REFERENCE
	"ITU-T Rec. Q.751.1 (1997), ANSI T1.116.1 (2000), attribute."
    ::= { mtpSpProfileEntry 28 }

mtpSpRsDefault OBJECT-TYPE
    SYNTAX SimpleNameType
    MAX-ACCESS not-accessible
    STATUS current
    DESCRIPTION
	"Provides a reference to an MTP Level 3 signalling route set 
	 protocol profile for use when creating signalling route sets 
	 that belong to this signalling point.  When unspecified, a 
	 value must be specified when creating signalling route sets for 
	 this signalling point."
    ::= { mtpSpProfileEntry 29 }

mtpSpLsDefault OBJECT-TYPE
    SYNTAX SimpleNameType
    MAX-ACCESS not-accessible
    STATUS current
    DESCRIPTION
	"Provides a reference to an MTP Level 3 signalling link set 
	 protocol profile for use when creating signalling link sets 
	 that belong to this singalling point.  When unspecified, a 
	 value must be specified when creating signalling link sets for 
	 this signalling point."
    ::= { mtpSpProfileEntry 30 }

mtpSpProfileRowStatus OBJECT-TYPE
    SYNTAX RowStatus
    MAX-ACCESS read-create
    STATUS current
    DESCRIPTION
	"Provides a mechanism whereby management stations may create and 
	 delete entries in this table.  Entries created by management 
	 stations survive an agent reboot.
	 
	 If the name package is supported: a create request with a value 
	 for the name attribute that is already used by another instance 
	 of the same object class will be rejected.  If an attempt is 
	 made to delete an spTimersProfile which is still referenced by 
	 an mtpSignPoint the delete request will be rejected."
    REFERENCE
	"STD 58, SNMPv2-TC RowStatus.
	 ITU-T Rec. Q.751.1 (1997) : 
	     managedSwitchingElement-spTimersProfile NAME BINDING."
    ::= { mtpSpProfileEntry 31 }


-- ====================================================================

mtpSpTable OBJECT-TYPE
    SYNTAX SEQUENCE OF MtpSpEntry
    MAX-ACCESS not-accessible
    STATUS current
    DESCRIPTION
	"Provides the signalling point table which defines all of the 
	 signalling points provided by the managed element.
	 
	 A signalling point is a node in the signalling network.  It is 
	 part of a managed switching element (exchange).  The MTP 
	 permits three types of node:
	 
	  - SEP: the signalling end point, this type of SP contains MTP 
	    and ISUP (and or other MTP Users), but cannot act as an 
	    intermediate MTP transfer node in the SS No.7 network.  (It 
	    can act as an SCCP Relay Node.)
	 
	  - STP: the MTP signalling transfer point, this type of SP acts 
	    as an intermediate node between SEPs to transfer messages 
	    through the SS No.7-network, it only contains MTP.  (In case 
	    of an STP, OMAP, and hence also TC and SCCP may be present.)
	 
	  - STEP: MTP signalling transfer and end point, the type 
	    combines the previous mentioned types, thus acting both as a 
	    SEP and as a STP.
	 
	 A mtpSignPoint can have the MTP status:
	 
	  - allowed, this means that the mtpSignPoint is accessible and 
	    is functioning normally (operational state = enabled, 
	    availability status = '')
	 
	  - congested, this means that the mtpSignPoint is accessible 
	    but is heavily loaded (operational state = enabled, 
	    availability status = {degraded})
	 
	  - prohibited, this means that the mtpSignPoint not accessible 
	    (operational state = disabled).
	 
	 During MTP restart, the proceduralStatus is {initializing} 
	 until the restart is finished."
    REFERENCE
	"ITU-T Rec. Q.751.1 (1997), ANSI T1.116.1 (2000), mtpSignPoint 
	 MOC."
    ::= { mtpSp 2 }

mtpSpEntry OBJECT-TYPE
    SYNTAX MtpSpEntry
    MAX-ACCESS not-accessible
    STATUS current
    DESCRIPTION
	"Provides an entry in the signalling point table.  Each entry 
	 provides fundamental information about the signalling point as 
	 well as protocol profile defaults for route sets and link sets 
	 created for the signalling point.
	 
	 Entries in this table can generate a qualityOfServiceAlarm with 
	 the following parameters:
	 
	  - ITU-T Rec. Q.752 (1997) : Table 5/Q.752, 5.5,
		probableCause = 505 (routingDataError)
		(also first and interval)
	  - ITU-T Rec. Q.752 (1997) : Table 5/Q.752, 5.6,
		probableCause = 506 (userPartUnavailableSent)
		(also first and interval)
	  - ITU-T Rec. Q.752 (1997) : Table 5/Q.752, 5.7,
		probableCause = 507 (userPartUnavailableReceived)
		(also first and interval)
	  - ITU-T Rec. Q.752 (1997) : Table 5/Q.752, 5.8,
		probableCause = 508 (transferControlledReceived)
		(also first and interval)
	"
    REFERENCE
	"ITU-T Rec. Q.751.1 (1997), ANSI T1.116.1 (2000), mtpSignPoint 
	 MO."
    INDEX {
	mtpMsId,
	mtpSpId
    }
    ::= { mtpSpTable 1 }

MtpSpEntry ::= SEQUENCE {
    mtpSpId					Unsigned32,
    mtpSpPointCode				NetworkPointCode,
    mtpSpType					MtpSpType,
    mtpSpOperationalState			OperationalState,
    mtpSpProceduralStatus			ProceduralStatus,
    mtpSpAvailabilityStatus			AvailabilityStatus,
    mtpSpVersion				GraphicString,
    mtpSpNetworkIndicator			MtpNetworkIndicator,
    mtpSpName					SimpleNameType,
    mtpSpMtpT1					TimeInterval,
    mtpSpMtpT2					TimeInterval,
    mtpSpMtpT3					TimeInterval,
    mtpSpMtpT4					TimeInterval,
    mtpSpMtpT5					TimeInterval,
    mtpSpMtpT6					TimeInterval,
    mtpSpMtpT7					TimeInterval,
    mtpSpMtpT8					TimeInterval,
    mtpSpMtpT10					TimeInterval,
    mtpSpMtpT11					TimeInterval,
    mtpSpMtpT12					TimeInterval,
    mtpSpMtpT13					TimeInterval,
    mtpSpMtpT14					TimeInterval,
    mtpSpMtpT15					TimeInterval,
    mtpSpMtpT16					TimeInterval,
    mtpSpMtpT17					TimeInterval,
    mtpSpMtpT19A				TimeInterval,
    mtpSpMtpT31A				TimeInterval,
    mtpSpMtpT32A				TimeInterval,
    mtpSpMtpT33A				TimeInterval,
    mtpSpMtpT34A				TimeInterval,
    mtpSpMtpT18I				TimeInterval,
    mtpSpMtpT19I				TimeInterval,
    mtpSpMtpT20I				TimeInterval,
    mtpSpMtpT21I				TimeInterval,
    mtpSpMtpT22I				TimeInterval,
    mtpSpMtpT23I				TimeInterval,
    mtpSpMtpT20A				TimeInterval,
    mtpSpMtpT21A				TimeInterval,
    mtpSpMtpT24I				TimeInterval,
    mtpSpMtpT1T					TimeInterval,
    mtpSpMtpT2T					TimeInterval,
    mtpSpMtpT1S					TimeInterval,
    mtpSpProfilePointer				SimpleNameType,
    mtpSpNaPointer				SimpleNameType,
    mtpSpFlags					BITS,
    mtpSpUsers					MtpSiMask,
    mtpSpAlarmStatus				AlarmStatus,
    mtpSpRowStatus				RowStatus
}

mtpSpId OBJECT-TYPE
    SYNTAX Unsigned32
    MAX-ACCESS not-accessible
    STATUS current
    DESCRIPTION
	"Provides an into the signalling point table.  This attribute is 
	 used for naming instances."
    REFERENCE
	"ITU-T Rec. Q.751.1 (1997), ANSI T1.116.1 (2000), mtpSignPointId 
	     attribute."
    ::= { mtpSpEntry 1 }

mtpSpPointCode OBJECT-TYPE
    SYNTAX NetworkPointCode
    MAX-ACCESS read-create
    STATUS current
    DESCRIPTION
	"Specifies the network signalling point code associated  with 
	 this signalling point.
	 
	 This attribute represents the pointcode of a certain SP.  Note 
	 that point codes are 14-bit for ITU (0..16383) and 24-bit for 
	 ANSI (0..16777215)."
    REFERENCE
	"ITU-T Rec. Q.751.1 (1997), ANSI T1.116.1 (2000), pointCode 
	     attribute."
    ::= { mtpSpEntry 2 }

mtpSpType OBJECT-TYPE
    SYNTAX MtpSpType
    MAX-ACCESS read-create
    STATUS current
    DESCRIPTION
	"This attribute represents the SP-type: SEP, STEP or STP.
	 
	  - sep(0), the Signalling End Point (SEP) is a signalling point 
	    that is equipped with local user parts but is not equipped 
	    with the transfer function; i.e. the system is an 
	    end-system (ES);
	 
	  - step(1), the Signalling Transfer End Point (STEP) is a 
	    signalling point that is both a signalling end point (it has 
	    user parts) and a signalling transfer point (it has the 
	    transfer function); i.e. the system is both an end-system 
	    (ES) and an intermediate-system (IS);
	 
	  - stp(2), the Signal Transfer Point (STP) is a signalling 
	    point that has the transfer function but does not have user 
	    parts; i.e. the system is an intermediate-system (IS).
	 
	 Note that for some implementations this may be a read-only 
	 value."
    REFERENCE
	"ITU-T Rec. Q.751.1 (1997), ANSI T1.116.1 (2000), spType 
	     attribute."
    ::= { mtpSpEntry 3 }

mtpSpOperationalState OBJECT-TYPE
    SYNTAX OperationalState
    MAX-ACCESS read-only
    STATUS current
    DESCRIPTION
	"Provides the operational state of the MTP signalling point 
	 following the OperationalState textual convention of the 
	 OPENSS7-SMI-MIB module and ITU-T Rec. X.721 | ISO/IEC 10165-2.
	 
	  - disabled(0),
	  - enabled(1),
	"
    REFERENCE
	"ITU-T Rec. X.721 (1992) | ISO/IEC 10165-2 : 1992, 
	     Attribute-ASN1Module.OperationalState.
	 ITU-T Rec. X.731 (1992) | ISO/IEC 10164-2 : 1993, 
	     Section 8.1.1.1.
	 ITU-T Rec. Q.751.1 (1997), ANSI T1.116.1 (2000), 
	     operationalState attribute."
    DEFVAL { 0 } -- disabled
    ::= { mtpSpEntry 4 }

mtpSpProceduralStatus OBJECT-TYPE
    SYNTAX ProceduralStatus
    MAX-ACCESS read-only
    STATUS current
    DESCRIPTION
	"Provides the procedural status of the MTP signalling point 
	 following the ProceduralStatus textual convention of the 
	 OPENSS7-SMI-MIB module and ITU-T Rec. X.721 | ISO/IEC 10165-2.
	 
	  - initializationRequired(0), MTP restart procedures are 
	    required but have not yet been initiated;
	 
	  - notInitialized(1), the signalling point is not initialized 
	    and needs to be started;
	 
	  - initializing(2), indicated during MTP restart and present 
	    until the MTP restart procedure completes;
	 
	  - reporting(3), unused;
	  - terminating(4), unused.
	"
    REFERENCE
	"ITU-T Rec. X.721 | ISO/IEC 10165-2, proceduralStatus 
	     attribute.
	 ITU-T Rec. Q.751.1 (1997), ANSI T1.116.1 (2000) : 
	     proceduralStatus attribute."
    DEFVAL { 0 } -- initializationRequired
    ::= { mtpSpEntry 5 }

mtpSpAvailabilityStatus OBJECT-TYPE
    SYNTAX AvailabilityStatus
    MAX-ACCESS read-only
    STATUS current
    DESCRIPTION
	"Provides the availability status of the MTP signalling point 
	 following the AvailabilityStatus textual convention of the 
	 OPENSS7-SMI-MIB module and ITU-T Rec. X.721 | ISO/IEC 10165-2.
	 
	  - inTest(0),
	  - failed(1),
	  - powerOff(2),
	  - offLine(3),
	  - offDuty(4),
	  - dependency(5),
	  - degraded(6), the signalling point is congested, accessible 
	    but heavily loaded;
	  - notInstalled(7),
	  - logFull(8),
	 
	 When the value set is empty, the signalling point is allowed, 
	 accessible and is functioning normally, when operational state 
	 is enabled(1).
	 "
    REFERENCE
	"ITU-T Rec. X.721 | ISO/IEC 10165-2, availabilityStatus 
	     attribute.
	 ITU-T Rec. Q.751.1 (1997), ANSI T1.116.1 (2000), 
	     availabilityStatus attribute."
    ::= { mtpSpEntry 6 }

mtpSpVersion OBJECT-TYPE
    SYNTAX GraphicString
    MAX-ACCESS read-create
    STATUS current
    DESCRIPTION
	"Provides the version of the MTP signalling point."
    REFERENCE
	"ITU-T Rec. Q.751.1 (1997), ANSI T1.116.1 (2000), version 
	 attribute."
    ::= { mtpSpEntry 7 }

mtpSpNetworkIndicator OBJECT-TYPE
    SYNTAX MtpNetworkIndicator
    MAX-ACCESS read-create
    STATUS current
    DESCRIPTION
	"This attribute models the network indicator of the network the 
	 signalling point belongs to."
    REFERENCE
	"ITU-T Rec. Q.751.1 (1997), ANSI T1.116.1 (2000), 
	 networkIndicator attribute."
    ::= { mtpSpEntry 8 }

mtpSpName OBJECT-TYPE
    SYNTAX SimpleNameType
    MAX-ACCESS read-create
    STATUS current
    DESCRIPTION
	"This attribute is an additional name for instances of the 
	 mtpSignPoint managed object class.
	 
	 Provides an optional administrative name for this signalling 
	 point.  It is typical to use as a prefix the common language 
	 name associated with the corresponding managed switching 
	 element (e.g. ETDNAB01DS1SP0)."
    REFERENCE
	"ITU-T Rec. Q.751.1 (1997), ANSI T1.116.1 (2000), 
	     mtpSignPointName attribute."
    ::= { mtpSpEntry 9 }

mtpSpMtpT1 OBJECT-TYPE
    SYNTAX TimeInterval
    UNITS "centiseconds"
    MAX-ACCESS read-create
    STATUS current
    DESCRIPTION
	"This attribute defines the initial timer value of timer T1 
	 'Delay to avoid message mis-sequencing on changeover from this 
	 link' defined in Recommendation Q.704.  The value range is from 
	 500 to 1200ms.  For routes with long propagation delays a 
	 minimum value of 800 ms is used.  The same value applies for 
	 all links associated with an instance of the procedure."
    REFERENCE
	"ITU-T Rec. Q.751.1 (1997), ANSI T1.116.1 (2000), q704-t1 
	 attribute."
    ::= { mtpSpEntry 10 }

mtpSpMtpT2 OBJECT-TYPE
    SYNTAX TimeInterval
    UNITS "centiseconds"
    MAX-ACCESS read-create
    STATUS current
    DESCRIPTION
	"This attribute defines the initial timer value of timer T2 
	 'Waiting for changeover acknowledgement' defined in 
	 Recommendation Q.704.  The value range is from 700 to 2000 ms.  
	 For routes with long propagation delays a minimum value of 1400 
	 ms is used."
    REFERENCE
	"ITU-T Rec. Q.751.1 (1997), ANSI T1.116.1 (2000), q704-t2 
	 attribute."
    ::= { mtpSpEntry 11 }

mtpSpMtpT3 OBJECT-TYPE
    SYNTAX TimeInterval
    UNITS "centiseconds"
    MAX-ACCESS read-create
    STATUS current
    DESCRIPTION
	"This attribute defines the initial timer value of timer T3 
	 'Time controlled diversion-delay to avoid mis-sequencing on 
	 changeback from this link' defined in Recommendation Q.704.  
	 The value range is from 500 to 1200 ms.  For routes with long 
	 propagation delays a minimum value of 800 ms is used.  The 
	 value of this attribute is network implementation dependent."
    REFERENCE
	"ITU-T Rec. Q.751.1 (1997), ANSI T1.116.1 (2000), q704-t3 
	 attribute."
    ::= { mtpSpEntry 12 }

mtpSpMtpT4 OBJECT-TYPE
    SYNTAX TimeInterval
    UNITS "centiseconds"
    MAX-ACCESS read-create
    STATUS current
    DESCRIPTION
	"This attribute defines the initial timer value of timer T4 
	 'Waiting for changeback acknowledgement (first attempt)' 
	 defined in Recommendation Q.704.  The value range is from 500 
	 to 1200 ms.  For routes with long propagation delays a minimum 
	 value of 800 ms is used."
    REFERENCE
	"ITU-T Rec. Q.751.1 (1997), ANSI T1.116.1 (2000), q704-t4 
	 attribute."
    ::= { mtpSpEntry 13 }

mtpSpMtpT5 OBJECT-TYPE
    SYNTAX TimeInterval
    UNITS "centiseconds"
    MAX-ACCESS read-create
    STATUS current
    DESCRIPTION
	"This attribute defines the initial timer value of timer T5 
	 Waiting for changeback acknowledgement (second attempt) defined 
	 in Recommendation Q.704.  The value range is from 500 to 1200 
	 ms.  For routes with long propagation delays a minimum value of 
	 800 ms is used."
    REFERENCE
	"ITU-T Rec. Q.751.1 (1997), ANSI T1.116.1 (2000), q704-t5 
	 attribute."
    ::= { mtpSpEntry 14 }

mtpSpMtpT6 OBJECT-TYPE
    SYNTAX TimeInterval
    UNITS "centiseconds"
    MAX-ACCESS read-create
    STATUS current
    DESCRIPTION
	"This attribute defines the initial timer value of timer T6 
	 Delay to avoid message mis-sequencing on controlled rerouting 
	 defined in Recommendation Q.704.  The value range is from 500 
	 to 1200 ms.  For routes with long propagation delays a minimum 
	 value of 800 ms is used."
    REFERENCE
	"ITU-T Rec. Q.751.1 (1997), ANSI T1.116.1 (2000), q704-t6 
	 attribute."
    ::= { mtpSpEntry 15 }

mtpSpMtpT7 OBJECT-TYPE
    SYNTAX TimeInterval
    UNITS "centiseconds"
    MAX-ACCESS read-create
    STATUS current
    DESCRIPTION
	"This attribute defines the initial timer value of timer T7 
	 Waiting for signalling data link connection acknowledgement 
	 defined in Recommendation Q.704.  The value range is from 1 to 
	 2 seconds."
    REFERENCE
	"ITU-T Rec. Q.751.1 (1997), ANSI T1.116.1 (2000), q704-t7 
	 attribute."
    ::= { mtpSpEntry 16 }

mtpSpMtpT8 OBJECT-TYPE
    SYNTAX TimeInterval
    UNITS "centiseconds"
    MAX-ACCESS read-create
    STATUS current
    DESCRIPTION
	"This attribute defines the initial timer value of timer T8 
	 Transfer prohibited inhibition timer (transient solution) 
	 defined in Recommendation Q.704.  The value range is from 800 
	 to 
	 1200 ms."
    REFERENCE
	"ITU-T Rec. Q.751.1 (1997), ANSI T1.116.1 (2000), q704-t8 
	 attribute."
    ::= { mtpSpEntry 17 }

mtpSpMtpT10 OBJECT-TYPE
    SYNTAX TimeInterval
    UNITS "centiseconds"
    MAX-ACCESS read-create
    STATUS current
    DESCRIPTION
	"This attribute defines the initial timer value of timer T10 
	 Waiting to repeat signalling route set test message defined in 
	 Recommendation Q.704.  The value range is from 30 to 60 
	 seconds.  The maximum value may be extended at the discretion 
	 of the management function in certain situations, e.g.  many 
	 signalling points being unavailable or signalling points of 
	 known long term unavailability."
    REFERENCE
	"ITU-T Rec. Q.751.1 (1997), ANSI T1.116.1 (2000), q704-t10 
	 attribute."
    ::= { mtpSpEntry 18 }

mtpSpMtpT11 OBJECT-TYPE
    SYNTAX TimeInterval
    UNITS "centiseconds"
    MAX-ACCESS read-create
    STATUS current
    DESCRIPTION
	"This attribute defines the initial timer value of timer T11 
	 Transfer restricted timer defined in Recommendation Q.704.  The 
	 value range is from 30 to 90 seconds.  This is one way of 
	 implementing the function described in 
	 13.4/Q.704 and mainly intended to simplify STPs."
    REFERENCE
	"ITU-T Rec. Q.751.1 (1997), ANSI T1.116.1 (2000), q704-t11 
	 attribute."
    ::= { mtpSpEntry 19 }

mtpSpMtpT12 OBJECT-TYPE
    SYNTAX TimeInterval
    UNITS "centiseconds"
    MAX-ACCESS read-create
    STATUS current
    DESCRIPTION
	"This attribute defines the initial timer value of timer T12 
	 Waiting for uninhibit acknowledgement defined in Recommendation 
	 Q.704.  The value range is from 800 to 
	 1500 ms."
    REFERENCE
	"ITU-T Rec. Q.751.1 (1997), ANSI T1.116.1 (2000), q704-t12 
	 attribute."
    ::= { mtpSpEntry 20 }

mtpSpMtpT13 OBJECT-TYPE
    SYNTAX TimeInterval
    UNITS "centiseconds"
    MAX-ACCESS read-create
    STATUS current
    DESCRIPTION
	"This attribute defines the initial timer value of timer T13 
	 Waiting for force uninhibit defined in Recommendation Q.704.  
	 The value range is from 800 to 
	 1500 ms."
    REFERENCE
	"ITU-T Rec. Q.751.1 (1997), ANSI T1.116.1 (2000), q704-t13 
	 attribute."
    ::= { mtpSpEntry 21 }

mtpSpMtpT14 OBJECT-TYPE
    SYNTAX TimeInterval
    UNITS "centiseconds"
    MAX-ACCESS read-create
    STATUS current
    DESCRIPTION
	"This attribute defines the initial timer value of timer T14 
	 Waiting for inhibition acknowledgement defined in 
	 Recommendation Q.704.  The value range is from 2 to 3 seconds."
    REFERENCE
	"ITU-T Rec. Q.751.1 (1997), ANSI T1.116.1 (2000), q704-t14 
	 attribute."
    ::= { mtpSpEntry 22 }

mtpSpMtpT15 OBJECT-TYPE
    SYNTAX TimeInterval
    UNITS "centiseconds"
    MAX-ACCESS read-create
    STATUS current
    DESCRIPTION
	"This attribute defines the initial timer value of timer T15 
	 Waiting to start signalling route set congestion test defined 
	 in Recommendation Q.704.  The value range is from 2 to 3 
	 seconds."
    REFERENCE
	"ITU-T Rec. Q.751.1 (1997), ANSI T1.116.1 (2000), q704-t15 
	 attribute."
    ::= { mtpSpEntry 23 }

mtpSpMtpT16 OBJECT-TYPE
    SYNTAX TimeInterval
    UNITS "centiseconds"
    MAX-ACCESS read-create
    STATUS current
    DESCRIPTION
	"This attribute defines the initial timer value of timer T16 
	 Waiting for route set congestion status update defined in 
	 Recommendation Q.704.  The value range is from 1.4 to 2 
	 seconds."
    REFERENCE
	"ITU-T Rec. Q.751.1 (1997), ANSI T1.116.1 (2000), q704-t16 
	 attribute."
    ::= { mtpSpEntry 24 }

mtpSpMtpT17 OBJECT-TYPE
    SYNTAX TimeInterval
    UNITS "centiseconds"
    MAX-ACCESS read-create
    STATUS current
    DESCRIPTION
	"This attribute defines the initial timer value of timer T17 
	 Delay to avoid oscillation of initial alignment failure and 
	 link restart defined in Recommendation Q.704.  The value range 
	 is from 800 to 1500 ms.  The value should be less than the 
	 corresponding timer 2 in 
	 12.2.1.2/Q.703.

	 This timer value and procedure is in effect whenever the 
	 signalling link is set to use ITU-T link oscillation 
	 procedures.  For link oscillation procedure A, see 
	 mtpSignPointMtpT32A.  For link oscillation procedure B, see 
	 mtpSignPointMtpT33A and mtpSignPointMtpT34A."
    REFERENCE
	"ITU-T Rec. Q.751.1 (1997), ANSI T1.116.1 (2000), q704-t17 
	 attribute."
    ::= { mtpSpEntry 25 }

mtpSpMtpT19A OBJECT-TYPE
    SYNTAX TimeInterval
    UNITS "centiseconds"
    MAX-ACCESS read-create
    STATUS current
    DESCRIPTION
	"This attribute defines the initial timer value of timer T19 
	 (ANSI) link maintenance timer defined in ANSI T1.111.4.  This 
	 timer is of local significance only and is equally applicable 
	 to ANSI, ITU-T and ETSI protocol variant based signalling 
	 links.
	 
	 ANSI T1.111.4 (1996 and 2000) 12.2.2: After a signalling link 
	 failure is detected, signalling link initial alignment will 
	 take place.  When the initial alignment procedure is 
	 successful, a signalling link test is started.  If the 
	 isgnalling link test is successful, the signalling link is 
	 regarded as restored and thus available for signalling.  If 
	 initial alignment is not possible, as determined at level 2 
	 (see Section 7 of Chapter T1.111.3 or Section 6.2.2 of T1.645), 
	 new initial alignment procedures may be started on the same 
	 signalling link after a timer T17 until the signalling link is 
	 restored or a manual intervention is made, e.g., to replace the 
	 signalling data link or the signalling terminal.  If after time 
	 T19 the signalling link is not activated, a management function 
	 is notified, and, optionally, T19 may be restarted."
    REFERENCE
	"ANSI T1.111.4/2000, Section 12.2.2, Timer T19."
    ::= { mtpSpEntry 26 }

mtpSpMtpT31A OBJECT-TYPE
    SYNTAX TimeInterval (1000..12000)
    UNITS "centiseconds"
    MAX-ACCESS read-create
    STATUS current
    DESCRIPTION
	"This attribute defines the initial timer value of timer T31 
	 (ANSI) false link congestion detection timer defined in ANSI 
	 T1.111.4 (2000) 3.8.2.2.  The value range is from 10 to 120 
	 seconds.
	 
	 Note that the procedure associated with T31 (ANSI) is a local 
	 matter and can equally be applied to ANSI, ITU-T and ETSI based 
	 protocol variant signalling links.
	 
	 ANSI T1.111.4 (2000) 3.8.2.2.  ...  If the link remains at a 
	 congestion level, as defined below, for greater than T31 [10] 
	 (a false link congestion condition), and it also remains in 
	 service, an audit should trigger the link to be restarted.  T31 
	 is started when buffer occupancy increases through onset level 
	 1.  Any change of congestion level [defined as a change of 
	     signalling link congestion status (see Section 3.8.2.1) and 
	     optionally including the first time the discard status is 
	     increased to n after signalling link congestion status is 
	     increased to  n (n=1, 2, 3)] restarts the timer.  T31 is 
	     stopped when the signalling link congestion status is zero.  
	     The management should be notified if the link is restarted 
	     due to false link congestion."
    REFERENCE
	"ANSI T1.111.4 (2000) Section 3.8.2.2."
    DEFVAL { 6000 }
    ::= { mtpSpEntry 27 }

mtpSpMtpT32A OBJECT-TYPE
    SYNTAX TimeInterval (500..12000)
    UNITS "centiseconds"
    MAX-ACCESS read-create
    STATUS current
    DESCRIPTION
	"This attribute defines the initial timer value of timer T32 
	 (ANSI) link oscillation timer (Procedure A) defined in ANSI 
	 T1.111.4 (2000) 12.2.2.  The value range is from 5 to 120 
	 seconds.
	 
	 This timer value and procedure is in effect whenever the 
	 signalling link is set to use link oscillation procedure A.  
	 For link oscillation procedure B, see mtpSignPointMtpT33A and 
	 mtpSignPointMtpT34A.  For link oscillation using ITU-T 
	 procedures, see mtpSignPointMtpT17.
	 
	 ANSI T1.111.4 (1996 and 2000) 12.2.2 ...  In order to [sic] 
	 prevent links from oscillating rapidly between the in-service 
	 and out-of-service states, a link oscillation filtering 
	 procedure shall be provided.  This procedure is applicable in 
	 all cases where automatic restoration and removal of signalling 
	 links to and from service is used.  The procedure is not 
	 invoked if restoration to or removal from service is initiated 
	 manually.
	 
	 Link oscillation filtering is a local procedure.  One of the 
	 following procedures, A or B, is used.
	 
	 (A) When restoration begins, the oscillation timer T32 is 
	 started.  If the link fails within T32, the link is placed in 
	 the 'suspension' state until T32 expires.
	 
	 When a link exits in the 'suspension' state, link restoration 
	 is to be started and T32 is restarted.
	 
	 When a link is in 'suspension,' the link remains in the 
	 out-of-service state at level 2, restoration procedures to 
	 bring the link back into alignment are not invoked and 
	 realignment attempts initiated by the remote end are ignored.
	 
	 The oscillation timer T32 value chosen in a given signalling 
	 point may be modified by management action.  The expiration of 
	 the timer does not change the link status."
    REFERENCE
	"ANSI T1.111.4/2000 Section 12.2.2, Timer T32."
    DEFVAL { 6000 }
    ::= { mtpSpEntry 28 }

mtpSpMtpT33A OBJECT-TYPE
    SYNTAX TimeInterval (6000..60000)
    UNITS "centiseconds"
    MAX-ACCESS read-create
    STATUS current
    DESCRIPTION
	"This attribute defines the initial timer value of timer T33 
	 (ANSI) link oscillation probation timer (Procedure B) defined 
	 in ASNI T1.111.4 (2000) 12.2.2.  The value range is from 1 to 
	 10 minutes (60 to 600 seconds).
	 
	 This timer value and procedure is in effect whenever the 
	 signalling link is set to use link oscillation procedure B.  
	 For link oscillation procedure A, see mtpSignPointMtpT32A.  For 
	 link oscillation using ITU-T procedures see mtpSignPointMtpT17.
	 
	 ANSI T1.111.4 (1996 and 2000) 12.2.2 ...  In order to [sic] 
	 prevent links from oscillating rapidly between the in-service 
	 and out-of-service states, a link oscillation filtering 
	 procedure shall be provided.  This procedure is applicable in 
	 all cases where automatic restoration and removal of signalling 
	 links to and from service is used.  The procedure is not 
	 invoked if restoration to or removal from service is initiated 
	 manually.
	 
	 Link oscillation filtering is a local procedure.  One of the 
	 following procedures, A or B, is used.
	 
	 (B) When activation or restoration of a signalling link has 
	 been completed, it is put on probation for a period controlled 
	 by timer T33 which starts running when the link enters the 
	 in-service state and is stopped either on time-out or on link 
	 failure.
	 
	 If a link fails during the probation, i.e. before expiration 
	 of timer T33, it is put on suspension.  While suspended the 
	 link remains in the out-of-service state at level 2, 
	 restoration procedures to bring the link back into alignment 
	 are not invoked and realignment attempts initiated by the 
	 remote end are ignored.
	 
	 The suspension time period is controlled by timer T34 which 
	 starts running when the link enters the out-of-service state.  
	 Link restoration is resumed, on expiry of timer T34.
	 
	 The values chosen in a given network node for the probation and 
	 suspension time periods are dependent on the type and function 
	 of the node in the network and may be modified by management 
	 action."
    REFERENCE
	"ANSI T1.111.4/2000 Section 12.2.2, Timer T33."
    DEFVAL { 36000 }
    ::= { mtpSpEntry 29 }

mtpSpMtpT34A OBJECT-TYPE
    SYNTAX TimeInterval (500..12000)
    UNITS "centiseconds"
    MAX-ACCESS read-create
    STATUS current
    DESCRIPTION
	"This attribute defines the initial timer value of timer T34 
	 (ANSI) link oscillation suspension timer (Procedure B) defined 
	 in ANSI T1.111.4 (2000) 12.2.2.  The value range is from 5 to 
	 120 seconds.
	 
	 This timer value and procedure is in effect whenever the 
	 signalling link is set to use link oscillation procedure B.  
	 For link oscillation procedure A, see mtpSignPointMtpT32A.  For 
	 link oscillation using ITU-T procedures see mtpSignPointMtpT17.
	 
	 ANSI T1.111.4 (1996 and 2000) 12.2.2 ...  In order to [sic] 
	 prevent links from oscillating rapidly between the in-service 
	 and out-of-service states, a link oscillation filtering 
	 procedure shall be provided.  This procedure is applicable in 
	 all cases where automatic restoration and removal of signalling 
	 links to and from service is used.  The procedure is not 
	 invoked if restoration to or removal from service is initiated 
	 manually.
	 
	 Link oscillation filtering is a local procedure.  One of the 
	 following procedures, A or B, is used.
	 
	 (B) When activation or restoration of a signalling link has 
	 been completed, it is put on probation for a period controlled 
	 by timer T33 which starts running when the link enters the 
	 in-service state and is stopped either on time-out or on link 
	 failure.
	 
	 If a link fails during the probation, i.e. before expiration of 
	 timer T33, it is put on suspension.  While suspended the link 
	 remains in the out-of-service state at level 2, restoration 
	 procedures to bring the link back into alignment are not 
	 invoked and realignment attempts initiated by the remote end 
	 are ignored.
	 
	 The suspension time period is controlled by timer T34 which 
	 starts running when the link enters the out-of-service state.  
	 Link restoration is resumed, on expiry of timer T34.
	 
	 The values chosen in a given network node for the probation and 
	 suspension time periods are dependent on the type and function 
	 of the node in the network and may be modified by management 
	 action."
    REFERENCE
	"ANSI T1.111.4/2000 Section 12.2.2, Timer T34."
    DEFVAL { 6000 }
    ::= { mtpSpEntry 30 }

mtpSpMtpT18I OBJECT-TYPE
    SYNTAX TimeInterval
    UNITS "centiseconds"
    MAX-ACCESS read-create
    STATUS current
    DESCRIPTION
	"This attribute defines the initial timer value of timer T18 
	 defined in Recommendation Q.704.  T18 is the Timer within a 
	 signalling point whose MTP restarts, for supervising link and 
	 linkset activation as well as the receipt of routing 
	 information.  The value is implementation and network 
	 dependent.  Criteria to choose T18 are given in 9.2/Q.704."
    REFERENCE
	"ITU-T Rec. Q.751.1 (1997), ANSI T1.116.1 (2000), q704-t18 
	 attribute."
    ::= { mtpSpEntry 31 }

mtpSpMtpT19I OBJECT-TYPE
    SYNTAX TimeInterval
    UNITS "centiseconds"
    MAX-ACCESS read-create
    STATUS current
    DESCRIPTION
	"This attribute defines the initial timer value of timer T19 
	 Supervision timer during MTP restart to avoid possible 
	 ping-pong of TFP, TFR and TRA messages.  defined in 
	 Recommendation Q.704.  The value range is from 67 to 69 
	 seconds."
    REFERENCE
	"ITU-T Rec. Q.751.1 (1997), ANSI T1.116.1 (2000), q704-t19 
	 attribute."
    ::= { mtpSpEntry 32 }

mtpSpMtpT20I OBJECT-TYPE
    SYNTAX TimeInterval
    UNITS "centiseconds"
    MAX-ACCESS read-create
    STATUS current
    DESCRIPTION
	"This attribute defines the initial timer value of timer T20 
	 Overall MTP restart timer at the signalling point whose MTP 
	 restarts, defined in Recommendation Q.704.  The value range is 
	 from 59 to 61 seconds."
    REFERENCE
	"ITU-T Rec. Q.751.1 (1997), ANSI T1.116.1 (2000), q704-t20 
	 attribute."
    ::= { mtpSpEntry 33 }

mtpSpMtpT21I OBJECT-TYPE
    SYNTAX TimeInterval
    UNITS "centiseconds"
    MAX-ACCESS read-create
    STATUS current
    DESCRIPTION
	"This attribute defines the initial timer value of timer T21 
	 Overall MTP restart timer at a signalling point adjacent to one 
	 whose MTP restarts, defined in Recommendation Q.704.  The value 
	 range is from 63 to 65 seconds."
    REFERENCE
	"ITU-T Rec. Q.751.1 (1997), ANSI T1.116.1 (2000), q704-t21 
	 attribute."
    ::= { mtpSpEntry 34 }

mtpSpMtpT22I OBJECT-TYPE
    SYNTAX TimeInterval
    UNITS "centiseconds"
    MAX-ACCESS read-create
    STATUS current
    DESCRIPTION
	"This attribute defines the initial timer value of timer T22 
	 Local inhibit test timer defined in Recommendation Q.704.  The 
	 value range is from 3 to 6 minutes (provisional value).

	 This timer value and associated procedure is only applicable to 
	 ITU-T based protocol variants.  For ANSI based protocol 
	 variants, see mtpSignPointMtpT20A."
    REFERENCE
	"ITU-T Rec. Q.751.1 (1997), ANSI T1.116.1 (2000), q704-t22 
	 attribute."
    ::= { mtpSpEntry 35 }

mtpSpMtpT23I OBJECT-TYPE
    SYNTAX TimeInterval
    UNITS "centiseconds"
    MAX-ACCESS read-create
    STATUS current
    DESCRIPTION
	"This attribute defines the initial timer value of timer T23 
	 Remote inhibit test timer defined in Recommendation Q.704.  The 
	 value range is from 3 to 6 minutes (provisional value).

	 This timer value and associated procedure is only applicable to 
	 ITU-T based protocol variants.  For ANSI based protocol 
	 variants, see mtpSignPointMtpT21A."
    REFERENCE
	"ITU-T Rec. Q.751.1 (1997), ANSI T1.116.1 (2000), q704-t23 
	 attribute."
    ::= { mtpSpEntry 36 }

mtpSpMtpT20A OBJECT-TYPE
    SYNTAX TimeInterval (9000..12000)
    UNITS "centiseconds"
    MAX-ACCESS read-create
    STATUS current
    DESCRIPTION
	"This attribute defines the initial timer value of timer T20 
	 (ANSI) local inihibit test timer defined in ANSI T1.111.4 
	 10.3A.  The value range is from 90 to 120 seconds (1.5 to 2 
	    minutes).
	 
	 Note that timer T20(ANSI) is equivalent to timer T22(ITU-T) in 
	 function but has a range from 1.5 to 2.0 minutes instead of 3 
	 to 6 minutes.
	 
	 This timer value and associated procedure is appliable only to 
	 ANSI based protocol variants.  For ITU-T based protocol 
	 variants, see mtpSignPointMtpT22.
	 
	 ANSI T1.111.4/2000 10.3A (Inhibit Test Procedure Actions).  
	 When a signalling link becomes inibited, either locally, 
	 remotely or both, the following test procedure actions take 
	 place, as appropriate:
	 
	 1. If timer T20 expires at signalling point X and the 
	    signalling link is locally inhibited at signalling point X, 
	    signalling point X transmits a local inhibit test message to 
	    the signalling point at the other end of the locally 
	    inhibited link and restarts timer T20.
	 
	 2. If timer T20 expires at signalling point X and the 
	    signalling link is no longer locally inhibited, no action is 
	    taken.
	 
	 3. If timer T21 expires at signalling point X and the 
	    signalling link is remotely inhibtied at signalling point X, 
	    signalling point X transmits a remote inhibit teset message 
	    to the signalling point at the other end of the remotely 
	    inhibited link and restarts timer T21.
	 
	 4. If timer T21 expires at signalling point X and the 
	    signalling link is no longer remotely inihibited, no action 
	    is taken.
	 
	 5. If signalling point Y receives a local inhibit test message 
	    from signalling point X and the concerned link is marked 
	    remotely inhibited, no action is taken.
	 
	 6. If signalling point Y receoves a local inhibit test message 
	    from signalling point X and the concerned link is not marked 
	    remotely inhibited, the forced uninhibiting procedure is 
	    invoked at signalling point Y, beginning with the 
	    transmission of a force uninhibit signalling link message to 
	    signalling point X.  As a result of this procedure, the 
	    local inhibit indicator is canceled at signalling point X.
	 
	 7. If signalling point Y receives a remote inhibit test message 
	    from signalling point X and the concerned link is marked 
	    locally inhibited, no action is taken.
	 
	 8. If signalling point Y receives a remote inhibit test message 
	    from signalling point X and the concerned signalling link is 
	    not marked locally inhibited, the uninhibiting procedure is 
	    invoked at signalling point Y, beginning with the 
	    transmission of an uninhibit signalling link message to 
	    signalling point X.  As a result of this procedure, the 
	    remote inhibit indicator is canceled at signalling point X.
	 
	 Note: ANSI Timer T20 is simply ITU-T Timer T22 renumbered."
    REFERENCE
	"ANSI T1.111.4/2000 Section 10.3A, Timer T20."
    DEFVAL { 10000 }
    ::= { mtpSpEntry 37 }

mtpSpMtpT21A OBJECT-TYPE
    SYNTAX TimeInterval (9000..12000)
    UNITS "centiseconds"
    MAX-ACCESS read-create
    STATUS current
    DESCRIPTION
	"This attribute defines the initial timer value of timer T21 
	 (ANSI) remote inhibit test timer defined in ANSI T1.111.4 
	 10.3A.  The value range is from 90 to 120 seconds (1.5 to 2 
	    minutes).
	 
	 Note that timer T21(ANSI) is equivalent to timer T23(ITU-T) in 
	 function but has a range from 1.5 to 2.0 minutes instead of 3 
	 to 6 minutes.
	 
	 This timer value and associated procedure is appliable only to 
	 ANSI based protocol variants.  For ITU-T based protocol 
	 variants see mtpSignPointMtpT23.
	 
	 ANSI T1.111.4/2000 10.3A (Inhibit Test Procedure Actions).  
	 When a signalling link becomes inibited, either locally, 
	 remotely or both, the following test procedure actions take 
	 place, as appropriate:
	 
	 1. If timer T20 expires at signalling point X and the 
	    signalling link is locally inhibited at signalling point X, 
	    signalling point X transmits a local inhibit test message to 
	    the signalling point at the other end of the locally 
	    inhibited link and restarts timer T20.
	 
	 2. If timer T20 expires at signalling point X and the 
	    signalling link is no longer locally inhibited, no action is 
	    taken.
	 
	 3. If timer T21 expires at signalling point X and the 
	    signalling link is remotely inhibtied at signalling point X, 
	    signalling point X transmits a remote inhibit teset message 
	    to the signalling point at the other end of the remotely 
	    inhibited link and restarts timer T21.
	 
	 4. If timer T21 expires at signalling point X and the 
	    signalling link is no longer remotely inihibited, no action 
	    is taken.
	 
	 5. If signalling point Y receives a local inhibit test message 
	    from signalling point X and the concerned link is marked 
	    remotely inhibited, no action is taken.
	 
	 6. If signalling point Y receoves a local inhibit test message 
	    from signalling point X and the concerned link is not marked 
	    remotely inhibited, the forced uninhibiting procedure is 
	    invoked at signalling point Y, beginning with the 
	    transmission of a force uninhibit signalling link message to 
	    signalling point X.  As a result of this procedure, the 
	    local inhibit indicator is canceled at signalling point X.
	 
	 7. If signalling point Y receives a remote inhibit test message 
	    from signalling point X and the concerned link is marked 
	    locally inhibited, no action is taken.
	 
	 8. If signalling point Y receives a remote inhibit test message 
	    from signalling point X and the concerned signalling link is 
	    not marked locally inhibited, the uninhibiting procedure is 
	    invoked at signalling point Y, beginning with the 
	    transmission of an uninhibit signalling link message to 
	    signalling point X.  As a result of this procedure, the 
	    remote inhibit indicator is canceled at signalling point X.
	 
	 Note: ANSI Timer T21 is simply ITU-T Timer T23 renumbered."
    REFERENCE
	"ANSI T1.111.4/2000 Section 10.3A, Timer T21."
    DEFVAL { 10000 }
    ::= { mtpSpEntry 38 }

mtpSpMtpT24I OBJECT-TYPE
    SYNTAX TimeInterval
    UNITS "centiseconds"
    MAX-ACCESS read-create
    STATUS current
    DESCRIPTION
	"This attribute defines the initial timer value of timer T24 
	 Stabilising timer after removal of local processor outage, used 
	 in LPO latching to RPO (national option) defined in 
	 Recommendation Q.704.  The value is 500 ms (provisional 
	 value)."
    REFERENCE
	"ITU-T Rec. Q.751.1 (1997), ANSI T1.116.1 (2000), q704-t24 
	 attribute."
    ::= { mtpSpEntry 39 }

mtpSpMtpT1T OBJECT-TYPE
    SYNTAX TimeInterval
    UNITS "centiseconds"
    MAX-ACCESS read-create
    STATUS current
    DESCRIPTION
	"This attribute defines a timer value of timer T1 which is 
	 defined in Recommendation Q.707."
    REFERENCE
	"ITU-T Rec. Q.751.1 (1997), ANSI T1.116.1 (2000), q707-t1 
	 attribute."
    ::= { mtpSpEntry 40 }

mtpSpMtpT2T OBJECT-TYPE
    SYNTAX TimeInterval
    UNITS "centiseconds"
    MAX-ACCESS read-create
    STATUS current
    DESCRIPTION
	"This attribute defines a timer value of timer T2 which is 
	 defined in Recommendation Q.707."
    REFERENCE
	"ITU-T Rec. Q.751.1 (1997), ANSI T1.116.1 (2000), q707-t2 
	 attribute."
    ::= { mtpSpEntry 41 }

mtpSpMtpT1S OBJECT-TYPE
    SYNTAX TimeInterval
    UNITS "centiseconds"
    MAX-ACCESS read-create
    STATUS current
    DESCRIPTION
	"This attribute defines a timer value of timer T1 special which 
	 is defined in ANSI T1.111.7/2000."
    REFERENCE
	"ANSI T1.111.7/2000, Timer T1 Special."
    ::= { mtpSpEntry 42 }

mtpSpProfilePointer OBJECT-TYPE
    SYNTAX SimpleNameType
    MAX-ACCESS read-create
    STATUS current
    DESCRIPTION
	"Provides reference to an MTP Level 3 signalling point protocol 
	 profile for use with this signalling point.  When unspecified, 
	 the signalling point protocol profile specified for the network 
	 appearance is used by default.  When the network appearance 
	 signalling point profile is unspecified, this value must be 
	 specified upon creation of the signalling point. 
	 
	 Specifies the index into the signalling point profile table 
	 that describes the protocol profile to be applied to this 
	 signalling point.
	 
	 This attribute points to the instance of the class 
	 spTimersProfile, containing the Q.704 and Q.707 timers for the 
	 signalling point.  When a null string is specified, it 
	 specifies that there is no default signalling point protocol 
	 profile associated with this signalling point, and that 
	 signalling links, link set, routes and route sets created for 
	 this signalling point must have protocol profile information 
	 specified.  The agent may refuse to create a row in this table 
	 when:
	 
	   1. the string is null;
	 
	   2. the string does not reference the network appearance 
	      table;
	 
	   3. the string does not reference an existing entry in the 
	      network appearance table.
	
	 Once the signalling point row has been created with a non-null 
	 string, alterations make to the corresponding signalling point 
	 profile entry might or might not change the characteristics of 
	 existing and operational signalling points, route sets, routes, 
	 link sets and links."
    REFERENCE
	"ITU-T Rec. Q.751.1 (1997), ANSI T1.116.1 (2000), 
	     spTimersProfilePointer attribute."
    ::= { mtpSpEntry 43 }

mtpSpNaPointer OBJECT-TYPE
    SYNTAX SimpleNameType
    MAX-ACCESS read-create
    STATUS current
    DESCRIPTION
	"Specifies the index into the network appearance table that 
	 defined the network into which this signalling point appears.  
	 Each signalling point appears in one and only one network 
	 appearance.  This value must be specified when creating the 
	 signalling point row.
	 
	 This attribute points to the instance of the class 
	 networkAppearance, containing the Q.703, Q.704, Q.705 and Q.707 
	 network-supported options for the network in which this 
	 signalling point appears.
	 
	 When a null string is specified upon creation of a row, the 
	 agent may refuse creation of the row or it may use default 
	 information instead.  When a non-null string is specified upon 
	 creation of a row, the agent may refuse creation of the row 
	 when:
	 
	  1. the string does not reference the network appearance table 
	     (mtpNaTable);
	  2. the string references a non-existent entry in the netowrk 
	     appearance table (mtpNaEntry).
	 
	 Once the signalling point row has be created with a non-null 
	 string, alterations made to the network appearance attributes 
	 might or might not change the characteristics of existing and 
	 operational signalling points."
    REFERENCE
	""
    ::= { mtpSpEntry 44 }

mtpSpFlags OBJECT-TYPE
    SYNTAX BITS {
	spfCluster(0),
	spfXferFunc(1),
	spfSecurity(2),
	spfLOscProcA(3),
	spfLOscProcB(4)
    }
    MAX-ACCESS read-create
    STATUS current
    DESCRIPTION
	"Specifies additional information about this signalling point.  
	 This value is set-valued and may contain the following:
	 
	  - spfCluster(0), signalling point is a cluster route;
	  - spfXferFunc(1), signalling point has the transfer function;
	  - spfSecurity(2), signalling point has the gateway screening 
	    function;
	  - spfLOscProcA(3), signalling links for this signalling point 
	    use link oscillation procedure A by default;
	  - spfLOscProcB(4), signalling links for this signalling point 
	    use link oscillation procedure B by default.
	 
	 Not all combinations of flag values are valid.  Not all valid 
	 combinaation of flags are applicable to all protocol variants."
    ::= { mtpSpEntry 45 }

mtpSpUsers OBJECT-TYPE
    SYNTAX MtpSiMask
    MAX-ACCESS read-create
    STATUS current
    DESCRIPTION
	"Provides a mask of equipped users.  Note that users snmm(0), 
	 sntm(1) and snsm(2) are always equipped.
	 
	  - snmm(0), signalling network management messages;
	  - sntm(1), signalling network traffic messages;
	  - snsm(2), signalling network special messages;
	  - sccp(3), signalling connection control part; 
	  - tup(4), telephone user part;
	  - isup(5), ISDN user part;
	  - dup1(6), Data user part (type 1);
	  - dup2(7), Data user part (type 2);
	  - mtup(8), MTP Test user part;
	  - bisup(9), B-ISDN user part;
	  - siup(10), ;
	  - user11(11), user part 11;
	  - user12(12), user part 12;
	  - user13(13), user part 13;
	  - user14(14), user part 14;
	  - user15(15), user part 15.
	 
	 When the bit corresponding to the user is set, the user will be 
	 considered equipped and is either available or unavailable.  
	 When the corresponding bit is clear, the user is always 
	 unequipped."
    ::= { mtpSpEntry 46 }

mtpSpAlarmStatus OBJECT-TYPE
    SYNTAX AlarmStatus
    MAX-ACCESS read-create
    STATUS current
    DESCRIPTION
	"Provides the alarm status of the MTP signalling point following 
	 the AlarmStatus textual convention and ITU-T Rec. X.721 (1992) 
	 | ISO/IEC 10165-2 : 1992.
	 
	  - underRepair(0),
	  - critical(1),
	  - major(2),
	  - minor(3),
	  - alarmOutstanding(4),
	"
    REFERENCE
	"ITU-T Rec. Q.751.1 (1997), ANSI T1.116.1 (2000) : alarmStatus 
	     attribute.
	 ITU-T Rec. X.721 (1992) | ISO/IEC 10165-2 : 1992, 
	     Attribute-ASN1Module.AlarmStatus.
	 ITU-T Rec. X.731 (1992) | ISO/IEC 10164-2 : 1993, 
	     Section 8.1.2.1."
    ::= { mtpSpEntry 47 }

mtpSpRowStatus OBJECT-TYPE
    SYNTAX RowStatus
    MAX-ACCESS read-create
    STATUS current
    DESCRIPTION
	"Provides a mechanism whereby management stations may create or 
	 delete entires in this table.  Entries created by management 
	 stations must survive an agent reboot.  Entries cannot be 
	 deleted from this table when referenced by other tables.  
	 Entries cannot be deleted while they contain signalling route 
	 sets, signalling routes, signalling link sets or signalling 
	 links.
	 
	 A mtpSignPoint can be created by an operator or automatically.  
	 In cas the spTimersProfilePackage is used, a create or set 
	 request is rejected, if:
	 
	  1. the spTimersProfilePointer does not reference a 
	     spTimersProfile OR
	     
	  2. the spTimersProfilePointer would reference an instance that 
	     does not exist.
	     
	 If the name package is supported: a create request with a value 
	 for the name attribute that is already used by another instance 
	 of the same object class will be rejected.  An mtpSignPoint can 
	 be deleted if and only if it does not contain any other managed 
	 object class instances, except for contained measurements."
    REFERENCE
	"STD 52, SNMPv2-TC RowStatus.
	 ITU-T Rec. Q.751.1 (1997) : 
	     managedSwitchingElement-mtpSignPoint NAME BINDING."
    ::= { mtpSpEntry 48 }


-- ====================================================================

mtpSpStatsTable OBJECT-TYPE
    SYNTAX SEQUENCE OF MtpSpStatsEntry
    MAX-ACCESS not-accessible
    STATUS current
    DESCRIPTION
	"This table provides SP statistics."
    REFERENCE
	"ITU-T Rec. Q.752, ANSI T1.116.2"
    ::= { mtpSp 3 }

mtpSpStatsEntry OBJECT-TYPE
    SYNTAX MtpSpStatsEntry
    MAX-ACCESS not-accessible
    STATUS current
    DESCRIPTION
	"This is an entry in the SP statisitics table.  It is indexed by 
	 the same index as the SP table."
    REFERENCE
	"ITU-T Rec. Q.752, ANSI T1.116.2"
    AUGMENTS    { mtpSpEntry }
    ::= { mtpSpStatsTable 1 }

MtpSpStatsEntry ::= SEQUENCE {
    mtpSpStatsRowStatus				RowStatus
}

mtpSpStatsRowStatus OBJECT-TYPE
    SYNTAX RowStatus
    MAX-ACCESS read-create
    STATUS current
    DESCRIPTION
	""
    ::= { mtpSpStatsEntry 1 }


-- ====================================================================

mtpSpCurrentTable OBJECT-TYPE
    SYNTAX SEQUENCE OF MtpSpCurrentEntry
    MAX-ACCESS not-accessible
    STATUS current
    DESCRIPTION
	"Provides a table of signalling point current operational 
	 measurements."
    ::= { mtpSp 4 }

mtpSpCurrentEntry OBJECT-TYPE
    SYNTAX MtpSpCurrentEntry
    MAX-ACCESS not-accessible
    STATUS current
    DESCRIPTION
	"Each entry in this table corresponds to the current operational 
	 measurements for on signalling point provided by the managed 
	 element."
    INDEX {
	mtpSpId -- shared index
    }
    ::= { mtpSpCurrentTable 1 }

MtpSpCurrentEntry ::= SEQUENCE {
    mtpSpCurrentValidIntervals			HCPerfValidIntervals,
    mtpSpCurrentTimeDiscontinuity		TimeStamp,
    mtpSpCurrentDiscardedMSUs			PerfCurrentCount, -- Q.752, 5.5
    mtpSpCurrentReceivedTFCstatus0		PerfCurrentCount, -- Q.752, 5.8
    mtpSpCurrentReceivedTFCstatus1		PerfCurrentCount, -- Q.752, 5.8
    mtpSpCurrentReceivedTFCstatus2		PerfCurrentCount, -- Q.752, 5.8
    mtpSpCurrentOctetsXferred			PerfCurrentCount,
}

mtpSpCurrentValidIntervals OBJECT-TYPE
    SYNTAX HCPerfValidIntervals
    MAX-ACCESS read-only
    STATUS current
    DESCRIPTION
	""
    ::= { mtpSpCurrentEntry 1 }

mtpSpCurrentTimeDiscontinuity OBJECT-TYPE
    SYNTAX TimeStamp
    MAX-ACCESS read-only
    STATUS current
    DESCRIPTION
	""
    ::= { mtpSpCurrentEntry 2 }

mtpSpCurrentDiscardedMSUs OBJECT-TYPE
    SYNTAX PerfCurrentCount
    UNITS "MSUs"
    MAX-ACCESS read-only
    STATUS current
    DESCRIPTION
	""
    REFERENCE
	"ITU-T Rec. Q.751.1 (10/95) : discardedMSUs.
	 ITU-T Rec. Q.752 (1997) : Table 5/Q.752, 5.5."
    ::= { mtpSpCurrentEntry 3 }

mtpSpCurrentReceivedTFCstatus0 OBJECT-TYPE
    SYNTAX PerfCurrentCount
    UNITS "TFCs"
    MAX-ACCESS read-only
    STATUS current
    DESCRIPTION
	""
    REFERENCE
	"ITU-T Rec. Q.751.1 (10/95) : receivedTFC.
	 ITU-T Rec. Q.752 (1997) : Table 5/Q.752, 5.8."
    ::= { mtpSpCurrentEntry 4 }

mtpSpCurrentReceivedTFCstatus1 OBJECT-TYPE
    SYNTAX PerfCurrentCount
    UNITS "TFCs"
    MAX-ACCESS read-only
    STATUS current
    DESCRIPTION
	""
    REFERENCE
	"ITU-T Rec. Q.751.1 (10/95) : receivedTFC.
	 ITU-T Rec. Q.752 (1997) : Table 5/Q.752, 5.8."
    ::= { mtpSpCurrentEntry 5 }

mtpSpCurrentReceivedTFCstatus2 OBJECT-TYPE
    SYNTAX PerfCurrentCount
    UNITS "TFCs"
    MAX-ACCESS read-only
    STATUS current
    DESCRIPTION
	""
    REFERENCE
	"ITU-T Rec. Q.751.1 (10/95) : receivedTFC.
	 ITU-T Rec. Q.752 (1997) : Table 5/Q.752, 5.8."
    ::= { mtpSpCurrentEntry 6 }

mtpSpCurrentOctetsXferred OBJECT-TYPE
    SYNTAX PerfCurrentCount
    MAX-ACCESS read-only
    STATUS current
    DESCRIPTION
	""
    ::= { mtpSpCurrentEntry 7 }


-- ====================================================================

mtpSpInt5minTable OBJECT-TYPE
    SYNTAX SEQUENCE OF MtpSpInt5minEntry
    MAX-ACCESS not-accessible
    STATUS current
    DESCRIPTION
	"Provides a table of signalling point 5-minute inteval 
	 historical operational measurements."
    ::= { mtpSp 5 }

mtpSpInt5minEntry OBJECT-TYPE
    SYNTAX MtpSpInt5minEntry
    MAX-ACCESS not-accessible
    STATUS current
    DESCRIPTION
	""
    INDEX {
	mtpSpId, -- shared index
	mtpSpInt5minInterval
    }
    ::= { mtpSpInt5minTable 1 }


MtpSpInt5minEntry ::= SEQUENCE {
    mtpSpInt5minInterval			Unsigned32,
    mtpSpInt5minTimeStamp			TimeStamp,
    mtpSpInt5minDiscardedMSUs			PerfIntervalCount, -- Q.752, 5.5
    mtpSpInt5minReceivedTFCstatus0		PerfIntervalCount, -- Q.752, 5.8
    mtpSpInt5minReceivedTFCstatus1		PerfIntervalCount, -- Q.752, 5.8
    mtpSpInt5minReceivedTFCstatus2		PerfIntervalCount, -- Q.752, 5.8
    mtpSpInt5minOctetsXferred			PerfIntervalCount
}

mtpSpInt5minInterval OBJECT-TYPE
    SYNTAX Unsigned32
    MAX-ACCESS not-accessible
    STATUS current
    DESCRIPTION
	""
    ::= { mtpSpInt5minEntry 1 }

mtpSpInt5minTimeStamp OBJECT-TYPE
    SYNTAX TimeStamp
    MAX-ACCESS read-only
    STATUS current
    DESCRIPTION
	""
    ::= { mtpSpInt5minEntry 2 }

mtpSpInt5minDiscardedMSUs OBJECT-TYPE
    SYNTAX PerfIntervalCount
    UNITS "MSUs"
    MAX-ACCESS read-only
    STATUS current
    DESCRIPTION
	""
    REFERENCE
	"ITU-T Rec. Q.751.1 (10/95) : discardedMSUs.
	 ITU-T Rec. Q.752 (1997) : Table 5/Q.752, 5.5."
    ::= { mtpSpInt5minEntry 3 }

mtpSpInt5minReceivedTFCstatus0 OBJECT-TYPE
    SYNTAX PerfIntervalCount
    UNITS "TFCs"
    MAX-ACCESS read-only
    STATUS current
    DESCRIPTION
	""
    REFERENCE
	"ITU-T Rec. Q.751.1 (10/95) : receivedTFC.
	 ITU-T Rec. Q.752 (1997) : Table 5/Q.752, 5.8."
    ::= { mtpSpInt5minEntry 4 }

mtpSpInt5minReceivedTFCstatus1 OBJECT-TYPE
    SYNTAX PerfIntervalCount
    UNITS "TFCs"
    MAX-ACCESS read-only
    STATUS current
    DESCRIPTION
	""
    REFERENCE
	"ITU-T Rec. Q.751.1 (10/95) : receivedTFC.
	 ITU-T Rec. Q.752 (1997) : Table 5/Q.752, 5.8."
    ::= { mtpSpInt5minEntry 5 }

mtpSpInt5minReceivedTFCstatus2 OBJECT-TYPE
    SYNTAX PerfIntervalCount
    UNITS "TFCs"
    MAX-ACCESS read-only
    STATUS current
    DESCRIPTION
	""
    REFERENCE
	"ITU-T Rec. Q.751.1 (10/95) : receivedTFC.
	 ITU-T Rec. Q.752 (1997) : Table 5/Q.752, 5.8."
    ::= { mtpSpInt5minEntry 6 }

mtpSpInt5minOctetsXferred OBJECT-TYPE
    SYNTAX PerfIntervalCount
    MAX-ACCESS read-only
    STATUS current
    DESCRIPTION
	""
    ::= { mtpSpInt5minEntry 7 }



-- ====================================================================

mtpSpInt15minTable OBJECT-TYPE
    SYNTAX SEQUENCE OF MtpSpInt15minEntry
    MAX-ACCESS not-accessible
    STATUS current
    DESCRIPTION
	"Provides a table of signalling point 15-minute inteval 
	 historical operational measurements."
    ::= { mtpSp 6 }

mtpSpInt15minEntry OBJECT-TYPE
    SYNTAX MtpSpInt15minEntry
    MAX-ACCESS not-accessible
    STATUS current
    DESCRIPTION
	""
    INDEX {
	mtpSpId, -- shared index
	mtpSpInt15minInterval
    }
    ::= { mtpSpInt15minTable 1 }


MtpSpInt15minEntry ::= SEQUENCE {
    mtpSpInt15minInterval			Unsigned32,
    mtpSpInt15minTimeStamp			TimeStamp,
    mtpSpInt15minDiscardedMSUs			PerfIntervalCount, -- Q.752, 5.5
    mtpSpInt15minReceivedTFCstatus0		PerfIntervalCount, -- Q.752, 5.8
    mtpSpInt15minReceivedTFCstatus1		PerfIntervalCount, -- Q.752, 5.8
    mtpSpInt15minReceivedTFCstatus2		PerfIntervalCount, -- Q.752, 5.8
    mtpSpInt15minOctetsXferred			PerfIntervalCount
}

mtpSpInt15minInterval OBJECT-TYPE
    SYNTAX Unsigned32
    MAX-ACCESS not-accessible
    STATUS current
    DESCRIPTION
	""
    ::= { mtpSpInt15minEntry 1 }

mtpSpInt15minTimeStamp OBJECT-TYPE
    SYNTAX TimeStamp
    MAX-ACCESS read-only
    STATUS current
    DESCRIPTION
	""
    ::= { mtpSpInt15minEntry 2 }

mtpSpInt15minDiscardedMSUs OBJECT-TYPE
    SYNTAX PerfIntervalCount
    UNITS "MSUs"
    MAX-ACCESS read-only
    STATUS current
    DESCRIPTION
	""
    REFERENCE
	"ITU-T Rec. Q.751.1 (10/95) : discardedMSUs.
	 ITU-T Rec. Q.752 (1997) : Table 5/Q.752, 5.5."
    ::= { mtpSpInt15minEntry 3 }

mtpSpInt15minReceivedTFCstatus0 OBJECT-TYPE
    SYNTAX PerfIntervalCount
    UNITS "TFCs"
    MAX-ACCESS read-only
    STATUS current
    DESCRIPTION
	""
    REFERENCE
	"ITU-T Rec. Q.751.1 (10/95) : receivedTFC.
	 ITU-T Rec. Q.752 (1997) : Table 5/Q.752, 5.8."
    ::= { mtpSpInt15minEntry 4 }

mtpSpInt15minReceivedTFCstatus1 OBJECT-TYPE
    SYNTAX PerfIntervalCount
    UNITS "TFCs"
    MAX-ACCESS read-only
    STATUS current
    DESCRIPTION
	""
    REFERENCE
	"ITU-T Rec. Q.751.1 (10/95) : receivedTFC.
	 ITU-T Rec. Q.752 (1997) : Table 5/Q.752, 5.8."
    ::= { mtpSpInt15minEntry 5 }

mtpSpInt15minReceivedTFCstatus2 OBJECT-TYPE
    SYNTAX PerfIntervalCount
    UNITS "TFCs"
    MAX-ACCESS read-only
    STATUS current
    DESCRIPTION
	""
    REFERENCE
	"ITU-T Rec. Q.751.1 (10/95) : receivedTFC.
	 ITU-T Rec. Q.752 (1997) : Table 5/Q.752, 5.8."
    ::= { mtpSpInt15minEntry 6 }

mtpSpInt15minOctetsXferred OBJECT-TYPE
    SYNTAX PerfIntervalCount
    MAX-ACCESS read-only
    STATUS current
    DESCRIPTION
	""
    ::= { mtpSpInt15minEntry 7 }




-- ====================================================================

mtpSpSiTable OBJECT-TYPE
    SYNTAX SEQUENCE OF MtpSpSiEntry
    MAX-ACCESS not-accessible
    STATUS current
    DESCRIPTION
	"Provides a table of optional current signalling point 
	 operational measurements broken out be SI code."
    ::= { mtpSp 7 }

mtpSpSiEntry OBJECT-TYPE
    SYNTAX MtpSpSiEntry
    MAX-ACCESS not-accessible
    STATUS current
    DESCRIPTION
	""
    INDEX {
	mtpSpId, -- shared index
	mtpSpSiCode
    }
    ::= { mtpSpSiTable 1 }

MtpSpSiEntry ::= SEQUENCE {
    mtpSpSiCode					Unsigned32,
    mtpSpSiValidIntervals			HCPerfValidIntervals,
    mtpSpSiTimeDiscontinuity			TimeStamp,
    mtpSpSiTransmittedUPUnavailable		PerfCurrentCount, -- Q.752, 5.6
    mtpSpSiReceivedUPUnavailable		PerfCurrentCount, -- Q.752, 5.7
    mtpSpSiHandledOctetsSIO			PerfCurrentCount, -- Q.752, 6.3
    mtpSpSiStatus				RowStatus
}

mtpSpSiCode OBJECT-TYPE
    SYNTAX Unsigned32
    MAX-ACCESS not-accessible
    STATUS current
    DESCRIPTION
	""
    ::= { mtpSpSiEntry 1 }

mtpSpSiValidIntervals OBJECT-TYPE
    SYNTAX HCPerfValidIntervals
    MAX-ACCESS read-only
    STATUS current
    DESCRIPTION
	""
    ::= { mtpSpSiEntry 2 }

mtpSpSiTimeDiscontinuity OBJECT-TYPE
    SYNTAX TimeStamp
    MAX-ACCESS read-only
    STATUS current
    DESCRIPTION
	""
    ::= { mtpSpSiEntry 3 }

mtpSpSiTransmittedUPUnavailable OBJECT-TYPE
    SYNTAX PerfCurrentCount
    UNITS "UPUs"
    MAX-ACCESS read-only
    STATUS current
    DESCRIPTION
	""
    REFERENCE
	"ITU-T Rec. Q.751.1 (10/95) : transmitedUPUnavailable.
	 ITU-T Rec. Q.752 (1997) : Table 5/Q.752, 5.6."
    ::= { mtpSpSiEntry 4 }

mtpSpSiReceivedUPUnavailable OBJECT-TYPE
    SYNTAX PerfCurrentCount
    UNITS "UPUs"
    MAX-ACCESS read-only
    STATUS current
    DESCRIPTION
	""
    REFERENCE
	"ITU-T Rec. Q.751.1 (10/95) : receivedUPUnavailable.
	 ITU-T Rec. Q.752 (1997) : Table 5/Q.752, 5.7."
    ::= { mtpSpSiEntry 5 }

mtpSpSiHandledOctetsSIO OBJECT-TYPE
    SYNTAX PerfCurrentCount
    UNITS "octets"
    MAX-ACCESS read-only
    STATUS current
    DESCRIPTION
	""
    REFERENCE
	"ITU-T Rec. Q.751.1 (10/95) : handledOctetsSIO.
	 ITU-T Rec. Q.752 (1997) : Table 6/Q.752, 6.3."
    ::= { mtpSpSiEntry 6 }

mtpSpSiStatus OBJECT-TYPE
    SYNTAX RowStatus
    MAX-ACCESS read-create
    STATUS current
    DESCRIPTION
	""
    REFERENCE
	"STD 58, SNMPv2-TC RowStatus."
    ::= { mtpSpSiEntry 7 }




-- ====================================================================

mtpSpSiInt5minTable OBJECT-TYPE
    SYNTAX SEQUENCE OF MtpSpSiInt5minEntry
    MAX-ACCESS not-accessible
    STATUS current
    DESCRIPTION
	"Provides a table of optional 5-minute interval historical 
	 signalling point operational measurements broken out be SI 
	 code."
    ::= { mtpSp 8 }

mtpSpSiInt5minEntry OBJECT-TYPE
    SYNTAX MtpSpSiInt5minEntry
    MAX-ACCESS not-accessible
    STATUS current
    DESCRIPTION
	""
    INDEX {
	mtpSpId, -- shared index
	mtpSpSiCode,
	mtpSpSiInt5minInterval 
    }
    ::= { mtpSpSiInt5minTable 1 }


MtpSpSiInt5minEntry ::= SEQUENCE {
    mtpSpSiInt5minInterval			Unsigned32,
    mtpSpSiInt5minTimeStamp			TimeStamp,
    mtpSpSiInt5minTransmittedUPUnavailable	PerfIntervalCount, -- Q.752, 5.6
    mtpSpSiInt5minReceivedUPUnavailable		PerfIntervalCount, -- Q.752, 5.7
    mtpSpSiInt5minHandledOctetsSIO		PerfIntervalCount  -- Q.752, 6.3
}

mtpSpSiInt5minInterval OBJECT-TYPE
    SYNTAX Unsigned32
    MAX-ACCESS not-accessible
    STATUS current
    DESCRIPTION
	""
    ::= { mtpSpSiInt5minEntry 1 }

mtpSpSiInt5minTimeStamp OBJECT-TYPE
    SYNTAX TimeStamp
    MAX-ACCESS read-only
    STATUS current
    DESCRIPTION
	""
    ::= { mtpSpSiInt5minEntry 2 }

mtpSpSiInt5minTransmittedUPUnavailable OBJECT-TYPE
    SYNTAX PerfIntervalCount
    UNITS "UPUs"
    MAX-ACCESS read-only
    STATUS current
    DESCRIPTION
	""
    REFERENCE
	"ITU-T Rec. Q.751.1 (10/95) : transmitedUPUnavailable.
	 ITU-T Rec. Q.752 : Table 5/Q.752, 5.6."
    ::= { mtpSpSiInt5minEntry 3 }

mtpSpSiInt5minReceivedUPUnavailable OBJECT-TYPE
    SYNTAX PerfIntervalCount
    UNITS "UPUs"
    MAX-ACCESS read-only
    STATUS current
    DESCRIPTION
	""
    REFERENCE
	"ITU-T Rec. Q.751.1 (10/95) : receivedUPUnavailable.
	 ITU-T Rec. Q.752 : Table 5/Q.752, 5.7."
    ::= { mtpSpSiInt5minEntry 4 }

mtpSpSiInt5minHandledOctetsSIO OBJECT-TYPE
    SYNTAX PerfIntervalCount
    UNITS "octets"
    MAX-ACCESS read-only
    STATUS current
    DESCRIPTION
	""
    REFERENCE
	"ITU-T Rec. Q.751.1 (10/95) : handledOctetsSIO.
	 ITU-T Rec. Q.752 (1997) : Table 6/Q.752, 6.3."
    ::= { mtpSpSiInt5minEntry 5 }




-- ====================================================================

mtpSpSiInt15minTable OBJECT-TYPE
    SYNTAX SEQUENCE OF MtpSpSiInt15minEntry
    MAX-ACCESS not-accessible
    STATUS current
    DESCRIPTION
	"Provides a table of optional 15-minute interval historical 
	 signalling point operational measurements broken out be SI 
	 code."
    ::= { mtpSp 9 }

mtpSpSiInt15minEntry OBJECT-TYPE
    SYNTAX MtpSpSiInt15minEntry
    MAX-ACCESS not-accessible
    STATUS current
    DESCRIPTION
	""
    INDEX {
	mtpSpId, -- shared index
	mtpSpSiCode,
	mtpSpSiInt15minInterval
    }
    ::= { mtpSpSiInt15minTable 1 }


MtpSpSiInt15minEntry ::= SEQUENCE {
    mtpSpSiInt15minInterval			Unsigned32,
    mtpSpSiInt15minTimeStamp			TimeStamp,
    mtpSpSiInt15minTransmittedUPUnavailable	PerfIntervalCount, -- Q.752, 5.6
    mtpSpSiInt15minReceivedUPUnavailable	PerfIntervalCount, -- Q.752, 5.7
    mtpSpSiInt15minHandledOctetsSIO		PerfIntervalCount  -- Q.752, 6.3
}

mtpSpSiInt15minInterval OBJECT-TYPE
    SYNTAX Unsigned32
    MAX-ACCESS not-accessible
    STATUS current
    DESCRIPTION
	""
    ::= { mtpSpSiInt15minEntry 1 }

mtpSpSiInt15minTimeStamp OBJECT-TYPE
    SYNTAX TimeStamp
    MAX-ACCESS read-only
    STATUS current
    DESCRIPTION
	""
    ::= { mtpSpSiInt15minEntry 2 }

mtpSpSiInt15minTransmittedUPUnavailable OBJECT-TYPE
    SYNTAX PerfIntervalCount
    UNITS "UPUs"
    MAX-ACCESS read-only
    STATUS current
    DESCRIPTION
	""
    REFERENCE
	"ITU-T Rec. Q.751.1 (10/95) : transmitedUPUnavailable.
	 ITU-T Rec. Q.752 : Table 5/Q.752, 5.6."
    ::= { mtpSpSiInt15minEntry 3 }

mtpSpSiInt15minReceivedUPUnavailable OBJECT-TYPE
    SYNTAX PerfIntervalCount
    UNITS "UPUs"
    MAX-ACCESS read-only
    STATUS current
    DESCRIPTION
	""
    REFERENCE
	"ITU-T Rec. Q.751.1 (10/95) : receivedUPUnavailable.
	 ITU-T Rec. Q.752 : Table 5/Q.752, 5.7."
    ::= { mtpSpSiInt15minEntry 4 }

mtpSpSiInt15minHandledOctetsSIO OBJECT-TYPE
    SYNTAX PerfIntervalCount
    UNITS "octets"
    MAX-ACCESS read-only
    STATUS current
    DESCRIPTION
	""
    REFERENCE
	"ITU-T Rec. Q.751.1 (10/95) : handledOctetsSIO.
	 ITU-T Rec. Q.752 (1997) : Table 6/Q.752, 6.3."
    ::= { mtpSpSiInt15minEntry 5 }



-- ====================================================================

mtpSpStudyTable OBJECT-TYPE
    SYNTAX SEQUENCE OF MtpSpStudyEntry
    MAX-ACCESS not-accessible
    STATUS current
    DESCRIPTION
	""
    ::= { mtpSp 10 }

mtpSpStudyEntry OBJECT-TYPE
    SYNTAX MtpSpStudyEntry
    MAX-ACCESS not-accessible
    STATUS current
    DESCRIPTION
	""
    INDEX {
	mtpSpStudyId
    }
    ::= { mtpSpStudyTable 1 }


MtpSpStudyEntry ::= SEQUENCE {
    mtpSpStudyId				Unsigned32,
    mtpSpStudyValidIntervals			HCPerfValidIntervals,
    mtpSpStudyTimeDiscontinuity			TimeStamp,
    mtpSpStudyHandledOctetsOpcDpcSio		PerfCurrentCount, -- Q.752, 6.6
    mtpSpStudyHandledMSUsOpcDpcSio		PerfCurrentCount, -- Q.752, 6.7
    mtpSpStudyStatus				RowStatus
}

mtpSpStudyId OBJECT-TYPE
    SYNTAX Unsigned32
    MAX-ACCESS not-accessible
    STATUS current
    DESCRIPTION
	"Provides a non-zero index into the signalling point study 
	 table."
    ::= { mtpSpStudyEntry 1 }

mtpSpStudyValidIntervals OBJECT-TYPE
    SYNTAX HCPerfValidIntervals
    MAX-ACCESS read-only
    STATUS current
    DESCRIPTION
	""
    ::= { mtpSpStudyEntry 2 }

mtpSpStudyTimeDiscontinuity OBJECT-TYPE
    SYNTAX TimeStamp
    MAX-ACCESS read-only
    STATUS current
    DESCRIPTION
	""
    ::= { mtpSpStudyEntry 3 }

mtpSpStudyHandledOctetsOpcDpcSio OBJECT-TYPE
    SYNTAX PerfCurrentCount
    UNITS "octets"
    MAX-ACCESS read-only
    STATUS current
    DESCRIPTION
	""
    REFERENCE
	"ITU-T Rec. Q.751.1 (10/95) : handledOctetsOpcDpcSio.
	 ITU-T Rec. Q.752 (1997) : Table 6/Q.752, 6.6."
    ::= { mtpSpStudyEntry 4 }

mtpSpStudyHandledMSUsOpcDpcSio OBJECT-TYPE
    SYNTAX PerfCurrentCount
    UNITS "MSUs"
    MAX-ACCESS read-only
    STATUS current
    DESCRIPTION
	""
    REFERENCE
	"ITU-T Rec. Q.751.1 (10/95) : handledMSUsOpcDpcSio.
	 ITU-T Rec. Q.752 (1997) : Table 6/Q.752, 6.7."
    ::= { mtpSpStudyEntry 5 }

mtpSpStudyStatus OBJECT-TYPE
    SYNTAX RowStatus
    MAX-ACCESS read-create
    STATUS current
    DESCRIPTION
	""
    REFERENCE
	"STD 58, SNMPv2-TC RowStatus."
    ::= { mtpSpStudyEntry 6 }



-- ====================================================================

mtpSpStudyInt5minTable OBJECT-TYPE
    SYNTAX SEQUENCE OF MtpSpStudyInt5minEntry
    MAX-ACCESS not-accessible
    STATUS current
    DESCRIPTION
	""
    ::= { mtpSp 11 }

mtpSpStudyInt5minEntry OBJECT-TYPE
    SYNTAX MtpSpStudyInt5minEntry
    MAX-ACCESS not-accessible
    STATUS current
    DESCRIPTION
	""
    INDEX {
	mtpSpStudyId,
	mtpSpStudyInt5minInterval
    }
    ::= { mtpSpStudyInt5minTable 1 }


MtpSpStudyInt5minEntry ::= SEQUENCE {
    mtpSpStudyInt5minInterval			Unsigned32,
    mtpSpStudyInt5minTimeStamp			TimeStamp,
    mtpSpStudyInt5minHandledOctetsOpcDpcSio	PerfIntervalCount, -- Q.752, 6.6
    mtpSpStudyInt5minHandledMSUsOpcDpcSio	PerfIntervalCount  -- Q.752, 6.7
}

mtpSpStudyInt5minInterval OBJECT-TYPE
    SYNTAX Unsigned32
    MAX-ACCESS not-accessible
    STATUS current
    DESCRIPTION
	""
    ::= { mtpSpStudyInt5minEntry 1 }

mtpSpStudyInt5minTimeStamp OBJECT-TYPE
    SYNTAX TimeStamp
    MAX-ACCESS read-only
    STATUS current
    DESCRIPTION
	""
    ::= { mtpSpStudyInt5minEntry 2 }

mtpSpStudyInt5minHandledOctetsOpcDpcSio OBJECT-TYPE
    SYNTAX PerfIntervalCount
    UNITS "octets"
    MAX-ACCESS read-only
    STATUS current
    DESCRIPTION
	""
    REFERENCE
	"ITU-T Rec. Q.751.1 (10/95) : handledOctetsOpcDpcSio.
	 ITU-T Rec. Q.752 (1997) : Table 6/Q.752, 6.6."
    ::= { mtpSpStudyInt5minEntry 3 }

mtpSpStudyInt5minHandledMSUsOpcDpcSio OBJECT-TYPE
    SYNTAX PerfIntervalCount
    UNITS "MSUs"
    MAX-ACCESS read-only
    STATUS current
    DESCRIPTION
	""
    REFERENCE
	"ITU-T Rec. Q.751.1 (10/95) : handledMSUsOpcDpcSio.
	 ITU-T Rec. Q.752 (1997) : Table 6/Q.752, 6.7."
    ::= { mtpSpStudyInt5minEntry 4 }



-- ====================================================================

mtpSpStudyInt15minTable OBJECT-TYPE
    SYNTAX SEQUENCE OF MtpSpStudyInt15minEntry
    MAX-ACCESS not-accessible
    STATUS current
    DESCRIPTION
	""
    ::= { mtpSp 12 }

mtpSpStudyInt15minEntry OBJECT-TYPE
    SYNTAX MtpSpStudyInt15minEntry
    MAX-ACCESS not-accessible
    STATUS current
    DESCRIPTION
	""
    INDEX {
	mtpSpStudyId,
	mtpSpStudyInt15minInterval
    }
    ::= { mtpSpStudyInt15minTable 1 }


MtpSpStudyInt15minEntry ::= SEQUENCE {
    mtpSpStudyInt15minInterval			Unsigned32,
    mtpSpStudyInt15minTimeStamp			TimeStamp,
    mtpSpStudyInt15minHandledOctetsOpcDpcSio	PerfIntervalCount, -- Q.752, 6.6
    mtpSpStudyInt15minHandledMSUsOpcDpcSio	PerfIntervalCount  -- Q.752, 6.7
}

mtpSpStudyInt15minInterval OBJECT-TYPE
    SYNTAX Unsigned32
    MAX-ACCESS not-accessible
    STATUS current
    DESCRIPTION
	""
    ::= { mtpSpStudyInt15minEntry 1 }

mtpSpStudyInt15minTimeStamp OBJECT-TYPE
    SYNTAX TimeStamp
    MAX-ACCESS read-only
    STATUS current
    DESCRIPTION
	""
    ::= { mtpSpStudyInt15minEntry 2 }

mtpSpStudyInt15minHandledOctetsOpcDpcSio OBJECT-TYPE
    SYNTAX PerfIntervalCount
    UNITS "octets"
    MAX-ACCESS read-only
    STATUS current
    DESCRIPTION
	""
    REFERENCE
	"ITU-T Rec. Q.751.1 (10/95) : handledOctetsOpcDpcSio.
	 ITU-T Rec. Q.752 (1997) : Table 6/Q.752, 6.6."
    ::= { mtpSpStudyInt15minEntry 3 }

mtpSpStudyInt15minHandledMSUsOpcDpcSio OBJECT-TYPE
    SYNTAX PerfIntervalCount
    UNITS "MSUs"
    MAX-ACCESS read-only
    STATUS current
    DESCRIPTION
	""
    REFERENCE
	"ITU-T Rec. Q.751.1 (10/95) : handledMSUsOpcDpcSio.
	 ITU-T Rec. Q.752 (1997) : Table 6/Q.752, 6.7."
    ::= { mtpSpStudyInt15minEntry 4 }


-- ====================================================================

mtpSpStudyMapTable OBJECT-TYPE
    SYNTAX SEQUENCE OF MtpSpStudyMapEntry
    MAX-ACCESS not-accessible
    STATUS current
    DESCRIPTION
	""
    ::= { mtpSp 13 }

mtpSpStudyMapEntry OBJECT-TYPE
    SYNTAX MtpSpStudyMapEntry
    MAX-ACCESS not-accessible
    STATUS current
    DESCRIPTION
	""
    INDEX {
	mtpSpId, -- shared index
	mtpOpcRsId,	-- OPC value
	mtpDpcRsId,	-- DPC value
	mtpSpSiCode,	-- SI code
	mtpSpStudyId
    }
    ::= { mtpSpStudyMapTable 1 }


MtpSpStudyMapEntry ::= SEQUENCE {
    mtpOpcRsId					Unsigned32,
    mtpDpcRsId					Unsigned32,
    mtpSpStudyMapStatus				RowStatus
}

mtpOpcRsId OBJECT-TYPE
    SYNTAX Unsigned32
    MAX-ACCESS not-accessible
    STATUS current
    DESCRIPTION
	"Provides an OPC index into the table.  The is the index of the 
	 originating signalling point in the route set table 
	 mtpRsTable.  The entry must exist or the creation of a row will 
	 be refused."
    ::= { mtpSpStudyMapEntry 1 }

mtpDpcRsId OBJECT-TYPE
    SYNTAX Unsigned32
    MAX-ACCESS not-accessible
    STATUS current
    DESCRIPTION
	"Provides an DPC index into the table.  The is the index of the 
	 destination signalling point in the route set table 
	 mtpRsTable.  The entry must exist or the creation of a row will 
	 be refused."
    ::= { mtpSpStudyMapEntry 2 }

mtpSpStudyMapStatus OBJECT-TYPE
    SYNTAX RowStatus
    MAX-ACCESS read-create
    STATUS current
    DESCRIPTION
	""
    REFERENCE
	"STD 58, SNMPv2-TC RowStatus."
    ::= { mtpSpStudyMapEntry 3 }

-- ====================================================================

mtpL3Table OBJECT-TYPE
    SYNTAX SEQUENCE OF MtpL3Entry
    MAX-ACCESS not-accessible
    STATUS current
    DESCRIPTION
	"This managed object class models MTP Level 3 functionality.
	 
	 If the 'ITU-T Rec. X.721 (1992) | ISO/IEC 10165-2 : 
	 1992':communicationsAlarm notification is used, the following 
	 probable causes can apply:
	 
	 Probable Cause = 501 (AdjacentPCInaccessible), with the 
	 inaccessible adjacent pointcode as a parameter, which 
	 represents measurement Q.752/5.1 
	 (PerceivedSeverity=Maj/Min/War) and measurement Q.752/5.4 
	 (PerceivedSeverity=Cleared).
	 
	 If the ss7OnOccEventPackage is included, event notifications 
	 with the following probable causes can apply:
	 
	 Probable Cause = 405 (LinkSetFailure), with the inaccessible 
	 adjacent pointcode as a parameter, which represents measurement 
	 Q.752/4.5 (PerceivedSeverity=Maj/Min/War) and measurement 
	 Q.752/4.6 (PerceivedSeverity=Cleared).
	 
	 Probable Cause = 413 (LinkSetChange), with the involved link 
	 sets as parameter, which represents measurement Q.752/4.13."
    REFERENCE
	"ITU-T Rec. Q.751.1 (1997), ANSI T1.116.1 (2000), mtpLevel3 
	 MOC."
    ::= { mtpL3 1 }

mtpL3Entry OBJECT-TYPE
    SYNTAX MtpL3Entry
    MAX-ACCESS not-accessible
    STATUS current
    DESCRIPTION
	""
    REFERENCE
	"ITU-T Rec. Q.751.1 (1997), ANSI T1.116.1 (2000), mtpLevel3 MO."
    INDEX {
	mtpL3Id
    }
    ::= { mtpL3Table 1 }

MtpL3Entry ::= SEQUENCE {
    mtpL3Id					SimpleNameType,
    mtpL3AdministrativeState			AdministrativeState,
    mtpL3OperationalState			OperationalState,
    mtpL3UsageState				UsageState,
    mtpL3ProceduralStatus			ProceduralStatus,
    mtpL3AsaProfilePointer			RowPointer,
    mtpL3Name					VisibleString,
    mtpL3RowStatus				RowStatus
}

mtpL3Id OBJECT-TYPE
    SYNTAX SimpleNameType
    MAX-ACCESS not-accessible
    STATUS current
    DESCRIPTION
	"This attribute is used for naming instances."
    REFERENCE
	"ITU-T Rec. Q.751.1 (1997), ANSI T1.116.1 (2000), mtpLevel3Id 
	 attribute."
    ::= { mtpL3Entry 1 }

mtpL3AdministrativeState OBJECT-TYPE
    SYNTAX AdministrativeState
    MAX-ACCESS read-create
    STATUS current
    DESCRIPTION
	"Provides the administrative state of the MTP level 3 entity 
	 followin the AdministrativeState textual convention of the 
	 OPENSS7-SMI-MIB module and according to ITU-T Rec. X.721 | 
	 ISO/IEC 10165-2.

	 - locked(0), 
	 - unlocked(1), 
	 - shuttingDown(2), 
	 "
    REFERENCE
	"ITU-T Rec. Q.751.1 (1997), ANSI T1.116.1 (2000), 
	 administrativeState attribute."
    DEFVAL { 0 } -- locked
    ::= { mtpL3Entry 2 }

mtpL3OperationalState OBJECT-TYPE
    SYNTAX OperationalState
    MAX-ACCESS read-only
    STATUS current
    DESCRIPTION
	"Provides the operational state of the MTP level 3 entity 
	 followin the OperationalState textual convention of the 
	 OPENSS7-SMI-MIB module and according to ITU-T Rec. X.721 | 
	 ISO/IEC 10165-2.

	 - disabled(0), 
	 - enabled(1), 
	 "
    REFERENCE
	"ITU-T Rec. Q.751.1 (1997), ANSI T1.116.1 (2000), 
	 operationalState attribute."
    DEFVAL { 0 } -- disabled
    ::= { mtpL3Entry 3 }

mtpL3UsageState OBJECT-TYPE
    SYNTAX UsageState
    MAX-ACCESS read-only
    STATUS current
    DESCRIPTION
	"Provides the usage state of the MTP level 3 entity followin the 
	 UsageState textual convention of the OPENSS7-SMI-MIB module and 
	 according to ITU-T Rec. X.721 | ISO/IEC 10165-2.

	 - idle(0),
	 - active(1),
	 - busy(2),
	 "
    REFERENCE
	"ITU-T Rec. Q.751.1 (1997), ANSI T1.116.1 (2000), usageState 
	 attribute."
    DEFVAL { 0 } -- idle
    ::= { mtpL3Entry 4 }

mtpL3ProceduralStatus OBJECT-TYPE
    SYNTAX ProceduralStatus
    MAX-ACCESS read-only
    STATUS current
    DESCRIPTION
	"Provides the procedural status of the MTP level 3 entity 
	 followin the ProceduralStatus textual convention of the 
	 OPENSS7-SMI-MIB module and according to ITU-T Rec. X.721 | 
	 ISO/IEC 10165-2.
	 
	 - initializationRequired(0),
	 - notInitialized(1),
	 - initializing(2),
	 - reporting(3),
	 - terminating(4),
	 "
    REFERENCE
	"ITU-T Rec. Q.751.1 (1997), ANSI T1.116.1 (2000), 
	 proceduralStatus attribute."
    DEFVAL { 0 } -- initializationRequired
    ::= { mtpL3Entry 5 }

mtpL3AsaProfilePointer OBJECT-TYPE
    SYNTAX RowPointer
    MAX-ACCESS read-create
    STATUS current
    DESCRIPTION
	"Provides a pointer to an alarm severity assignment profile to 
	 be used for alarms generated by this signalling link 
	 termination point, or zeroDotZero."
    REFERENCE
	"ITU-T Rec. Q.751.1 (1997), ANSI T1.116.1 (2000), 
	 alarmSeverityAssignmentProfilePointer attribute."
    DEFVAL { { zeroDotZero }}
    ::= { mtpL3Entry 6 }

mtpL3Name OBJECT-TYPE
    SYNTAX VisibleString
    MAX-ACCESS read-create
    STATUS current
    DESCRIPTION
	"This attribute is an additional name for instances of the 
	 mtpLevel3 managed object class."
    REFERENCE
	"ITU-T Rec. Q.751.1 (1997), ANSI T1.116.1 (2000), mtpLevel3Name 
	 attribute."
    ::= { mtpL3Entry 7 }

mtpL3RowStatus OBJECT-TYPE
    SYNTAX RowStatus
    MAX-ACCESS read-create
    STATUS current
    DESCRIPTION
	"Provides a mechanism whereby management stations may create and 
	 delete rows in this table.
	 
	 If the name package is supported: a create request with a value 
	 for the name attribute that is already used by another instance 
	 of the same object class will be rejected."
    REFERENCE
	"STD 58, SNMPv2-TC RowStatus.
	 ITU-T Rec. Q.751.1 (1997) : mtpSignPoint-mtpLevel3 NAME 
	 BINDING."
    ::= { mtpL3Entry 8 }


-- ====================================================================


mtpRsProfileTable OBJECT-TYPE
    SYNTAX SEQUENCE OF MtpRsProfileEntry
    MAX-ACCESS not-accessible
    STATUS current
    DESCRIPTION
	""
    ::= { mtpRs 1 }

mtpRsProfileEntry OBJECT-TYPE
    SYNTAX MtpRsProfileEntry
    MAX-ACCESS not-accessible
    STATUS current
    DESCRIPTION
	""
    INDEX {
	mtpRsProfileId
    }
    ::= { mtpRsProfileTable 1 }

MtpRsProfileEntry ::= SEQUENCE {
    mtpRsProfileId				SimpleNameType,
    mtpRsProfileName				SnmpAdminString,
    mtpRsProfileTimerT8				TimeInterval,
    mtpRsProfileTimerT11			TimeInterval,
    mtpRsProfileTimerT15			TimeInterval,
    mtpRsProfileTimerT16			TimeInterval,
    mtpRsProfileTimerT18A			TimeInterval,
    mtpRsProfileRtDefault			SimpleNameType,
    mtpRsProfileRowStatus			RowStatus
}

mtpRsProfileId OBJECT-TYPE
    SYNTAX SimpleNameType
    MAX-ACCESS not-accessible
    STATUS current
    DESCRIPTION
	"Provides an into the signalling route set profile table.  Rows 
	 in this table can be referred to using this index or using the 
	 RowPointer pointer.  The index valud zero (0) has special 
	 semantics: the zero index contains default default values."
    ::= { mtpRsProfileEntry 1 }

mtpRsProfileName OBJECT-TYPE
    SYNTAX SnmpAdminString
    MAX-ACCESS read-create
    STATUS current
    DESCRIPTION
	"Provides an optional administrative name for this signalling 
	 route set profile."
    ::= { mtpRsProfileEntry 2 }

mtpRsProfileTimerT8 OBJECT-TYPE
    SYNTAX TimeInterval (80..120)
    UNITS "centiseconds"
    MAX-ACCESS read-create
    STATUS current
    DESCRIPTION
	"This attribute defines the initial timer value of timer T8 
	 Transfer prohibited inhibition timer (transient solution) 
	 defined in Recommendation Q.704. The value range is from 800 to 
	 1200 ms.
	 
	 Note that in ITU-T Rec. Q.751.1 (1997) and ANSI T1.116.1 (2000) 
	 this timer is part of the lsTimersProfile MOC."
    REFERENCE
	"ITU-T Rec. Q.751.1 (1997), ANSI T1.116.1 (2000), q704-t8 
	     attribute."
    DEFVAL { 100 }
    ::= { mtpRsProfileEntry 3 }

mtpRsProfileTimerT11 OBJECT-TYPE
    SYNTAX TimeInterval (3000..9000)
    UNITS "centiseconds"
    MAX-ACCESS read-create
    STATUS current
    DESCRIPTION
	"This attribute defines the initial timer value of timer T11 
	 Transfer restricted timer defined in Recommendation Q.704. The 
	 value range is from 30 to 90 seconds.  This is one way of 
	 implementing the function described in 13.4/Q.704 and mainly 
	 intended to simplify STPs.
	 
	 ANSI T1.111.4 (1996-2000)  13.4.2 ... (1) When the normal 
	     route(s) to destination X become unavailable and signalling 
	     transfer point Y begins using a lower priority route to 
	     destination X, timer T11 is started.  When timer T11 
	     expires or the lower priority route experiences danger of 
	     congestion (whichever occurs first), signalling transfer 
	     point Y notifies accessible adjacent signalling points 
	     using one of two possible methods:
	 
	     (a) Broadcast Method
	 
	     Signalling transfer point Y sends transfer-restricted 
	     messages concerning destination X to all accessible 
	     adjacent signalling points, except those signalling points 
	     that receive a transfer-prohibited message according to 
	     13.2.2 (1) and except destination X if it is an adjacent 
	     point.  Timer T18 is started after the broadcast is 
	     complete.  If the failure is still present and T18 expires, 
	     a transfer-restricted message is sent once per incoming 
	     link or link set by signalling transfer point Y in response 
	     to a message for destination X.
	 
	     As a network option, the rate that transfer-restricted 
	     messages are broadcast may be regulated to minimize the 
	     burst of traffic that can occur due to controlled rerouting 
	     in adjacent nodes.  This regulation is not performed for 
	     the broadcasting of transfer-restricted messages indicating 
	     that a previously isolated destination is accessible."
    REFERENCE
	"ITU-T Rec. Q.751.1 (1997), ANSI T1.116.1 (2000), q704-t11 
	 attribute."
    DEFVAL { 6000 }
    ::= { mtpRsProfileEntry 4 }

mtpRsProfileTimerT15 OBJECT-TYPE
    SYNTAX TimeInterval (200..300)
    UNITS "centiseconds"
    MAX-ACCESS read-create
    STATUS current
    DESCRIPTION
	"This attribute defines the initial timer value of timer T15 
	 Waiting to start signalling route set congestion test defined 
	 in Recommendation Q.704. The value range is from 2 to 3 
	 seconds.
	 
	 13.7.5  If T15 expires after the last update of the signalling 
	    route set toward destination X by a transfer-controlled 
	    message relating to the same destination, the signalling 
	    route set congestion test procedure is invoked (see 13.9).
	 
	 13.9.4  Provided that the signalling route set toward 
	    destination X is not in the 'unavailable' state, a 
	    signalling route set congestion test message is sent from an 
	    originating signalling point to destination X in the 
	    following cases: i) When T15 expires after the last update 
	    of the congestion status of the signalling route set toward 
	    destination X by a transfer controlled message relating to 
	    the same destination.
	 
	 Start:  TFC received
	 Stop:   --
	 Expiry: Send RCT, start T16"
    REFERENCE
	"ITU-T Rec. Q.751.1 (1997), ANSI T1.116.1 (2000), q704-t15 
	 attribute."
    DEFVAL { 250 }
    ::= { mtpRsProfileEntry 5 }

mtpRsProfileTimerT16 OBJECT-TYPE
    SYNTAX TimeInterval (140..200)
    UNITS "centiseconds"
    MAX-ACCESS read-create
    STATUS current
    DESCRIPTION
	"This attribute defines the initial timer value of timer T16 
	 Waiting for route set congestion status update defined in 
	 Recommendation Q.704. The value range is from 1.4 to 2 seconds.
	 
	 13.9.3  If T16 expires after sending a signalling route set 
	    congestion test message without a transfer controlled 
	    message relating to the concerned destination having been 
	    received, the signalling point changes the congestion status 
	    associated with the signalling route set toward the 
	    concerned destination to the next lower status.
	 
	 13.9.4  Provided that the signalling route set toward 
	    destination X is not in the 'unavailable' state, a 
	    signalling route set congestion test message is sent from an 
	    originating signalling point to destination X in the 
	    following cases: i) ... ii) When T16 expires after sending a 
	    signalling route set congestion test message to destination 
	    X without a transfer controlled message relating to the same 
	    destination having been received.  After the congestion 
	    status have been decremented by one, the test is repeated, 
	    unless the congestion status is zero.
	 
	 Start:  T15 expires
	 Stop:   TFC received
	 Expiry: Decrement cong status, inform users, send RCT and 
	 restart if still congested."
    REFERENCE
	"ITU-T Rec. Q.751.1 (1997), ANSI T1.116.1 (2000), q704-t16 
	 attribute."
    DEFVAL { 175 }
    ::= { mtpRsProfileEntry 6 }

mtpRsProfileTimerT18A OBJECT-TYPE
    SYNTAX TimeInterval (200..2000)
    UNITS "centiseconds"
    MAX-ACCESS read-create
    STATUS current
    DESCRIPTION
	"This attribute defines the intial timer value of timer T18 
	 (ANSI) waiting TFR final response defined in ANSI T1.111.4.  
	 The value range is from 2 to 20 seconds."
    DEFVAL { 1200 }
    ::= { mtpRsProfileEntry 7 }

mtpRsProfileRtDefault OBJECT-TYPE
    SYNTAX SimpleNameType
    MAX-ACCESS read-create
    STATUS current
    DESCRIPTION
	"provides a reference to an MTP signalling route protocol 
	 profile to use when creating signalling routes under this 
	 signalling route set.  When unspecified, the signalling route 
	 protocol profile specified for the signalling point is 
	 inherited."
    ::= { mtpRsProfileEntry 8 }

mtpRsProfileRowStatus OBJECT-TYPE
    SYNTAX RowStatus
    MAX-ACCESS read-create
    STATUS current
    DESCRIPTION
	""
    REFERENCE
	"STD 58, SNMPv2-TC RowStatus."
    ::= { mtpRsProfileEntry 9 }


-- ====================================================================

mtpRsTable OBJECT-TYPE
    SYNTAX SEQUENCE OF MtpRsEntry
    MAX-ACCESS not-accessible
    STATUS current
    DESCRIPTION
	"A Signalling Route Set is a complete set of routes that can be 
	 used to carry traffic toward a specific destination signalling 
	 point.  The signRouteSetNePart Managed Object class defines the 
	 management capabilities of the resources which represent a 
	 specific destination SP and its accessibility as seen from the 
	 own SP.  This SP may be the originating SP of the MTP messages 
	 or an STP.  A particular signRouteSetNePart may be related to 
	 one or more Signalling Route Sets on network level.
	 
	 The administrativeState attribute describes whether it is 
	 administratively permitted to route SS No. 7 MSUs towards the 
	 respective destination point.  Before the administrative state 
	 of a signRouteSetNePart can be set to 'unlocked', there must be 
	 at least one signRouteNePart contained within the 
	 signRouteSetNePart.
	 
	 The operationalState attribute describes whether the respective 
	 destination signalling point is accessible - ('enabled') or not 
	 ('disabled').  If the operational states of all signRouteNePart 
	 instances contained in the signRouteSetNePart are 'disabled', 
	 then the operational state of the signRouteSetNePart is 
	 'disabled', in any other case it is 'enabled'.
	 
	 The usageState attribute is used to reflect route set 
	 congestion.  The value is 'busy' in case of route set 
	 congestion.
	 
	 If the 'ITU-T Rec. X.721 (1992) | ISO/IEC 10165-2: 
	 1992':communicationsAlarm notification is present, it indicates 
	 at least the following probable causes:
	 
	 Probable Cause = 411(RouteSetUnavailable), which represents 
	 measurements Q.752/4.11 (PerceivedSeverity=Maj/Min/War) and 
	 Q.751/4.12 (PerceivedSeverity=Cleared).
	 
	 If the ss7OnOccEventPackage is present, event notifications 
	 with the following probable cause can apply:
	 
	 Probable Cause = 002 (remoteUserPartUnavailable), with the 
	 involved user part as parameter.  Possible values for 
	 SpecificProblems are: 007 'unknown', 008 'unequipped' and 009 
	 'inaccessibleRemoteUser'.
	 
	 An activation or deactivation of a signRouteSetNePart must lead 
	 to the activation respectively deactivation of all contained 
	 signRouteNeParts."
    REFERENCE
	"ITU-T Rec. Q.751.1 (1997), ANSI T1.116.1 (2000), 
	 signRouteSetNePart MOC."
    ::= { mtpRs 2 }

mtpRsEntry OBJECT-TYPE
    SYNTAX MtpRsEntry
    MAX-ACCESS not-accessible
    STATUS current
    DESCRIPTION
	"This is an entry of the signalling route set table.
	 
	 Entries in this table can generate an ss7OnOccEvent 
	 notification with the following parameters:
	 
	  - ITU-T Rec. Q.752 (1997) : Table 4/Q.752 4.5 
		probableCause = 405, (linkSetFailureTFPBroadcast)
		PerceivedSeverity = M/m/w, 
		AdditionalInfo = InaccessibleSp
	  - ITU-T Rec. Q.752 (1997) : Table 4/Q.752 4.6 
		probableCause = 405, (linkSetFailureTFPBroadcast)
		PerceivedSeverity = Cleared, 
		AdditionalInfo = InaccessibleSp
	 
	 Entries in this table can generate a communicationsAlarm with 
	 the following parameters:
	 
	  - ITU-T Rec. Q.752 (1997) : Table 4/Q.752 4.11
		probableCause = 411, (routesetUnavailability)
		PerceivedSeverity = M/m/w/,
	  - ITU-T Rec. Q.752 (1997) : Table 4/Q.752 4.12
		probableCause = 411, (routesetUnavailability)
		PerceivedSeverity = Cleared
	 
	 "
    REFERENCE
	"ITU-T Rec. Q.751.1 (1997), ANSI T1.116.1 (2000), 
	 signRouteSetNePart MO."
    INDEX {
	mtpSpId,
	mtpRsId
    }
    ::= { mtpRsTable 1 }

MtpRsEntry ::= SEQUENCE {
    mtpRsId					Unsigned32,
    mtpRsDest					NetworkPointCode,
    mtpRsFlags					BITS,
    mtpRsAdministrativeState			AdministrativeState,
    mtpRsOperationalState			OperationalState,
    mtpRsAsaProfilePointer			RowPointer,
    mtpRsCongestedState				MtpCongestedState,
    mtpRsCongestionLevel			MtpCongestionLevel,
    mtpRsLoadsharingInformation			OCTET STRING,
    mtpRsLoadsharingObject			RowPointer,
    mtpRsRemoteExchangeLabel			CommonLanguageName,
    mtpRsName					SimpleNameType,
    mtpRsProfile				SimpleNameType,
    mtpRsAlarmStatus				AlarmStatus,
    mtpRsRowStatus				RowStatus
}

mtpRsId OBJECT-TYPE
    SYNTAX Unsigned32
    MAX-ACCESS not-accessible
    STATUS current
    DESCRIPTION
	"Provides an index into the signalling route set table.
	 
	 This is the naming attribute of signRouteSetNePart.  It 
	 identifies a signRouteSetNePart instance within the 
	 mtpSignPoint and equals the signalling point code of the 
	 respective destination signalling point."
    REFERENCE
	"ITU-T Rec. Q.751.1 (1997), ANSI T1.116.1 (2000), 
	     signRouteSetNePartId attribute."
    ::= { mtpRsEntry 1 }

mtpRsDest OBJECT-TYPE
    SYNTAX NetworkPointCode
    MAX-ACCESS read-create
    STATUS current
    DESCRIPTION
	""
    ::= { mtpRsEntry 2 }

mtpRsFlags OBJECT-TYPE
    SYNTAX BITS {
		rsfCluster(0), rsfXferFunc(1), rsfSecurity(2), 
		rsfAdjacent(3) }
    MAX-ACCESS read-create
    STATUS current
    DESCRIPTION
	"This object indicates some additional information associated 
	 with the route set.  The object is set-valued and can contain 
	 the following:
	 
	  - rsfCluster(0), the route set corresponds to a cluster route 
	    set (cluster routing is only defined by ANSI);
	 
	  - rsfXferFunc(1),the destination signalling point associated 
	    with the route set has the transfer function;
	 
	  - rsfSecurity(2), the destination signalling point associated 
	    with the route set has security screening applied;
	 
	  - rsfAdjacent(3), the destination signalling point associated 
	    with the route set is an a adjacent signalling point (may 
	    not be combined with 'rsfCluster').
	  
	 Not all combinations of flags are legal.  Not all flag 
	 combinations are applicable to all protocol variants."
    ::= { mtpRsEntry 3 }

mtpRsAdministrativeState OBJECT-TYPE
    SYNTAX AdministrativeState
    MAX-ACCESS read-create
    STATUS current
    DESCRIPTION
	"Provides the administrative state of the signalling route set 
	 network element part following the AdministrativeState textual 
	 convention and ITU-T Rec. X.721 | ISO/IEC 10165-2.
	 
	  - locked(0), the signalling route set is administratively 
	    prohibited from use;
	 
	  - unlocked(1), the signalling route set is administratively 
	    permitted for use;
	 
	  - shuttingDown(2), not used.
	 "
    REFERENCE
	"ITU-T Rec. X.721 (1992) | ISO/IEC 10165-2 : 1992, 
	     Attribute-ASN1Module.AdministrativeState.
	 ITU-T Rec. Q.751.1 (1997), ANSI T1.116.1 (2000), 
	     administrativeState attribute."
    DEFVAL { 0 } -- locked
    ::= { mtpRsEntry 4 }

mtpRsOperationalState OBJECT-TYPE
    SYNTAX OperationalState
    MAX-ACCESS read-only
    STATUS current
    DESCRIPTION
	"Provides the operational state of the signalling route set 
	 network element part following the OperationalState textual 
	 convention and ITU-T Rec. X.721 | ISO/IEC 10165-2.
	 
	 - disabled(0), the destination is inaccessible due to the 
	   unavailability of all routes in the route set;
	 
	 - enabled(1), the destination is accessible: at least one 
	   signalling route in the route set is available.
	"
    REFERENCE
	"ITU-T Rec. X.721 (1992) | ISO/IEC 10165-2 : 1992, 
	     Attribute-ASN1Module.OperationalState.
	 ITU-T Rec. X.731 (1992) | ISO/IEC 10164-2 : 1993, 
	     Section 8.1.1.1.
	 ITU-T Rec. Q.751.1 (1997), ANSI T1.116.1 (2000), 
	     operationalState attribute."
    DEFVAL { 0 } -- disabled
    ::= { mtpRsEntry 5 }

mtpRsAsaProfilePointer OBJECT-TYPE
    SYNTAX RowPointer
    MAX-ACCESS read-create
    STATUS current
    DESCRIPTION
	"Provides a pointer to an alarm severity assignment profile to 
	 be used for alarms generated by this signalling route set 
	 network element part, or zeroDotZero." 
    REFERENCE
	"ITU-T Rec. Q.751.1 (1997), ANSI T1.116.1 (2000), 
	     alarmSeverityAssignmentProfilePointer attribute."
    DEFVAL { { zeroDotZero } }
    ::= { mtpRsEntry 6 }

mtpRsCongestedState OBJECT-TYPE
    SYNTAX MtpCongestedState
    MAX-ACCESS read-only
    STATUS current
    DESCRIPTION
	"This attribute is used to reflect route set congestion, when 
	 multiple congestion levels are not used.  Its value is 
	 congested(1) in case of route set congestion and 
	 notCongested(0) otherwise.  Its value is changed by the managed 
	 system.  Transitions to and from the congested state are 
	 indicated with a qualityOfServiceAlarm.
	 
	 Note that a route set can be administratively locked, and still 
	 congested."
    REFERENCE
	"ITU-T Rec. Q.751.1 (1997), ANSI T1.116.1 (2000), congestedState 
	     attribute."
    ::= { mtpRsEntry 7 }

mtpRsCongestionLevel OBJECT-TYPE
    SYNTAX MtpCongestionLevel
    MAX-ACCESS read-only
    STATUS current
    DESCRIPTION
	"This attribute is used to reflect route set congestion, when 
	 multiple congestion levels are used.  Its value in case of no 
	 congestion is none(0), and has the value congestionLevel1(1), 
	 congestionLevel2(2) or congestionLevel(3) when congested.  Its 
	 value is changed by the managed system.  Transitions to an from 
	 a congestion level are indicated by a qualityOfServiceAlarm.
	 
	 Note that a route set can be administratively locked, and still 
	 congested."
    REFERENCE
	"ITU-T Rec. Q.751.1 (1997), ANSI T1.116.1 (2000), 
	     congestionLevel attribute."
    ::= { mtpRsEntry 8 }

mtpRsLoadsharingInformation OBJECT-TYPE
    SYNTAX OCTET STRING
    MAX-ACCESS read-create
    STATUS current
    DESCRIPTION
	"This attribute contains specific information for target 
	 specific loadsharing via the current routes working on a 
	 routeset basis via the current routes.  This information can be 
	 used by e.g. the referenced mtpLoadsharingObjectFor-RouteSet to 
	 execute the target specific loadsharing."
    REFERENCE
	"ITU-T Rec. Q.751.1 (1997), ANSI T1.116.1 (2000), 
	     loadsharingInformationRouteSetNePart attribute."
    ::= { mtpRsEntry 9 }

mtpRsLoadsharingObject OBJECT-TYPE
    SYNTAX RowPointer
    MAX-ACCESS read-create
    STATUS current
    DESCRIPTION
	"This attribute is used to reference implementation dependent 
	 loadsharing object class instances needed to model 
	 implementation dependent mechanisms for loadsharing over 
	 linksets working on a routeset basis."
    REFERENCE
	"ITU-T Rec. Q.751.1 (1997), ANSI T1.116.1 (2000), 
	     mtpLoadsharingObjectForRouteSetNePartPointer attribute."
    DEFVAL { { zeroDotZero }}
    ::= { mtpRsEntry 10 }

mtpRsRemoteExchangeLabel OBJECT-TYPE
    SYNTAX CommonLanguageName
    MAX-ACCESS read-create
    STATUS current
    DESCRIPTION
	"This attribute specifies the remote exchange which contains the 
	 mtpSignPoint with the point code equal to the 
	 signRouteSetNePartId."
    REFERENCE
	"ITU-T Rec. Q.751.1 (1997), ANSI T1.116.1 (2000), 
	     remoteExchangeLabel attribute."
    ::= { mtpRsEntry 11 }

mtpRsName OBJECT-TYPE
    SYNTAX SimpleNameType
    MAX-ACCESS read-create
    STATUS current
    DESCRIPTION
	"Provides an optional administrative name for this signalling 
	 route set.  It is typical to name signalling route sets using 
	 the common language name of the managed switching element at 
	 which the route terminates (e.g. EDTNAB01DS1).
	 
	 Identifies a signRouteSetNePart instance within the managed 
	 object class; its value is unique within the signRouteSetNePart 
	 object class.  In this attribute implementation or 
	 administration dependent information - like used for naming 
	 schemes - can be stored.  If at creation time the value of this 
	 attribute given for the instance to be created already exists 
	 in another signRouteNePart instance, then the creation is 
	 rejected and not carried out."
    REFERENCE
	"ITU-T Rec. Q.751.1 (1997), ANSI T1.116.1 (2000), 
	 signRouteSetNePartName attribute."
    ::= { mtpRsEntry 12 }

mtpRsProfile OBJECT-TYPE
    SYNTAX SimpleNameType
    MAX-ACCESS read-create
    STATUS current
    DESCRIPTION
	"Provides the index into the signalling route set profile table 
	 corresponding to the signalling route set profile used by this 
	 signalling route set.  The profile consists of timer values for 
	 timers concerned with MTP Level 3 route set proceudres."
    ::= { mtpRsEntry 13 }

mtpRsAlarmStatus OBJECT-TYPE
    SYNTAX AlarmStatus
    MAX-ACCESS read-create
    STATUS current
    DESCRIPTION
	"Provides the alarm status of the MTP signalling route set 
	 following the AlarmStatus textual convention and ITU-T Rec. 
	 X.721 (1992) | ISO/IEC 10165-2 : 1992.
	 
	  - underRepair(0),
	  - critical(1),
	  - major(2),
	  - minor(3),
	  - alarmOutstanding(4),
	"
    REFERENCE
	"ITU-T Rec. Q.751.1 (1997), ANSI T1.116.1 (2000) : alarmStatus 
	     attribute.
	 ITU-T Rec. X.721 (1992) | ISO/IEC 10165-2 : 1992, 
	     Attribute-ASN1Module.AlarmStatus.
	 ITU-T Rec. X.731 (1992) | ISO/IEC 10164-2 : 1993, 
	     Section 8.1.2.1."
    ::= { mtpRsEntry 14 }

mtpRsRowStatus OBJECT-TYPE
    SYNTAX RowStatus
    MAX-ACCESS read-create
    STATUS current
    DESCRIPTION
	"Provides a mechanism whereby management stations may create and 
	 delete entries in this table.  This object is used by a 
	 management station SET operation to create a new entry in this 
	 table.
	 
	 If the name package is supported: a create request with a value 
	 for the name attribute that is already used by another instance 
	 of the same object class will be rejected.  A delete request is 
	 rejected, if the administrativeState of the signRouteSetNePart 
	 does not equal locked."
    REFERENCE
	"STD 58, SNMPv2-TC RowStatus.
	 ITU-T Rec. Q.751.1 (1997) : mtpSignPoint-signRouteSetNePart 
	     NAME BINDING."
    ::= { mtpRsEntry 15 }

-- ====================================================================

mtpRsStatsTable OBJECT-TYPE
    SYNTAX SEQUENCE OF MtpRsStatsEntry
    MAX-ACCESS not-accessible
    STATUS current
    DESCRIPTION
	"This table provides RS statistics."
    REFERENCE
	"ITU-T Rec. Q.752, ANSI T1.116.2"
    ::= { mtpRs 3 }

mtpRsStatsEntry OBJECT-TYPE
    SYNTAX MtpRsStatsEntry
    MAX-ACCESS not-accessible
    STATUS current
    DESCRIPTION
	"This provides the table entry for RS statistics."
    REFERENCE
	"ITU-T Rec. Q.752, ANSI T1.116.2"
    AUGMENTS    { mtpRsEntry }
    ::= { mtpRsStatsTable 1 }

MtpRsStatsEntry ::= SEQUENCE {
    mtpRsStatsStatus				RowStatus
}

mtpRsStatsStatus OBJECT-TYPE
    SYNTAX RowStatus
    MAX-ACCESS read-create
    STATUS current
    DESCRIPTION
	""
    ::= { mtpRsStatsEntry 1 }


-- ====================================================================

mtpRsCurrentTable OBJECT-TYPE
    SYNTAX SEQUENCE OF MtpRsCurrentEntry
    MAX-ACCESS not-accessible
    STATUS current
    DESCRIPTION
	""
    ::= { mtpRs 4 }

mtpRsCurrentEntry OBJECT-TYPE
    SYNTAX MtpRsCurrentEntry
    MAX-ACCESS not-accessible
    STATUS current
    DESCRIPTION
	""
    INDEX {
	mtpRsId
    }
    ::= { mtpRsCurrentTable 1 }

MtpRsCurrentEntry ::= SEQUENCE {
    mtpRsCurrentValidIntervals			HCPerfValidIntervals,
    mtpRsCurrentTimeDiscontinuity		TimeStamp,
    mtpRsCurrentReceivedOctetsOPC		PerfCurrentCount, -- Q.752, 6.1
    mtpRsCurrentTransmittedOctetsDPC		PerfCurrentCount, -- Q.752, 6.2
    mtpRsCurrentReceivedMSUsOpc			PerfCurrentCount,
    mtpRsCurrentTransmittedMSUsDpc		PerfCurrentCount,
    mtpRsCurrentRouteSetUnavailable		PerfCurrentCount, -- Q.752, 4.9
    mtpRsCurrentRouteSetUnavailableDuration	PerfCurrentCount, -- Q.752, 4.10
}

mtpRsCurrentValidIntervals OBJECT-TYPE
    SYNTAX HCPerfValidIntervals
    MAX-ACCESS read-create
    STATUS current
    DESCRIPTION
	""
    ::= { mtpRsCurrentEntry 1 }

mtpRsCurrentTimeDiscontinuity OBJECT-TYPE
    SYNTAX TimeStamp
    MAX-ACCESS read-create
    STATUS current
    DESCRIPTION
	""
    ::= { mtpRsCurrentEntry 2 }

mtpRsCurrentReceivedOctetsOPC OBJECT-TYPE
    SYNTAX PerfCurrentCount
    UNITS "octets"
    MAX-ACCESS read-create
    STATUS current
    DESCRIPTION
	""
    REFERENCE
	"ITU-T Rec. Q.751.1 (10/95) : receivedOctetsOPC.
	 ITU-T Rec. Q.752 (1997) : Table 6/Q.752, 6.1."
    ::= { mtpRsCurrentEntry 3 }

mtpRsCurrentTransmittedOctetsDPC OBJECT-TYPE
    SYNTAX PerfCurrentCount
    UNITS "octets"
    MAX-ACCESS read-create
    STATUS current
    DESCRIPTION
	""
    REFERENCE
	"ITU-T Rec. Q.751.1 (10/95) : transmittedOctetsDPC.
	 ITU-T Rec. Q.752 (1997) : Table 6/Q.752, 6.2."
    ::= { mtpRsCurrentEntry 4 }

mtpRsCurrentReceivedMSUsOpc OBJECT-TYPE
    SYNTAX PerfCurrentCount
    UNITS "MSUs"
    MAX-ACCESS read-create
    STATUS current
    DESCRIPTION
	""
    ::= { mtpRsCurrentEntry 5 }

mtpRsCurrentTransmittedMSUsDpc OBJECT-TYPE
    SYNTAX PerfCurrentCount
    UNITS "MSUs"
    MAX-ACCESS read-create
    STATUS current
    DESCRIPTION
	""
    ::= { mtpRsCurrentEntry 6 }

mtpRsCurrentRouteSetUnavailable OBJECT-TYPE
    SYNTAX PerfCurrentCount
    MAX-ACCESS read-create
    STATUS current
    DESCRIPTION
	""
    REFERENCE
	"ITU-T Rec. Q.751.1, (10/95) : routeSetUnavailable.
	 ITU-T Rec. Q.752, (1997) : Table 3/Q.752 4.9"
    ::= { mtpRsCurrentEntry 7 }

mtpRsCurrentRouteSetUnavailableDuration OBJECT-TYPE
    SYNTAX PerfCurrentCount
    UNITS "seconds"
    MAX-ACCESS read-create
    STATUS current
    DESCRIPTION
	""
    REFERENCE
	"ITU-T Rec. Q.751.1, (10/95) : routeSetUnavailableDuration.
	 ITU-T Rec. Q.752, (1997) : Table 3/Q.752 4.10"
    ::= { mtpRsCurrentEntry 8 }


-- ====================================================================

mtpRsInt5minTable OBJECT-TYPE
    SYNTAX SEQUENCE OF MtpRsInt5minEntry
    MAX-ACCESS not-accessible
    STATUS current
    DESCRIPTION
	""
    ::= { mtpRs 5 }

mtpRsInt5minEntry OBJECT-TYPE
    SYNTAX MtpRsInt5minEntry
    MAX-ACCESS not-accessible
    STATUS current
    DESCRIPTION
	""
    INDEX {
	mtpRsId,
	mtpRsInt5minInterval
    }
    ::= { mtpRsInt5minTable 1 }


MtpRsInt5minEntry ::= SEQUENCE {
    mtpRsInt5minInterval			Unsigned32,
    mtpRsInt5minTimeStamp			TimeStamp,
    mtpRsInt5minReceivedOctetsOPC		PerfIntervalCount, -- Q.752, 6.1
    mtpRsInt5minTransmittedOctetsDPC		PerfIntervalCount, -- Q.752, 6.2
    mtpRsInt5minReceivedMSUsOpc			PerfIntervalCount,
    mtpRsInt5minTransmittedMSUsDpc		PerfIntervalCount,
    mtpRsInt5minRouteSetUnavailable		PerfIntervalCount, -- Q.752, 4.9
    mtpRsInt5minRouteSetUnavailableDuration	PerfIntervalCount  -- Q.752, 4.10
}

mtpRsInt5minInterval OBJECT-TYPE
    SYNTAX Unsigned32
    MAX-ACCESS not-accessible
    STATUS current
    DESCRIPTION
	""
    ::= { mtpRsInt5minEntry 1 }

mtpRsInt5minTimeStamp OBJECT-TYPE
    SYNTAX TimeStamp
    MAX-ACCESS read-only
    STATUS current
    DESCRIPTION
	""
    ::= { mtpRsInt5minEntry 2 }

mtpRsInt5minReceivedOctetsOPC OBJECT-TYPE
    SYNTAX PerfIntervalCount
    UNITS "octets"
    MAX-ACCESS read-only
    STATUS current
    DESCRIPTION
	""
    REFERENCE
	"ITU-T Rec. Q.751.1 (10/95) : receivedOctetsOPC.
	 ITU-T Rec. Q.752 (1997) : Table 6/Q.752, 6.1."
    ::= { mtpRsInt5minEntry 3 }

mtpRsInt5minTransmittedOctetsDPC OBJECT-TYPE
    SYNTAX PerfIntervalCount
    UNITS "octets"
    MAX-ACCESS read-only
    STATUS current
    DESCRIPTION
	""
    REFERENCE
	"ITU-T Rec. Q.751.1 (10/95) : transmittedOctetsDPC.
	 ITU-T Rec. Q.752 (1997) : Table 6/Q.752, 6.2."
    ::= { mtpRsInt5minEntry 4 }

mtpRsInt5minReceivedMSUsOpc OBJECT-TYPE
    SYNTAX PerfIntervalCount
    UNITS "MSUs"
    MAX-ACCESS read-only
    STATUS current
    DESCRIPTION
	""
    ::= { mtpRsInt5minEntry 5 }

mtpRsInt5minTransmittedMSUsDpc OBJECT-TYPE
    SYNTAX PerfIntervalCount
    UNITS "MSUs"
    MAX-ACCESS read-only
    STATUS current
    DESCRIPTION
	""
    ::= { mtpRsInt5minEntry 6 }

mtpRsInt5minRouteSetUnavailable OBJECT-TYPE
    SYNTAX PerfIntervalCount
    MAX-ACCESS read-only
    STATUS current
    DESCRIPTION
	""
    REFERENCE
	"ITU-T Rec. Q.751.1, (10/95) : routeSetUnavailable.
	 ITU-T Rec. Q.752, (1997) : Table 3/Q.752 4.9"
    ::= { mtpRsInt5minEntry 7 }

mtpRsInt5minRouteSetUnavailableDuration OBJECT-TYPE
    SYNTAX PerfIntervalCount
    UNITS "seconds"
    MAX-ACCESS read-only
    STATUS current
    DESCRIPTION
	""
    REFERENCE
	"ITU-T Rec. Q.751.1, (10/95) : routeSetUnavailableDuration.
	 ITU-T Rec. Q.752, (1997) : Table 3/Q.752 4.10"
    ::= { mtpRsInt5minEntry 8 }

-- ====================================================================

mtpRsInt15minTable OBJECT-TYPE
    SYNTAX SEQUENCE OF MtpRsInt15minEntry
    MAX-ACCESS not-accessible
    STATUS current
    DESCRIPTION
	""
    ::= { mtpRs 6 }

mtpRsInt15minEntry OBJECT-TYPE
    SYNTAX MtpRsInt15minEntry
    MAX-ACCESS not-accessible
    STATUS current
    DESCRIPTION
	""
    INDEX {
	mtpRsId,
	mtpRsInt15minInterval
    }
    ::= { mtpRsInt15minTable 1 }


MtpRsInt15minEntry ::= SEQUENCE {
    mtpRsInt15minInterval			Unsigned32,
    mtpRsInt15minTimeStamp			TimeStamp,
    mtpRsInt15minReceivedOctetsOPC		PerfIntervalCount, -- Q.752, 6.1
    mtpRsInt15minTransmittedOctetsDPC		PerfIntervalCount, -- Q.752, 6.2
    mtpRsInt15minReceivedMSUsOpc		PerfIntervalCount,
    mtpRsInt15minTransmittedMSUsDpc		PerfIntervalCount,
    mtpRsInt15minRouteSetUnavailable		PerfIntervalCount, -- Q.752, 4.9
    mtpRsInt15minRouteSetUnavailableDuration	PerfIntervalCount  -- Q.752, 4.10
}

mtpRsInt15minInterval OBJECT-TYPE
    SYNTAX Unsigned32
    MAX-ACCESS not-accessible
    STATUS current
    DESCRIPTION
	""
    ::= { mtpRsInt15minEntry 1 }

mtpRsInt15minTimeStamp OBJECT-TYPE
    SYNTAX TimeStamp
    MAX-ACCESS read-only
    STATUS current
    DESCRIPTION
	""
    ::= { mtpRsInt15minEntry 2 }

mtpRsInt15minReceivedOctetsOPC OBJECT-TYPE
    SYNTAX PerfIntervalCount
    UNITS "octets"
    MAX-ACCESS read-only
    STATUS current
    DESCRIPTION
	""
    REFERENCE
	"ITU-T Rec. Q.751.1 (10/95) : receivedOctetsOPC.
	 ITU-T Rec. Q.752 (1997) : Table 6/Q.752, 6.1."
    ::= { mtpRsInt15minEntry 3 }

mtpRsInt15minTransmittedOctetsDPC OBJECT-TYPE
    SYNTAX PerfIntervalCount
    UNITS "octets"
    MAX-ACCESS read-only
    STATUS current
    DESCRIPTION
	""
    REFERENCE
	"ITU-T Rec. Q.751.1 (10/95) : transmittedOctetsDPC.
	 ITU-T Rec. Q.752 (1997) : Table 6/Q.752, 6.2."
    ::= { mtpRsInt15minEntry 4 }

mtpRsInt15minReceivedMSUsOpc OBJECT-TYPE
    SYNTAX PerfIntervalCount
    UNITS "MSUs"
    MAX-ACCESS read-only
    STATUS current
    DESCRIPTION
	""
    ::= { mtpRsInt15minEntry 5 }

mtpRsInt15minTransmittedMSUsDpc OBJECT-TYPE
    SYNTAX PerfIntervalCount
    UNITS "MSUs"
    MAX-ACCESS read-only
    STATUS current
    DESCRIPTION
	""
    ::= { mtpRsInt15minEntry 6 }

mtpRsInt15minRouteSetUnavailable OBJECT-TYPE
    SYNTAX PerfIntervalCount
    MAX-ACCESS read-only
    STATUS current
    DESCRIPTION
	""
    REFERENCE
	"ITU-T Rec. Q.751.1, (10/95) : routeSetUnavailable.
	 ITU-T Rec. Q.752, (1997) : Table 3/Q.752 4.9"
    ::= { mtpRsInt15minEntry 7 }

mtpRsInt15minRouteSetUnavailableDuration OBJECT-TYPE
    SYNTAX PerfIntervalCount
    UNITS "seconds"
    MAX-ACCESS read-only
    STATUS current
    DESCRIPTION
	""
    REFERENCE
	"ITU-T Rec. Q.751.1, (10/95) : routeSetUnavailableDuration.
	 ITU-T Rec. Q.752, (1997) : Table 3/Q.752 4.10"
    ::= { mtpRsInt15minEntry 8 }

-- ====================================================================

mtpRsSiTable OBJECT-TYPE
    SYNTAX SEQUENCE OF MtpRsSiEntry
    MAX-ACCESS not-accessible
    STATUS current
    DESCRIPTION
	""
    ::= { mtpRs 7 }

mtpRsSiEntry OBJECT-TYPE
    SYNTAX MtpRsSiEntry
    MAX-ACCESS not-accessible
    STATUS current
    DESCRIPTION
	""
    INDEX {
	mtpRsSiCode
    }
    ::= { mtpRsSiTable 1 }


MtpRsSiEntry ::= SEQUENCE {
    mtpRsSiCode					Unsigned32,
    mtpRsSiValidIntervals			HCPerfValidIntervals,
    mtpRsSiTimeDiscontinuity			TimeStamp,
    mtpRsSiReceivedOctetsOpcSio			PerfCurrentCount, -- Q.752, 6.4
    mtpRsSiTransmittedOctetsDpcSio		PerfCurrentCount, -- Q.752, 6.5
    mtpRsSiReceivedMSUsOpcSio			PerfCurrentCount,
    mtpRsSiTransmittedMSUsDpcSio		PerfCurrentCount,
    mtpRsSiStatus				RowStatus
}

mtpRsSiCode OBJECT-TYPE
    SYNTAX Unsigned32
    MAX-ACCESS not-accessible
    STATUS current
    DESCRIPTION
	""
    ::= { mtpRsSiEntry 1 }

mtpRsSiValidIntervals OBJECT-TYPE
    SYNTAX HCPerfValidIntervals
    MAX-ACCESS read-create
    STATUS current
    DESCRIPTION
	""
    ::= { mtpRsSiEntry 2 }

mtpRsSiTimeDiscontinuity OBJECT-TYPE
    SYNTAX TimeStamp
    MAX-ACCESS read-create
    STATUS current
    DESCRIPTION
	""
    ::= { mtpRsSiEntry 3 }

mtpRsSiReceivedOctetsOpcSio OBJECT-TYPE
    SYNTAX PerfCurrentCount
    UNITS "octets"
    MAX-ACCESS read-create
    STATUS current
    DESCRIPTION
	""
    REFERENCE
	"ITU-T Rec. Q.751.1, (10/95) : receivedOctetsOpcSio.
	 ITU-T Rec. Q.752, (1997) : Table 6/Q.752 6.4"
    ::= { mtpRsSiEntry 4 }

mtpRsSiTransmittedOctetsDpcSio OBJECT-TYPE
    SYNTAX PerfCurrentCount
    UNITS "octets"
    MAX-ACCESS read-create
    STATUS current
    DESCRIPTION
	""
    REFERENCE
	"ITU-T Rec. Q.751.1, (10/95) : transmittedOctetsDpcSio.
	 ITU-T Rec. Q.752, (1997) : Table 6/Q.752 6.5"
    ::= { mtpRsSiEntry 5 }

mtpRsSiReceivedMSUsOpcSio OBJECT-TYPE
    SYNTAX PerfCurrentCount
    UNITS "MSUs"
    MAX-ACCESS read-create
    STATUS current
    DESCRIPTION
	""
    ::= { mtpRsSiEntry 6 }

mtpRsSiTransmittedMSUsDpcSio OBJECT-TYPE
    SYNTAX PerfCurrentCount
    UNITS "MSUs"
    MAX-ACCESS read-create
    STATUS current
    DESCRIPTION
	""
    ::= { mtpRsSiEntry 7 }

mtpRsSiStatus OBJECT-TYPE
    SYNTAX RowStatus
    MAX-ACCESS read-create
    STATUS current
    DESCRIPTION
	""
    REFERENCE
	"STD 58, SNMPv2-TC RowStatus."
    ::= { mtpRsSiEntry 8 }

-- ====================================================================

mtpRsSiInt5minTable OBJECT-TYPE
    SYNTAX SEQUENCE OF MtpRsSiInt5minEntry
    MAX-ACCESS not-accessible
    STATUS current
    DESCRIPTION
	""
    ::= { mtpRs 8 }

mtpRsSiInt5minEntry OBJECT-TYPE
    SYNTAX MtpRsSiInt5minEntry
    MAX-ACCESS not-accessible
    STATUS current
    DESCRIPTION
	""
    INDEX {
	mtpRsSiCode,
	mtpRsSiInt5minInterval
    }
    ::= { mtpRsSiInt5minTable 1 }


MtpRsSiInt5minEntry ::= SEQUENCE {
    mtpRsSiInt5minInterval			Unsigned32,
    mtpRsSiInt5minTimeStamp			TimeStamp,
    mtpRsSiInt5minReceivedOctetsOpcSio		PerfIntervalCount, -- Q.752, 6.4
    mtpRsSiInt5minTransmittedOctetsDpcSio	PerfIntervalCount, -- Q.752, 6.5
    mtpRsSiInt5minReceivedMSUsOpcSio		PerfIntervalCount,
    mtpRsSiInt5minTransmittedMSUsDpcSio		PerfIntervalCount
}

mtpRsSiInt5minInterval OBJECT-TYPE
    SYNTAX Unsigned32
    MAX-ACCESS not-accessible
    STATUS current
    DESCRIPTION
	""
    ::= { mtpRsSiInt5minEntry 1 }

mtpRsSiInt5minTimeStamp OBJECT-TYPE
    SYNTAX TimeStamp
    MAX-ACCESS read-only
    STATUS current
    DESCRIPTION
	""
    ::= { mtpRsSiInt5minEntry 2 }

mtpRsSiInt5minReceivedOctetsOpcSio OBJECT-TYPE
    SYNTAX PerfIntervalCount
    UNITS "octets"
    MAX-ACCESS read-only
    STATUS current
    DESCRIPTION
	""
    REFERENCE
	"ITU-T Rec. Q.751.1, (10/95) : receivedOctetsOpcSio.
	 ITU-T Rec. Q.752, (1997) : Table 6/Q.752 6.4"
    ::= { mtpRsSiInt5minEntry 3 }

mtpRsSiInt5minTransmittedOctetsDpcSio OBJECT-TYPE
    SYNTAX PerfIntervalCount
    UNITS "octets"
    MAX-ACCESS read-only
    STATUS current
    DESCRIPTION
	""
    REFERENCE
	"ITU-T Rec. Q.751.1, (10/95) : transmittedOctetsDpcSio.
	 ITU-T Rec. Q.752, (1997) : Table 6/Q.752 6.5"
    ::= { mtpRsSiInt5minEntry 4 }

mtpRsSiInt5minReceivedMSUsOpcSio OBJECT-TYPE
    SYNTAX PerfIntervalCount
    UNITS "MSUs"
    MAX-ACCESS read-only
    STATUS current
    DESCRIPTION
	""
    ::= { mtpRsSiInt5minEntry 5 }

mtpRsSiInt5minTransmittedMSUsDpcSio OBJECT-TYPE
    SYNTAX PerfIntervalCount
    UNITS "MSUs"
    MAX-ACCESS read-only
    STATUS current
    DESCRIPTION
	""
    ::= { mtpRsSiInt5minEntry 6 }

-- ====================================================================

mtpRsSiInt15minTable OBJECT-TYPE
    SYNTAX SEQUENCE OF MtpRsSiInt15minEntry
    MAX-ACCESS not-accessible
    STATUS current
    DESCRIPTION
	""
    ::= { mtpRs 9 }

mtpRsSiInt15minEntry OBJECT-TYPE
    SYNTAX MtpRsSiInt15minEntry
    MAX-ACCESS not-accessible
    STATUS current
    DESCRIPTION
	""
    INDEX {
	mtpRsSiCode,
	mtpRsSiInt15minInterval
    }
    ::= { mtpRsSiInt15minTable 1 }

MtpRsSiInt15minEntry ::= SEQUENCE {
    mtpRsSiInt15minInterval			Unsigned32,
    mtpRsSiInt15minTimeStamp			TimeStamp,
    mtpRsSiInt15minReceivedOctetsOpcSio		PerfIntervalCount, -- Q.752, 6.4
    mtpRsSiInt15minTransmittedOctetsDpcSio	PerfIntervalCount, -- Q.752, 6.5
    mtpRsSiInt15minReceivedMSUsOpcSio		PerfIntervalCount,
    mtpRsSiInt15minTransmittedMSUsDpcSio	PerfIntervalCount
}

mtpRsSiInt15minInterval OBJECT-TYPE
    SYNTAX Unsigned32
    MAX-ACCESS not-accessible
    STATUS current
    DESCRIPTION
	""
    ::= { mtpRsSiInt15minEntry 1 }

mtpRsSiInt15minTimeStamp OBJECT-TYPE
    SYNTAX TimeStamp
    MAX-ACCESS read-only
    STATUS current
    DESCRIPTION
	""
    ::= { mtpRsSiInt15minEntry 2 }

mtpRsSiInt15minReceivedOctetsOpcSio OBJECT-TYPE
    SYNTAX PerfIntervalCount
    UNITS "octets"
    MAX-ACCESS read-only
    STATUS current
    DESCRIPTION
	""
    REFERENCE
	"ITU-T Rec. Q.751.1, (10/95) : receivedOctetsOpcSio.
	 ITU-T Rec. Q.752, (1997) : Table 6/Q.752 6.4"
    ::= { mtpRsSiInt15minEntry 3 }

mtpRsSiInt15minTransmittedOctetsDpcSio OBJECT-TYPE
    SYNTAX PerfIntervalCount
    UNITS "octets"
    MAX-ACCESS read-only
    STATUS current
    DESCRIPTION
	""
    REFERENCE
	"ITU-T Rec. Q.751.1, (10/95) : transmittedOctetsDpcSio.
	 ITU-T Rec. Q.752, (1997) : Table 6/Q.752 6.5"
    ::= { mtpRsSiInt15minEntry 4 }

mtpRsSiInt15minReceivedMSUsOpcSio OBJECT-TYPE
    SYNTAX PerfIntervalCount
    UNITS "MSUs"
    MAX-ACCESS read-only
    STATUS current
    DESCRIPTION
	""
    ::= { mtpRsSiInt15minEntry 5 }

mtpRsSiInt15minTransmittedMSUsDpcSio OBJECT-TYPE
    SYNTAX PerfIntervalCount
    UNITS "MSUs"
    MAX-ACCESS read-only
    STATUS current
    DESCRIPTION
	""
    ::= { mtpRsSiInt15minEntry 6 }


-- ====================================================================


mtpRtProfileTable OBJECT-TYPE
    SYNTAX SEQUENCE OF MtpRtProfileEntry
    MAX-ACCESS not-accessible
    STATUS current
    DESCRIPTION
	"Provides a table of MTP Level 3 signalling route protocol 
	 profiles.  Each entry in the table provide a single MTP Level 3 
	 signalling route protocol profile for use when creating 
	 signalling routes or providing defaults."
    ::= { mtpRt 1 }

mtpRtProfileEntry OBJECT-TYPE
    SYNTAX MtpRtProfileEntry
    MAX-ACCESS not-accessible
    STATUS current
    DESCRIPTION
	"Each entry in the table provide a single MTP Level 3 signalling 
	 route protocol profile for use when creating signalling routes 
	 or providing defaults."
    INDEX {
	mtpRtProfileId
    }
    ::= { mtpRtProfileTable 1 }

MtpRtProfileEntry ::= SEQUENCE {
    mtpRtProfileId				SimpleNameType,
    mtpRtProfileTimerT6				TimeInterval,
    mtpRtProfileTimerT10			TimeInterval,
    mtpRtProfileRowStatus			RowStatus
}

mtpRtProfileId OBJECT-TYPE
    SYNTAX SimpleNameType
    MAX-ACCESS not-accessible
    STATUS current
    DESCRIPTION
	"Provides an index into the signalling route profile table.  
	 Rows in this table can be referred to using this index or using 
	 the RowPointer pointer.  The index value zero (0) has special 
	 semantics: the zero index contains default default values."
    ::= { mtpRtProfileEntry 1 }

mtpRtProfileTimerT6 OBJECT-TYPE
    SYNTAX TimeInterval (50..120)
    UNITS "centiseconds"
    MAX-ACCESS read-create
    STATUS current
    DESCRIPTION
	"This attribute defines the initial timer value of timer T6 
	 Delay to avoid message mis-sequencing on controlled rerouting 
	 defined in Recommendation Q.704.  The value range is from 500 
	 to 1200 ms. For routes with long propagation delays a minimum 
	 value of 800 ms is used.
	 
	 Controlled rerouting is performed with a special controlled 
	 rerouting buffer which is attached to both the route from which 
	 traffic is being rerouted and the route to which traffic is 
	 being rerouted.  If the route set has become unavailable while 
	 the timer was running, this will result in purging the 
	 controlled rerouting buffer.  If the unavailability was 
	 transient and the route set is now available again, these 
	 messages will not be lost.  This is not mentioned in the MTP 
	 specifications.
	 
	 Note that in ITU-T Rec. Q.751.1 (1997) and ANSI T1.116.1 (2000) 
	 this timer is part of the lsTimersProfile MOC."
    REFERENCE
	"ITU-T Rec. Q.751.1 (1997), ANSI T1.116.1 (2000), q704-t6 
	 attribute."
    DEFVAL { 80 }
    ::= { mtpRtProfileEntry 2 }

mtpRtProfileTimerT10 OBJECT-TYPE
    SYNTAX TimeInterval (3000..6000)
    UNITS "centiseconds"
    MAX-ACCESS read-create
    STATUS current
    DESCRIPTION
	"This attribute defines the initial timer value of timer T10 
	 Waiting to repeat signalling route set test message defined in 
	 Recommendation Q.704. The value range is from 30 to 60 seconds. 
	 The maximum value may be extended at the discretion of the 
	 management function in certain situations, e.g. many signalling 
	 points being unavailable or signalling points of known long 
	 term unavailability.
	 
	 This timer is started after receiving a TFP, TCP, TFR or TCR 
	 for the route.  It runs and sends a RST message on the route 
	 every T10 seconds until stopped.  This timer is stopped after 
	 receiving a TFA or TCA message for the route.
	 
	 13.5.2  A signalling route set test message is sent from a 
	    signalling point after a transfer prohibited or transfer 
	    restricted message is received from an adjacent signalling 
	    transfer point (see 13.2.4 and 
	 13.4.4).  In this case, a signalling route set test message is 
	    sent to that signalling transfer point referring to the 
	    destination declared inaccessible or restricted by the 
	    transfer prohibited or transfer restricted message, every 
	    T10 period (see clause 16) until a transfer-allowed message, 
	    indicating that the destination has become accessible, is 
	    received.
	 
	 Start:  receive TFP, TCP, TFR, TCR for first time Stop:   
	 receive TFA, TCA Expiry: send RST, RCP, RSR, RCR and start T10
	 
	 Note that in ITU-T Rec. Q.751.1 (1997) and ANSI T1.116.1 (2000) 
	 this timer is part of the lsTimersProfile MOC."
    REFERENCE
	"ITU-T Rec. Q.751.1 (1997), ANSI T1.116.1 (2000), q704-t10 
	 attribute."
    DEFVAL { 4500 }
    ::= { mtpRtProfileEntry 3 }

mtpRtProfileRowStatus OBJECT-TYPE
    SYNTAX RowStatus
    MAX-ACCESS read-create
    STATUS current
    DESCRIPTION
	"Provides a mechanism whereby management stations may create and 
	 delete entries in this table.  All entries created by 
	 management stations survive and agent reboot."
    REFERENCE
	"STD 58, SNMPv2-TC RowStatus."
    ::= { mtpRtProfileEntry 4 }


-- ====================================================================

mtpRtTable OBJECT-TYPE
    SYNTAX SEQUENCE OF MtpRtEntry
    MAX-ACCESS not-accessible
    STATUS current
    DESCRIPTION
	"A signalling route (A,C,B)i is defined as an ordered sequence 
	 of the near end signalling point A (i.e. the network element), 
	 an adjacent SP C and the destination SP B.  The adjacent SP C 
	 may be identical with the destination B, or it may or may not 
	 be directly interconnected to the destination SP.  The adjacent 
	 SP C must be directly connected to the near end SP by at least 
	 one linkset which is intended to convey MSUs sent from A to B 
	 (hence the use of the term 'adjacent').
	 
	 Two signalling routes (A,C,B)i and (A,C,B)j are distinct if the 
	 adjacent SP is different.
	 
	 The signRouteNePart Managed Object class defines the management 
	 capabilities of the resources which define a specific route 
	 segment (Link Set to be traversed) and its priority within the 
	 routeset as seen from the own SP.  A particular signRouteNePart 
	 is related to one or more Signalling Routes on the network 
	 level.
	 
	 The priority in which the network Signalling Routes are used, 
	 is defined by means of assigning priorities to all involved 
	 route segments.  If from a particular SP two or more route 
	 segments are used with the same priority, loadsharing between 
	 Signalling Routes may occur.
	 
	 A Combined Link Set is a set of Link Sets used with the same 
	 priority by message routing.
	 
	 The signLinkSetTp used for routing is allocated at creation 
	 time and cannot be changed during the existence of a particular 
	 signRouteNePart.
	 
	 The administrativeState attribute describes whether it is 
	 administratively permitted to route messages towards the 
	 respective destination point via the referenced signLinkSetTp.
	 
	 The operationalState attribute is 'enabled' if both the 
	 referenced signLinkSetTp is in the operational state 'enabled' 
	 and no TFP message concerning the respective destination has 
	 been received from the adjPC of the respective signLinkSetTp.
	 
	 The optional usageState attribute is used to cover restriction 
	 of a route.  Its value is set to 'busy', if the route is 
	 restricted ('transfer restricted' is a national option).
	 
	 The availabilityStatus attribute gives additional information 
	 about the availability of the signRouteNePart instance.  It is 
	 furthermore needed to map some of the MTP functional states 
	 (prohibited: availabilityStatus = {dependency}, restricted: 
	 availabilityStatus={degraded}) and is used for the case that 
	 the route is locked not by the OS, but e.g. by a local 
	 administrator (administrativeState=unlocked and 
	 availabilityStatus={off line})."
    REFERENCE
	"ITU-T Rec. Q.751.1 (1997), ANSI T1.116.1 (2000), 
	 signRouteNePart MOC."
    ::= { mtpRt 2 }

mtpRtEntry OBJECT-TYPE
    SYNTAX MtpRtEntry
    MAX-ACCESS not-accessible
    STATUS current
    DESCRIPTION
	"Each signalling route network element part belongs to a 
	 signalling route set network element part which belongs to a 
	 signalling point.  The indices represent this relationship."
    REFERENCE
	"ITU-T Rec. Q.751.1 (1997), ANSI T1.116.1 (2000), 
	 signRouteNePart MO."
    INDEX {
	mtpSpId,
	mtpRsId,
	mtpRtId
    }
    ::= { mtpRtTable 1 }

MtpRtEntry ::= SEQUENCE {
    mtpRtId					Unsigned32,
    mtpRtLsPointer				SimpleNameType,
    mtpRtAdministrativeState			AdministrativeState,
    mtpRtOperationalState			OperationalState,
    mtpRtAvailabilityStatus			AvailabilityStatus,
    mtpRtInClsLoadsharingAlgorithm		Unsigned32,
    mtpRtFixedPriority				Unsigned32,
    mtpRtFlexiblePriority			Unsigned32,
    mtpRtPriorityMode				INTEGER,
    mtpRtLoadsharingInformation			OCTET STRING,
    mtpRtLoadsharingObject			RowPointer,
    mtpRtName					CommonLanguageName,
    mtpRtSlsList				SlsList,
    mtpRtUsageState				UsageState,
    mtpRtRlSlot					Unsigned32,
    mtpRtProfile				SimpleNameType,
    mtpRtRowStatus				RowStatus
}

mtpRtId OBJECT-TYPE
    SYNTAX Unsigned32
    MAX-ACCESS not-accessible
    STATUS current
    DESCRIPTION
	"Provides a non-zero index into the signalling route table.  
	 This is the naming attribute of signRouteNePart.  It identifies 
	 a signRouteNePart instance within the signRouteSetNePart."
    REFERENCE
	"ITU-T Rec. Q.751.1 (1997), ANSI T1.116.1 (2000), 
	     signRouteNePartId attribute."
    ::= { mtpRtEntry 1 }

mtpRtLsPointer OBJECT-TYPE
    SYNTAX SimpleNameType
    MAX-ACCESS read-create
    STATUS current
    DESCRIPTION
	"References the signLinkSetTp which is intended to be used as 
	 first segment of the succession of linksets, which form the 
	 signalling route on the network level.
	 
	 If during creation of a signRouteNePart instance the value of 
	 this attribute is referencing a signLinkSetTp instance, which 
	 is not created or is already referenced by a signRouteNePart of 
	 the same signRouteSetNePart, then the creation of the 
	 signRouteNePart is rejected and not carried out.  It is not 
	 allowed to reference a signLinksetTp, which is not contained in 
	 the same mtpSignPoint as the signRouteSetNePart where the 
	 signRouteNePart is contained in."
    REFERENCE
	"ITU-T Rec. Q.751.1 (1997), ANSI T1.116.1 (2000), 
	 signLinkSetTpPointer attribute."
    ::= { mtpRtEntry 2 }

mtpRtAdministrativeState OBJECT-TYPE
    SYNTAX AdministrativeState
    MAX-ACCESS read-create
    STATUS current
    DESCRIPTION
	"Provides the administrative state of the signalling route 
	 network element part following the AdministrativeState textual 
	 convention and ITU-T Rec. X.721 | ISO/IEC 10165-2.
	 
	  - locked(0), the signalling route is administratively 
	    prohibited from carrying traffic either by the NMS or EMS; 
	    if the signalling route was carrying traffic when set to 
	    this value, traffic will be force rerouted on other 
	    available routes;  the operatoinal state is 'disabled', the 
	    usage state is 'idle', and the availability status is 
	    'offLine';
	 
	  - unlocked(1), the signalling route is administratively 
	    permitted to carry traffic; if the signalling route is in 
	    the highest priority route list controlled rerouting 
	    procedures will move traffic to this signalling route;
	 
	  - shuttingDown(2), the signalling route is shutting down; 
	    controlled rerouting procedures are invoked to other 
	    available routes and the state will become locked(0) once 
	    the controlled rerouting procedure (if necessary) has 
	    completed.
	 
	 The administrative state describes whether it is 
	 administratively permittted to route messages towards the 
	 respective destination point via the referenced signalling link 
	 set termination point."
    REFERENCE
	"ITU-T Rec. X.721 | ISO/IEC 10165-2 administrativeState 
	     attribute.
	 ITU-T Rec. Q.751.1 (1997), ANSI T1.116.1 (2000), 
	     administrativeState attribute."
    DEFVAL { 0 } -- locked
    ::= { mtpRtEntry 3 }

mtpRtOperationalState OBJECT-TYPE
    SYNTAX OperationalState
    MAX-ACCESS read-only
    STATUS current
    DESCRIPTION
	"Provides the operational state of the signalling route network 
	 element part following the OperationalState textual convention 
	 of the OPENSS7-SMI-MIB module and according to ITU-T Rec. 
	 X.721 | ISO/IEC 10165-2.
	 
	  - disabled(0), the signalling route is operationally unable to 
	    carry traffic; the route may be prohibited or there may be 
	    no signalling links in the associated signalling link set 
	    that can carry traffic; the signalling route is unavailable 
	    due to management locking, or due to the unavailablity of 
	    the allocated link set, or the signalling route is 
	    prohibited;
	 
	  - enabled(1), the signalling route is operationally able to 
	    carry traffic: the signalling route is available but may 
	    also be restricted.
	 
	 The operational state is enabled(1) if both the referenced 
	 signalling link set termination point is in operational state 
	 enabled(1) and no TFP message concerning the respective 
	 destination have been received from the adjacent point code of 
	 the respective signalling link set termination point."
    REFERENCE
	"ITU-T Rec. X.721 (1992) | ISO/IEC 10165-2 : 1992, 
	     Attribute-ASN1Module.OperationalState.
	 ITU-T Rec. X.731 (1992) | ISO/IEC 10164-2 : 1993, 
	     Section 8.1.1.1.
	 ITU-T Rec. Q.751.1 (1997), ANSI T1.116.1 (2000), 
	     operationalState attribute."
    DEFVAL { 0 } -- disabled
    ::= { mtpRtEntry 4 }

mtpRtAvailabilityStatus OBJECT-TYPE
    SYNTAX AvailabilityStatus
    MAX-ACCESS read-only
    STATUS current
    DESCRIPTION
	"Provides the availability status of the signalling route 
	 network element part following the AvailabilityStatus textual 
	 convention of the OPENSS7-SMI-MIB module and according to ITU-T 
	 Rec. X.721 | ISO/IEC 10165-2.
	 
	  - inTest(0), not used;
	 
	  - failed(1), the adjacent signalling point code on the 
	    signalling route is inaccessible;
	 
	  - powerOff(2), not used;
	 
	  - offLine(3), the signalling route network element part has 
	    been taken off line by a local administrator;
	 
	  - offDuty(4), the signalling route network element part is not 
	    currently available to carry signalling traffic;
	 
	  - dependency(5), the signalling route network element part is 
	    prohibited; a transfer-prohibited message has been received 
	    for the route, or the associated link set is unavailable;
	 
	  - degraded(6), the signalling route network element part is 
	    restricted; a transfer-restricted message has been received 
	    for the route (regardless of whether the route is in use or 
	    not);
	 
	  - notInstalled(7), not used;
	 
	  - logFull(8), not used.
	 
	 The availability status attribute gives additional information 
	 about the availability of the signalling route network element 
	 part instance.  It is furthermore needed to map some of the MTP 
	 functional states (prohibited: dependency(5), restricted: 
	 degraded(6)), and is used for the case that the route is locked 
	 not by the OS, but e.g. by a local administrator 
	 (administrative state unlocked(1) and availability status 
	 offLine(3))."
    REFERENCE
	"ITU-T Rec. X.721 | ISO/IEC 10165-2 availabilityStatus 
	     attribute.
	 ITU-T Rec. Q.751.1 (1997), ANSI T1.116.1 (2000), 
	     availabilityStatus attribute."
    ::= { mtpRtEntry 5 }

mtpRtInClsLoadsharingAlgorithm OBJECT-TYPE
    SYNTAX Unsigned32 (0 | 16 | 32 | 256)
    MAX-ACCESS read-create
    STATUS current
    DESCRIPTION
	"Provides the count of the entries corresponding to this 
	 signalling route network element part in the in combined link 
	 set load sharing algorithm side table.  This will be 16 for 
	 ITU-T 4-bit SLS, 32 for ANSI 5-bit SLS and 256 for ANSI 8-bit 
	 SLS.  When the in combined link set load sharing algorithm 
	 cannot be represented by the side table, or the side table is 
	 not supported by the agent, this value will be zero (0)."
    REFERENCE
	"ITU-T Rec. Q.751.1 (1997), ANSI T1.116.1 (2000), 
	     inClsLoadsharingAlgorithm attribute."
    ::= { mtpRtEntry 6 }

mtpRtFixedPriority OBJECT-TYPE
    SYNTAX Unsigned32
    MAX-ACCESS read-create
    STATUS current
    DESCRIPTION
	"This attribute determines, if the signRouteNePart is used as 
	 the current route.  The signRouteNePart instances with 
	 operational state = 'enabled' contained in the same 
	 signRouteSetNePart are chosen in ascending order as current 
	 routes (The lower the value, the higher the priority).  There 
	 are different behaviours for the handling of 'priority gaps' 
	 possible:
	 
	 i)  priorityGapAllowedBehaviour
	 
	 ii) priorityGapNotAllowedBehaviour:
	 
	 In the latter case it is not possible, to have a priority 
	 value, if there is a lower value, which is not used in one of 
	 the routes of the route set.  E.g. in case of deleting a 
	 signRouteNePart instance whose priority value is not equal to 
	 the priority of at least one of the remaining signRouteNeParts 
	 contained in the same signRouteSetNePart, the priority values 
	 of the remaining instances have to be decremented by one (see 
	 also example in table below).
	 
	 What kind of priority gap behaviour is performed by the switch 
	 is to be derived from the combination of the values of the 
	 attributes vendorName and version of the 
	 managedSwitchingElement."
	 -- note that OpenSS7 implementation permits priority gaps.
    REFERENCE
	"ITU-T Rec. Q.751.1 (1997), ANSI T1.116.1 (2000), fixedPriority 
	     attribute."
    ::= { mtpRtEntry 7 }

mtpRtFlexiblePriority OBJECT-TYPE
    SYNTAX Unsigned32
    MAX-ACCESS read-create
    STATUS current
    DESCRIPTION
	"This attribute determines, if the signRouteNePart is used as 
	 the current route.  The signRouteNePart instances with 
	 operational state = 'enabled' contained in the same 
	 signRouteSetNePart are chosen in ascending order as current 
	 routes (The lower the value, the higher the priority).  There 
	 are different behaviours for the handling of 'priority gaps' 
	 possible:
	 
	 i)  priorityGapAllowedBehaviour
	 
	 ii) priorityGapNotAllowedBehaviour:
	 
	 In the latter case it is not possible, to have a priority 
	 value.  If there is a lower value, which is not used in one of 
	 the routes of the route set.  E.g. in case of deleting a 
	 signRouteNePart instance whose priority value is not equal to 
	 the priority of at least one of the remaining signRouteNeParts 
	 contained in the same signRouteSetNePart, the priority values 
	 of the remaining instances have to be decremented by one (see 
	 also example in table below).
	 
	 What kind of priority gap behaviour is performed by the switch 
	 is to be derived from the combination of the values of the 
	 attributes vendorName and version of the 
	 managedSwitchingElement.  This attribute is writable only 
	 together with the attribute priorityMode."
    REFERENCE
	"ITU-T Rec. Q.751.1 (1997), ANSI T1.116.1 (2000), 
	     flexiblePriority attribute."
    ::= { mtpRtEntry 8 }

mtpRtPriorityMode OBJECT-TYPE
    SYNTAX INTEGER {
	insert(0), equal(1), exchangeSingle(2), exchangeGroup(3) }
    MAX-ACCESS read-create
    STATUS current
    DESCRIPTION
	"This attribute is necessary in case of creating a 
	 signRouteNePart instance or modifiying its priority attribute.  
	 It describes the influence of the management action on the 
	 priority attributes of other signRouteNePart instances 
	 contained in the same signRouteSetNePart.
	 
	 This attribute is only writable, and this only together with 
	 the writing of attribute flexiblePriority.
	 
	 The meanings of the attribute values are:
	 
	  - insert(0): Priority values of all created signRouteNePart 
	    instances from the same signRouteSetNePart with equal or 
	    lower priorities are incremented by one.
	 
	  - equal(1): If by modifying the priority with priorityMode 
	    'EQUAL' a 'priority gap' would come into existence, then for 
	    the priorities of all created signRouteNePart instances from 
	    the same signRouteSetNePart with priorities lower than the 
	    'gap priority' the priority value has to be decremented by 
	    one.
	 
	  - exchangeSingle(2): The priority values of all created 
	    signRouteNePart instances from the same signRouteSetNePart 
	    which have the specified 'target' priority value, are 
	    exchanged for the last ('starting') priority value of the 
	    specified signRouteNePart instance.
	 
	  - exchangeGroup(3): The priority values of all created 
	    signRouteNePart instances from the same signRouteSetNePart 
	    which have the specified 'target' priority value, are 
	    exchanged for the last ('starting') priority value of the 
	    specified signRouteNePart instance.  Additionally the 
	    priority values of all created signRouteNePart instances 
	    from the same signRouteSetNePart, which have the same value 
	    as the 'starting' priority value of the specified 
	    signRouteNePart instance, are changed to the 'target' 
	    value."
    REFERENCE
	"ITU-T Rec. Q.751.1 (1997), ANSI T1.116.1 (2000), priorityMode 
	     attribute."
    ::= { mtpRtEntry 9 }

mtpRtLoadsharingInformation OBJECT-TYPE
    SYNTAX OCTET STRING
    MAX-ACCESS read-create
    STATUS current
    DESCRIPTION
	"This attribute contains specific information for target 
	 specific loadsharing via the current routes working on a route 
	 basis.  This information can be used by e.g. the referenced 
	 mtpLoadsharingObjectFor-Route to execute the target specific 
	 loadsharing."
    REFERENCE
	"ITU-T Rec. Q.751.1 (1997), ANSI T1.116.1 (2000), 
	 loadsharingInformationRouteNePart attribute."
    ::= { mtpRtEntry 10 }

mtpRtLoadsharingObject OBJECT-TYPE
    SYNTAX RowPointer
    MAX-ACCESS read-create
    STATUS current
    DESCRIPTION
	"This attribute is used to reference implementation dependent 
	 loadsharing object class instances needed to model 
	 implementation dependent mechanisms for loadsharing over 
	 linksets working on a route basis."
    REFERENCE
	"ITU-T Rec. Q.751.1 (1997), ANSI T1.116.1 (2000), 
	 mtpLoadsharingObjectForRouteNePartPointer attribute."
    DEFVAL { { zeroDotZero }}
    ::= { mtpRtEntry 11 }

mtpRtName OBJECT-TYPE
    SYNTAX CommonLanguageName
    MAX-ACCESS read-create
    STATUS current
    DESCRIPTION
	"This attribute is an additional name for instances of the 
	 signRouteNePart managed object class.
	 
	 Provides an optional administrative name for this signalling 
	 route.  It is typical to name signalling routes using as a 
	 prefix the common language name of the managed switching 
	 element at which the route terminates (e.g EDTNAB01DS1RT0)."
    REFERENCE
	"ITU-T Rec. Q.751.1 (1997), ANSI T1.116.1 (2000), 
	     signRouteNePartName attribute."
    ::= { mtpRtEntry 12 }

mtpRtSlsList OBJECT-TYPE
    SYNTAX SlsList
    MAX-ACCESS read-create
    STATUS current
    DESCRIPTION
	"This attribute has to be used if loadsharing over link sets 
	 toward a specific destination is done.  It indicates which SLSs 
	 are assigned to this signRouteNePart, in case it is a current 
	 route (i.e. the messages with these SLSs are sent over the 
	 allocated link set).  It has to be ensured that all SLSs are 
	 covered and no SLS exists more than one time within the slsList 
	 attributes of the current routes.  The attribute can be written 
	 from system inside."
    REFERENCE
	"ITU-T Rec. Q.751.1 (1997), ANSI T1.116.1 (2000), slsList 
	 attribute."
    ::= { mtpRtEntry 13 }

mtpRtUsageState OBJECT-TYPE
    SYNTAX UsageState
    MAX-ACCESS read-only
    STATUS current
    DESCRIPTION
	"Provides the usage state of the signalling route network 
	 element part following the UsageState textual convention of the 
	 OPENSS7-SMI-MIB module and according to ITU-T Rec. X.721 | 
	 ISO/IEC 10165-2.
	 
	  - idle(0), the signalling route is idle and is not currently 
	    carrying signalling traffic; the signalling route is 
	    prohibited, restricted, unavailable, or not used because a 
	    higher priority route exists that is carrying traffic;
	 
	  - active(1), the signalling route is active and is carrying 
	    signalling traffic; the signalling route is available and in 
	    use (no higher priority route is available);
	 
	  - busy(2), the signalling route is restricted and is unable to 
	    carry additional signalling traffic; a transfer-restricted 
	    message has been received for the route, but the route is 
	    still in use (no available equal priority alternate route 
	    exists).
	 
	 The usage state is used to cover restriction of a route.  Its 
	 value is set to busy(2) if the route is restricted."
    REFERENCE
	"ITU-T Rec. X.721 | ISO/IEC 10165-2 usageState attribute.
	 ITU-T Rec. Q.751.1 (1997), ANSI T1.116.1 (2000), usageState 
	     attribute."
    DEFVAL { 0 } -- idle
    ::= { mtpRtEntry 14 }

mtpRtRlSlot OBJECT-TYPE
    SYNTAX Unsigned32 (0..3)
    MAX-ACCESS read-create
    STATUS current
    DESCRIPTION
	"Provides the slot within the signalling route list 
	 corresponding to this signalling route.  Typically, only slots 
	 0 and 1 are used.  For STPs in a quad arrangement slots 0 
	 through 3 can be used.  Selection of the signalling route 
	 within a signalling route list is made based on a match of the 
	 value of this number and the value of masked signalling link 
	 selection bits defined for the signalling route list."
    ::= { mtpRtEntry 15 }

mtpRtProfile OBJECT-TYPE
    SYNTAX SimpleNameType
    MAX-ACCESS read-create
    STATUS current
    DESCRIPTION
	"Provides a reference to a signalling route profile used by this 
	 signalling route.  The reference is the index of the signalling 
	 route profile in the signalling route profile table."
    ::= { mtpRtEntry 16 }

mtpRtRowStatus OBJECT-TYPE
    SYNTAX RowStatus
    MAX-ACCESS read-create
    STATUS current
    DESCRIPTION
	"Provides a mechanism whereby management stations may create and 
	 delete rows in this table.  Values survive agent reboot.
	 
	 A create request is rejected, if the signLinkSetTpPointer would 
	 reference an instance, which
	 
	  1. does not belong to the signLinkSetTp object class OR
	 
	  2. does not exist OR
	 
	  3. is not contained in the same mtpSignPoint as the 
	     signRouteNePart OR
	 
	  4. is already referenced by a signRouteNePart contained within 
	     the same signRouteSetNePart
	 
	 A delete request is rejected if its administrativeState does 
	 not equal locked.  If the name package is supported: a create 
	 request with a value for the name attribute that is already 
	 used by another instance of the same object class will be 
	 rejected."
    REFERENCE
	"STD 58, SNMPv2-TC RowStatus.
	 ITU-T Rec. Q.751.1 (1997) : signRouteSetNePart-signRouteNePart 
	     NAME BINDING."
    ::= { mtpRtEntry 17 }


-- ====================================================================

mtpRtLsaTable OBJECT-TYPE
    SYNTAX SEQUENCE OF MtpRtLsaEntry
    MAX-ACCESS not-accessible
    STATUS current
    DESCRIPTION
	"Provides a side table that contains the signalling link set 
	 link priority list for each signalling route network element 
	 part."
    ::= { mtpRt 3 }

mtpRtLsaEntry OBJECT-TYPE
    SYNTAX MtpRtLsaEntry
    MAX-ACCESS not-accessible
    STATUS current
    DESCRIPTION
	"Entries in this table can neither be created nor deleted by 
	 management stations.  When a signRouteNePart is created, one 
	 entry exists in this table for each applicable slsCode ([0..15] 
	 for ITU-T with 4-bit SLS, [0..31] for ANSI with 5-bit SLS, and 
	 [0..255] for ANSI with 8-bit SLS).  A default setting of normal 
	 and alternate signaling links is provided by the managed 
	 system.  These assignment can then be altered by management 
	 stations.
	 
	 Note that the signRouteNePartRowStatus also controls the 
	 inservice state of entries in this table with the same indices 
	 as the signRouteNePartRowStatus."
    INDEX {
	mtpSpId,
	mtpRsId,
	mtpRtId,
	mtpRtLsaSlsCode
    }
    ::= { mtpRtLsaTable 1 }

MtpRtLsaEntry ::= SEQUENCE {
    mtpRtLsaSlsCode				Unsigned32,
    mtpRtLsaNormalSlCode			Unsigned32,
    mtpRtLsaAlternativeSlCodeList		SlsCodeList
}

mtpRtLsaSlsCode OBJECT-TYPE
    SYNTAX Unsigned32 (0..255)
    MAX-ACCESS not-accessible
    STATUS current
    DESCRIPTION
	"Provides an index for a specific signalling link selection 
	 code.  This index will range from (0..15) for 4-bit SLS 
	 (ITU-T), (0..31) for 5-bit SLS (ANSI) and (0..255) for 8-bit 
	 SLS (ANSI)."
    ::= { mtpRtLsaEntry 1 }

mtpRtLsaNormalSlCode OBJECT-TYPE
    SYNTAX Unsigned32 (0..15)
    MAX-ACCESS read-write
    STATUS current
    DESCRIPTION
	"Provides the normal signalling link code for the indexed 
	 siginalling link selection.  When written by a  management 
	 station the value written need not correspond to  an existing 
	 signalling link in the combined signalling link set to be 
	 valid."
    ::= { mtpRtLsaEntry 2 }

mtpRtLsaAlternativeSlCodeList OBJECT-TYPE
    SYNTAX SlsCodeList
    MAX-ACCESS read-write
    STATUS current
    DESCRIPTION
	"Provides a list of alternate signalling link codes for the 
	 signalling link selection.  The entries in this table do not 
	 need to correspond to an existing signalling link, however, the 
	 list should be exhaustive of all existing signalling link 
	 codes.  Failure to list a signalling link code in either the 
	 normalSlCode or in the alternativeSlCodeList can be considered 
	 an invalid entry by a managed system."
    ::= { mtpRtLsaEntry 3 }


-- ====================================================================

-- NOTE: Q.751.1 only associates timeouts for T6, T8 and T10 with a link 
-- set.  This does not make must sense to me as T6 is a controlled 
-- rerouting timer that should be provisioned on a route basis, T8 is a 
-- trasnfer prohibited inhibition timer which should be provisioned on a 
-- route-set (or route) basis.  T10 is a route-set test message repeat 
-- timer that should be provisioned on a route-set basis.  In the same 
-- vein, Q.751.1 does not allocate T7, T19 and T21 on a link set basis.  
-- T7 should clearly be on a link set basis as it has to do with the 
-- automatic allocation of signalling data links and terminals between 
-- signalling points for a link set.  T19 and T21 can clearly be 
-- provisioned on a link set basis as they have to do with restart 
-- procedures for the direct link set.  The ANSI equivalent timers T25, 
-- T28, T29 and T30 should be provisioned according to the same 
-- reasoning.

-- Q.751.1 uses profile objects for timers.  I prefer to use inheritance 
-- as it provides more opportunity for rational underspecification when 
-- establishing objects.  For example, if standard timer values are 
-- used, it is never necessary to specify a timer when establishing any 
-- object.

-- The following are default link timers to be inherited by links 
-- created under this link set.


mtpLsProfileTable OBJECT-TYPE
    SYNTAX SEQUENCE OF MtpLsProfileEntry
    MAX-ACCESS not-accessible
    STATUS current
    DESCRIPTION
	"Provides a table of  MTP Level 3 signalling link set protocol 
	 profiles.
	 
	 A signalling link set timer profile is a set of Q.704  or 
	 T1.111.4 timers related to the characteristics of signalling 
	 links sets.  The managed object class lsTimersProfile is a 
	 support managed object class which can be instantiated in order 
	 to define a particular profile.  At creation time of a 
	 signLinkSetTp one of the slTimersProfiles is referenced."
    REFERENCE
	"ITU-T Rec. Q.751.1 (1997), ANSI T1.116.1 (2000), 
	     lsTimersProfile MOC."
    ::= { mtpLs 1 }

mtpLsProfileEntry OBJECT-TYPE
    SYNTAX MtpLsProfileEntry
    MAX-ACCESS not-accessible
    STATUS current
    DESCRIPTION
	"Each entry in this table provides an MTP Level 3 signalling 
	 link set protocol profile for use in the creation of signalling 
	 link sets and for specifying defaults for signalling link 
	 sets."
    REFERENCE
	"ITU-T Rec. Q.751.1 (1997), ANSI T1.116.1 (2000), 
	 lsTimersProfile MO."
    INDEX {
	mtpLsProfileId
    }
    ::= { mtpLsProfileTable 1 }

MtpLsProfileEntry ::= SEQUENCE {
    mtpLsProfileId				SimpleNameType,
    mtpLsProfileTimerT6				TimeInterval,
    mtpLsProfileTimerT8				TimeInterval,
    mtpLsProfileTimerT10			TimeInterval,
--
    mtpLsProfileTimerT7				TimeInterval,
    mtpLsProfileTimerT19I			TimeInterval,
    mtpLsProfileTimerT21I			TimeInterval,
    mtpLsProfileTimerT25A			TimeInterval,
    mtpLsProfileTimerT28A			TimeInterval,
    mtpLsProfileTimerT29A			TimeInterval,
    mtpLsProfileTimerT30A			TimeInterval,
    mtpLsProfileName				SimpleNameType,
    mtpLsProfileSlDefault			SimpleNameType,
    mtpLsProfileRowStatus			RowStatus
}

mtpLsProfileId OBJECT-TYPE
    SYNTAX SimpleNameType
    MAX-ACCESS not-accessible
    STATUS current
    DESCRIPTION
	"Provides an index for the mtpLsProfileTable.
	 
	 Provides an into the direct link set profile table.  Rows in 
	 this table can be referred to using this index or using the 
	 RowPointer pointer.  The index valud zero (0) has special 
	 semantics: the zero index contains default default values."
    REFERENCE
	"ITU-T Rec. Q.751.1 (1997), ANSI T1.116.1 (2000), 
	     lsTimersProfileId attribute."
    ::= { mtpLsProfileEntry 1 }

mtpLsProfileTimerT6 OBJECT-TYPE
    SYNTAX TimeInterval
    UNITS "centiseconds"
    MAX-ACCESS read-create
    STATUS current
    DESCRIPTION
	"This attribute defines the initial timer value of timer T6 
	 'Delay to avoid message mis-sequencing on controlled rerouting' 
	 defined in ITU-T Recommendation Q.704, ANSI T1.111.4.  The 
	 value range is from 500 to 1200 ms.  For routes with long 
	 propagation delays a minimum value of 
	 800 ms is used."
    REFERENCE
	"ITU-T Rec. Q.751.1 (1997), ANSI T1.116.1 (2000), q704-t6 
	 attribute."
    ::= { mtpLsProfileEntry 2 }

mtpLsProfileTimerT8 OBJECT-TYPE
    SYNTAX TimeInterval
    UNITS "centiseconds"
    MAX-ACCESS read-create
    STATUS current
    DESCRIPTION
	"This attribute defines the initial timer value of timer T8 
	 'Transfer prohibited inhibition timer (transient solution)' 
	 defined in ITU-T Recommendation Q.704, ANSI T1.111.4.  The 
	 value range is from 800 to 1200 ms."
    REFERENCE
	"ITU-T Rec. Q.751.1 (1997), ANSI T1.116.1 (2000), q704-t8 
	 attribute."
    DEFVAL { 100 } -- 1000 milliseconds
    ::= { mtpLsProfileEntry 3 }

mtpLsProfileTimerT10 OBJECT-TYPE
    SYNTAX TimeInterval
    UNITS "centiseconds"
    MAX-ACCESS read-create
    STATUS current
    DESCRIPTION
	"This attribute defines the initial timer value of timer T10 
	 'Waiting to repeat signalling route set test message' defined 
	 in ITU-T Recommendation Q.704, ANSI T1.111.4.  The value range 
	 is from 30 to 60 seconds.  The maximum value may be extended at 
	 the discretion of the management function in certain 
	 situations, e.g. many signalling points being unavailable or 
	 signalling points of known long term unavailability."
    REFERENCE
	"ITU-T Rec. Q.751.1 (1997), ANSI T1.116.1 (2000), q704-t10 
	 attribute."
    DEFVAL { 4500 } -- 45 seconds
    ::= { mtpLsProfileEntry 4 }

mtpLsProfileTimerT7 OBJECT-TYPE
    SYNTAX TimeInterval (100..200)
    UNITS "centiseconds"
    MAX-ACCESS read-create
    STATUS current
    DESCRIPTION
	"This attribute defines the initial timer value of timer T7 
	 Waiting for signalling data link connection acknowledgement 
	 defined in Recommendation Q.704.  The value range is from 1 to 
	 2 seconds.
	 
	 This value and the associated procedure is only in effect when 
	 the automatic allocation of signalling data links procedure is 
	 activate.  The automatic allocation of signalling data links 
	 procedure is not normally permitted by most modern protocol 
	 variants."
    REFERENCE
	"ITU-T Rec. Q.751.1 (1997), ANSI T1.116.1 (2000), q704-t7 attribute.
	 ITU-T Rec. Q.704 (1996), ANSI T1.111.4/2000"
    DEFVAL { 150 } -- 1.5 seconds
    ::= { mtpLsProfileEntry 5 }

mtpLsProfileTimerT19I OBJECT-TYPE
    SYNTAX TimeInterval
    UNITS "centiseconds"
    MAX-ACCESS read-create
    STATUS current
    DESCRIPTION
	"This attribute defines the initial timer value of timer T19 
	 Supervision timer during MTP restart to avoid possible 
	 ping-pong of TFP, TFR and TRA messages.  defined in 
	 Recommendation Q.704. The value range is from 67 to 69 seconds.
	 
	 This timer value and associated procedure is only in effect for 
	 ITU-T based signalling protocol variants.
	 
	 9.2.4 ... In addition, [to sending TRA] timer T19 is started 
	   (see 9.5.2) for all signalling points to which a TRA message 
	   has just been sent.  Normal operation is then resumed.
	 
	 9.5.1  If a signalling point X receives an unexpected TRA 
	   message from an adjacent node Y and no associated T19 timer 
	   is running, X sends to Y any necessary TFP and TFR messages 
	   if X has the transfer function, and a TRA message to Y.  In 
	   addition, X starts timer T19 associated with Y.
	 
	 9.5.2  If a signalling point receives a TRA message from an 
	   adjacent node and an associated T19 is running, this TRA is 
	   discarded and no further action is taken.
	 
	 IMPLEMENTATION NOTES:- ITU T19 is like ANSI T29 and T30 and is 
	 set on a link set basis."
    REFERENCE
	"ITU-T Rec. Q.751.1 (1997), ANSI T1.116.1 (2000), q704-t19 attribute.
	 ITU-T Rec. Q.704 (1996)"
    ::= { mtpLsProfileEntry 6 }

mtpLsProfileTimerT21I OBJECT-TYPE
    SYNTAX TimeInterval
    UNITS "centiseconds"
    MAX-ACCESS read-create
    STATUS current
    DESCRIPTION
	"This attribute defines the initial timer value of timer T21 
	 Overall MTP restart timer at a signalling point adjacent to one 
	 whose MTP restarts. defined in Recommendation Q.704. The value 
	 range is from 63 to 65 seconds.
	 
	 This timer value and associated procedure is only in effect for 
	 ITU-T based signalling protocol variants.
	 
	 9.3.1  A signalling point X considers that MTP of an 
	   inaccessible adjacent signalling point Y is restarting when: 
	   the first link in a direct link set is in the 'in service' 
	   state at level 2; or another route becomes available due 
	   either to reception of a corresponding TFA, TFR or TRA 
	   message, or by the corresponding link set becoming available 
	   (see 3.6.2.2).
	 
	 9.3.2  When the first link in a direct link set toward 
	   signalling point Y, whose MTP is restarting, is in the 'in 
	   service' state at level 2, signalling point X starts a timer 
	   T21 and takes account of any TFP, TFA and TFR messages 
	   received from signalling point Y.  In addition, X takes the 
	   following actions: if X has the transfer function, when the 
	   direct link set is available at level 3, X sends any 
	   necessary TFP and TFR message to Y; then X sends a traffic 
	   restart allowed message to signalling point Y.
	 
	 If a signalling point, previously declared to be inaccessible, 
	 becomes available again before T21 is stopped or expires, a 
	 corresponding TFA or TFR message is sent to the signalling 
	 point Y whose MTP is restarting.
	 
	 If a signalling point becomes prohibited or restricted to 
	 signalling X after a TRA message has been sent by X to Y, X 
	 sends a corresponding TFP or TFR message to Y.
	 
	 When a traffic restart allowed message has been received by X 
	 from signalling point Y, and a TRA message has been sent by X 
	 to Y, X stops timer T21.
	 
	 ...
	 
	 When T21 is stopped or expires, signalling point X sends a 
	 MTP-RESUME primitive concerning Y, and all signalling points 
	 made available via Y, to all local MTP Users.  If X has the 
	 transfer function, it broadcasts to adjacent available 
	 signalling points transfer-allowed and/or transfer restricted 
	 messages concerning Y and all signalling points made accessible 
	 by Y.
	 
	 9.6.2  After the MTP of an adjacent node X has restarted, and 
	   if T21 has been started (see 9.3.2), all routes using X are 
	   considered to be available unless corresponding TFP or TFR 
	   message have been received whilst T21 was running.
	 
	 IMPLEMENTATION NOTES:- ITU-T T21 is similar to ANSI T28 and 
	 T25."
    REFERENCE
	"ITU-T Rec. Q.751.1 (1997), ANSI T1.116.1 (2000), q704-t21 attribute.
	 ITU-T Rec. Q.704 (1996)"
    ::= { mtpLsProfileEntry 7 }

mtpLsProfileTimerT25A OBJECT-TYPE
    SYNTAX TimeInterval
    UNITS "centiseconds"
    MAX-ACCESS read-create
    STATUS current
    DESCRIPTION
	"This object specifies the duration of the ANSI traffic restart 
	 waiting timer, T25 (ANSI).  This timer is started or restarted 
	 when a traffic restart waiting message is received during the 
	 restart procedure.  When the timer expires, traffic is 
	 restarted on the link set.
	 
	 If unspecified on a management station SET operation creating 
	 an entry, the value of the containing signalling point should 
	 be inherited.
	 
	 This timer value and associated procedure is only in effect for 
	 ANSI based signalling protocol variants.
	 
	 ANSI T1.111.4/2000 9.1 When the first signalling link goes into 
	     the in service state at level 2, the restarting signalling 
	     point begins taking into account any transfer-prohibited, 
	     transfer-restricted, transfer-allowed, traffic restart 
	     allowed, and traffic restart waiting messages received.  
	     The restarting point starts timers T22 and T26 either when 
	     the first signalling link goes in the in service state at 
	     level 2 or when the first signalling link becomes available 
	     at level 3.  When a traffic restart waiting message is 
	     receive before user traffic is restarted on the link(s) to 
	     the point that sent the traffic restart waiting message, 
	     timer T25 is started and user traffic is not restarted on 
	     that link set until a traffic restart allowed message is 
	     received or timer T25 expires (see 9.3).
	 
	 ANSI T1.111.4/2000 9.3 A signalling point X considers that the 
	     MTP of an inaccessible adjacent signalling point Y is 
	     restarting when: (1) The first link in a direct link set is 
	     in the in service state at level 2, or (2) A route other 
	     than a direct link set becomes available, e.g. through 
	     receipt of a transfer allowed or traffic restart allowed 
	     message or the availability of the corresponding link set.
	 
	     When the first link in a direct link set toward the 
	     restarting signalling point Y goes into the in services 
	     state at level 2, signalling point X begins taking into 
	     account any traffic restart waiting, traffic restart 
	     allowed, transfer-prohibited, transfer-restricted, and 
	     transfer-allowed messages from Y.  Signalling point X 
	     starts timer T28 either when the first link goes into the 
	     in service state at level 2 or when the first signalling 
	     link becomes available at level 3.  IN addition it takes 
	     the following actions:
	     
	      1. If a TRW message is received from Y while T28 is 
		 running or before it is started, X starts T25.  X stops 
		 T28 if it is running.
	     
	      2. If a TRW message is received from Y while T25 is 
		 running, X restarts T25.
	     
	      3. When the first link in a link set to Y becomes 
		 available, signalling point X sends to Y a traffic 
		 restart allowed message or, if X has the transfer 
		 function, a traffic restart waiting message followed by 
		 transfer-prohibited (note that all transfer prohibited 
		 messages according to 13.2.2 (1) must be sent) and 
		 transfer-restricted messages and a traffic restart 
		 allowed message.
	     
	      4. If a destination becomes prohibited, restricted, or 
		 available at X, after X has sent a traffic restart 
		 allowed message to Y, X notifies Y of the status change 
		 by the normal procedures in Section 13.
	     
	      5. When a traffic restart allowed message has been sent to 
		 Y and a traffic restart allowed message has been 
		 received from Y, X stops T25 or T28, whichever is 
		 running, and restarts traffic on the link set to Y.  X 
		 gives MTP-RESUME primitives to users concerning Y and 
		 any destinations made accessible via Y.  If X has the 
		 transfer function it also broadcasts transfer-allowed 
		 or transfer-restricted messages concerning the same 
		 destinations.
	     
	      6. If T28 expires, X restarts traffic on the link set to Y 
		 as in (5), unless a traffic restart allowed message has 
		 not been sent to Y.  In that case, X starts T25 and 
		 completes the sending of transfer prohibited and 
		 transfer-restricted messages, followed by a traffic 
		 restart allowed message.  Then, unless a traffic 
		 restart waiting message has been received from Y 
		 without a subsequent traffic restart allowed message, X 
		 stops 25 and restarts traffic on the link set to Y.
	     
	      7. If T25 expires, X restarts traffic on the link set 
		 toward Y.  In the abnormal case when X has not 
		 completed sending transfer-prohibited and 
		 transfer-restricted messages to Y, X completes sending 
		 the transfer-prohibited messages required by 13.2.2 (1) 
		 and sends a traffic restart allowed message before 
		 restarting user traffic.
	     
	      8. If no traffic restart allowed message has been received 
		 from Y when traffic is restarted to Y, timer T9 (see 
		 9.4) is started.
	     
	     When signalling point Y becomes accessible via a route 
	     other than a direct link set between X and Y, X sends a 
	     MTP-RESUME primitive concerning Y to all local MTP users.  
	     In addition, if signalling point X has the transfer 
	     function, X sends to Y any required transfer-prohibited and 
	     transfer-restricted message by the available route and 
	     broadcasts transfer-allowed or transfer-restricted messages 
	     concerning Y."
    REFERENCE
	"ANSI T1.111.4/2000 9.1, 9.3"
    ::= { mtpLsProfileEntry 8 }

mtpLsProfileTimerT28A OBJECT-TYPE
    SYNTAX TimeInterval
    UNITS "centiseconds"
    MAX-ACCESS read-create
    STATUS current
    DESCRIPTION
	"This object specifies the duration of the ANSI traffic restart 
	 allowed sent timer, T28 (ANSI).  This timer is started when the 
	 first link in a direct link set becomes available.  When the 
	 timer expires and T25 is not running, traffic is restarted on 
	 the link set.
	 
	 If unspecified on a management station set operation creating 
	 an entry, the value of the containing signalling point should 
	 be inherited.
	 
	 This timer value and associated procedure is only in effect for 
	 ANSI based signalling protocol variants.
	 
	 ANSI T1.111.4/2000 9.3 (Actions in Signalling Point X Adjacent 
	     to a Restarting Signalling Point Y.)  A signalling point X 
	     considers that the MTP of an inaccessible adjacent 
	     signalling point Y is restarting when:
	 
	     1. The first link in a direct link set is in the in service 
		state at level 2, or
	 
	     2. A route other than a direct link set becomes available, 
		e.g., through receipt of a transfer allowed or traffic 
		restart allowed message or the availability of the 
		corresponding link set.
	 
	     When the first link in a direct link set toward the 
	     restarting signalling point Y goes into the in service 
	     state at level 2, signalling point X begins taking into 
	     account any traffic restart waiting, traffic restart 
	     allowed, transfer-prohibited, transfer-restricted, and 
	     transfer-allowed messages from Y.  Signalling point X 
	     starts timer T28 either when the first link goes into the 
	     in services state at level 2 or when the first signalling 
	     link becomes available at level 3.  In addition, it takes 
	     the following actions:
	     
	     1. If a TRW message is received from Y while T28 is running 
		or before it is started, X starts T25.  X stops T28 if 
		it is running.
	     
	     2. If a TRW message is received from Y while T25 is 
		running, X restarts T25.
	     
	     3. When the first link in a link set to Y becomes 
		available, signalling point X sends to Y a traffic 
		restart allowed message or, if X has the transfer 
		function, a traffic restart waiting message followed by 
		transfer-prohibited (note that all transfer-prohibited 
		messages according to 13.2.2 (1) must be sent) and 
		transfer restricted messages and a traffic restart 
		allowed message.
	     
	     4. If a destination becomes prohibited, restricted, or 
		available at X, after X has sent a traffic restart 
		allowed message to Y, X notifies Y of the status change 
		by the normal procedures in Section 13.
	     
	     5. When a traffic restart allowed message has been sent to 
		Y and a traffic restart allowed message has been 
		received from Y, X stops T25 or T28, whichever is 
		running, and restarts traffic on the link set to Y.  X 
		gives MTP-RESUME primitives to users concerning Y and 
		any destinations made accessible via Y.  If X has the 
		transfer function it also broadcasts transfer-allowed or 
		transfer-restricted messages concerning the same 
		destinations.
	     
	     6. If T28 expires, X restarts traffic on the link set to Y 
		as in (5), unless a traffic allowed message has not been 
		sent to Y.  In that case, X starts T25 and completes the 
		sending of transfer-prohibited and transfer-restricted 
		messages, followed by a traffic restart allowed message.  
		Then, unless a traffic restart waiting message has been 
		received from Y without a subsequent traffic restart 
		allowed message, X stops T25 and restarts traffic on the 
		link set to Y.
	     
	     7. If T25 expires, X restarts traffic on the link set 
		toward Y.  In the abnormal case when X has not completed 
		sending transfer-prohibited and transfer-restricted 
		messages to Y, X completes sending the 
		transfer-prohibited messages required by 13.2.2 (1) and 
		sends a traffic restart allowed message before 
		restarting user traffic.
	     
	     8. If no traffic restart allowed message has been received 
		from Y when traffic is restarted to Y, timer T29 (see 
		9.4) is started.
	     
	     When signalling point Y becomes accessible via a route 
	     other than a direct link set between X and Y, X sends an 
	     MTP-RESUME primitive concerning Y to all local MTP users.  
	     In addition, if signalling point X has the transfer 
	     function, X sends to Y any required transfer-prohibited and 
	     transfer-restricted messages by the available route and 
	     broadcasts transfer-allowed or transfer-restricted messages 
	     concerning Y."
    REFERENCE
	"ANSI T1.111.4/2000 9.3"
    ::= { mtpLsProfileEntry 9 }

mtpLsProfileTimerT29A OBJECT-TYPE
    SYNTAX TimeInterval
    UNITS "centiseconds"
    MAX-ACCESS read-create
    STATUS current
    DESCRIPTION
	"This object specifies the duration of the ANSI unexpected 
	 traffic restart condition timer, T29 (ANSI).  This timer is 
	 started when an unexpected traffic restart condition occurs.  
	 Unexpected conditions are ignored for the duration that the 
	 timer is running.
	 
	 If unspecified on a management station set operation creating 
	 an entry, the value of the containing signalling point should 
	 be inherited.
	 
	 This timer value and associated procedure is only in effect for 
	 ANSI based signalling protocol variants."
    REFERENCE
	"ANSI T1.111.4/2000 9."
    ::= { mtpLsProfileEntry 10 }

mtpLsProfileTimerT30A OBJECT-TYPE
    SYNTAX TimeInterval
    UNITS "centiseconds"
    MAX-ACCESS read-create
    STATUS current
    DESCRIPTION
	"This object specifies the duration of the ANSI unexpected 
	 traffic restart condition timer, T30 (ANSI).  This timer is 
	 started by an STP when an unexpected traffic restart condition 
	 occurs.  Unexpected conditions are ignored for the duration 
	 that the timer is running.
	 
	 If unspecified on a management station set operation creating 
	 an entry, the value of the containing signalling point should 
	 be inherited.
	 
	 This timer value and associated procedure is only in effect for 
	 ANSI based signalling protocol variants.
	 
	 ANSI T1.111.4/2000 9.4 ... If the receiving point has the 
	     transfer function, it starts timer T30, sends a traffic 
	     restart waiting message followed by the necessary 
	     transfer-restricted and transfer-prohibited messages 
	     (preventive transfer-prohibited messages according to 
	     13.2.2 (1) are required for traffic currently being routed 
	     via the point from which the unexpected traffic restart 
	     allowed or traffic restart waiting message was received), 
	     and a traffic restart allowed message.  It then stops T30 
	     and starts T29.  In the abnormal case that T30 expires 
	     before the sending of transfer-prohibited and 
	     transfer-restricted messages is completed, it sends a 
	     traffic restart allowed message, starts T29, and then 
	     completes sending any preventative transfer-prohibited 
	     messages according to 13.2.2 (1) for traffic currently 
	     being routed via the point from which the unexpected 
	     traffic restart allowed or traffic restart waiting message 
	     was received."
    REFERENCE
	"ANSI T1.111.4/2000 9.4"
    ::= { mtpLsProfileEntry 11 }

mtpLsProfileName OBJECT-TYPE
    SYNTAX SimpleNameType
    MAX-ACCESS read-create
    STATUS current
    DESCRIPTION
	"This attribute is an additional name for instances of the 
	 lsTimersProfile managed object class."
    REFERENCE
	"ITU-T Rec. Q.751.1 (1997), ANSI T1.116.1 (2000), 
	 lsTimersProfileId attribute."
    DEFVAL { "" }
    ::= { mtpLsProfileEntry 12 }

mtpLsProfileSlDefault OBJECT-TYPE
    SYNTAX SimpleNameType
    MAX-ACCESS read-create
    STATUS current
    DESCRIPTION
	"Specifies the index of the entry in the mtpSlL3ProfileTable to be 
	 used as the default for signalling links created within this 
	 link set.  Provides a reference to an MTP Level 3 signalling 
	 link protocol profiel for use as a default when creating 
	 signalling links belonging to this signalling link set.  When 
	 not specified, the signalling link MTP Level 3 protocol profile 
	 specified for the signalling point is inherited."
    ::= { mtpLsProfileEntry 13 }

mtpLsProfileRowStatus OBJECT-TYPE
    SYNTAX RowStatus
    MAX-ACCESS read-create
    STATUS current
    DESCRIPTION
	"Provides a mechanism whereby management stations may create and 
	 delete rows in this table.  Rows created in this table must 
	 survive an agent reboot.  Columns that are not specified at the 
	 time of row creation will assume their defined default value.  
	 Rows that are referenced by other tables in this MIB cannot be 
	 deleted.
	 
	 If the name package is supported: a create request with a value 
	 for the name attribute that is already used by another instance 
	 of the same object class will be rejected.  If an attempt is 
	 made to delete an lsTimersProfile which is still referenced by 
	 a signLinkSetTp the delete request will be rejected."
    REFERENCE
	"STD 58, SNMPv2-TC RowStatus.
	 ITU-T Rec. Q.751.1 (1997), ANSI T1.116.1 (2000), 
	     managedSwitchingElement-lsTimersProfile NAME BINDING."
    ::= { mtpLsProfileEntry 14 }


-- ====================================================================

mtpLsTable OBJECT-TYPE
    SYNTAX SEQUENCE OF MtpLsEntry
    MAX-ACCESS not-accessible
    STATUS current
    DESCRIPTION
	"This managed object class represents the SS No. 7 signalling 
	 link set termination point.  Link sets are defined in 
	 Recommendation Q.704.  The states are directly related to the 
	 set of link termination point's states, except for the optional 
	 administrativeState.
	 
	 General principles on state information:
	 
	  1. The states of the managed object linkset are only readable, 
	     except for the optional administrativeState.
	 
	  2. Activation and deactivation of a linkset may be done via 
	     operations on the links (e.g. by using scoping functions) 
	     or the optional administrativeState can be used for this.
	 
	 Based on these principles the states of a linkset are defined 
	 as follows:
	 
	  - operational state (read-only for the OS).  The operational 
	    state is enabled whenever one link of the linkset is 
	    enabled, i.e. neither FAILED nor DEACTIVATED nor LOCAL 
	    BLOCKED nor REMOTE BLOCKED.
	 
	  - Usage state (read-only for the OS).  The usage state 
	    reflects the usage of the belonging links.  It is ACTIVE if 
	    at least one of the belonging links is ACTIVE and no link is 
	    BUSY.  It contains BUSY if one of the belonging links is 
	    BUSY.  It is IDLE if all links are UNAVAILABLE.
	 
	  - Availability status (read-only for the OS).  The 
	    availability status indicates unavailability or reduced 
	    availability of the belonging links.  It contains DEPENDENCY 
	    if all the belonging links are unavailable for user traffic.  
	    It contains DEGRADED if at least one belonging link is not 
	    available for user traffic.  For the different reasons of 
	    unavailability (failed, deactivated, local blocked, remote 
	    blocked, local inhibited and remote inhibited) see 
	    3.2.1/Q.704.
	 
	 If the 'ITU-T Rec. X.721 (1992) | ISO/IEC 10165-2 : 
	 1992':communicationsAlarm notification is used, the following 
	 probable causes can apply:
	 
	  - Probable Cause=403 (LinkSetFailure), which represents 
	    measurements Q.752/4.3 (PerceivedSeverity=Maj/Min/War) and 
	    Q.752/4.4 (PerceivedSeverity=Cleared).
	 
	 State change notifications are emitted for all state and status 
	 changes."
    REFERENCE
	"ITU-T Rec. Q.751.1 (1997), ANSI T1.116.1 (2000), signLinkSetTp 
	 MOC."
    ::= { mtpLs 2 }

mtpLsEntry OBJECT-TYPE
    SYNTAX MtpLsEntry
    MAX-ACCESS not-accessible
    STATUS current
    DESCRIPTION
	"Signalling link set termination points are contained by MTP 
	 signalling points.  The specific signalling link set 
	 termination point (signLinkSetTpId) is contained by one MTP 
	 signalling point (mtpSignPointId).
	 
	 An entry in this table can generate a communicationsAlarm with 
	 the following parmeters:

	  - ITU-T Rec. Q.752 (1997) : Table 4/Q.752 4.3,
		probableCause = 403, (linkSetFailure)
		PerceivedSeverity = M/m/W
	  - ITU-T Rec. Q.752 (1997) : Table 4/Q.752 4.4,
		probableCause = 403, (linkSetFailure)
		PerceivedSeverity = Cleared
	  - ITU-T Rec. Q.752 (1997) : Table 4/Q.752 5.1,
		probableCause = 501, (adjSpInaccessibility)
		PerceivedSeverity = M/m/w, 
		AdditionalInfo = InaccessibleSpi
	  - ITU-T Rec. Q.752 (1997) : Table 4/Q.752 5.4,
		probableCause = 501, (adjSpInaccessibility)
		PerceivedSeverity = Cleared, 
		AdditionalInfo = InaccessibleSpi
	 
	 The mtpSpId specifies an index into the SP table that specifies 
	 the signalling point to which this link set will 
	 belong.  Underspecified values on management station SET 
	 operations that create an entry in this table will be inherited 
	 from the specified SP table signalling point entry."
    REFERENCE
	"ITU-T Rec. Q.751.1 (1997), ANSI T1.116.1 (2000), signLinkSetTp 
	 MO."
    INDEX {
	mtpSpId, -- shared index
	mtpLsId
    }
    ::= { mtpLsTable 1 }

-- NOTE: The following is slightly different from the optional Q.751.1 
-- method of loadsharing within a combined link set using the 
-- conditional clsLoadsharingInformationPackage.

MtpLsEntry ::= SEQUENCE {
    mtpLsId					Unsigned32,
    mtpLsAdjPc					NetworkPointCode,
    mtpLsRsId					SimpleNameType,
    mtpLsMaxCapacity				Unsigned32,
    mtpLsCurrentCapacity			Unsigned32,
    mtpLsCongestionControlMethod		INTEGER,
    mtpLsUsageState				UsageState,
    mtpLsOperationalState			OperationalState,
    mtpLsAvailabilityStatus			AvailabilityStatus,
    mtpLsPeriodicLinkTestFlag			INTEGER,
    mtpLsPeriodicLinkTestFail			TruthValue,
    mtpLsAdministrativeState			AdministrativeState,
    mtpLsInLsLoadShareAlgorithm			AutonomousType,
    mtpLsProfilePointer				SimpleNameType,
    mtpLsNumberOfNormallyActiveSignLinks	Unsigned32,
    mtpLsName					CommonLanguageName,
    mtpLsAsaProfilePointer			RowPointer,
    mtpLsAlarmStatus				AlarmStatus,
    mtpLsRowStatus				RowStatus
}

mtpLsId OBJECT-TYPE
    SYNTAX Unsigned32
    MAX-ACCESS not-accessible
    STATUS current
    DESCRIPTION
	"Provides a non-zero index into the direct link set table, 
	 mtpLsTable.  This attribute is used for naming instances."
    REFERENCE
	"ITU-T Rec. Q.751.1 (1997), ANSI T1.116.1 (2000), 
	     signLinkSetTpId attribute."
    ::= { mtpLsEntry 1 }

mtpLsAdjPc OBJECT-TYPE
    SYNTAX NetworkPointCode
    MAX-ACCESS read-create
    STATUS current
    DESCRIPTION
	"This attribute represents the pointcode of an adjacent SP.
	 
	 Provides the adjacent signalling point code for the signalling 
	 point at the other end of this signalling link set.  When not 
	 specfied, the signalling route set index (mtpLsRsId) must be 
	 specified.
	 
	 This object is an entry of the signalling route set table that 
	 indicates the signalling point code of the adjacent signalling 
	 point (the signalling point at the opposite end of the links in 
	 the link set).  Because the Signalling Point could be operating 
	 in multiple National and International networks, the 
	 NetworkPointCode contains a network identifier."
    REFERENCE
	"ITU-T Rec. Q.751.1 (1997), ANSI T1.116.1 (2000), adjPc 
	     attribute."
    ::= { mtpLsEntry 2 }

mtpLsRsId OBJECT-TYPE
    SYNTAX SimpleNameType
    MAX-ACCESS read-create
    STATUS current
    DESCRIPTION
	"Specifies an index into the mtpRsTable corresponding to the 
	 signalling route set for the adjacent signalling point for 
	 this direct link set.  Direct link sets are a set of signalling 
	 links that all terminate on the same adjacent signalling point.  
	 This route set is the route set for the adjacent signalling 
	 point.  When not specified, the signalling point code of the 
	 adjacent signalling point must be specified (mtpLsAdjPc)."
    ::= { mtpLsEntry 3 }

mtpLsMaxCapacity OBJECT-TYPE
    SYNTAX Unsigned32 (0..128000)
    UNITS "octets per second"
    MAX-ACCESS read-create
    STATUS current
    DESCRIPTION
	"This is the maximum signalling capacity of the link set in 
	 octets per second.  It is less than or equal to the sum of the 
	 traffic handling capacities of the individual signalling links 
	 that could be contained by the signalling link set.  When 
	 signalling links with a mixture of speeds are specified for the 
	 direct link set, this value should be less than or equal to the  
	 sum of the lowest speed signalling links that could complete 
	 the direct link set."
    REFERENCE
	"ITU-T Rec. Q.751.1 (1997), ANSI T1.116.1 (2000), 
	     signLinkSetTp::maxCapacityLS attribute.
	     Note that the maximum is for ITU-T."
    ::= { mtpLsEntry 4 }

mtpLsCurrentCapacity OBJECT-TYPE
    SYNTAX Unsigned32 (0..128000)
    UNITS "octets per second"
    MAX-ACCESS read-only
    STATUS current
    DESCRIPTION
	"This attribute represents the current capacity of a signalling 
	 link set.
	 
	 This is the current signalling capacity of the direct link set 
	 in octets per second.  It is the sum of the traffic handling 
	 capacities of the individual signalling links that are curently 
	 contained by the signalling link set."
    REFERENCE
	"ITU-T Rec. Q.751.1 (1997), ANSI T1.116.1 (2000) : 
	     signLinkSetTp::currentCapacityLS ATTRIBUTE."
    ::= { mtpLsEntry 5 }

mtpLsCongestionControlMethod OBJECT-TYPE
    SYNTAX INTEGER {
	unknown(0), ccmQ704International(1), ccmQ704NationalWithPrio(2), 
	ccmQ704NationalNoPrioBufferMechanism(3), 
	ccmQ704NationalNoPrioTimerMechanism(4) }
    MAX-ACCESS read-create
    STATUS current
    DESCRIPTION
	"This object specifies the congestion control method that is 
	 used on the signalling link set.  The choices are (the labels 
	 are taken from Q.751.1):
	 
	  - unknown(0), implementation specific;
	 
	  - ccmQ704International(1), which is the international method 
	    of congestion control specified in Q.704;
	 
	  - ccmQ704NationalWithPrio(2), which is multiple congestion 
	    levels with message priorities using the buffer allocation 
	    method (e.g. ANSI);
	 
	  - ccmQ704NationalNoPrioBufferMechanism(3), which is multiple 
	    congestion states without message priority using the buffer 
	    method;
	 
	  - ccmQ704NationalNoPrioTimerMechanism(4), is multiple 
	    congesiton states without message priority using the timer 
	    method.
	   
	 Default values are ccmQ704International(1) for ITU-T based 
	 networks and ccmQ704NationalWithPrio(2) for ANSI based 
	 networks."
    REFERENCE
	"ITU-T Rec. Q.751.1 (1997), ANSI T1.116.1 (2000) : 
	     signLinkSetTp::congestionControlMethod ATTRIBUTE."
    ::= { mtpLsEntry 6 }

mtpLsUsageState OBJECT-TYPE
    SYNTAX UsageState
    MAX-ACCESS read-only
    STATUS current
    DESCRIPTION
	"Provides the usage state of the signalling link set termination 
	 point following the UsageState textual convention of the 
	 OPENSS7-SMI-MIB module, and according to ITU-T Rec. X.721 | 
	 ISO/IEC 10165-2.
	 
	  - idle(0), all of the contained signalling links are 
	    unavailable;
	 
	  - active(1), at least one of the contained signalling links is 
	    active(1) and no signalling link is busy(2);
	 
	  - busy(2), one of the contained signalling links is busy(2).
	 
	 The usage state of the signalling link set reflects the usage 
	 state of the contained signalling links."
    REFERENCE
	"ITU-T Rec. X.721 | ISO/IEC 10165-2, usageState attribute.
	 ITU-T Rec. Q.751.1 (1997), ANSI T1.116.1 (2000), usageState 
	     attribute."
    DEFVAL { 0 } -- idle
    ::= { mtpLsEntry 7 }

mtpLsOperationalState OBJECT-TYPE
    SYNTAX OperationalState
    MAX-ACCESS read-only
    STATUS current
    DESCRIPTION
	"Provides the operational state of the signalling link set 
	 termination point following the OperationalState textual 
	 convention of the OPENSS7-SMI-MIB module, and according to 
	 ITU-T Rec. X.721 | ISO/IEC 10165-2.
	 
	  - disabled(0), the operational state of the signalling link 
	    set is disabled whenever all signalling links in the 
	    signalling link set are disabled(0), i.e. either failed(4) 
	    or deactivated(5) or localBlocked(0) or remoteBlocked(1); no 
	    signalling link in the link set is available and no 
	    signalling link in the link set is unavailable due soley to 
	    being locally or remotely inhibited;
	 
	  - enabled(1), the operational state of the signalling link set 
	    is enabled(1) whenever one signalling link of the signalling 
	    link set is enabled(1), i.e., neither failed(4) nor 
	    deactivated(5) nor localBlocked(0) nor remoteBlocked(1); at 
	    least one signalling link in the link set is available or is 
	    unavailable due only to being locally or remotely 
	    inhibited.
	    
	 The operational state of the signalling link set reflects the 
	 operational state of the contained signalling links.  When 
	 signalling link sets are created, they begin in the disabled(0) 
	 state."
    REFERENCE
	"ITU-T Rec. Q.751.1 signLinkSetTp::operationalState
	 ITU-T Rec. X.721 (1992) | ISO/IEC 10165-2 : 1992, 
	     Attribute-ASN1Module.OperationalState.
	 ITU-T Rec. X.731 (1992) | ISO/IEC 10164-2 : 1993, 
	     Section 8.1.1.1.
	 ITU-T Rec. Q.751.1 (1997), ANSI T1.116.1 (2000), 
	     operationalState attribute."
    DEFVAL { 0 } -- disabled
    ::= { mtpLsEntry 8 }

mtpLsAvailabilityStatus OBJECT-TYPE
    SYNTAX AvailabilityStatus
    MAX-ACCESS read-only
    STATUS current
    DESCRIPTION
	"Provides the availability status of the signalling link set 
	 termination point following the AvailablityStatus textual 
	 convention of the OPENSS7-SMI-MIB module, and accord to ITU-T 
	 Rec. X.721 | ISO/IEC 10165-2.
	 
	 The availability status indicates unavailability or reduced 
	 availability of the contained links as follows:
	 
	  - inTest(0), not used;
	  - failed(1), not used;
	  - powerOff(2), not used;
	  - offLine(3), not used;
	  - offDuty(4), not used;
	 
	  - dependency(5), all signalling links in the link set are 
	    unavailable for user traffic: the availability of the link 
	    set depends upon the availability of one of its signalling 
	    links;
	 
	  - degraded(6), at least one of the contained signalling links 
	    is not available for user traffic; at least one signalling 
	    link in the link set is available, however, at least one 
	    other signalling link in the link set is unavailable: the 
	    link set has a degraded traffic handling capacity;
	 
	  - notInstalled(7), no signalling links have been assigned to 
	    the link set;
	 
	  - logFull(8), not used.
	 
	 The availability status indicates unavailability or reduced 
	 availability of the contained links.  When all signalling links 
	 in the link set are available, whether congested or not, this 
	 set contains no value.  For the different reasons of 
	 unavailability (failed, deactivated, local block, remote 
	 blocked, lock inhibited and remote inhibited) see 3.2.1/Q.704"
    REFERENCE
	"ITU-T Rec. X.721 | ISO/IEC 10165-2, availabilityStatus 
	     attribute.
	 ITU-T Rec. Q.751.1 (1997), ANSI T1.116.1 (2000), 
	     availabilityStatus attribute.
	 ITU-T Rec. Q.751.1 (1997) : signLinkSetTp::availabilityStatus"
    ::= { mtpLsEntry 9 }

mtpLsPeriodicLinkTestFlag OBJECT-TYPE
    SYNTAX INTEGER {
	on(0), off(1) }
    MAX-ACCESS read-create
    STATUS current
    DESCRIPTION
	"This attribute indicates whether the periodical signalling link 
	 test procedure of Recommendation Q.707 is applied to a link 
	 set.
	 
	 This object specifies whether periodic link tests will be 
	 performed on signalling links in this link set.  At one time 
	 the default was to not perform periodic signalling link tests 
	 for all variants, then we added default signalling link tests 
	 to most variants, then we added the option as to whether the 
	 procedure should fail the link set if the period procedure 
	 failed, then it was made mandatory in ANSI to fail the 
	 signalling link if the periodic signalling link test fails.
	 
	 This complexity is reflected by two values which determine the 
	 behaviour.  Note that these flags might not permit being set 
	 under some conformances.
	 
	 When this value is not specified on a management station SET 
	 operation that creates an entry, this value should be inherited 
	 from the containing combined link set."
    REFERENCE
	"ITU-T Rec. Q.751.1 (1997), ANSI T1.116.1 (2000), 
	     periodicLinkTestFlag attribute.
	 ITU-T Rec. Q.751.1 signLinkSetTp::periodicLinkTestFlag"
    DEFVAL { 0 } -- on
    ::= { mtpLsEntry 10 }

mtpLsPeriodicLinkTestFail OBJECT-TYPE
    SYNTAX TruthValue
    MAX-ACCESS read-create
    STATUS current
    DESCRIPTION
	"This object specifies whether periodic link test failure will 
	 fail the signalling link.  When true(1), the failure of a 
	 periodic signalling link set procedure will fail the signalling 
	 link; false(2), a notification will be generated but the 
	 signalling link will not fail.
	 
	 When this value is not specified on a management station SET 
	 operation that creates an entry, this value should be inherited 
	 from the containing combined link set."
    REFERENCE
	"ANSI T1.111.7/2000 2.2"
    DEFVAL { 1 } -- true
    ::= { mtpLsEntry 11 }

mtpLsAdministrativeState OBJECT-TYPE
    SYNTAX AdministrativeState
    MAX-ACCESS read-create
    STATUS current
    DESCRIPTION
	"Provides the administrative state of the signalling link set 
	 termination point following the AdministrativeState textual 
	 convention of the OPENSS7-SMI-MIB module, and according to 
	 ITU-T Rec. X.721 | ISO/IEC 10165-2.
	 
	  - locked(0), the signalling link set is administratively 
	    prohibited from carrying signalling traffic; setting this 
	    value results in deactivation of the contained signalling 
	    links;
	 
	  - unlocked(1), the signalling link set is administratively 
	    permitted to carry signalling traffic;  setting this value 
	    results in activation of the contained signalling links;
	 
	  - shuttingDown(2), the signalling link set will be 
	    administratively prohibited from carrying signalling traffic 
	    once existing users of the combined signalling link set 
	    cease using the resource; controlled rerouting procedures 
	    will be effected where possible to remove signalling 
	    traffic.
	 
	 Activation or deactivation of a signalling link set may by 
	 performed using the administrative state.
	 
	 This object can be used for activation and deactivation of link 
	 sets.  Possible values of the AdministrativeState textual 
	 convention are: locked(0) and unlocked(1).  If transition takes 
	 place from locked(0) to unlocked(1), this will result in 
	 activation of all links in the set that are unlocked.  If 
	 transition takes place from unlocked to locked, this will 
	 result in deactivation of all links in the set.  This has no 
	 effect on the administrative states of the links themselves.
	 
	 Signalling link sets are created in the locked(0) state."
    REFERENCE
	"ITU-T Rec. X.721 | ISO/IEC 10165-2, administrativeState 
	     attribute.
	 ITU-T Rec. Q.751.1 (1997), ANSI T1.116.1 (2000), 
	     administrativeState attribute."
    DEFVAL { 0 } -- locked
    ::= { mtpLsEntry 12 }

mtpLsInLsLoadShareAlgorithm OBJECT-TYPE
    SYNTAX AutonomousType
    MAX-ACCESS read-create
    STATUS current
    DESCRIPTION
	"This object specifies a registered, vendor-specific 
	 within-link-set load sharing algorithm.  This value can only be 
	 changed on creation or when the link set is in the locked(1) 
	 administrative state.
	 
	 This object specifies the within-link-set load sharing 
	 algorithm used.  This value can only be changed on creation or 
	 when the link set is in the locked(1) administrative state."
    REFERENCE
	"ITU-T Rec. Q.751.1 (1997), ANSI T1.116.1 (2000) : 
	     signLinkSetTp::inLsLoadShareAlgorithm attribute."
    ::= { mtpLsEntry 13 }

mtpLsProfilePointer OBJECT-TYPE
    SYNTAX SimpleNameType
    MAX-ACCESS read-create
    STATUS current
    DESCRIPTION
	"This attribute to the instance of the class lsTimersProfile, 
	 containing the Q.704 timers for the signalling link set.
	 
	 Provides a reference to an MTP Level 3 signalling link set 
	 protocol profile for use with this signalling link set.  If not 
	 specified, the signalling link set MTP Level 3 protocol profile 
	 specified for the signalling point is inherited."
    REFERENCE
	"ITU-T Rec. Q.751.1 (1997), ANSI T1.116.1 (2000), 
	 lsTimersProfilePointer attribute."
    ::= { mtpLsEntry 14 }

mtpLsNumberOfNormallyActiveSignLinks OBJECT-TYPE
    SYNTAX Unsigned32 (0..32)
    MAX-ACCESS read-create
    STATUS current
    DESCRIPTION
	"This attribute represents the number of normally active 
	 signalling links in a link set, as defined in clause 12/Q.704 
	 and 12/T1.111.4.
	 
	 This object specifies the number of normally active signalling 
	 links.  This value is set to a number less than or equal to the 
	 number of signalling links that belong to this link set.  The 
	 special value zero (0) on a SET operation is reserved for when 
	 the number of normally active signalling links is always the 
	 same as the number of signalling links that belong to this link 
	 set.  This is the basic allocation method that is required by 
	 ANSI and the default for ITU-T.  When the special value zero 
	 (0) is performed on a SET operation, a GET operation will 
	 always return the number of signalling links that belong to 
	 this link set.  The range (0..32) is specified to allow ANSI 
	 based link sets to use this feature: for ITU-T based link sets, 
	 the range is (0..16)"
    REFERENCE
	"ITU-T Rec. Q.751.1 (1997), ANSI T1.116.1 (2000), 
	     numberOfNormallyActiveSignLinksTps attribute.
	 ITU-T Rec. Q.704 (1996) 12., Q.751.1 
	     signLinkSetTp::noBasicLinkAllocationPackage"
    DEFVAL { 0 }
    ::= { mtpLsEntry 15 }

mtpLsName OBJECT-TYPE
    SYNTAX CommonLanguageName
    MAX-ACCESS read-create
    STATUS current
    DESCRIPTION
	"This attribute is an additional name for instances of the 
	 signLinkSetTp managed object class.
	 
	 Provides an optional administrative name for the direct link 
	 set.  Direct link sets are typically named using the common 
	 language name of the managed switching element to which the 
	 direct signalling link terminates (e.g. EDTNAB01DS1)."
    REFERENCE
	"ITU-T Rec. Q.751.1 (1997), ANSI T1.116.1 (2000), 
	     signLinkSetTpName attribute."
    ::= { mtpLsEntry 16 }

mtpLsAsaProfilePointer OBJECT-TYPE
    SYNTAX RowPointer
    MAX-ACCESS read-create
    STATUS current
    DESCRIPTION
	"Provides a pointer to an alarm severity assignment profile to 
	 be used for alarms generated by this signalling link set, or 
	 zeroDotZero."
    REFERENCE
	"ITU-T Rec. Q.751.1 (1997), ANSI T1.116.1 (2000), 
	     alarmSeverityAssignmentProfilePointer attribute."
    DEFVAL { { zeroDotZero } }
    ::= { mtpLsEntry 17 }

mtpLsAlarmStatus OBJECT-TYPE
    SYNTAX AlarmStatus
    MAX-ACCESS read-create
    STATUS current
    DESCRIPTION
	"Provides the alarm status of the MTP direct link set following 
	 the AlarmStatus textual convention and ITU-T Rec. X.721 (1992) 
	 | ISO/IEC 10165-2 : 1992.
	 
	  - underRepair(0),
	  - critical(1),
	  - major(2),
	  - minor(3),
	  - alarmOutstanding(4),
	"
    REFERENCE
	"ITU-T Rec. Q.751.1 (1997), ANSI T1.116.1 (2000) : alarmStatus 
	     attribute.
	 ITU-T Rec. X.721 (1992) | ISO/IEC 10165-2 : 1992, 
	     Attribute-ASN1Module.AlarmStatus.
	 ITU-T Rec. X.731 (1992) | ISO/IEC 10164-2 : 1993, 
	     Section 8.1.2.1."
    ::= { mtpLsEntry 18 }

mtpLsRowStatus OBJECT-TYPE
    SYNTAX RowStatus
    MAX-ACCESS read-create
    STATUS current
    DESCRIPTION
	"Provides a mechanism whereby management stations may create and 
	 delete rows in this table.  Configuration values survive an 
	 agent reboot.
	 
	 A creation request is only successful if a signRouteSetNePart 
	 exists within the mtpSignPoint for the value of attribute adjPC
	 
	 In case the lsTimersProfilePackage is used, a create or set 
	 request is rejected, if
	 
	 1. the lsTimersProfilePointer does not reference an 
	    lsTimersProfile OR
	 
	 2. the lsTimersProfilePointer would reference an instance which 
	    does not exist If the name package is supported: a create 
	    request with a value for the name attribute that is already 
	    used by another instance of the same object class will be 
	    rejected.
	 
	 If it is tried to delete a signLinkSetTp, which is referenced 
	 by at least one signRouteNePart, the deletion of the 
	 signLinkSetTp is rejected and not carried out."
    REFERENCE
	"STD 58, SNMPv2-TC RowStatus.
	 ITU-T Rec. Q.751.1 (1997) : mtpSignPoint-signLinkSetTp NAME 
	     BINDING."
    ::= { mtpLsEntry 19 }


-- ====================================================================

mtpLsStatsTable OBJECT-TYPE
    SYNTAX SEQUENCE OF MtpLsStatsEntry
    MAX-ACCESS not-accessible
    STATUS current
    DESCRIPTION
	"This table provides link set statistics."
    REFERENCE
	"ITU-T Rec. Q.752, ANSI T1.116.2"
    ::= { mtpLs 3 }

mtpLsStatsEntry OBJECT-TYPE
    SYNTAX MtpLsStatsEntry
    MAX-ACCESS not-accessible
    STATUS current
    DESCRIPTION
	"This provides the table entry for link set statistics."
    REFERENCE
	"ITU-T Rec. Q.752, ANSI T1.116.2"
    AUGMENTS    { mtpLsEntry }
    ::= { mtpLsStatsTable 1 }

MtpLsStatsEntry ::= SEQUENCE {
    mtpLsStatsStatus				RowStatus
}

mtpLsStatsStatus OBJECT-TYPE
    SYNTAX RowStatus
    MAX-ACCESS read-create
    STATUS current
    DESCRIPTION
	""
    ::= { mtpLsStatsEntry 1 }


-- ====================================================================

mtpLsCurrentTable OBJECT-TYPE
    SYNTAX SEQUENCE OF MtpLsCurrentEntry
    MAX-ACCESS not-accessible
    STATUS current
    DESCRIPTION
	""
    ::= { mtpLs 4 }

mtpLsCurrentEntry OBJECT-TYPE
    SYNTAX MtpLsCurrentEntry
    MAX-ACCESS not-accessible
    STATUS current
    DESCRIPTION
	""
    INDEX {
	mtpLsId	-- shared index
    }
    ::= { mtpLsCurrentTable 1 }

MtpLsCurrentEntry ::= SEQUENCE {
    mtpLsCurrentValidIntervals			HCPerfValidIntervals,
    mtpLsCurrentTimeDiscontinuity		TimeStamp,
    mtpLsCurrentAdjacentInaccessibleEvents	PerfCurrentCount, -- Q.752, 5.1
    mtpLsCurrentAdjacentInaccessibleDuration	PerfCurrentCount, -- Q.752, 5.2
    mtpLsCurrentSlsUnavailable			PerfCurrentCount, -- Q.752, 4.2
}

mtpLsCurrentValidIntervals OBJECT-TYPE
    SYNTAX HCPerfValidIntervals
    MAX-ACCESS read-create
    STATUS current
    DESCRIPTION
	""
    ::= { mtpLsCurrentEntry 1 }

mtpLsCurrentTimeDiscontinuity OBJECT-TYPE
    SYNTAX TimeStamp
    MAX-ACCESS read-create
    STATUS current
    DESCRIPTION
	""
    ::= { mtpLsCurrentEntry 2 }

mtpLsCurrentAdjacentInaccessibleEvents OBJECT-TYPE
    SYNTAX PerfCurrentCount
    UNITS "events"
    MAX-ACCESS read-create
    STATUS current
    DESCRIPTION
	""
    REFERENCE
	"ITU-T Rec. Q.751.1 (10/95) : adjacentInaccessibleEvents.
	 ITU-T Rec. Q.752 (1997) : Table 5/Q.752, 5.1."
    ::= { mtpLsCurrentEntry 3 }

mtpLsCurrentAdjacentInaccessibleDuration OBJECT-TYPE
    SYNTAX PerfCurrentCount
    UNITS "seconds"
    MAX-ACCESS read-create
    STATUS current
    DESCRIPTION
	""
    REFERENCE
	"ITU-T Rec. Q.751.1 (10/95) : adjacentInacessibleDuration.
	 ITU-T Rec. Q.752 (1997) : Table 5/Q.752, 5.2."
    ::= { mtpLsCurrentEntry 4 }

mtpLsCurrentSlsUnavailable OBJECT-TYPE
    SYNTAX PerfCurrentCount
    MAX-ACCESS read-create
    STATUS current
    DESCRIPTION
	""
    REFERENCE
	"ITU-T Rec. Q.751.1, (10/95) : slsUnavailable.
	 ITU-T Rec. Q.752, (1997) : Table 3/Q.752 4.2"
    ::= { mtpLsCurrentEntry 5 }



-- ====================================================================

mtpLsInt5minTable OBJECT-TYPE
    SYNTAX SEQUENCE OF MtpLsInt5minEntry
    MAX-ACCESS not-accessible
    STATUS current
    DESCRIPTION
	""
    ::= { mtpLs 5 }

mtpLsInt5minEntry OBJECT-TYPE
    SYNTAX MtpLsInt5minEntry
    MAX-ACCESS not-accessible
    STATUS current
    DESCRIPTION
	""
    INDEX {
	mtpLsId,	-- shared index
	mtpLsInt5minInterval
    }
    ::= { mtpLsInt5minTable 1 }

MtpLsInt5minEntry ::= SEQUENCE {
    mtpLsInt5minInterval			Unsigned32,
    mtpLsInt5minTimeStamp			TimeStamp,
    mtpLsInt5minAdjacentInaccessibleEvents	PerfIntervalCount, -- Q.752, 5.1
    mtpLsInt5minAdjacentInaccessibleDuration	PerfIntervalCount, -- Q.752, 5.2
    mtpLsInt5minSlsUnavailable			PerfIntervalCount  -- Q.752, 4.2
}

mtpLsInt5minInterval OBJECT-TYPE
    SYNTAX Unsigned32
    MAX-ACCESS not-accessible
    STATUS current
    DESCRIPTION
	""
    ::= { mtpLsInt5minEntry 1 }

mtpLsInt5minTimeStamp OBJECT-TYPE
    SYNTAX TimeStamp
    MAX-ACCESS read-only
    STATUS current
    DESCRIPTION
	""
    ::= { mtpLsInt5minEntry 2 }

mtpLsInt5minAdjacentInaccessibleEvents OBJECT-TYPE
    SYNTAX PerfIntervalCount
    UNITS "events"
    MAX-ACCESS read-only
    STATUS current
    DESCRIPTION
	""
    REFERENCE
	"ITU-T Rec. Q.751.1 (10/95) : adjacentInaccessibleEvents.
	 ITU-T Rec. Q.752 (1997) : Table 5/Q.752, 5.1."
    ::= { mtpLsInt5minEntry 3 }

mtpLsInt5minAdjacentInaccessibleDuration OBJECT-TYPE
    SYNTAX PerfIntervalCount
    UNITS "seconds"
    MAX-ACCESS read-only
    STATUS current
    DESCRIPTION
	""
    REFERENCE
	"ITU-T Rec. Q.751.1 (10/95) : adjacentInacessibleDuration.
	 ITU-T Rec. Q.752 (1997) : Table 5/Q.752, 5.2."
    ::= { mtpLsInt5minEntry 4 }

mtpLsInt5minSlsUnavailable OBJECT-TYPE
    SYNTAX PerfIntervalCount
    MAX-ACCESS read-only
    STATUS current
    DESCRIPTION
	""
    REFERENCE
	"ITU-T Rec. Q.751.1, (10/95) : slsUnavailable.
	 ITU-T Rec. Q.752, (1997) : Table 3/Q.752 4.2"
    ::= { mtpLsInt5minEntry 5 }

-- ====================================================================

mtpLsInt15minTable OBJECT-TYPE
    SYNTAX SEQUENCE OF MtpLsInt15minEntry
    MAX-ACCESS not-accessible
    STATUS current
    DESCRIPTION
	""
    ::= { mtpLs 6 }

mtpLsInt15minEntry OBJECT-TYPE
    SYNTAX MtpLsInt15minEntry
    MAX-ACCESS not-accessible
    STATUS current
    DESCRIPTION
	""
    INDEX {
	mtpLsId,	-- shared index
	mtpLsInt15minInterval
    }
    ::= { mtpLsInt15minTable 1 }


MtpLsInt15minEntry ::= SEQUENCE {
    mtpLsInt15minInterval			Unsigned32,
    mtpLsInt15minTimeStamp			TimeStamp,
    mtpLsInt15minAdjacentInaccessibleEvents	PerfIntervalCount, -- Q.752, 5.1
    mtpLsInt15minAdjacentInaccessibleDuration	PerfIntervalCount, -- Q.752, 5.2
    mtpLsInt15minSlsUnavailable			PerfIntervalCount  -- Q.752, 4.2
}

mtpLsInt15minInterval OBJECT-TYPE
    SYNTAX Unsigned32
    MAX-ACCESS not-accessible
    STATUS current
    DESCRIPTION
	""
    ::= { mtpLsInt15minEntry 1 }

mtpLsInt15minTimeStamp OBJECT-TYPE
    SYNTAX TimeStamp
    MAX-ACCESS read-only
    STATUS current
    DESCRIPTION
	""
    ::= { mtpLsInt15minEntry 2 }

mtpLsInt15minAdjacentInaccessibleEvents OBJECT-TYPE
    SYNTAX PerfIntervalCount
    UNITS "events"
    MAX-ACCESS read-only
    STATUS current
    DESCRIPTION
	""
    REFERENCE
	"ITU-T Rec. Q.751.1 (10/95) : adjacentInaccessibleEvents.
	 ITU-T Rec. Q.752 (1997) : Table 5/Q.752, 5.1."
    ::= { mtpLsInt15minEntry 3 }

mtpLsInt15minAdjacentInaccessibleDuration OBJECT-TYPE
    SYNTAX PerfIntervalCount
    UNITS "seconds"
    MAX-ACCESS read-only
    STATUS current
    DESCRIPTION
	""
    REFERENCE
	"ITU-T Rec. Q.751.1 (10/95) : adjacentInacessibleDuration.
	 ITU-T Rec. Q.752 (1997) : Table 5/Q.752, 5.2."
    ::= { mtpLsInt15minEntry 4 }

mtpLsInt15minSlsUnavailable OBJECT-TYPE
    SYNTAX PerfIntervalCount
    MAX-ACCESS read-only
    STATUS current
    DESCRIPTION
	""
    REFERENCE
	"ITU-T Rec. Q.751.1, (10/95) : slsUnavailable.
	 ITU-T Rec. Q.752, (1997) : Table 3/Q.752 4.2"
    ::= { mtpLsInt15minEntry 5 }

-- ====================================================================

mtpSlL3ProfileTable OBJECT-TYPE
    SYNTAX SEQUENCE OF MtpSlL3ProfileEntry
    MAX-ACCESS not-accessible
    STATUS current
    DESCRIPTION
	"Provides an MTP Level 3 protocol profile for signalling links.
	 
	 A signalling link timer profile is a set of Q.704 timers which 
	 are related to the characteristics of Signalling Links.  The 
	 managed object class slTimersProfile is a support managed 
	 object class which can be instantiated in order to define a 
	 particular profile.  At creation time of a signLinkTp one of 
	 the slTimersProfiles may be referenced."
    REFERENCE
	"ITU-T Rec. Q.751.1 (1997), ANSI T1.116.1 (2000), 
	 slTimersProfile MOC."
    ::= { mtpSl 1 }

mtpSlL3ProfileEntry OBJECT-TYPE
    SYNTAX MtpSlL3ProfileEntry
    MAX-ACCESS not-accessible
    STATUS current
    DESCRIPTION
	"Each entry in the table provides a single MTP Level 3 
	 signalling link protocol profile."
    REFERENCE
	"ITU-T Rec. Q.751.1 (1997), ANSI T1.116.1 (2000), 
	 slTimersProfile MO."
    INDEX {
	mtpSlL3ProfileId
    }
    ::= { mtpSlL3ProfileTable 1 }

MtpSlL3ProfileEntry ::= SEQUENCE {
    mtpSlL3ProfileId				SimpleNameType,
    mtpSlL3ProfileTimerT1			TimeInterval,
    mtpSlL3ProfileTimerT3			TimeInterval,
    mtpSlL3ProfileTimerT17			TimeInterval,
    mtpSlL3ProfileTimerT24I			TimeInterval,
    mtpSlL3ProfileName				SimpleNameType,
    mtpSlL3ProfileTimerT2			TimeInterval,
    mtpSlL3ProfileTimerT4			TimeInterval,
    mtpSlL3ProfileTimerT5			TimeInterval,
    mtpSlL3ProfileTimerT12			TimeInterval,
    mtpSlL3ProfileTimerT13			TimeInterval,
    mtpSlL3ProfileTimerT14			TimeInterval,
    mtpSlL3ProfileTimerT19A			TimeInterval,
    mtpSlL3ProfileTimerT20A			TimeInterval,
    mtpSlL3ProfileTimerT21A			TimeInterval,
    mtpSlL3ProfileTimerT22I			TimeInterval,
    mtpSlL3ProfileTimerT23I			TimeInterval,
    mtpSlL3ProfileTimerT31A			TimeInterval,
    mtpSlL3ProfileTimerT32A			TimeInterval,
    mtpSlL3ProfileTimerT33A			TimeInterval,
    mtpSlL3ProfileTimerT34A			TimeInterval,
    mtpSlL3ProfileTimerT1T			TimeInterval,
    mtpSlL3ProfileTimerT2T			TimeInterval,
    mtpSlL3ProfileTimerT1S			TimeInterval,
    mtpSlL3ProfileL2Default			SimpleNameType,
    mtpSlL3ProfileRowStatus			RowStatus
}

mtpSlL3ProfileId OBJECT-TYPE
    SYNTAX SimpleNameType
    MAX-ACCESS not-accessible
    STATUS current
    DESCRIPTION
	"Provides an index into the signalling link MTP Level 3 profile 
	 table.  Rows in this table can be referred to using this index 
	 or using the RowPointer pointer.  The index valud zero (0) has 
	 special semantics: the zero index contains default default 
	 values.
	 
	 Provides a naming attribute for the MTP L3 signalling link 
	 protocol profile table.  This attribute is used for naming 
	 instances."
    REFERENCE
	"ITU-T Rec. Q.751.1 (1997), ANSI T1.116.1 (2000), 
	     slTimersProfileId attribute."
    ::= { mtpSlL3ProfileEntry 1 }

mtpSlL3ProfileTimerT1 OBJECT-TYPE
    SYNTAX TimeInterval
    UNITS "centiseconds"
    MAX-ACCESS read-create
    STATUS current
    DESCRIPTION
	"This attribute defines the initial timer value of timer T1 
	 'Delay to avoid message mis-sequencing on changeover from this 
	 link' defined in Recommendation Q.704.  The value range is from 
	 500 to 1200ms.  For routes with long propagation delays a 
	 minimum value of 800 ms is used.  The same value applies for 
	 all links associated with an instance of the procedure."
    REFERENCE
	"ITU-T Rec. Q.751.1 (1997), ANSI T1.116.1 (2000), q704-t1 
	 attribute."
    ::= { mtpSlL3ProfileEntry 2 }

mtpSlL3ProfileTimerT3 OBJECT-TYPE
    SYNTAX TimeInterval
    UNITS "centiseconds"
    MAX-ACCESS read-create
    STATUS current
    DESCRIPTION
	"This attribute defines the initial timer value of timer T3 
	 'Time controlled diversion-delay to avoid mis-sequencing on 
	 changeback from this link' defined in Recommendation Q.704.  
	 The value range is from 500 to 1200 ms.  For routes with long 
	 propagation delays a minimum value of 800 ms is used.  The 
	 value of this attribute is network implementation dependent.
	 
	 6.2.5  If the signalling point at the far end of the link made 
	   available currently is inaccessible, from the signalling 
	   point initiating changeback (see clause 9 on MTP Restart), 
	   the sequence control procedure specified in 6.3 (which 
	   requires communication between the two concerned signalling 
	   points) does not apply; instead, the time-controlled 
	   diversion specified in 6.4 is performed.  This is made also 
	   when the concerned signalling points are accessible, but 
	   there is no signalling route to it using the same outgoing 
	   signalling link(s) (or one of the same signalling links) from 
	   which traffic will be diverted.
	 
	 6.4.1  The timer-controlled diversion procedure is used at the 
	   end of the MTP restart procedure (see clause 9) when an 
	   adjacent signalling point becomes available, as well as for 
	   the reasons given in 6.2.5.  ...
	 
	 6.4.2  When changeback is initiated after the MTP restart 
	   procedure, the adjacent signalling point of the point whose 
	   MTP is restarting stops traffic to be directed from the 
	   alternative signalling link(s) for a time T3, after which it 
	   starts traffic on the signalling link(s) made available.  The 
	   time delay minimizes the probability of out-of-sequence 
	   delivery to the destination point(s)."
    REFERENCE
	"ITU-T Rec. Q.751.1 (1997), ANSI T1.116.1 (2000), q704-t3 
	 attribute."
    ::= { mtpSlL3ProfileEntry 3 }

mtpSlL3ProfileTimerT17 OBJECT-TYPE
    SYNTAX TimeInterval
    UNITS "centiseconds"
    MAX-ACCESS read-create
    STATUS current
    DESCRIPTION
	"This attribute defines the initial timer value of timer T17 
	 Delay to avoid oscillation of initial alignment failure and 
	 link restart defined in Recommendation Q.704.  The value range 
	 is from 800 to 1500 ms.  The value should be less than the 
	 corresponding timer T2 in 12.2.1.2/Q.703.
	 
	 This value and procedure are in effect when the signalling link 
	 is set for neither link oscillation procedure A nor link 
	 osciallation procedure B.
	 
	 12.2.1.2    When a decision is taken to activate an inactive 
	    signalling link; initial alignment starts.  If the initial 
	    alignment procedure is successful, the signalling link is 
	    active and a signalling link test is started.  If the 
	    signalling link test is successful the link becomes ready to 
	    convey signalling traffic.  In the case when initial 
	    alignment is not possible, as determined at Message Transfer 
	    Part level 2 (see clause 7/Q.703), new initial alignment 
	    procedures are started on the same signalling link after a 
	    timer T17 (delay to avoid the oscillation of initial 
	    alignment failure and link restart.  The value of T17 should 
	    be greater than the loop delay and less than timer T2, see 
	    7.3/Q.703).  If the signalling link test fails, link 
	    restoration starts until the signalling link is activated or 
	    a manual intervention is made.
	 
	 12.2.2  Signalling link restoration
	 
	    After a signalling link failure is detected, signalling link 
	    initial alignment will take place.  In the case when the 
	    initial alignment procedure is successful, a signalling link 
	    test is started.  If the signalling link test is successful 
	    the link becomes restored and thus available for signalling.
	 
	    If the initial alignment is not possible, as determined at 
	    Message Transfer Part level 2 (see clause 7/Q.703), new 
	    initial alignment procedures may be started on the same 
	    signalling link after a time T17 until the signalling link 
	    is restored or a manual intervention is made, e.g. to 
	    replace the signalling data link or the signalling terminal.
	 
	    If the signalling link test fails, the restoration procedure 
	    is repeated until the link is restored or a manual 
	    intervention is made."
    REFERENCE
	"ITU-T Rec. Q.751.1 (1997), ANSI T1.116.1 (2000), q704-t17 
	 attribute."
    ::= { mtpSlL3ProfileEntry 4 }

mtpSlL3ProfileTimerT24I OBJECT-TYPE
    SYNTAX TimeInterval
    UNITS "centiseconds"
    MAX-ACCESS read-create
    STATUS current
    DESCRIPTION
	"This attribute defines the initial timer value of timer T24 
	 Stabilising timer after removal of local processor outage, used 
	 in LPO latching to RPO (national option) defined in 
	 Recommendation Q.704.  The value is 500 ms (provisional value).
	 
	 Q.704/3.3.5.1 Signalling traffic management: as specified in 
	     3.3.1.1.  (See SL_OUT_OF_SERVICE_IND).
	 
	     As a national option, local processor outage may also be 
	     applied to the affected signalling link before commencement 
	     of the appropriate signalling traffic management option.  
	     On completion of that signalling traffic management action, 
	     local processor outage is removed from the affected 
	     signalling link.  No further signalling traffic management 
	     will be performed on that affected signalling link until a 
	     timer T24 (see 16.8) has expired or been cancelled, thus 
	     allowing time for indications from the remote end to 
	     stabilize as it carries out any signalling traffic 
	     management of its own."
    REFERENCE
	"ITU-T Rec. Q.751.1 (1997), ANSI T1.116.1 (2000), q704-t24 
	 attribute."
    DEFVAL { 50 }
    ::= { mtpSlL3ProfileEntry 5 }

mtpSlL3ProfileName OBJECT-TYPE
    SYNTAX SimpleNameType
    MAX-ACCESS read-create
    STATUS current
    DESCRIPTION
	"Provides an optional administrative name for this signalling 
	 link MTP Level 3 profile.
	-
	 This attribute is an additional name for instances of the 
	 slTimersProfile managed object class."
    REFERENCE
	"ITU-T Rec. Q.751.1 (1997), ANSI T1.116.1 (2000), 
	     slTimersProfileName attribute."
    ::= { mtpSlL3ProfileEntry 6 }

mtpSlL3ProfileTimerT2 OBJECT-TYPE
    SYNTAX TimeInterval
    UNITS "centiseconds"
    MAX-ACCESS read-create
    STATUS current
    DESCRIPTION
	"This attribute defines the initial timer value of timer T2 
	 'Waiting for changeover acknowledgement' defined in 
	 Recommendation Q.704.  The value range is from 700 to 2000 ms.  
	 For routes with long propagation delays a minimum value of 1400 
	 ms is used.
	 
	 5.7.2  If no changeover message in response to a changeover 
	   order is received within a timer T2 (see 16.8), new traffic 
	   is started on the alternative signalling link(s).
	 
	 IMPLEMENTATION NOTE: There is a problem here.  We cannot check 
	 the link for congestion when transferring the buffer.  If we a 
	 transferring a very large changeover buffer (up to 2 seconds 
	 worth of messages at 1 Erlang) we could congest the new link 
	 leading to a cascading failure.  Section 5.7.2 above, does not 
	 say to transfer the buffer on T2 expiry.  Instead it says to 
	 start 'new traffic' on the alternative signalling link(s).  
	 Taking this literally, we will flush the buffer and start new 
	 traffic only."
    REFERENCE
	"ITU-T Rec. Q.751.1 (1997), ANSI T1.116.1 (2000), q704-t2 
	 attribute."
    ::= { mtpSlL3ProfileEntry 7 }

mtpSlL3ProfileTimerT4 OBJECT-TYPE
    SYNTAX TimeInterval
    UNITS "centiseconds"
    MAX-ACCESS read-create
    STATUS current
    DESCRIPTION
	"This attribute defines the initial timer value of timer T4 
	 'Waiting for changeback acknowledgement (first attempt)' 
	 defined in Recommendation Q.704.  The value range is from 500 
	 to 1200 ms.  For routes with long propagation delays a minimum 
	 value of 800 ms is used.
	 
	 6.5.3   If no changeback-acknowledgement is received in 
	   response to a changeback declaration within a timer T4, the 
	   changeback declaration is repeated and a new timer T5 is 
	   started.  If no changeback acknowledgement is received before 
	   the expiry of T5, the maintenance functions are alerted and 
	   traffic on the link made available is started.  The 
	   changeback code contained in the changeback-acknowledgement 
	   message makes it possible to determine, in the case of 
	   parallel changebacks, from more than one reserve path, which 
	   changeback-declaration is unacknowledged and has therefore to 
	   be repeated."
    REFERENCE
	"ITU-T Rec. Q.751.1 (1997), ANSI T1.116.1 (2000), q704-t4 
	 attribute."
    ::= { mtpSlL3ProfileEntry 8 }

mtpSlL3ProfileTimerT5 OBJECT-TYPE
    SYNTAX TimeInterval
    UNITS "centiseconds"
    MAX-ACCESS read-create
    STATUS current
    DESCRIPTION
	"This attribute defines the initial timer value of timer T5 
	 Waiting for changeback acknowledgement (second attempt) defined 
	 in Recommendation Q.704.  The value range is from 500 to 1200 
	 ms.  For routes with long propagation delays a minimum value of 
	 800 ms is used."
    REFERENCE
	"ITU-T Rec. Q.751.1 (1997), ANSI T1.116.1 (2000), q704-t5 
	 attribute."
    ::= { mtpSlL3ProfileEntry 9 }

mtpSlL3ProfileTimerT12 OBJECT-TYPE
    SYNTAX TimeInterval
    UNITS "centiseconds"
    MAX-ACCESS read-create
    STATUS current
    DESCRIPTION
	"This attribute defines the initial timer value of timer T12 
	 Waiting for uninhibit acknowledgement defined in Recommendation 
	 Q.704.  The value range is from 800 to 1500 ms.
	 
	 Q.704/1996 10.2
	 
	 g) If, for any reason, the inhibit acknowledgement message is 
	 not received, a timer T14 expires and the procedure is 
	 restarted including inspection of the status of the destination 
	 of the inhibit message.  If the destination is not available, 
	 management is informed.
	 
	 At most two consecutive automatic attempts may be made to 
	 inhibit a particular signalling link."
    REFERENCE
	"ITU-T Rec. Q.751.1 (1997), ANSI T1.116.1 (2000), q704-t12 
	 attribute."
    ::= { mtpSlL3ProfileEntry 10 }

mtpSlL3ProfileTimerT13 OBJECT-TYPE
    SYNTAX TimeInterval
    UNITS "centiseconds"
    MAX-ACCESS read-create
    STATUS current
    DESCRIPTION
	"This attribute defines the initial timer value of timer T13 
	 Waiting for force uninhibit defined in Recommendation Q.704.  
	 The value range is from 800 to 
	 1500 ms.
	 
	 Q.704/1996 10.3.2 (Signalling routing control initiated 
	 uninhibiting)
	 
	 e) If for any reason, an uninhibit signalling link message is 
	    not received in response to the force uninhibit message, a 
	    timer T13 expires.  If this is the first expiry of T13 for 
	    this uninhibition attempt on this link, the procedure is 
	    restarted including inspection of the status of the 
	    inhibited link.  If the link is marked failed or blocked, or 
	    timer T13 has expired for the second time during 
	    uninhibition of this link, management is informed and the 
	    uninhibition is abandoned.
	 
	 f) If an attempt to uninhibit a signalling link is abandoned, 
	    signalling routing control attempts to uninhibit the next 
	    inhibited link to signalling point Y, starting from a) 
	    above.  The search continues until either a link is 
	    sucessfully uninhibited or all possible links to Y in the 
	    routing table have been exhausted, or the destination has 
	    become available for other reasons."
    REFERENCE
	"ITU-T Rec. Q.751.1 (1997), ANSI T1.116.1 (2000), q704-t13 
	     attribute."
    ::= { mtpSlL3ProfileEntry 11 }

mtpSlL3ProfileTimerT14 OBJECT-TYPE
    SYNTAX TimeInterval
    UNITS "centiseconds"
    MAX-ACCESS read-create
    STATUS current
    DESCRIPTION
	"This attribute defines the initial timer value of timer T14 
	 Waiting for inhibition acknowledgement defined in 
	 Recommendation Q.704.  The value range is from 2 to 3 seconds.
	 
	 Q.704/1996 10.2
	 
	 g) If, for any reason, the inihibit acknowledgement message is 
	    not received, a timer T14 epires and the procedure is 
	    restarted including inspection of the status of the 
	    destination of the inhibit mesage.  If the destination is 
	    not available, management is informed.
	 
	 At most two consecutive atuomatic attempts may be made to 
	 inhibit a particular signalling link."
    REFERENCE
	"ITU-T Rec. Q.751.1 (1997), ANSI T1.116.1 (2000), q704-t14 
	 attribute."
    ::= { mtpSlL3ProfileEntry 12 }

mtpSlL3ProfileTimerT19A OBJECT-TYPE
    SYNTAX TimeInterval
    UNITS "centiseconds"
    MAX-ACCESS read-create
    STATUS current
    DESCRIPTION
	"This attribute defines the initial timer value of timer T19 
	 (ANSI) link maintenance timer defined in ANSI T1.111.4.  This 
	 timer is of local significance only and is equally applicable 
	 to ITU-T signalling links.
	 
	 ANSI T1.111.4 (1996 and 2000) 12.2.2: After a signalling link 
	     failure is detected, signalling link initial alignment will 
	     take place.  When the initial alignment procedure is 
	     successful, a signalling link test is started.  If the 
	     isgnalling link test is successful, the signalling link is 
	     regarded as restored and thus available for signalling.  If 
	     initial alignment is not possible, as determined at level 2 
	     (see Section 7 of Chapter T1.111.3 or Section 6.2.2 of 
	     T1.645), new initial alignment procedures may be started on 
	     the same signalling link after a timer T17 until the 
	     signalling link is restored or a manual intervention is 
	     made, e.g., to replace the signalling data link or the 
	     signalling terminal.  If after time T19 the signalling link 
	     is not activated, a management function is notified, and, 
	     optionally, T19 may be restarted."
    REFERENCE
	"ANSI T1.111.4 Section 12.2.2."
    ::= { mtpSlL3ProfileEntry 13 }

mtpSlL3ProfileTimerT20A OBJECT-TYPE
    SYNTAX TimeInterval (9000..12000)
    UNITS "centiseconds"
    MAX-ACCESS read-create
    STATUS current
    DESCRIPTION
	"This attribute defines the initial timer value of timer T20 
	 (ANSI) local inihibit test timer defined in ANSI T1.111.4 
	 10.3A.  The value range is from 90 to 120 seconds (1.5 to 2 
	 minutes).
	 
	 Note that timer T20(ANSI) is equivalent to timer T22(ITU-T) in 
	 function but has a range from 1.5 to 2.0 minutes instead of 3 
	 to 6 minutes.
	 
	 This timer value and associated procedure is appliable only to 
	 ANSI based protocol variants.
	 
	 ANSI T1.111.4/2000 10.3A (Inhibit Test Procedure Actions).  
	     When a signalling link becomes inibited, either locally, 
	     remotely or both, the following test procedure actions take 
	     place, as appropriate:
	 
	     1. If timer T20 expires at signalling point X and the 
		signalling link is locally inhibited at signalling point 
		X, signalling point X transmits a local inhibit test 
		message to the signalling point at the other end of the 
		locally inhibited link and restarts timer T20.
	 
	     2. If timer T20 expires at signalling point X and the 
		signalling link is no longer locally inhibited, no 
		action is taken.
	 
	     3. If timer T21 expires at signalling point X and the 
		signalling link is remotely inhibtied at signalling 
		point X, signalling point X transmits a remote inhibit 
		teset message to the signalling point at the other end 
		of the remotely inhibited link and restarts timer T21.
	     
	     4. If timer T21 expires at signalling point X and the 
		signalling link is no longer remotely inihibited, no 
		action is taken.
	     
	     5. If signalling point Y receives a local inhibit test 
		message from signalling point X and the concerned link 
		is marked remotely inhibited, no action is taken.
	     
	     6. If signalling point Y receoves a local inhibit test 
		message from signalling point X and the concerned link 
		is not marked remotely inhibited, the forced 
		uninhibiting procedure is invoked at signalling point Y, 
		beginning with the transmission of a force uninhibit 
		signalling link message to signalling point X.  As a 
		result of this procedure, the local inhibit indicator is 
		canceled at signalling point X.
	     
	     7. If signalling point Y receives a remote inhibit test 
		message from signalling point X and the concerned link 
		is marked locally inhibited, no action is taken.
	     
	     8. If signalling point Y receives a remote inhibit test 
		message from signalling point X and the concerned 
		signalling link is not marked locally inhibited, the 
		uninhibiting procedure is invoked at signalling point Y, 
		beginning with the transmission of an uninhibit 
		signalling link message to signalling point X.  As a 
		result of this procedure, the remote inhibit indicator 
		is canceled at signalling point X.
	 
	 Note: ANSI Timer T20 is simply ITU-T Timer T22 renumbered."
    DEFVAL { 10000 }
    ::= { mtpSlL3ProfileEntry 14 }

mtpSlL3ProfileTimerT21A OBJECT-TYPE
    SYNTAX TimeInterval (9000..12000)
    UNITS "centiseconds"
    MAX-ACCESS read-create
    STATUS current
    DESCRIPTION
	"This attribute defines the initial timer value of timer T21 
	 (ANSI) remote inhibit test timer defined in ANSI T1.111.4 
	 10.3A.  The value range is from 90 to 120 seconds (1.5 to 2 
	 minutes).
	 
	 Note that timer T21(ANSI) is equivalent to timer T23(ITU-T) in 
	 function but has a range from 1.5 to 2.0 minutes instead of 3 
	 to 6 minutes.
	 
	 This timer value and associated procedure is appliable only to 
	 ANSI based protocol variants.
	 
	 ANSI T1.111.4/2000 10.3A (Inhibit Test Procedure Actions).  
	     When a signalling link becomes inibited, either locally, 
	     remotely or both, the following test procedure actions take 
	     place, as appropriate:
	     
	     1. If timer T20 expires at signalling point X and the 
		signalling link is locally inhibited at signalling point 
		X, signalling point X transmits a local inhibit test 
		message to the signalling point at the other end of the 
		locally inhibited link and restarts timer T20.
	     
	     2. If timer T20 expires at signalling point X and the 
		signalling link is no longer locally inhibited, no 
		action is taken.
	     
	     3. If timer T21 expires at signalling point X and the 
		signalling link is remotely inhibtied at signalling 
		point X, signalling point X transmits a remote inhibit 
		teset message to the signalling point at the other end 
		of the remotely inhibited link and restarts timer T21.
	     
	     4. If timer T21 expires at signalling point X and the 
		signalling link is no longer remotely inihibited, no 
		action is taken.
	     
	     5. If signalling point Y receives a local inhibit test 
		message from signalling point X and the concerned link 
		is marked remotely inhibited, no action is taken.
	     
	     6. If signalling point Y receoves a local inhibit test 
		message from signalling point X and the concerned link 
		is not marked remotely inhibited, the forced 
		uninhibiting procedure is invoked at signalling point Y, 
		beginning with the transmission of a force uninhibit 
		signalling link message to signalling point X.  As a 
		result of this procedure, the local inhibit indicator is 
		canceled at signalling point X.
	     
	     7. If signalling point Y receives a remote inhibit test 
		message from signalling point X and the concerned link 
		is marked locally inhibited, no action is taken.
	     
	     8. If signalling point Y receives a remote inhibit test 
		message from signalling point X and the concerned 
		signalling link is not marked locally inhibited, the 
		uninhibiting procedure is invoked at signalling point Y, 
		beginning with the transmission of an uninhibit 
		signalling link message to signalling point X.  As a 
		result of this procedure, the remote inhibit indicator 
		is canceled at signalling point X.
	 
	 Note: ANSI Timer T21 is simply ITU-T Timer T23 renumbered."
    DEFVAL { 10000 }
    ::= { mtpSlL3ProfileEntry 15 }

mtpSlL3ProfileTimerT22I OBJECT-TYPE
    SYNTAX TimeInterval (18000..36000)
    UNITS "centiseconds"
    MAX-ACCESS read-create
    STATUS current
    DESCRIPTION
	"This attribute defines the initial timer value of timer T22 
	 Local inhibit test timer defined in Recommendation Q.704.  The 
	 value range is from 3 to 6 minutes (provisional value).
	 
	 Q.704/1996 10.6 (Inihibit test procedure)  When a signalling 
	     link becomes mangaement inhibited, periodic tests are 
	     started to guard the inhibition status at each end of the 
	     link.
	 
	 10.6.1  A local inhibit test is performed when timer T22 
	    expires at signalling point X and the concerned link is 
	    marked locally inhibited.  In this case, a local inhibit 
	    test message is sent to the signalling point Y at the other 
	    end of the link, and timer T22 is restarted.
	 
	     Reception of a local inhibit test message causes:
	     
	     1. no action, if the concerned link is marked remotely 
		inhibited at the receiving signalling point Y; or
	     
	     2. the force unihibit proceudre to be invoked at the 
		receiving signalling point Y, if the concerned link is 
		not marked remotely inhibited at Y.  This procedure 
		causes the locally inhibited status of the link at X to 
		be cancelled.
	     
	     If a timer T22 expires and the concerned link is not 
	     locally inhibited, no further action is taken."
    REFERENCE
	"ITU-T Rec. Q.751.1 (1997), ANSI T1.116.1 (2000), q704-t22 
	 attribute."
    DEFVAL { 27000 }
    ::= { mtpSlL3ProfileEntry 16 }

mtpSlL3ProfileTimerT23I OBJECT-TYPE
    SYNTAX TimeInterval (18000..36000)
    UNITS "centiseconds"
    MAX-ACCESS read-create
    STATUS current
    DESCRIPTION
	"This attribute defines the initial timer value of timer T23 
	 Remote inhibit test timer defined in Recommendation Q.704.  The 
	 value range is from 3 to 6 minutes (provisional value).
	 
	 Q.704/1996 10.6 (Inhibit test procedure)  When a signalling 
	     link becomes management inhibited, periodic tests are 
	     started to guard the inhibition status at each end of the 
	     link.
	 
	 10.6.2  A remote inhibit test is performed when timer T23 
	    expires at signalling point Y and the concerned link is 
	    marked remotely inhibited.  In this case a remote inhibit 
	    test message is sent to signalling point X at the other end 
	    of the link, and timer T23 is restarted."
    REFERENCE
	"ITU-T Rec. Q.751.1 (1997), ANSI T1.116.1 (2000), q704-t23 
	 attribute."
    DEFVAL { 27000 }
    ::= { mtpSlL3ProfileEntry 17 }

mtpSlL3ProfileTimerT31A OBJECT-TYPE
    SYNTAX TimeInterval (1000..12000)
    UNITS "centiseconds"
    MAX-ACCESS read-create
    STATUS current
    DESCRIPTION
	"This attribute defines the initial timer value of timer T31 
	 (ANSI) false link congestion detection timer defined in ANSI 
	 T1.111.4 (2000) 3.8.2.2.  The value range is from 10 to 120 
	 seconds.
	 
	 Note that the procedure associated with T31 (ANSI) is a local 
	 matter and can equally be applied to ITU-T and ETSI signalling 
	 links.
	 
	 ANSI T1.111.4 (2000) 3.8.2.2.  ...  If the link remains at a 
	     congestion level, as defined below, for greater than T31 
	     [10] (a false link congestion condition), and it also 
	     remains in service, an audit should trigger the link to be 
	     restarted.  T31 is started when buffer occupancy increases 
	     through onset level 1.  Any change of congestion level 
	     [defined as a change of signalling link congestion status 
	     (see Section 3.8.2.1) and optionally including the first 
	     time the discard status is increased to n after signalling 
	     link congestion status is increased to  n (n=1, 2, 3)] 
	     restarts the timer.  T31 is stopped when the signalling 
	     link congestion status is zero.  The management should be 
	     notified if the link is restarted due to false link 
	     congestion."
    REFERENCE
	"ANSI T1.111.4 (2000) Section 3.8.2.2."
    DEFVAL { 6000 }
    ::= { mtpSlL3ProfileEntry 18 }

mtpSlL3ProfileTimerT32A OBJECT-TYPE
    SYNTAX TimeInterval (500..12000)
    UNITS "centiseconds"
    MAX-ACCESS read-create
    STATUS current
    DESCRIPTION
	"This attribute defines the initial timer value of timer T32 
	 (ANSI) link oscillation timer (Procedure A) defined in ANSI 
	 T1.111.4 (2000) 12.2.2.  The value range is from 5 to 120 
	 seconds.
	 
	 This timer value and procedure is in effect whenever the 
	 signalling link is set to use link oscillation procedure A.
	 
	 ANSI T1.111.4 (1996 and 2000) 12.2.2 ...  In order to [sic] 
	     prevent links from oscillating rapidly between the 
	     in-service and out-of-service states, a link oscillation 
	     filtering procedure shall be provided.  This procedure is 
	     applicable in all cases where automatic restoration and 
	     removal of signalling links to and from service is used.  
	     The procedure is not invoked if restoration to or removal 
	     from service is initiated manually.
	     
	     Link oscillation filtering is a local procedure.  One of 
	     the following procedures, A or B, is used.
	     
	     (A) When restoration begins, the oscillation timer T32 is 
	     started.  If the link fails within T32, the link is placed 
	     in the 'suspension' state until T32 expires.
	     
	     When a link exits in the 'suspension' state, link 
	     restoration is to be started and T32 is restarted.
	     
	     When a link is in 'suspension,' the link remains in the 
	     out-of-service state at level 2, restoration procedures to 
	     bring the link back into alignment are not invoked and 
	     realignment attempts initiated by the remote end are 
	     ignored.
	     
	     The oscillation timer T32 value chosen in a given 
	     signalling point may be modified by management action.  The 
	     expiration of the timer does not change the link status."
    DEFVAL { 6000 }
    ::= { mtpSlL3ProfileEntry 19 }

mtpSlL3ProfileTimerT33A OBJECT-TYPE
    SYNTAX TimeInterval (6000..60000)
    UNITS "centiseconds"
    MAX-ACCESS read-create
    STATUS current
    DESCRIPTION
	"This attribute defines the initial timer value of timer T33 
	 (ANSI) link oscillation probation timer (Procedure B) defined 
	 in ASNI T1.111.4 (2000) 12.2.2.  The value range is from 1 to 
	 10 minutes (60 to 600 seconds).
	 
	 This timer value and procedure is in effect whenever the 
	 signalling link is set to use link oscillation procedure B.
	 
	 ANSI T1.111.4 (1996 and 2000) 12.2.2 ...  In order to [sic] 
	     prevent links from oscillating rapidly between the 
	     in-service and out-of-service states, a link oscillation 
	     filtering procedure shall be provided.  This procedure is 
	     applicable in all cases where automatic restoration and 
	     removal of signalling links to and from service is used.  
	     The procedure is not invoked if restoration to or removal 
	     from service is initiated manually.
	     
	     Link oscillation filtering is a local procedure.  One of 
	     the following procedures, A or B, is used.
	     
	     (B) When activation or restoration of a signalling link has 
	     been completed, it is put on probation for a period 
	     controlled by timer T33 which starts running when the link 
	     enters the in-service state and is stopped either on 
	     time-out or on link failure.
	     
	     If a link fails during the probation, i.e. before 
	     expiration of timer T33, it is put on suspension.  While 
	     suspended the link remains in the out-of-service state at 
	     level 2, restoration procedures to bring the link back into 
	     alignment are not invoked and realignment attempts 
	     initiated by the remote end are ignored.
	     
	     The suspension time period is controlled by timer T34 which 
	     starts running when the link enters the out-of-service 
	     state.  Link restoration is resumed, on expiry of timer 
	     T34.
	     
	     The values chosen in a given network node for the probation 
	     and suspension time periods are dependent on the type and 
	     function of the node in the network and may be modified by 
	     management action."
    DEFVAL { 36000 }
    ::= { mtpSlL3ProfileEntry 20 }

mtpSlL3ProfileTimerT34A OBJECT-TYPE
    SYNTAX TimeInterval (500..12000)
    UNITS "centiseconds"
    MAX-ACCESS read-create
    STATUS current
    DESCRIPTION
	"This attribute defines the initial timer value of timer T34 
	 (ANSI) link oscillation suspension timer (Procedure B) defined 
	 in ANSI T1.111.4 (2000) 12.2.2.  The value range is from 5 to 
	 120 seconds.
	 
	 This timer value and procedure is in effect whenever the 
	 signalling link is set to use link oscillation procedure B.
	 
	 ANSI T1.111.4 (1996 and 2000) 12.2.2 ...  In order to [sic] 
	     prevent links from oscillating rapidly between the 
	     in-service and out-of-service states, a link oscillation 
	     filtering procedure shall be provided.  This procedure is 
	     applicable in all cases where automatic restoration and 
	     removal of signalling links to and from service is used.  
	     The procedure is not invoked if restoration to or removal 
	     from service is initiated manually.
	 
	     Link oscillation filtering is a local procedure.  One of 
	     the following procedures, A or B, is used.
	     
	     (B) When activation or restoration of a signalling link has 
	     been completed, it is put on probation for a period 
	     controlled by timer T33 which starts running when the link 
	     enters the in-service state and is stopped either on 
	     time-out or on link failure.
	     
	     If a link fails during the probation, i.e. before 
	     expiration of timer T33, it is put on suspension.  While 
	     suspended the link remains in the out-of-service state at 
	     level 2, restoration procedures to bring the link back into 
	     alignment are not invoked and realignment attempts 
	     initiated by the remote end are ignored.
	     
	     The suspension time period is controlled by timer T34 which 
	     starts running when the link enters the out-of-service 
	     state.  Link restoration is resumed, on expiry of timer 
	     T34.
	     
	     The values chosen in a given network node for the probation 
	     and suspension time periods are dependent on the type and 
	     function of the node in the network and may be modified by 
	     management action."
    DEFVAL { 6000 }
    ::= { mtpSlL3ProfileEntry 21 }

mtpSlL3ProfileTimerT1T OBJECT-TYPE
    SYNTAX TimeInterval
    UNITS "centiseconds"
    MAX-ACCESS read-create
    STATUS current
    DESCRIPTION
	"This attribute defines a timer value of timer T1 which is 
	 defined in Recommendation Q.707.
	 
	 Q.707 2.2 ...  In the case when the criteria given above are 
	 not met or a signalling link test acknowledgement message is 
	 not received on the link being tested within T1 (see 5.5) after 
	 the signalling link test message has been sent, the test is 
	 considered to have failed and is repeated once.  In the case 
	 when also the repeat test fails, the following actions have to 
	 be taken:
	 
	 - SLT applied on activation/restoration, the link is put out of 
	   service, restoration is attempted and a management system 
	   must be informed.
	 
	 - SLT applied periodically, for further study.
	 
	 IMPLEMENTATION NOTE:- The action when the periodic test fails 
	 is for further study.  Taking the link out of service can be an 
	 especially bad idea during times of congestion.  This is 
	 because the buffers may be filled with management messages 
	 already and the signalling link test might fail due to timeout.  
	 We merely report the information to management and leave the 
	 link in service.  If the test failed because of an inserted 
	 loop-back while the link is in service, the link will fail 
	 rapidly due to other causes.  So we do nothing more than report 
	 to management."
    REFERENCE
	"ITU-T Rec. Q.751.1 (1997), ANSI T1.116.1 (2000), q707-t1 
	     attribute."
    ::= { mtpSlL3ProfileEntry 22 }

mtpSlL3ProfileTimerT2T OBJECT-TYPE
    SYNTAX TimeInterval
    UNITS "centiseconds"
    MAX-ACCESS read-create
    STATUS current
    DESCRIPTION
	"This attribute defines a timer value of timer T2 which is 
	 defined in Recommendation Q.707.
	 
	 Q.707 2.2 ...  In the case the signalling link test (SLT) is 
	     applied while the signalling link is in service the 
	     signalling link test message is sent at regular intervals 
	     T2 (see 5.5).  The testing of a signalling link is 
	     performed independently from each end."
    REFERENCE
	"ITU-T Rec. Q.751.1 (1997), ANSI T1.116.1 (2000), q707-t2 
	     attribute."
    ::= { mtpSlL3ProfileEntry 23 }

mtpSlL3ProfileTimerT1S OBJECT-TYPE
    SYNTAX TimeInterval
    UNITS "centiseconds"
    MAX-ACCESS read-create
    STATUS current
    DESCRIPTION
	""
    ::= { mtpSlL3ProfileEntry 24 }

mtpSlL3ProfileL2Default OBJECT-TYPE
    SYNTAX SimpleNameType
    MAX-ACCESS read-create
    STATUS current
    DESCRIPTION
	"Specifies an entry in the mtpSlL2ProfileTable that provides the 
	 default mtpSlL2ProfileEntry for use during the creation of new 
	 signalling links using this profile."
    REFERENCE
	""
    ::= { mtpSlL3ProfileEntry 25 }

mtpSlL3ProfileRowStatus OBJECT-TYPE
    SYNTAX RowStatus
    MAX-ACCESS read-create
    STATUS current
    DESCRIPTION
	"Provide a mechanism whereby management stations may create and 
	 delete entries in this table.  All entries created by 
	 management survive an agent reboot.
	 
	 If the name package is supported: a create request with a value 
	 for the name attribute that is already used by another instance 
	 of the same object class will be rejected.  If an attempt is 
	 made to delete an slTimersProfile which is still referenced by 
	 a signLinkTp the delete request will be rejected."
    REFERENCE
	"STD 58, SNMPv2-TC RowStatus.
	 ITU-T Rec. Q.751.1 (1997) : 
	     managedSwitchingElement-slTimersProfile NAME BINDING."
    ::= { mtpSlL3ProfileEntry 26 }


-- ====================================================================

mtpSlL2ProfileTable OBJECT-TYPE
    SYNTAX SEQUENCE OF MtpSlL2ProfileEntry
    MAX-ACCESS not-accessible
    STATUS current
    DESCRIPTION
	"Provides the MTP signalling link level 2 protocol profile 
	 table.  This able contains MTP Level 2 protocol profiles for 
	 various transmission rates."
    REFERENCE
	"ITU-T Rec. Q.751.1 (1997), ANSI T1.116.1 (2000), 
	     mtpL2ProtocolProfile MOC."
    ::= { mtpSl 2 }

mtpSlL2ProfileEntry OBJECT-TYPE
    SYNTAX MtpSlL2ProfileEntry
    MAX-ACCESS not-accessible
    STATUS current
    DESCRIPTION
	"Provides the MTP signalling link level 2 protocol profile 
	 table entry.  Included in the entry is the transmission rate 
	 which is applicable to the entry as well as the settings of the 
	 various timer values and other fundamental protocol parameters.  
	 Each entry can be referred to by index or by RowPointer.  When 
	 a table refers to this one, the agent should ensure the 
	 consistency of MTP SL values with the transmission rate of the 
	 referencing table, and the MTP L3 protocol values associated 
	 with the referenceing table."
    REFERENCE
	"ITU-T Rec. Q.751.1 (1997), ANSI T1.116.1 (2000), 
	     mtpL2ProtocolProfile MO."
    INDEX {
	mtpSlL2ProfileId,
	mtpSlL2ProfileTransmissionRate
    }
    ::= { mtpSlL2ProfileTable 1 }

MtpSlL2ProfileEntry ::= SEQUENCE {
    mtpSlL2ProfileId				SimpleNameType,
    mtpSlL2ProfileErrorCorrectionMethod		INTEGER,
    mtpSlL2ProfileTransmissionRate		MtpTransmissionRate,
    mtpSlL2ProfileTimerT1			TimeInterval,
    mtpSlL2ProfileTimerT2			TimeInterval,
    mtpSlL2ProfileTimerT2L			TimeInterval,
    mtpSlL2ProfileTimerT2H			TimeInterval,
    mtpSlL2ProfileTimerT3			TimeInterval,
    mtpSlL2ProfileTimerT4N			TimeInterval,
    mtpSlL2ProfileTimerT4E			TimeInterval,
    mtpSlL2ProfileTimerT5			TimeInterval,
    mtpSlL2ProfileTimerT6			TimeInterval,
    mtpSlL2ProfileTimerT7			TimeInterval,
    mtpSlL2ProfileTbOnset1			Unsigned32,
    mtpSlL2ProfileTbAbate1			Unsigned32,
    mtpSlL2ProfileNumberOfThresholdLevels	Unsigned32,
    mtpSlL2ProfileCongestionCounting		INTEGER,
    mtpSlL2ProfileCongestionReportingBaseObject	INTEGER,
    mtpSlL2ProfileLoopDelay			Unsigned32,
    mtpSlL2ProfileName				SimpleNameType,
    mtpSlL2ProfileTbOnset2			Unsigned32,
    mtpSlL2ProfileTbAbate2			Unsigned32,
    mtpSlL2ProfileTbOnset3			Unsigned32,
    mtpSlL2ProfileTbAbate3			Unsigned32,
    mtpSlL2ProfileTbDiscard1			Unsigned32,
    mtpSlL2ProfileTbDiscard2			Unsigned32,
    mtpSlL2ProfileTbDiscard3			Unsigned32,
    mtpSlL2ProfileTimerTx			TimeInterval,
    mtpSlL2ProfileTimerTy			TimeInterval,
    mtpSlL2ProfileNumberOfCongestionStates	Unsigned32,
    mtpSlL2ProfileInitialLevelOfCongestion	Unsigned32,
    mtpSlL2ProfileMaxMSUsRetransN1		Unsigned32,
    mtpSlL2ProfileMaxOctRetransN2		Unsigned32,
    mtpSlL2ProfileReceiveCongestionThresholdOnset Unsigned32,
    mtpSlL2ProfileReceiveCongestionThresholdAbate Unsigned32,
    mtpSlL2ProfileReceiveCongestionThresholdDiscard Unsigned32,
    mtpSlL2ProfileM				Unsigned32,
    mtpSlL2ProfileRowStatus			RowStatus
}

mtpSlL2ProfileId OBJECT-TYPE
    SYNTAX SimpleNameType
    MAX-ACCESS not-accessible
    STATUS current
    DESCRIPTION
	"Provides an index into the signalling link MTP Level 2 profile 
	 table.  Rows in this table can be referred to using this index 
	 or using the RowPointer pointer.  The index valud zero (0) has 
	 special semantics: the zero index contains default default 
	 values.  Other vendors requiring additional device specific 
	 profile information can augment this table.
	 
	 Identifies a mtpL2ProtocolProfile instance within the 
	 managedSwitching-element; this is an attribute type whose 
	 distinguished value can be used as an RDN when naming an 
	 instance of the mtpL2ProtocolProfile object class."
    REFERENCE
	"ITU-T Rec. Q.751.1 (1997), ANSI T1.116.1 (2000), 
	     mtpL2ProtocolProfileId attribute."
    ::= { mtpSlL2ProfileEntry 1 }

mtpSlL2ProfileErrorCorrectionMethod OBJECT-TYPE
    SYNTAX INTEGER {
	basicRetr(0), prevCyclRetr(1) }
    MAX-ACCESS read-create
    STATUS current
    DESCRIPTION
	"This attribute is used to specify the type of error-correction 
	 the signalling link is using.
	 
	 - basicRetr(0), basic retransmission method;
	 
	 - prevCyclRetr(1), preventative cyclic retransmission method.
	 
	 Not all methods are applicable to all signalling links and all 
	 implementations."
    REFERENCE
	"ITU-T Rec. Q.751.1 (1997), ANSI T1.116.1 (2000), 
	 errorCorrectionMethod attribute."
    ::= { mtpSlL2ProfileEntry 2 }

mtpSlL2ProfileTransmissionRate OBJECT-TYPE
    SYNTAX MtpTransmissionRate
    MAX-ACCESS read-create
    STATUS current
    DESCRIPTION
	""
    REFERENCE
	"ITU-T Rec. Q.703 (1996).  ANSI T1.111.3/2000.  ETSI 300 008-1."
    ::= { mtpSlL2ProfileEntry 3 }

mtpSlL2ProfileTimerT1 OBJECT-TYPE
    SYNTAX TimeInterval (1290..60000)
    UNITS "centiseconds"
    MAX-ACCESS read-create
    STATUS current
    DESCRIPTION
	"MTP Level 2 T1 timer.
	 
	 Q.703/T1.111.3: Level 2 timer 'Alignment ready'.
	 
	 Timeout interval T1.  This is the time interval that a 
	 signalling link will await an MSU or FISU after sending an MSU 
	 or FISU at the end of the initial alignment procedure.
	 
	 For modems, ITU-T specifies a range from 500 to 600 seconds 
	 with a nominal value of 550 seconds.  For ds0, ITU-T specifies 
	 a range from 40 to 50 seconds with a nominal value of 45 
	 seconds.  For t1 and e1, ITU-T specifies a range of 25 to 360 
	 seconds with a nomiinal value of 300 seconds.
	 
	 For ds0a and ds0, ANSI specifies a range from 12.9 to 16 
	 seconds, with a nominal value of 13 seconds.  For t1, ANSI 
	 specifies a range of 165 to 200 seconds with a nominal value of 
	 170 seconds.
	 
	 It is the responsibility of the agent to enforce any necessary 
	 bounds."
    REFERENCE
	"ITU-T Rec. Q.751.1 (1997), ANSI T1.116.1 (2000), l2TimerT1 
	     attribute.
	 ITU-T Rec. Q.703 (1996).  ANSI T1.111.3/2000.  ETSI 300 008-1.
	 ITU-T Rec. Q.703, ANSI T1.111.3, T1 timer."
    ::= { mtpSlL2ProfileEntry 4 }

mtpSlL2ProfileTimerT2 OBJECT-TYPE
    SYNTAX TimeInterval (500..15000)
    UNITS "centiseconds"
    MAX-ACCESS read-create
    STATUS current
    DESCRIPTION
	"MTP Level 2 T2 timer.
	 
	 Q.703/T1.111.3: Level 2 timer 'Not aligned'.
	 
	 Timeout interval T2.  This is the time interval that a 
	 signalling link will await an SIO after sending an SIO at the 
	 start of the initial alignment procedure."
    REFERENCE
	"ITU-T Rec. Q.751.1 (1997), ANSI T1.116.1 (2000), l2TimerT2 
	     attribute.
	 ITU-T Rec. Q.703 (1996).  ANSI T1.111.3/2000.  ETSI 300 008-1.
	 ITU-T Rec. Q.703, ANSI T1.111.3, T2 timer."
    ::= { mtpSlL2ProfileEntry 5 }

mtpSlL2ProfileTimerT2L OBJECT-TYPE
    SYNTAX TimeInterval
    UNITS "centiseconds"
    MAX-ACCESS read-create
    STATUS current
    DESCRIPTION
	"MTP Level 2 T2 timer: low value for automatic allocation of 
	 signalling data terminals.

	 Timeout interval T2l.  This is the time interval that a 
	 signalling link will await an SIO after sending an SIO at the 
	 start of the intial alignment procedure.  This is the low value 
	 for use with automatic allocation of signalling data links and 
	 terminals, where the value of T2 at either end of the link must 
	 be different."
    REFERENCE
	"ITU-T Rec. Q.704 (1996) : 12.3.4.3
	 ITU-T Rec. Q.703 (1996).  ANSI T1.111.3/2000.  ETSI 300 008-1."
    ::= { mtpSlL2ProfileEntry 6 }

mtpSlL2ProfileTimerT2H OBJECT-TYPE
    SYNTAX TimeInterval
    UNITS "centiseconds"
    MAX-ACCESS read-create
    STATUS current
    DESCRIPTION
	"MTP Level 2 T2 timer: high value for automatic allocation of 
	 signalling data terminals.

	 Timeout interval T2h.  This is the time interval that a 
	 signalling link will await an SIO after sending an SIO at the 
	 start of the initial alignment procedure.  This is the high 
	 value for use with automatic allocation of signalling data 
	 links and terminals, where the value of T2 at either end of the 
	 link must be different."
    REFERENCE
	"ITU-T Rec. Q.704 (1996) : 12.3.4.3
	 ITU-T Rec. Q.703 (1996).  ANSI T1.111.3/2000.  ETSI 300 008-1."
    ::= { mtpSlL2ProfileEntry 7 }

mtpSlL2ProfileTimerT3 OBJECT-TYPE
    SYNTAX TimeInterval (100..1400)
    UNITS "centiseconds"
    MAX-ACCESS read-create
    STATUS current
    DESCRIPTION
	"MTP Level 2 T3 timer.
	 
	 Q.703/T1.111.3: Level 2 timer 'Aligned'.
	 
	 Timeout interval T3.  This is the time interval that a 
	 signalling link will await an MSU or FISU after sending an MSU 
	 or FISU at the end of the initial alignment procedure."
    REFERENCE
	"ITU-T Rec. Q.751.1 (1997), ANSI T1.116.1 (2000), l2TimerT3 
	     attribute.
	 ITU-T Rec. Q.703 (1996).  ANSI T1.111.3/2000.  ETSI 300 008-1.
	 ITU-T Rec. Q.703, ANSI T1.111.3, T3 timer."
    ::= { mtpSlL2ProfileEntry 8 }

mtpSlL2ProfileTimerT4N OBJECT-TYPE
    SYNTAX TimeInterval (230..12000)
    UNITS "centiseconds"
    MAX-ACCESS read-create
    STATUS current
    DESCRIPTION
	"MTP Level 2 T4n (normal) timer.
	 
	 Q.703/T1.111.3: Level 2 timer 'Proving period timer normal'.
	 
	 Timeout interval T4n.  This is the period for which a 
	 signalling link will send continuous SIN during the initial 
	 alignement procedure.  This is the interval of the 'normal' 
	 proving period.
	 
	 ITU-T 4800            110s (100-120s) (2^16)
	 ITU-T 64              8.2s (7.5-9.5s) (2^16)
	 ITU-T 1.536/1.984Mbps 30s (3-70s) (2^16)
	 ANSI  64/56           2.3s (+-10%) (2^14)
	 ANSI  1.536           30s (+-10%)
	"
    REFERENCE
	"ITU-T Rec. Q.751.1 (1997), ANSI T1.116.1 (2000), l2TimerT4N 
	     attribute.
	 ITU-T Rec. Q.703 (1996).  ANSI T1.111.3/2000.  ETSI 300 008-1.
	 ITU-T Rec. Q.703, ANSI T1.111.3, T4n timer."
    ::= { mtpSlL2ProfileEntry 9 }

mtpSlL2ProfileTimerT4E OBJECT-TYPE
    SYNTAX TimeInterval (40..800)
    UNITS "centiseconds"
    MAX-ACCESS read-create
    STATUS current
    DESCRIPTION
	"MTP Level 2 T4e (emergency) timer.

	 Q.703/T1.111.3: Level 2 timer 'Proving period timer 
	 emergency'.

	 Timeout interval T4e.  This is the period for which a 
	 signalling link will send continuous SIE during the initial 
	 alignment procedure.  This is the interval of the 'emergency' 
	 proving period.

	 ITU-T 4800            7s (6-8s) (2^12)
	 ITU-T 64              500ms (400-600ms) (2^12)
	 ITU-T 1.536/1.984Mbps 400-600ms (2^12)
	 ANSI  64/56           0.6s (+-10%) (2^12)
	 ANSI  1.536           5s (+-10%)
	"
    REFERENCE
	"ITU-T Rec. Q.751.1 (1997), ANSI T1.116.1 (2000), l2TimerT4E 
	     attribute.
	 ITU-T Rec. Q.703 (1996).  ANSI T1.111.3/2000.  ETSI 300 008-1.
	 ITU-T Rec. Q.703, ANSI T1.111.3, T4e timer."
    ::= { mtpSlL2ProfileEntry 10 }

mtpSlL2ProfileTimerT5 OBJECT-TYPE
    SYNTAX TimeInterval (8..12)
    UNITS "centiseconds"
    MAX-ACCESS read-create
    STATUS current
    DESCRIPTION
	"MTP Level 2 T5 timer.
	 
	 Q.703/T1.111.3: Level 2 timer 'Sending SIB'.
	 
	 Timeout interval T5.  This time interval defines the frequency 
	 at which a signalling link will sent SIB when it is 
	 experiencing receive congestion."
    REFERENCE
	"ITU-T Rec. Q.751.1 (1997), ANSI T1.116.1 (2000), l2TimerT5 
	     attribute.
	 ITU-T Rec. Q.703 (1996).  ANSI T1.111.3/2000.  ETSI 300 008-1.
	 ITU-T Rec. Q.703, ANSI T1.111.3, T5 timer."
    ::= { mtpSlL2ProfileEntry 11 }

mtpSlL2ProfileTimerT6 OBJECT-TYPE
    SYNTAX TimeInterval (300..1200)
    UNITS "centiseconds"
    MAX-ACCESS read-create
    STATUS current
    DESCRIPTION
	"MTP Level 2 T6 timer.
	 
	 Q.703/T1.111.3: Level 2 timer 'Remote congestion'.
	 
	 Timeout interval T6.  This interval is the maximum amount of 
	 time that a signalling link will await an acknowledgement for a 
	 previously sent signalling unit, when the remote signalling 
	 link is busy, before failing the signalling link."
    REFERENCE
	"ITU-T Rec. Q.751.1 (1997), ANSI T1.116.1 (2000), l2TimerT6 
	     attribute.
	 ITU-T Rec. Q.703 (1996).  ANSI T1.111.3/2000.  ETSI 300 008-1.
	 ITU-T Rec. Q.703, ANSI T1.111.3, T6 timer."
    ::= { mtpSlL2ProfileEntry 12 }

mtpSlL2ProfileTimerT7 OBJECT-TYPE
    SYNTAX TimeInterval (50..600)
    UNITS "centiseconds"
    MAX-ACCESS read-create
    STATUS current
    DESCRIPTION
	"MTP Level 2 T7 timer.
	 
	 Q.703/T1.111.3: Level 2 timer 'Excessive delay of 
	 acknowledgement'.
	 
	 Timeout interval T7.  This interval is the maximum amount of 
	 time that a signalling link will await an acknowledgement for a 
	 previously sent signalling unit, when the remote signalling 
	 link is not busy, before failing the signalling link."
    REFERENCE
	"ITU-T Rec. Q.751.1 (1997), ANSI T1.116.1 (2000), l2TimerT7 
	     attribute.
	 ITU-T Rec. Q.703 (1996).  ANSI T1.111.3/2000.  ETSI 300 008-1.
	 ITU-T Rec. Q.703, ANSI T1.111.3, T7 timer."
    ::= { mtpSlL2ProfileEntry 13 }

mtpSlL2ProfileTbOnset1 OBJECT-TYPE
    SYNTAX Unsigned32
    UNITS "MSUs or octets"
    MAX-ACCESS read-create
    STATUS current
    DESCRIPTION
	"If the number of MSUs in the transmission / retransmission 
	 buffer gets bigger than this value, the respective link is 
	 congested in congestionLevel 1.  CongestionLevel 1 measures 
	 start.
	 
	 Transmit congestion onset threshold 1.  When the number of 
	 octets in the transmission buffers surpasses this threshold, 
	 MTP will issue congestion indications to the message originator 
	 for congestion level 1."
    REFERENCE
	"ITU-T Rec. Q.751.1 (1997), ANSI T1.116.1 (2000), 
	     transmissionCongestionThresholdOnsetLevel1 attribute.
	 ITU-T Rec. Q.703 (1996).  ANSI T1.111.3/2000.  ETSI 300 008-1."
    ::= { mtpSlL2ProfileEntry 14 }

mtpSlL2ProfileTbAbate1 OBJECT-TYPE
    SYNTAX Unsigned32
    UNITS "MSUs or octets"
    MAX-ACCESS read-create
    STATUS current
    DESCRIPTION
	"If the number of MSUs in the transmission / retransmission 
	 buffer gets smaller than this number, Level 2 flow control 
	 measures end. The value has to be smaller than the respective 
	 congestion onset threshold.
	 
	 Transmit congestion abate threshold 1.  When the number of 
	 MSUs or octets in the transmission buffers falls beneath this 
	 threshold, MTP will resume sending MSUs of message priority 0."
    REFERENCE
	"ITU-T Rec. Q.751.1 (1997), ANSI T1.116.1 (2000), 
	     transCongThreshAbatementLevel1 attribute.
	 ITU-T Rec. Q.703 (1996).  ANSI T1.111.3/2000.  ETSI 300 008-1."
    ::= { mtpSlL2ProfileEntry 15 }

mtpSlL2ProfileNumberOfThresholdLevels OBJECT-TYPE
    SYNTAX Unsigned32
    MAX-ACCESS read-create
    STATUS current
    DESCRIPTION
	"This attribute equals the number of threshold levels that are 
	 used for congestion control."
    REFERENCE
	"ITU-T Rec. Q.751.1 (1997), ANSI T1.116.1 (2000), 
	 numberOfThresholdLevels attribute."
    ::= { mtpSlL2ProfileEntry 16 }

mtpSlL2ProfileCongestionCounting OBJECT-TYPE
    SYNTAX INTEGER {
	octet(0), message(1) }
    MAX-ACCESS read-create
    STATUS current
    DESCRIPTION
	"This attribute indicates whether congestion counting is message 
	 based or octet based."
    REFERENCE
	"ITU-T Rec. Q.751.1 (1997), ANSI T1.116.1 (2000), 
	 congestionCounting attribute."
    ::= { mtpSlL2ProfileEntry 17 }

mtpSlL2ProfileCongestionReportingBaseObject OBJECT-TYPE
    SYNTAX INTEGER {
	routeSet(0), linkSetOfCongestedRouteSet(1), 
	linkOfCongestedRouteSet(2), congestedLinkOfCongestedRoute(3) }
    MAX-ACCESS read-create
    STATUS current
    DESCRIPTION
	"This attribute indicates on what object congestion counting is 
	 based."
    REFERENCE
	"ITU-T Rec. Q.751.1 (1997), ANSI T1.116.1 (2000), 
	 congestionReportingBaseObject attribute."
    ::= { mtpSlL2ProfileEntry 18 }

mtpSlL2ProfileLoopDelay OBJECT-TYPE
    SYNTAX Unsigned32
    UNITS "milliseconds"
    MAX-ACCESS read-create
    STATUS current
    DESCRIPTION
	"This attribute models loop delay.  The value is in 
	 milliseconds."
    REFERENCE
	"ITU-T Rec. Q.751.1 (1997), ANSI T1.116.1 (2000), loopDelay 
	 attribute."
    ::= { mtpSlL2ProfileEntry 19 }

mtpSlL2ProfileName OBJECT-TYPE
    SYNTAX SimpleNameType
    MAX-ACCESS read-create
    STATUS current
    DESCRIPTION
	"This attribute is an additional name for instances of the 
	 mtpL2ProtocolProfile managed object class.  Provides an 
	 optional administrative name for this signalling link MTP Level 
	 2 profile."
    REFERENCE
	"ITU-T Rec. Q.751.1 (1997), ANSI T1.116.1 (2000), 
	     mtpL2ProtocolProfileName attribute."
    ::= { mtpSlL2ProfileEntry 20 }

mtpSlL2ProfileTbOnset2 OBJECT-TYPE
    SYNTAX Unsigned32
    UNITS "MSUs or octets"
    MAX-ACCESS read-create
    STATUS current
    DESCRIPTION
	"If the number of MSUs in the transmission / retransmission 
	 buffer gets bigger than this value, the respective link is 
	 congested in congestionLevel 2.  CongestionLevel 2 measures 
	 start.
	 
	 Transmit congestion onset threshold 2.  When the number of MSUs 
	 or octets in the transmission buffers surpasses this threshold, 
	 MTP will issue congestion indications to the message originator 
	 for congestion level 1."
    REFERENCE
	"ITU-T Rec. Q.751.1 (1997), ANSI T1.116.1 (2000), 
	     transmissionCongestionThresholdOnsetLevel2 attribute.
	 ITU-T Rec. Q.703 (1996).  ANSI T1.111.3/2000.  ETSI 300 008-1."
    ::= { mtpSlL2ProfileEntry 21 }

mtpSlL2ProfileTbAbate2 OBJECT-TYPE
    SYNTAX Unsigned32
    UNITS "MSUs or octets"
    MAX-ACCESS read-create
    STATUS current
    DESCRIPTION
	"If the number of MSUs in the transm./retransm. buffer of a link 
	 in the congestionLevel 2 gets smaller than this number, the 
	 resp. link is not any more in congestionLevel 2.  
	 CongestionLevel 2 measures end.  The value has to be smaller 
	 than the respective congestion onset threshold.
	 
	 Transmit congestion abate threshold 2.  When the number of MSUs 
	 or octets in the transmission buffers falls beneath this 
	 threshold, MTP will resume sending MSUs of message priority 1."
    REFERENCE
	"ITU-T Rec. Q.751.1 (1997), ANSI T1.116.1 (2000), 
	     transmissionCongestionThresholdAbatementLevel2 attribute.
	 ITU-T Rec. Q.703 (1996).  ANSI T1.111.3/2000.  ETSI 300 008-1."
    ::= { mtpSlL2ProfileEntry 22 }

mtpSlL2ProfileTbOnset3 OBJECT-TYPE
    SYNTAX Unsigned32
    UNITS "MSUs or octets"
    MAX-ACCESS read-create
    STATUS current
    DESCRIPTION
	"If the number of MSUs in the transmission / retransmission 
	 buffer gets bigger than this value, the respective link is 
	 congested in congestionLevel 3.  CongestionLevel 3 measures 
	 start.
	 
	 Transmit congestion onset threshold 2.  When the number of MSUs 
	 or octets in the transmission buffers surpasses this threshold, 
	 MTP will issue congestion indications to the message originator 
	 for congestion level 2."
    REFERENCE
	"ITU-T Rec. Q.751.1 (1997), ANSI T1.116.1 (2000), 
	     transmissionCongestionThresholdOnsetLevel3 attribute.
	 ITU-T Rec. Q.703 (1996).  ANSI T1.111.3/2000.  ETSI 300 008-1."
    ::= { mtpSlL2ProfileEntry 23 }

mtpSlL2ProfileTbAbate3 OBJECT-TYPE
    SYNTAX Unsigned32
    UNITS "MSUs or octets"
    MAX-ACCESS read-create
    STATUS current
    DESCRIPTION
	"If the number of MSUs in the transm./retransm. buffer of a link 
	 in the congestionLevel 3 gets smaller than this number, the 
	 resp. link is not any more in congestionLevel 3.  
	 CongestionLevel 3 measures end.  The value has to be smaller 
	 than the respective congestion onset threshold.
	 
	 Transmit congestion abate threshold 2.  When the number of 
	 MSUs or octets in the transmission buffers falls beneath this 
	 threshold, MTP will resume sending MSUs of message priority 2."
    REFERENCE
	"ITU-T Rec. Q.751.1 (1997), ANSI T1.116.1 (2000), 
	     transmissionCongestionThresholdAbatementLevel3 attribute.
	 ITU-T Rec. Q.703 (1996).  ANSI T1.111.3/2000.  ETSI 300 008-1."
    ::= { mtpSlL2ProfileEntry 24 }

mtpSlL2ProfileTbDiscard1 OBJECT-TYPE
    SYNTAX Unsigned32
    UNITS "MSUs or octets"
    MAX-ACCESS read-create
    STATUS current
    DESCRIPTION
	"If the number of MSUs in the transmission / retransmission 
	 buffer of a link in the congestion level 1 gets bigger than 
	 this number, MSUs are discarded (this threshold equals the 
	 respective buffer size).  The value has to be bigger than the 
	 respective congestion onset threshold.
	 
	 Transmit congestion discard threshold 1.  When the number of 
	 MSUs or octets in the transmission buffer surpasses this 
	 threshold, MTP will discard MSUs of message priority 0."
    REFERENCE
	"ITU-T Rec. Q.751.1 (1997), ANSI T1.116.1 (2000), 
	     transmissionCongestionThresholdDiscardLevel1 attribute.
	 ITU-T Rec. Q.703 (1996).  ANSI T1.111.3/2000.  ETSI 300 008-1."
    ::= { mtpSlL2ProfileEntry 25 }

mtpSlL2ProfileTbDiscard2 OBJECT-TYPE
    SYNTAX Unsigned32
    UNITS "MSUs or octets"
    MAX-ACCESS read-create
    STATUS current
    DESCRIPTION
	"If the number of MSUs in the transm./retransm buffer of a link 
	 in the congestion level 2 gets bigger than this number, MSUs 
	 are discarded (this threshold equals the respective buffer 
	 size).  The value has to be bigger than the respective 
	 congestion onset threshold.
	 
	 Transmit congestion discard threshold 2.  When the number of 
	 MSUs or octets in the transmission buffer surpasses this 
	 threshold, MTP will discard MSUs of message priority 1."
    REFERENCE
	"ITU-T Rec. Q.751.1 (1997), ANSI T1.116.1 (2000), 
	     transmissionCongestionThresholdDiscardLevel2 attribute.
	 ITU-T Rec. Q.703 (1996).  ANSI T1.111.3/2000.  ETSI 300 008-1."
    ::= { mtpSlL2ProfileEntry 26 }

mtpSlL2ProfileTbDiscard3 OBJECT-TYPE
    SYNTAX Unsigned32
    UNITS "MSUs or octets"
    MAX-ACCESS read-create
    STATUS current
    DESCRIPTION
	"If the number of MSUs in the transmission / retransmission 
	 buffer of a link in the congestion level 3 gets bigger than 
	 this number, MSUs are discarded (this threshold equals the 
	 respective buffer size).  The value has to be bigger than the 
	 respective congestion onset threshold.
	 
	 Transmit congestion discard threshold 3.  When the number of 
	 MSUs or octets in the transmission buffer surpasses this 
	 threshold, MTP will discard MSUs of message priority 2."
    REFERENCE
	"ITU-T Rec. Q.751.1 (1997), ANSI T1.116.1 (2000), 
	     transmissionCongestionThresholdDiscardLevel3 attribute.
	 ITU-T Rec. Q.703 (1996).  ANSI T1.111.3/2000.  ETSI 300 008-1."
    ::= { mtpSlL2ProfileEntry 27 }

mtpSlL2ProfileTimerTx OBJECT-TYPE
    SYNTAX TimeInterval
    UNITS "centiseconds"
    MAX-ACCESS read-create
    STATUS current
    DESCRIPTION
	"This attribute identifies the Tx timer value for the 'multiple 
	 link congestion states without congestion priority' mechanism 
	 as described in 3.8.2.3/T1.111.4 or 3.8.2.3/Q.704."
    REFERENCE
	"ITU-T Rec. Q.751.1 (1997), ANSI T1.116.1 (2000), timerTx 
	 attribute."
    ::= { mtpSlL2ProfileEntry 28 }

mtpSlL2ProfileTimerTy OBJECT-TYPE
    SYNTAX TimeInterval
    UNITS "centiseconds"
    MAX-ACCESS read-create
    STATUS current
    DESCRIPTION
	"This attribute identifies the Ty timer value for the 'multiple 
	 link congestion states without congestion priority' mechanism 
	 as described in 3.8.2.3/T1.111.4 or 3.8.2.3/Q.704."
    REFERENCE
	"ITU-T Rec. Q.751.1 (1997), ANSI T1.116.1 (2000), timerTy 
	 attribute."
    ::= { mtpSlL2ProfileEntry 29 }

mtpSlL2ProfileNumberOfCongestionStates OBJECT-TYPE
    SYNTAX Unsigned32
    MAX-ACCESS read-create
    STATUS current
    DESCRIPTION
	"This attribute specifies the number of congestion states used 
	 in the 'multiple link congestion states without congestion 
	 priority' mechanism as described in 3.8.2.3/T1.111.4 or 
	 3.8.2.3/Q.704."
    REFERENCE
	"ITU-T Rec. Q.751.1 (1997), ANSI T1.116.1 (2000), 
	 numberOfCongestionStates attribute."
    ::= { mtpSlL2ProfileEntry 30 }

mtpSlL2ProfileInitialLevelOfCongestion OBJECT-TYPE
    SYNTAX Unsigned32
    MAX-ACCESS read-create
    STATUS current
    DESCRIPTION
	"This attribute represents the initial level of congestion."
    REFERENCE
	"ITU-T Rec. Q.751.1 (1997), ANSI T1.116.1 (2000), 
	 initialLevelOfCongestion attribute."
    ::= { mtpSlL2ProfileEntry 31 }

mtpSlL2ProfileMaxMSUsRetransN1 OBJECT-TYPE
    SYNTAX Unsigned32 (0..16777215)
    UNITS "messages"
    MAX-ACCESS read-create
    STATUS current
    DESCRIPTION
	"This attribute specifies the maximum number of MSUs which are 
	 available for retransmission (name in Q.703/T1.111.3:N1) 0..127 
	 for normal sequence numbers 0..4095 for extended sequence 
	 numbers.
	 
	 This is the maximum numer of MSUs that can be outstanding (held 
	 in the retransmission buffer).  The maximum value of this 
	 object depends on the size of the sequence number field.  For 
	 low speed signalling links the maximum value is (2^7 - 1), or 
	 127.  For high speed signalling links with extended sequence 
	 numbers and length fields, the maximum value is (2^12 - 1) or 
	 4095.  For M2PA signalling links, the maximum value is (2^24 - 
	 1) or 16777215.  This value is not applicable to ATM SAAL 
	 links.
	 
	 The agent is responsible for enforcing any ranges or maximums 
	 set by the implementation"
    REFERENCE
	"ITU-T Rec. Q.751.1 (1997), ANSI T1.116.1 (2000), 
	     maxMSUsRetransN1 attribute.
	 ITU-T Rec. Q.703 (1996).  ANSI T1.111.3/2000.  ETSI 300 008-1."
    ::= { mtpSlL2ProfileEntry 32 }

mtpSlL2ProfileMaxOctRetransN2 OBJECT-TYPE
    SYNTAX Unsigned32
    UNITS "octets"
    MAX-ACCESS read-create
    STATUS current
    DESCRIPTION
	"This attribute specifies the maximum number of octets, which 
	 are available for retransmission (Q.703/T1.111.3: N2).
	 
	 This is the maximum number of message octets that can be 
	 outstanding (held in the retransmission buffer).  If the value 
	 is greater than N1 x m, where m is the maximum message length 
	 in octets, then this value will not act as a constraint on the 
	 retransmission buffer.  That is, when set to a suitably large 
	 value, this protocol parameter has no effect on the state 
	 machine."
    REFERENCE
	"ITU-T Rec. Q.751.1 (1997), ANSI T1.116.1 (2000), 
	     maxOctRetransN2 attribute.
	 ITU-T Rec. Q.703 (1996).  ANSI T1.111.3/2000.  ETSI 300 008-1."
    ::= { mtpSlL2ProfileEntry 33 }

mtpSlL2ProfileReceiveCongestionThresholdOnset OBJECT-TYPE
    SYNTAX Unsigned32
    UNITS "MSUs"
    MAX-ACCESS read-create
    STATUS current
    DESCRIPTION
	"If the number of MSUs in the reception buffer gets bigger than 
	 this value, Level 2 flow control measures begin.  MSUs are 
	 still accepted.
	 
	 Receive congestion accept threshold.  When the number of MSUs 
	 awaiting delivery to MTP Level 3 surpasses this number, the 
	 signalling links will consider itself in receive congestion and 
	 will begin sending periodic SIBs."
    REFERENCE
	"ITU-T Rec. Q.751.1 (1997), ANSI T1.116.1 (2000), 
	     receiveCongestionThresholdOnset attribute.
	 ITU-T Rec. Q.703 (1996).  ANSI T1.111.3/2000.  ETSI 300 008-1."
    ::= { mtpSlL2ProfileEntry 34 }

mtpSlL2ProfileReceiveCongestionThresholdAbate OBJECT-TYPE
    SYNTAX Unsigned32
    UNITS "MSUs"
    MAX-ACCESS read-create
    STATUS current
    DESCRIPTION
	"If the number of MSUs in the reception buffer gets smaller than 
	 this number, Level 2 flow control measures end.  The value has 
	 to be smaller than the respective congestion onset threshold.
	 
	 Receive congestion abate threshold.  When the number of MSUs 
	 awaiting delivery to MTP Level 3 falls beneath this number, the 
	 signalling link will consider itself to have ceased receive 
	 congestion and will stop sending periodic SIBs."
    REFERENCE
	"ITU-T Rec. Q.751.1 (1997), ANSI T1.116.1 (2000), 
	     receiveCongestionThresholdAbatement attribute.
	 ITU-T Rec. Q.703 (1996).  ANSI T1.111.3/2000.  ETSI 300 008-1."
    ::= { mtpSlL2ProfileEntry 35 }

mtpSlL2ProfileReceiveCongestionThresholdDiscard OBJECT-TYPE
    SYNTAX Unsigned32
    UNITS "MSUs"
    MAX-ACCESS read-create
    STATUS current
    DESCRIPTION
	"Receive congestion discard threshold.  When the number of MSUs 
	 awaiting delivery to MTP Level 3 surpasses this number, the 
	 signalling link will begin discarding received MSUs."
    REFERENCE
	"ITU-T Rec. Q.703 (1996).  ANSI T1.111.3/2000.  ETSI 300 008-1."
    ::= { mtpSlL2ProfileEntry 36 }

mtpSlL2ProfileM OBJECT-TYPE
    SYNTAX Unsigned32
    UNITS "periods"
    MAX-ACCESS read-create
    STATUS current
    DESCRIPTION
	"This object specifies the maximum number of failed proving 
	 periods that the signalling link will entertain consequtively 
	 before declaring the initial alignment procedure failed and 
	 failing the signalling link."
    REFERENCE
	"ITU-T Rec. Q.703 (1996).  ANSI T1.111.3/2000.  ETSI 300 008-1."
    DEFVAL { 5 }
    ::= { mtpSlL2ProfileEntry 37 }

mtpSlL2ProfileRowStatus OBJECT-TYPE
    SYNTAX RowStatus
    MAX-ACCESS read-create
    STATUS current
    DESCRIPTION
	"Provides a mechanism whereby management station can create and 
	 delete rows in this table.  Aside from a number of default rows 
	 provided by the managed system, rows are created and deleted by 
	 management stations.
	 
	 If the name package is supported: a create request with a value 
	 for the name attribute that is already used by another instance 
	 of the same object class will be rejected.  If an attempt is 
	 made to delete an mtpL2ProtocolProfile which is still 
	 referenced by a signLinkTp the delete request will be 
	 rejected."
    REFERENCE
	"STD 58, SNMPv2-TC RowStatus.
	 ITU-T Rec. Q.751.1 (1997) : 
	     managedSwitchingElement-mtpL2ProtocolProfile NAME BINDING."
    ::= { mtpSlL2ProfileEntry 38 }


-- ====================================================================

mtpSlTable OBJECT-TYPE
    SYNTAX SEQUENCE OF MtpSlEntry
    MAX-ACCESS not-accessible
    STATUS current
    DESCRIPTION
	"This managed object represents the termination of the 
	 signalling link within the signalling point as defined in 
	 Recommendation Q.703.  The signLinkTp object class represents 
	 that part of a signalling link which is located in one NE.
	 
	 The following state and status attributes are supported:
	 
	  1. administrative state:
	 
	     - locked: it is administratively not permitted to transport 
	       traffic on the link termination point.
	 
	     - unlocked: it is administratively permitted to transport 
	       user part traffic or test traffic on the link termination 
	       point.
	 
	  2. operational state:
	 
	     - enabled: the link termination point is operationally able 
	       to transport user part traffic or test traffic.
	 
	     - disabled: the link termination point is operationally 
	       unable to transport user part traffic or test traffic.  
	       The operational state is disabled whenever the link 
	       termination point status contains Failed, Deactivated, 
	       Local Blocked, Remote Blocked, or the procedural status 
	       is Initializing.
	 
	  3. usage state:
	 
	     - idle: the link termination point carries no user part 
	       traffic (test traffic may be present).
	 
	     - 'active': the link termination point is not congested.  
	       Currently the link termination point carries user part 
	       traffic.
	 
	     - busy: the link termination point is congested due to user 
	       part traffic.  The usage state is idle whenever the link 
	       termination point status is not empty i.e. the usage 
	       state immediately reflects the availability of the 
	       signLinkTp for user traffic.
	 
	     For national MTP options applying several congestion levels 
	     an additional attribute indicating these levels may be 
	     added.
	 
	  4. procedural status:
	 
	     The procedural status initializing is valid during initial 
	     alignment procedure.
	 
	     The procedural status not initalized applies when the link 
	     termination point is not aligned and the initial alignment 
	     procedure has not been started.
	 
	  5. Link termination point status.  This is a set-valued 
	     attribute.  The following statusses can exist alone or in 
	     combinations with each other.  The exact definition for 
	     each of the following SS7-functional states is to be gained 
	     from Q.704 local blocked remote blocked local inhibited 
	     remote inhibited failed deactivated.
	 
	 If the 'ITU-T Rec. X.721 (1992) | ISO/IEC 10165-2 : 
	 1992':communicationsAlarm notification is used, the following 
	 probable causes can apply:
	 
	  - Probable C102 (slFailure) which represents measurement 
	    Q.752/1.2 measurement Q.752/1.6 (SpecificProblems=003 
	    abnormalFIBRorBSNR, 004 excessiveAckDelay, 005 
	    excessiveErrorRate, 006 excessiveCongDuration) and 
	    Q.752/1.12.(PerceivedSeverity=cleared)
	 
	 If the ss7OnOccEventPackage is present, the event notifications 
	 with the following probable causes can apply:
	 
	  - Probable Cause = 110 (localChangeOver) which represents 
	    measurement Q.752/1.10 (PerceivedSeverity=Maj/Min/War) and 
	    measurement Q.752/1.11 (PerceivedSeverity=Cleared).
	 
	  - Probable Cause = 210 (remoteProcOutage) which represents 
	    measurements Q.752/2.10 (PerceivedSeverity=Maj/Min/War) and 
	    Q.752/2.11 (PerceivedSeverity=Cleared).
	 
	  - Probable Cause = 216 (start of local inhibition) which 
	    represents measurement Q.752/2.16 
	    (PerceivedSeverity=Maj/Min/War) and Q.752/2.17 
	    (PerceivedSeverity=Cleared).
	 
	  - Probable Cause = 218 (start of remote inhibition) which 
	    represents measurement Q.752/2.18 
	    (PerceivedSeverity=Maj/Min/War) and Q.752/2.19 
	    (PerceivedSeverity=Cleared).
	 
	 A create or set request is rejected, if
	 
	  1. a pointer would reference an instance, which does not 
	     belong to the appropriate object class OR
	 
	  2. a pointer would reference an instance which is not existing 
	     OR
	 
	  3. a signDataLinkTpPointer would reference a signDataLinkTp 
	     which is not in the same mtpSignPoint OR
	 
	  4. a signDataLinkTpPointer would reference a signDataLinkTp 
	     which has a different value of adjPc than the superior 
	     signLinkSetTp OR
	 
	  5. the link would reference a datalink and a 
	     mtpL2ProtocolProfile whose transmissionRates is not the 
	     same OR
	 
	  6. the link would reference a mtpL2ProtocolProfile where the 
	     appropriate packages for the congestionControlMethod of the 
	     superior signLinkSetTp are not present (see B.1.2.9.2) OR
	 
	  7. the spTimersProfilePackage is present in the superior 
	     mtpSignPoint AND the link would reference a 
	     mtpL2ProtocolProfile whose l2TimerT2 is not bigger than the 
	     q704-t17 of the spTimersProfile referenced by the 
	     mtpSignPoint OR
	 
	  8. the spTimersPackage is present in the superior mtpSignPoint 
	     AND the link would reference a mtpL2ProtocolProfile whose 
	     l2TimerT2 is not bigger than the q704-t17 of the 
	     mtpSignPoint.
	 
	 The rejection also takes place if only a single pointer within 
	 the signDataLinkList or the signTermList (if present) is wrong.
	 
	 A delete request is rejected, if the linkTpStatus does not 
	 contain the value deactivated."
    REFERENCE
	"ITU-T Rec. Q.751.1 (1997), ANSI T1.116.1 (2000), signLinkTp 
	     MOC.
	 ITU-T Rec. Q.703 (1996)."
    ::= { mtpSl 3 }

mtpSlEntry OBJECT-TYPE
    SYNTAX MtpSlEntry
    MAX-ACCESS not-accessible
    STATUS current
    DESCRIPTION
	"This is the signalling link table entry.  Each entry in the 
	 signalling link table represents a signalling link configured 
	 for operation in the managed element.
	 
	 Entries in this table can generate a communicationsAlarm with 
	 parameters:
	 
	  - ITU-T Rec. Q.752 (1997) : Table 1/Q.752 1.2,
		probableCause = 102 (slFailure)
	  - ITU-T Rec. Q.752 (1997) : Table 1/Q.752 1.3,
		probableCause = 102, (slFailure)
		specificProblems = 003
	  - ITU-T Rec. Q.752 (1997) : Table 1/Q.752 1.4,
		probableCause = 102, (slFailure)
		specificProblems = 004
	  - ITU-T Rec. Q.752 (1997) : Table 1/Q.752 1.5,
		probableCause = 102, (slFailure)
		specificProblems = 005
	  - ITU-T Rec. Q.752 (1997) : Table 1/Q.752 1.6,
		probableCause = 102, (slFailure)
		specificProblems = 006
	  - ITU-T Rec. Q.752 (1997) : Table 1/Q.752 1.12,
		probableCause = 102, (slFailure)
		PerceivedSeverity = Cleared
	 
	 Entries in this table can generate an ss7OnOccEvent with 
	 parameters:
	 
	  - ITU-T Rec. Q.752 (1997) : Table 1/Q.752 1.10,
		probableCause = 110, (localAutomaticChange)
		PerceivedSeverity = M/m/W
	  - ITU-T Rec. Q.752 (1997) : Table 1/Q.752 1.11,
		probableCause = 110, (localAutomaticChange)
		PerceivedSeverity = Cleared
	  - ITU-T Rec. Q.752 (1997) : Table 1/Q.752 2.10,
		probableCause = 210, (remoteProcOutage)
		PerceivedSeverity = M/m/W
	  - ITU-T Rec. Q.752 (1997) : Table 1/Q.752 2.11,
		probableCause = 210, (remoteProcOutage)
		PerceivedSeverity = Cleared
	  - ITU-T Rec. Q.752 (1997) : Table 1/Q.752 2.16,
		probableCause = 216, (localInhibition)
		PerceivedSeverity = M/m/W
	  - ITU-T Rec. Q.752 (1997) : Table 1/Q.752 2.17,
		probableCause = 216, (localInhibition)
		PerceivedSeverity = Cleared
	  - ITU-T Rec. Q.752 (1997) : Table 1/Q.752 2.18,
		probableCause = 218, (remoteInhibition)
		PerceivedSeverity = M/m/W
	  - ITU-T Rec. Q.752 (1997) : Table 1/Q.752 2.19,
		probableCause = 218, (remoteInhibition)
		PerceivedSeverity = Cleared
	 
	 Entries in this table can generate a qualityOfServiceAlarm with 
	 parameters:
	 
	  - ITU-T Rec. Q.752 (1997) : Table 1/Q.752 3.6,
		probableCause = 306, (linkCongestionIndications)
		PerceivedSeverity = M/m/W
		(also first and interval)
	  - ITU-T Rec. Q.752 (1997) : Table 1/Q.752 3.9,
		probableCause = 306, (linkCongestionIndications)
		PerceivedSeverity = Cleared
		(also first and interval)
	  - ITU-T Rec. Q.752 (1997) : Table 1/Q.752 3.11,
		probableCause = 311, (linkCongestionDiscard)
		PerceivedSeverity = M/m/W
		(also first and interval)
	 
	 The mtpSpId and mtpLsId specify an index into the mtpLsTable 
	 that specifies the link set to which this signalling link will 
	 belong.  Underspecified values on management station SET 
	 operations that create an entry in this table may be inherited 
	 from the specified mtpLsTable link set entry."
    REFERENCE
	"ITU-T Rec. Q.751.1 (1997), ANSI T1.116.1 (2000), signLinkTp 
	     MO.
	 ITU-T Rec. Q.751.1 signLinkSetTp-signLinkTp NAME BINDING
	 ITU-T Rec. Q.752, (1997) : Table 1/Q.752 1.2
	 ITU-T Rec. Q.752, (1997) : Table 1/Q.752 1.3
	 ITU-T Rec. Q.752, (1997) : Table 1/Q.752 1.4
	 ITU-T Rec. Q.752, (1997) : Table 1/Q.752 1.5
	 ITU-T Rec. Q.752, (1997) : Table 1/Q.752 1.6"
    INDEX {
	mtpSpId,
	mtpLsId,
	mtpSlSlCode
    }
    ::= { mtpSlTable 1 }

MtpSlEntry ::= SEQUENCE {
    mtpSlSlCode					Unsigned32,
    mtpSlSlsCodeCurrentList			SlsList,
    mtpSlMaxCapacitySL				Unsigned32,
    mtpSlCurrentCapacitySL			Unsigned32,
    mtpSlLinkTpStatus				MtpLinkStatus,
    mtpSlAdministrativeState			AdministrativeState,
    mtpSlOperationalState			OperationalState,
    mtpSlUsageState				UsageState,
    mtpSlProceduralStatus			ProceduralStatus,
    mtpSlMtpL2ProtocolProfilePointer		SimpleNameType,
    mtpSlSignTermPointer			RowPointer,
    mtpSlSignDataLinkTpPointer			RowPointer,
    mtpSlLocalInhibit				MtpResultOfAction,
    mtpSlLocalUninhibit				MtpResultOfAction,
    mtpSlReplaceSt				MtpResultOfAction,
    mtpSlAsaProfilePointer			RowPointer,
    mtpSlCongestionLevel			MtpCongestionLevel,
    mtpSlRelatedLinkGroupNumber			Unsigned32,
    mtpSlSdlList				Unsigned32,
    mtpSlTest					MtpResultOfAction,
    mtpSlName					CommonLanguageName,
    mtpSlSdtList				Unsigned32,
    mtpSlSlsCodeNormalList			SlsList,
    mtpSlL3ProfilePointer			SimpleNameType,
    mtpSlAlarmStatus				AlarmStatus,
    mtpSlRowStatus				RowStatus
}

mtpSlSlCode OBJECT-TYPE
    SYNTAX Unsigned32 (0..31)
    MAX-ACCESS not-accessible
    STATUS current
    DESCRIPTION
	"Specifies the signalling link code (SLC) associated with the 
	 signalling link within the link set.
	 
	 Signalling link codes are used by the MTP Level 3 protocol in 
	 changeover, changeback, inhibit and uninhibit messages to 
	 identify the signalling link upon which the associated action 
	 is to be performed.
	 
	 For ITU-T networks and some ITU-T based networks, the SLC must 
	 also be unique within the combined link set.  For ANSI 
	 networks, the value need not be unique within the combined link 
	 set, but is often done that way anyway.  The range of values 
	 permitted for ITU-T based networks is (0..15), for ANSI based 
	 networks it is (0..31).
	 
	 If a management station SET operation requests a value that is 
	 the same as that assigned to another entry associated with the 
	 same direct link set, the request will be refused.  If a 
	 management SET operation requests a value that is the same as 
	 that to another entry assocaited with the same combined link 
	 set, the request may be refused.
	 
	 If one SLC has been assigned, it should be checked that this 
	 SLC will not be assigned again.
	 
	 This object is the signalling link code (SLC) associated with 
	 the signalling link within the link set.  For ITU-T networks 
	 and some ITU-T based networks, the SLC must also be unique 
	 within the combined link set.  For ANSI networks, the value 
	 need not be unique within the combined link set, but is often 
	 done that way anyway.  The range of values permitted for ITU-T 
	 based networks is (0..15), for ANSI based networks it is 
	 (0..31).
	 
	 If a management station SET request, creating an entry in this 
	 table, has assigned an mtpSlSlCode value the same as another 
	 entry associated with the same link set, the request will be 
	 refused.  If a management station requests a SET operation 
	 creating an entry in this table, has assigned an mtpSlSlCode 
	 value the same as another entry associated with the same 
	 combined link set, the request may be refused."
    REFERENCE
	"ITU-T Rec. Q.751.1 (1997), ANSI T1.116.1 (2000), slCode 
	 attribute.
	 ITU-T Rec. Q.751.1 signLinkSetTp-signLinkTp NAME BINDING"
    ::= { mtpSlEntry 1 }

mtpSlSlsCodeCurrentList OBJECT-TYPE
    SYNTAX SlsList
    MAX-ACCESS read-create
    STATUS current
    DESCRIPTION
	"Provides a list of assigned signalling link selections that 
	 load this signalling link within its link set.  It will only be 
	 valid when this signalling link is associated with a link set 
	 and then it will be a unique subset of the SLS available within 
	 the link set.  See the SlsList textual convention for 
	 formatting.
	 
	 This attribute indicates, which SLSs are currently assigned to 
	 this signLinkTp.  It has to be ensured, that all SLSs are 
	 covered and no SLS exists more than one time within the 
	 slsCodeCurrentList attributes of the signLinkTp instances 
	 contained within one signLinkSetTp.  The content of this 
	 attribute can be different from that of the attribute 
	 slsCodeNormalList.  This attribute can be changed from system 
	 inside.
	 
	 This object is the list of assigned signalling link selections 
	 that load this signalling link within its link set.  It will 
	 only be valid when this signalling link is associated with a 
	 link set and then it will be a unique subset of the SLS 
	 available within the link set.  See the SlsList textual 
	 convention for formatting."
    REFERENCE
	"ITU-T Rec. Q.751.1 (1997), ANSI T1.116.1 (2000), 
	     slsCodeCurrentList attribute."
    ::= { mtpSlEntry 2 }

mtpSlMaxCapacitySL OBJECT-TYPE
    SYNTAX Unsigned32 (0..512000)
    UNITS "octets per second"
    MAX-ACCESS read-create
    STATUS current
    DESCRIPTION
	"Specifies the maximum traffic handling capacity of the 
	 signalling link in octets per second.
	 
	 This attribute represents the current capacity of a signalling 
	 link.  The capacity set can be less than the available capacity 
	 of the link.  The available capacity is 600 octets per second 
	 for 4.9 kbps signalling links, 7000 octets per second, 56 kbps 
	 signalling links, 8000 octest per second, 64 kbps, 192000, 
	 1.544 Mbps, 248000, 2.048 Mbps, 512000, 4.096 Mbps."
    REFERENCE
	"ITU-T Rec. Q.751.1 (1997), ANSI T1.116.1 (2000), maxCapacitySL 
	     attribute."
    ::= { mtpSlEntry 3 }

mtpSlCurrentCapacitySL OBJECT-TYPE
    SYNTAX Unsigned32 (0..512000)
    UNITS "octets per second"
    MAX-ACCESS read-only
    STATUS current
    DESCRIPTION
	"This attribute represents the current capacity of a signalling 
	 link.  Specifies the current traffic handling capacity of the 
	 signalling link in octets per second."
    REFERENCE
	"ITU-T Rec. Q.751.1 (1997), ANSI T1.116.1 (2000), 
	     currentCapacitySL attribute."
    ::= { mtpSlEntry 4 }

mtpSlLinkTpStatus OBJECT-TYPE
    SYNTAX MtpLinkStatus
    MAX-ACCESS read-only
    STATUS current
    DESCRIPTION
	"This object provides both the status of the signalling link and 
	 the mechanism for peforming inhibit and uninhibit actions on 
	 the signalling link.

	 The linkTpStatus contains the SS No. 7 functional statuses as 
	 described in Recommendation Q.704.  Possible states indicated 
	 are local blocked, remote blocked, local inhibited, remote 
	 inhibited, failed and deactivated:
	 
	 This is a set-valued attribute.  The following status can exist 
	 alone or in combinations with each other.  The exact definition 
	 for each of the following SS7-functional states is to be gained 
	 from Q.704:
	 
	  - localBlocked(0), the signalling link is locally blocked.  
	    Signalling links are locally blocked when experiencing local 
	    processor outage.
	 
	  - remoteBlocked(1), the signalling link is remotely blocked.  
	    Signalling links are remotely blocked when experiencing 
	    remote processor outage.
	 
	  - localInhibited(2), the signalling link is locally inhibited.  
	    Signalling links are locally inhibited when locally 
	    inhibited by MTP management.
	 
	  - remoteInhibited(3), the signalling link is remotely 
	    inhibited.  Signalling links are remotely inhibited when 
	    inhibited by the remote MTP management.
	 
	  - failed(4), the signalling link is failed.  Signalling links 
	    are failed when they were previously active and are inactive 
	    due to a failure rather than a management action.
	 
	  - deactivated(5), the signalling link is deactivated.  
	    Signalling links are deactivated when inactive due to 
	    management action.
	 
	 The localInhibit action of Q.751.1 can be performed by 
	 requesting a SET operation from a management station with a 
	 mtpSlLinkTpStatus value containing the localInihibted(2) bit set.  
	 Performing the localInhibit action inhibits the signalling 
	 link.  If the inhibition procedure completes successfully, a 
	 GET operation on the mtpSlLinkTpStatus will reveal a 
	 localInihibit(2) bit that is set.  The action is not performed 
	 when the signalling link is already locally inhibited.
	 
	 The localUninhibit action of Q.751.1 can be performed by 
	 performing a SET operation from a management station with a 
	 mtpSlLinkTpStatus value containing the localInhibited(2) bit 
	 cleared.  Performgin the localUninhibit action uninhibits the 
	 signalling link.  If the uninhibition procedure completes 
	 successfully, a GET operation on the mtpSlLinkTpStatus will 
	 reveal a localInhibit(2) bit that is clear.  The action is not 
	 performed when the signalling link is already locally 
	 inhibited."
    REFERENCE
	"ITU-T Rec. Q.751.1 (1997), ANSI T1.116.1 (2000), 
	     signLinkTp::linkTpStatus attribute."
    ::= { mtpSlEntry 5 }

mtpSlAdministrativeState OBJECT-TYPE
    SYNTAX AdministrativeState
    MAX-ACCESS read-create
    STATUS current
    DESCRIPTION
	"Provides the administrative state of the signalling link 
	 termination point following the AdminsitrativeState textual 
	 convention of the OPENSS7-SMI-MIB module and according to ITU-T 
	 Rec. X.721 | ISO/IEC 10165-2.
	 
	  - locked(0), the signalling link is deactivated by network 
	    management; it is administratively not permitted to 
	    transport traffic on the link;
	 
	  - unlocked(1), the signalling link is administratively 
	    permitted to carry traffic; it is administratively permitted 
	    to transport traffic on the link;
	 
	  - shuttingDown(2), the signalling link will be inhibited and 
	    once traffic is no longer being carried, deactivated; the 
	    administrative state of the link will move to locked(0) once 
	    all users are no longer using the link.
	 
	 Signalling links are created in the locked(0) state."
    REFERENCE
	"ITU-T Rec. Q.751.1 (1997), ANSI T1.116.1 (2000) : 
	     signLinkTpBehaviour.
	 ITU-T Rec. X.721 | ISO/IEC 10165-2, administrativeState 
	     attribute.
	 ITU-T Rec. Q.751.1 (1997), ANSI T1.116.1 (2000), 
	     administrativeState attribute."
    DEFVAL { 0 } -- locked
    ::= { mtpSlEntry 6 }

mtpSlOperationalState OBJECT-TYPE
    SYNTAX OperationalState
    MAX-ACCESS read-only
    STATUS current
    DESCRIPTION
	"Provides the operational state of the signalling link 
	 termination point following the OperationalState textual 
	 convention of the OPENSS7-SMI-MIB module and according to ITU-T 
	 Rec. X.721 | ISO/IEC 10165-2.
	 
	  - disabled(0), the links is operationally unable to transport 
	    user part traffic or test traffic; the operational state is 
	    disabled(0) whenever the link status contains failed(4), 
	    deactivated(5), localBlocked(0), remoteBlocked(1), or the 
	    procedural status is initializing(2).
	 
	  - enabled(1), the link is operationally able to transport user 
	    part traffic or test traffic; the signalling link is active 
	    or restored, and is not blocked.
	 
	 Signalling links are created in the disabled(0) state.
	"
    REFERENCE
	"ITU-T Rec. Q.751.1 signLinkTpBehaviour.
	 ITU-T Rec. X.721 (1992) | ISO/IEC 10165-2 : 1992, 
	     Attribute-ASN1Module.OperationalState.
	 ITU-T Rec. X.731 (1992) | ISO/IEC 10164-2 : 1993, 
	     Section 8.1.1.1.
	 ITU-T Rec. Q.751.1 (1997), ANSI T1.116.1 (2000), 
	     operationalState attribute."
    DEFVAL { 0 } -- disabled
    ::= { mtpSlEntry 7 }

mtpSlUsageState OBJECT-TYPE
    SYNTAX UsageState
    MAX-ACCESS read-only
    STATUS current
    DESCRIPTION
	"Provides the usage state of the signalling link termination 
	 point following the UsageState textual convention of the 
	 OPENSS7-SMI-MIB module and according to ITU-T Rec. X.721 | 
	 ISO/IEC 10165-2.
	 
	  - idle(0), the link carries no user part traffic (test traffic 
	    may be present); the signalling link is not currently 
	    handling message traffic: it is either inactive (failed or 
	    deactivated), activating, restoring, blocked or inhibited;
	 
	  - active(1), the signalling link is currently handling message 
	    traffic: it is active, unblocked and unihibited; the link is 
	    not congested and currently the link carries user part 
	    traffic; and,
	 
	  - busy(2), the signalling links is currently handling message 
	    traffic: it is active, unblocked and uninhibited, but it is 
	    congested: the link is congested due to user part traffic.
	 
	 The usage state is idle(0) whenever the link status is not 
	 empty (has some bit set) i.e. the usage state immediately 
	 reflects the availability of the link for user traffic.
	 
	 Signalling links are created in the idle(0) state."
    REFERENCE
	"ITU-T Rec. Q.751.1 signLinkTpBehaviour.
	 ITU-T Rec. X.721 | ISO/IEC 10165-2, usageState attribute.
	 ITU-T Rec. Q.751.1 (1997), ANSI T1.116.1 (2000), usageState 
	 attribute."
    DEFVAL { 0 } -- idle
    ::= { mtpSlEntry 8 }

mtpSlProceduralStatus OBJECT-TYPE
    SYNTAX ProceduralStatus
    MAX-ACCESS read-only
    STATUS current
    DESCRIPTION
	"Provides the procedural status of the signalling link 
	 termination point following the ProceduralStatus textual 
	 convention of the OPENSS7-SMI-MIB module and according to ITU-T 
	 Rec. X.721 | ISO/IEC 10165-2.
	 
	 - initializationRequired(0), initialization is required;
	 
	 - notInitialized(1), the signalling link is failed, deactivated 
	   by MTP L3 or deactivated by OS; the procedural status 
	   notInitialized(1) applies when the link is not aligned and 
	   the initial alignment procedure has not been started;
	 
	 - initializing(2), the signalling link has failed and is being 
	   restored, or is being activated by MTP L3; the procedural 
	   status initializing(2) is valid during initial alignment 
	   procedure;
	 
	 - reporting(3), not used;
	 - terminating(4), not used.
	
	 Signalling links are created in the initialization required 
	 state."
    REFERENCE
	"ITU-T Rec. Q.751.1 signLinkTpBehaviour
	 ITU-T Rec. X.721 | ISO/IEC 10165-2, proceduralStatus 
	     attribute.
	 ITU-T Rec. Q.751.1 (1997), ANSI T1.116.1 (2000) : 
	     proceduralStatus attribute."
    DEFVAL { 0 } -- initializationRequired
    ::= { mtpSlEntry 9 }

mtpSlMtpL2ProtocolProfilePointer OBJECT-TYPE
    SYNTAX SimpleNameType
    MAX-ACCESS read-create
    STATUS current
    DESCRIPTION
	"Identifies an mtpL2ProtocolProfile instance."
    REFERENCE
	"ITU-T Rec. Q.751.1 (1997), ANSI T1.116.1 (2000), 
	     mtpL2ProtocolProfilePointer attribute."
    ::= { mtpSlEntry 10 }

mtpSlSignTermPointer OBJECT-TYPE
    SYNTAX RowPointer
    MAX-ACCESS read-create
    STATUS current
    DESCRIPTION
	"This attribute identifies a particular signTerm instance."
    REFERENCE
	"ITU-T Rec. Q.751.1 (1997), ANSI T1.116.1 (2000), 
	 signTermPointer attribute."
    DEFVAL { { zeroDotZero }}
    ::= { mtpSlEntry 11 }

mtpSlSignDataLinkTpPointer OBJECT-TYPE
    SYNTAX RowPointer
    MAX-ACCESS read-create
    STATUS current
    DESCRIPTION
	"This attribute references a particular mtpSignDataLinkTp 
	 instance.  The following restriction applies to this attribute: 
	 modification is only allowed if the administrative state of the 
	 instance that contains this attribute is 'locked'."
    REFERENCE
	"ITU-T Rec. Q.751.1 (1997), ANSI T1.116.1 (2000), 
	 signDataLinkTpPointer attribute."
    DEFVAL { { zeroDotZero }}
    ::= { mtpSlEntry 12 }

mtpSlLocalInhibit OBJECT-TYPE
    SYNTAX MtpResultOfAction
    MAX-ACCESS read-create
    STATUS current
    DESCRIPTION
	"This action inhibits the signalling link termination point.  If 
	 the inhibition procedure completes successfully the 
	 linkTpStatus contains localInhibit.  This action is not 
	 performed if the linkTpStatus contains localInhibit."
    REFERENCE
	"ITU-T Rec. Q.751.1 (1997), ANSI T1.116.1 (2000), localInhibit 
	 action."
    ::= { mtpSlEntry 13 }

mtpSlLocalUninhibit OBJECT-TYPE
    SYNTAX MtpResultOfAction
    MAX-ACCESS read-create
    STATUS current
    DESCRIPTION
	"This action uninhibits the signalling link termination point.  
	 If the uninhibition procedure completes successfully the 
	 localInhibit is removed from linkTpStatus.  This action is not 
	 performed if the linkTpStatus does not contain localInhibit."
    REFERENCE
	"ITU-T Rec. Q.751.1 (1997), ANSI T1.116.1 (2000), localUninhibit 
	 action."
    ::= { mtpSlEntry 14 }

mtpSlReplaceSt OBJECT-TYPE
    SYNTAX MtpResultOfAction
    MAX-ACCESS read-create
    STATUS current
    DESCRIPTION
	"This action replaces the signalling terminal in a signalling 
	 link termination point.  This action is not performed if:
	 
	 i)   the signTermPointer does not reference a signTerm or
	 ii)  the new signTerm does not exist or
	 iii) the signTerm is already referenced by the link or
	 iv)  the linkTpStatus does not contain the values 'deactivated' 
	 or 'failed'.
	 
	 If the action has been successful, the signTermPointer has the 
	 value of the signTermId given in the information syntax; 
	 otherwise the pointer value remains unchanged."
    REFERENCE
	"ITU-T Rec. Q.751.1 (1997), ANSI T1.116.1 (2000), 
	 replaceSignTerm action."
    ::= { mtpSlEntry 15 }

mtpSlAsaProfilePointer OBJECT-TYPE
    SYNTAX RowPointer
    MAX-ACCESS read-create
    STATUS current
    DESCRIPTION
	"Provides a pointer to an alarm severity assignment profile to 
	 be used for alarms generated by this signalling link 
	 termination point, or zeroDotZero."
    REFERENCE
	"ITU-T Rec. Q.751.1 (1997), ANSI T1.116.1 (2000), 
	     alarmSeverityAssignmentProfilePointer attribute."
    DEFVAL { { zeroDotZero } }
    ::= { mtpSlEntry 16 }

mtpSlCongestionLevel OBJECT-TYPE
    SYNTAX MtpCongestionLevel
    MAX-ACCESS read-only
    STATUS current
    DESCRIPTION
	"This object reflects the current transmit congestion level 
	 being experienced by the signalling link.  Note that it would 
	 be abnormal for a signalling link to indicate 
	 congestionLevel3(3).
	 
	 This attribute is used to reflect link congestion when multiple 
	 congestion levels are used.  Its value in the case of no 
	 congestion is none(0) and, when congested, has one of the 
	 values congestionLevel1(1), congestionLevel2(2) or 
	 congestionLevel3(3).  Its value can by changed by the managed 
	 system.  Transition between congestion levels are indicated 
	 with a qualityOfServiceAlarm."
    REFERENCE
	"ITU-T Rec. Q.751.1 (1997), ANSI T1.116.1 (2000), 
	     linkCongestionLevel attribute."
    ::= { mtpSlEntry 17 }

mtpSlRelatedLinkGroupNumber OBJECT-TYPE
    SYNTAX Unsigned32 (0..15)
    MAX-ACCESS read-create
    STATUS current
    DESCRIPTION
	"This attribute identifies the link group which the signalling 
	 link belongs to."
    REFERENCE
	"ITU-T Rec. Q.751.1 (1997), ANSI T1.116.1 (2000), 
	     relatedLinkGroupNumber attribute."
    ::= { mtpSlEntry 18 }

mtpSlSdlList OBJECT-TYPE
    SYNTAX Unsigned32
    MAX-ACCESS read-create
    STATUS current
    DESCRIPTION
	"This attribute lists the signalling data link instances that 
	 can be used for dynamical allocation to the mtpSl.  The integer 
	 value is the number of entries in the mtpSlSdlListTable that 
	 correspond to this signalling link.  When automatic allocation 
	 of signalling data links is in effect, this value will be 
	 greater than zero; otherwise, the value will be zero."
    REFERENCE
	"ITU-T Rec. Q.751.1 (1997), ANSI T1.116.1 (2000), 
	 signDataLinkTpList attribute."
    ::= { mtpSlEntry 19 }

mtpSlTest OBJECT-TYPE
    SYNTAX MtpResultOfAction
    MAX-ACCESS read-create
    STATUS current
    DESCRIPTION
	"This test is performed to analyse the signalling link."
    REFERENCE
	"ITU-T Rec. Q.751.1 (1997), ANSI T1.116.1 (2000), signLinkTest 
	 attribute."
    ::= { mtpSlEntry 20 }

mtpSlName OBJECT-TYPE
    SYNTAX CommonLanguageName
    MAX-ACCESS read-create
    STATUS current
    DESCRIPTION
	"Provides an optional administrative name for this signalling 
	 link.  Signalling links are typically named using, as a prefix, 
	 the common language name of the managed switching element to 
	 which the signalling link terminates (e.g. EDTNAB01DS1SL0).
	 
	 This attribute is an additional name for instances of the 
	 signLinkTp managed object class."
    REFERENCE
	"ITU-T Rec. Q.751.1 (1997), ANSI T1.116.1 (2000), signLinkTpName 
	     attribute."
    ::= { mtpSlEntry 21 }

mtpSlSdtList OBJECT-TYPE
    SYNTAX Unsigned32
    MAX-ACCESS read-create
    STATUS current
    DESCRIPTION
	"This attribute lists the signTerm instances that can be used 
	 for dynamical allocation to the signLinkTp.  The integer value 
	 is the number of entries in the signTermListTable that 
	 correspond to this signalling link.  When automatic allocation 
	 of signalling terminals is in effect, this value will be 
	 greater than zero; otherwise, the value will be zero."
    REFERENCE
	"ITU-T Rec. Q.751.1 (1997), ANSI T1.116.1 (2000), signTermList 
	     attribute."
    ::= { mtpSlEntry 22 }

mtpSlSlsCodeNormalList OBJECT-TYPE
    SYNTAX SlsList
    MAX-ACCESS read-create
    STATUS current
    DESCRIPTION
	"This attribute indicates, which SLSs are administratively 
	 assigned to this signLinkTp for the case of normal 
	 operation."
    REFERENCE
	"ITU-T Rec. Q.751.1 (1997), ANSI T1.116.1 (2000), 
	 slsCodeNormalList attribute."
    ::= { mtpSlEntry 23 }

mtpSlL3ProfilePointer OBJECT-TYPE
    SYNTAX SimpleNameType
    MAX-ACCESS read-create
    STATUS current
    DESCRIPTION
	"Specifies the MTP Level 3 signalling link protocol profile for 
	 this signalling link.
	 
	 This attribute points to the instance of the class 
	 slTimersProfile, containing the Q.704 timers for the signalling 
	 link."
    REFERENCE
	"ITU-T Rec. Q.751.1 (1997), ANSI T1.116.1 (2000), 
	 slTimersProfilePointer attribute."
    DEFVAL { { zeroDotZero } }
    ::= { mtpSlEntry 24 }

mtpSlAlarmStatus OBJECT-TYPE
    SYNTAX AlarmStatus
    MAX-ACCESS read-create
    STATUS current
    DESCRIPTION
	"Provides the alarm status of the MTP signalling link following 
	 the AlarmStatus textual convention and ITU-T Rec. X.721 (1992) 
	 | ISO/IEC 10165-2 : 1992.
	 
	  - underRepair(0),
	  - critical(1),
	  - major(2),
	  - minor(3),
	  - alarmOutstanding(4),
	"
    REFERENCE
	"ITU-T Rec. Q.751.1 (1997), ANSI T1.116.1 (2000) : alarmStatus 
	     attribute.
	 ITU-T Rec. X.721 (1992) | ISO/IEC 10165-2 : 1992, 
	     Attribute-ASN1Module.AlarmStatus.
	 ITU-T Rec. X.731 (1992) | ISO/IEC 10164-2 : 1993, 
	     Section 8.1.2.1."
    ::= { mtpSlEntry 25 }

mtpSlRowStatus OBJECT-TYPE
    SYNTAX RowStatus
    MAX-ACCESS read-create
    STATUS current
    DESCRIPTION
	"Provides a mechanism whereby management stations may create or 
	 delete signalling link termination point entries in this table.
	 
	 If the name package is supported: a create request with a value 
	 for the name attribute that is already used by another instance 
	 of the same object class will be rejected."
    REFERENCE
	"STD 58, SNMPv2-TC RowStatus.
	 ITU-T Rec. Q.751.1 (1997) : signLinkSetTp-signLinkTp NAME 
	 BINDING."
    ::= { mtpSlEntry 26 }

-- ====================================================================

mtpSlSdlListTable OBJECT-TYPE
    SYNTAX SEQUENCE OF MtpSlSdlListEntry
    MAX-ACCESS not-accessible
    STATUS current
    DESCRIPTION
	"Provides a side table of the signalling link termination point 
	 table that provides the signalling data links that can be used 
	 to provide a given signalling link.
	 
	 When automatic signalling data link allocation is in effect, 
	 one or more signalling data links in the list will be provided 
	 for each signaling link.  Otherwise, the list will be empty."
    REFERENCE
	"ITU-T Rec. Q.751.1 (1997), ANSI T1.116.1 (2000), 
	     signDataLinkList attribute."
    ::= { mtpSl 4 }

mtpSlSdlListEntry OBJECT-TYPE
    SYNTAX MtpSlSdlListEntry
    MAX-ACCESS not-accessible
    STATUS current
    DESCRIPTION
	"Provides an entry in the signalling data link termination point 
	 list table.  The combination of indices uniquely identifies a 
	 signalling link within a signallin link set within a signalling 
	 point and the ordinal value of the signalling data link 
	 termination point within the list."
    REFERENCE
	"ITU-T Rec. Q.751.1 (1997), ANSI T1.116.1 (2000), 
	     signDataLinkList attribute."
    INDEX {
	mtpSpId, -- shared index
	mtpLsId,
	mtpSlSlCode,
	mtpSlSdlListId
    }
    ::= { mtpSlSdlListTable 1 }

MtpSlSdlListEntry ::= SEQUENCE {
    mtpSlSdlListId				Unsigned32,
    mtpSlSdlListPointer				RowPointer,
    mtpSlSdlListRowStatus			RowStatus
}

mtpSlSdlListId OBJECT-TYPE
    SYNTAX Unsigned32
    MAX-ACCESS not-accessible
    STATUS current
    DESCRIPTION
	"Provides an ordinal index for this element in the signalling 
	 data link termination point list."
    ::= { mtpSlSdlListEntry 1 }

mtpSlSdlListPointer OBJECT-TYPE
    SYNTAX RowPointer
    MAX-ACCESS read-create
    STATUS current
    DESCRIPTION
	"Provides a pointer to a signalling data link termination point 
	 instance."
    DEFVAL { { zeroDotZero } }
    ::= { mtpSlSdlListEntry 2 }

mtpSlSdlListRowStatus OBJECT-TYPE
    SYNTAX RowStatus
    MAX-ACCESS read-create
    STATUS current
    DESCRIPTION
	"Provides a mechanism whereby management stations may create or 
	 delete entries in the signalling data link termination point 
	 list."
    ::= { mtpSlSdlListEntry 3 }

-- ====================================================================

mtpSlSdtListTable OBJECT-TYPE
    SYNTAX SEQUENCE OF MtpSlSdtListEntry
    MAX-ACCESS not-accessible
    STATUS current
    DESCRIPTION
	"Provides a side table of the signalling link termination point 
	 table that provides the signalling terminals that can be used 
	 to provide a given signalling link.
	 
	 When automatic signalling terminal allocation is in effect, one 
	 or more signalling terminal in the list will be provided for 
	 each signalling link.  Otherwise,  the list will be empty."
    REFERENCE
	"ITU-T Rec. Q.751.1 (1997), ANSI T1.116.1 (2000), signTermList 
	     attribute."
    ::= { mtpSl 5 }

mtpSlSdtListEntry OBJECT-TYPE
    SYNTAX MtpSlSdtListEntry
    MAX-ACCESS not-accessible
    STATUS current
    DESCRIPTION
	"Provides an entry in the signalling terminal list table.  The 
	 combination of indices uniquely identifies a signalling link 
	 within a signalling link set within a signalling point and the 
	 ordinal value of the signalling terminal within the list."
    REFERENCE
	"ITU-T Rec. Q.751.1 (1997), ANSI T1.116.1 (2000), signTermList 
	     attribute."
    INDEX {
	mtpSpId, -- shared index
	mtpLsId, -- shared index
	mtpSlSlCode, -- shared index
	mtpSlSdtListId
    }
    ::= { mtpSlSdtListTable 1 }

MtpSlSdtListEntry ::= SEQUENCE {
    mtpSlSdtListId				Unsigned32,
    mtpSlSdtListPointer				RowPointer,
    mtpSlSdtListRowStatus			RowStatus
}

mtpSlSdtListId OBJECT-TYPE
    SYNTAX Unsigned32
    MAX-ACCESS not-accessible
    STATUS current
    DESCRIPTION
	"Provides an ordinal index for this element in the signalling 
	 terminal list."
    ::= { mtpSlSdtListEntry 1 }

mtpSlSdtListPointer OBJECT-TYPE
    SYNTAX RowPointer
    MAX-ACCESS read-create
    STATUS current
    DESCRIPTION
	"Provides a pointer to a signalling terminal instance."
    DEFVAL { { zeroDotZero } }
    ::= { mtpSlSdtListEntry 2 }

mtpSlSdtListRowStatus OBJECT-TYPE
    SYNTAX RowStatus
    MAX-ACCESS read-create
    STATUS current
    DESCRIPTION
	"Provides a mechanism whereby management stations may create or 
	 delete entries in the signalling terminal list."
    ::= { mtpSlSdtListEntry 3 }

-- ====================================================================

mtpSlStatsTable OBJECT-TYPE
    SYNTAX SEQUENCE OF MtpSlStatsEntry
    MAX-ACCESS not-accessible
    STATUS current
    DESCRIPTION
	"This table provides SL statistics."
    REFERENCE
	"ITU-T Rec. Q.752, ANSI T1.116.2"
    ::= { mtpSl 6 }

mtpSlStatsEntry OBJECT-TYPE
    SYNTAX MtpSlStatsEntry
    MAX-ACCESS not-accessible
    STATUS current
    DESCRIPTION
	"This provides the table entry for SL statistics."
    REFERENCE
	"ITU-T Rec. Q.752, ANSI T1.116.2"
    AUGMENTS    { mtpSlEntry }
    ::= { mtpSlStatsTable 1 }

MtpSlStatsEntry ::= SEQUENCE {
    mtpSlStatsDurInService			Counter32,
    mtpSlStatsFailAlignOrProving		Counter32,
    mtpSlStatsNacksReceived			Counter32,
    mtpSlStatsDurUnavail			Counter32,
    mtpSlStatsDurUnavailFailed			Counter32,
    mtpSlStatsDurUnavailRpo			Counter32,
    mtpSlStatsSibsSent				Counter32,
    mtpSlStatsTranSioSifOctets			Counter32,
    mtpSlStatsRetransOctets			Counter32,
    mtpSlStatsTranMsus				Counter32,
    mtpSlStatsRecvSioSifOctets			Counter32,
    mtpSlStatsRecvMsus				Counter32,
    mtpSlStatsCongOnsetInd0			Counter32,
    mtpSlStatsCongOnsetInd1			Counter32,
    mtpSlStatsCongOnsetInd2			Counter32,
    mtpSlStatsCongOnsetInd3			Counter32,
    mtpSlStatsDurCongStatus0			Counter32,
    mtpSlStatsDurCongStatus1			Counter32,
    mtpSlStatsDurCongStatus2			Counter32,
    mtpSlStatsDurCongStatus3			Counter32,
    mtpSlStatsCongDiscdInd0			Counter32,
    mtpSlStatsCongDiscdInd1			Counter32,
    mtpSlStatsCongDiscdInd2			Counter32,
    mtpSlStatsCongDiscdInd3			Counter32
}

mtpSlStatsDurInService OBJECT-TYPE
    SYNTAX Counter32
    MAX-ACCESS read-only
    STATUS current
    DESCRIPTION
	"This is a count of the duration in service for the signalling 
	 link."
    REFERENCE
	"ITU-T Rec. Q.752, ANSI T1.116.2"
    ::= { mtpSlStatsEntry 1 }

mtpSlStatsFailAlignOrProving OBJECT-TYPE
    SYNTAX Counter32
    MAX-ACCESS read-only
    STATUS current
    DESCRIPTION
	""
    REFERENCE
	"ITU-T Rec. Q.752, ANSI T1.116.2"
    ::= { mtpSlStatsEntry 2 }

mtpSlStatsNacksReceived OBJECT-TYPE
    SYNTAX Counter32
    MAX-ACCESS read-only
    STATUS current
    DESCRIPTION
	""
    REFERENCE
	"ITU-T Rec. Q.752, ANSI T1.116.2"
    ::= { mtpSlStatsEntry 3 }

mtpSlStatsDurUnavail OBJECT-TYPE
    SYNTAX Counter32
    MAX-ACCESS read-only
    STATUS current
    DESCRIPTION
	""
    REFERENCE
	"ITU-T Rec. Q.752, ANSI T1.116.2"
    ::= { mtpSlStatsEntry 4 }

mtpSlStatsDurUnavailFailed OBJECT-TYPE
    SYNTAX Counter32
    MAX-ACCESS read-only
    STATUS current
    DESCRIPTION
	""
    REFERENCE
	"ITU-T Rec. Q.752, ANSI T1.116.2"
    ::= { mtpSlStatsEntry 5 }

mtpSlStatsDurUnavailRpo OBJECT-TYPE
    SYNTAX Counter32
    MAX-ACCESS read-only
    STATUS current
    DESCRIPTION
	""
    REFERENCE
	"ITU-T Rec. Q.752, ANSI T1.116.2"
    ::= { mtpSlStatsEntry 6 }

mtpSlStatsSibsSent OBJECT-TYPE
    SYNTAX Counter32
    MAX-ACCESS read-only
    STATUS current
    DESCRIPTION
	""
    REFERENCE
	"ITU-T Rec. Q.752, ANSI T1.116.2"
    ::= { mtpSlStatsEntry 7 }

mtpSlStatsTranSioSifOctets OBJECT-TYPE
    SYNTAX Counter32
    MAX-ACCESS read-only
    STATUS current
    DESCRIPTION
	""
    REFERENCE
	"ITU-T Rec. Q.752, ANSI T1.116.2"
    ::= { mtpSlStatsEntry 8 }

mtpSlStatsRetransOctets OBJECT-TYPE
    SYNTAX Counter32
    MAX-ACCESS read-only
    STATUS current
    DESCRIPTION
	""
    REFERENCE
	"ITU-T Rec. Q.752, ANSI T1.116.2"
    ::= { mtpSlStatsEntry 9 }

mtpSlStatsTranMsus OBJECT-TYPE
    SYNTAX Counter32
    MAX-ACCESS read-only
    STATUS current
    DESCRIPTION
	""
    REFERENCE
	"ITU-T Rec. Q.752, ANSI T1.116.2"
    ::= { mtpSlStatsEntry 10 }

mtpSlStatsRecvSioSifOctets OBJECT-TYPE
    SYNTAX Counter32
    MAX-ACCESS read-only
    STATUS current
    DESCRIPTION
	""
    REFERENCE
	"ITU-T Rec. Q.752, ANSI T1.116.2"
    ::= { mtpSlStatsEntry 11 }

mtpSlStatsRecvMsus OBJECT-TYPE
    SYNTAX Counter32
    MAX-ACCESS read-only
    STATUS current
    DESCRIPTION
	""
    REFERENCE
	"ITU-T Rec. Q.752, ANSI T1.116.2"
    ::= { mtpSlStatsEntry 12 }

mtpSlStatsCongOnsetInd0 OBJECT-TYPE
    SYNTAX Counter32
    MAX-ACCESS read-only
    STATUS current
    DESCRIPTION
	""
    REFERENCE
	"ITU-T Rec. Q.752, ANSI T1.116.2"
    ::= { mtpSlStatsEntry 13 }

mtpSlStatsCongOnsetInd1 OBJECT-TYPE
    SYNTAX Counter32
    MAX-ACCESS read-only
    STATUS current
    DESCRIPTION
	""
    REFERENCE
	"ITU-T Rec. Q.752, ANSI T1.116.2"
    ::= { mtpSlStatsEntry 14 }

mtpSlStatsCongOnsetInd2 OBJECT-TYPE
    SYNTAX Counter32
    MAX-ACCESS read-only
    STATUS current
    DESCRIPTION
	""
    REFERENCE
	"ITU-T Rec. Q.752, ANSI T1.116.2"
    ::= { mtpSlStatsEntry 15 }

mtpSlStatsCongOnsetInd3 OBJECT-TYPE
    SYNTAX Counter32
    MAX-ACCESS read-only
    STATUS current
    DESCRIPTION
	""
    REFERENCE
	"ITU-T Rec. Q.752, ANSI T1.116.2"
    ::= { mtpSlStatsEntry 16 }

mtpSlStatsDurCongStatus0 OBJECT-TYPE
    SYNTAX Counter32
    MAX-ACCESS read-only
    STATUS current
    DESCRIPTION
	""
    REFERENCE
	"ITU-T Rec. Q.752, ANSI T1.116.2"
    ::= { mtpSlStatsEntry 17 }

mtpSlStatsDurCongStatus1 OBJECT-TYPE
    SYNTAX Counter32
    MAX-ACCESS read-only
    STATUS current
    DESCRIPTION
	""
    REFERENCE
	"ITU-T Rec. Q.752, ANSI T1.116.2"
    ::= { mtpSlStatsEntry 18 }

mtpSlStatsDurCongStatus2 OBJECT-TYPE
    SYNTAX Counter32
    MAX-ACCESS read-only
    STATUS current
    DESCRIPTION
	""
    REFERENCE
	"ITU-T Rec. Q.752, ANSI T1.116.2"
    ::= { mtpSlStatsEntry 19 }

mtpSlStatsDurCongStatus3 OBJECT-TYPE
    SYNTAX Counter32
    MAX-ACCESS read-only
    STATUS current
    DESCRIPTION
	""
    REFERENCE
	"ITU-T Rec. Q.752, ANSI T1.116.2"
    ::= { mtpSlStatsEntry 20 }

mtpSlStatsCongDiscdInd0 OBJECT-TYPE
    SYNTAX Counter32
    MAX-ACCESS read-only
    STATUS current
    DESCRIPTION
	""
    REFERENCE
	"ITU-T Rec. Q.752, ANSI T1.116.2"
    ::= { mtpSlStatsEntry 21 }

mtpSlStatsCongDiscdInd1 OBJECT-TYPE
    SYNTAX Counter32
    MAX-ACCESS read-only
    STATUS current
    DESCRIPTION
	""
    REFERENCE
	"ITU-T Rec. Q.752, ANSI T1.116.2"
    ::= { mtpSlStatsEntry 22 }

mtpSlStatsCongDiscdInd2 OBJECT-TYPE
    SYNTAX Counter32
    MAX-ACCESS read-only
    STATUS current
    DESCRIPTION
	""
    REFERENCE
	"ITU-T Rec. Q.752, ANSI T1.116.2"
    ::= { mtpSlStatsEntry 23 }

mtpSlStatsCongDiscdInd3 OBJECT-TYPE
    SYNTAX Counter32
    MAX-ACCESS read-only
    STATUS current
    DESCRIPTION
	""
    REFERENCE
	"ITU-T Rec. Q.752, ANSI T1.116.2"
    ::= { mtpSlStatsEntry 24 }


-- ====================================================================

mtpSlL3CurrentTable OBJECT-TYPE
    SYNTAX SEQUENCE OF MtpSlL3CurrentEntry
    MAX-ACCESS not-accessible
    STATUS current
    DESCRIPTION
	""
    ::= { mtpSl 7 }

mtpSlL3CurrentEntry OBJECT-TYPE
    SYNTAX MtpSlL3CurrentEntry
    MAX-ACCESS not-accessible
    STATUS current
    DESCRIPTION
	""
    INDEX {
	mtpSpId, -- shared index
	mtpLsId, -- shared index
	mtpSlSlCode -- shared index
    }
    ::= { mtpSlL3CurrentTable 1 }

MtpSlL3CurrentEntry ::= SEQUENCE {
    mtpSlL3CurrentValidIntervals		HCPerfValidIntervals,
    mtpSlL3CurrentTimeDiscontinuity		TimeStamp,
    mtpSlL3CurrentSlUnavailabilityDuration	PerfCurrentCount, -- Q.752, 2.1
    mtpSlL3CurrentSlLocalInhibition		PerfCurrentCount, -- Q.752, 2.5
    mtpSlL3CurrentSlRemoteInhibition		PerfCurrentCount, -- Q.752, 2.6
    mtpSlL3CurrentSlFailed			PerfCurrentCount, -- Q.752, 2.7
    mtpSlL3CurrentSlRemoteProcOutage		PerfCurrentCount, -- Q.752, 2.9
    mtpSlL3CurrentLocalMgmtInhibit		PerfCurrentCount, -- Q.752, 2.13
    mtpSlL3CurrentLocalMgmtUninhibit		PerfCurrentCount, -- Q.752, 2.14
    mtpSlL3CurrentLocalBusy			PerfCurrentCount, -- Q.752, 2.15
    mtpSlL3CurrentSlCongestedStarts		PerfCurrentCount, -- Q.752, 3.6
    mtpSlL3CurrentSlCongestedDuration		PerfCurrentCount, -- Q.752, 3.7
    mtpSlL3CurrentSlCongestionStops		PerfCurrentCount, -- Q.752, 3.9
    mtpSlL3CurrentDiscardedMSUs			PerfCurrentCount, -- Q.752, 3.10
    mtpSlL3CurrentCongestionEventsMSULoss	PerfCurrentCount, -- Q.752, 3.11
    mtpSlL3CurrentChangeovers			PerfCurrentCount, -- Q.752, 1.10
    mtpSlL3CurrentChangebacks			PerfCurrentCount, -- Q.752, 1.11
    mtpSlL3CurrentRestorations			PerfCurrentCount, -- Q.752, 1.12
}

mtpSlL3CurrentValidIntervals OBJECT-TYPE
    SYNTAX HCPerfValidIntervals
    MAX-ACCESS read-only
    STATUS current
    DESCRIPTION
	""
    ::= { mtpSlL3CurrentEntry 1 }

mtpSlL3CurrentTimeDiscontinuity OBJECT-TYPE
    SYNTAX TimeStamp
    MAX-ACCESS read-only
    STATUS current
    DESCRIPTION
	""
    ::= { mtpSlL3CurrentEntry 2 }

mtpSlL3CurrentSlUnavailabilityDuration OBJECT-TYPE
    SYNTAX PerfCurrentCount
    UNITS "seconds"
    MAX-ACCESS read-only
    STATUS current
    DESCRIPTION
	""
    REFERENCE
	"ITU-T Rec. Q.751.1, (10/95) : slUnavailabilityDuration.
	 ITU-T Rec. Q.752, (1997) : Table 2/Q.752 2.1"
    ::= { mtpSlL3CurrentEntry 3 }

mtpSlL3CurrentSlLocalInhibition OBJECT-TYPE
    SYNTAX PerfCurrentCount
    UNITS "seconds"
    MAX-ACCESS read-only
    STATUS current
    DESCRIPTION
	""
    REFERENCE
	"ITU-T Rec. Q.751.1, (10/95) : slLocalInhibition
	 ITU-T Rec. Q.752, (1997) : Table 2/Q.752 2.5"
    ::= { mtpSlL3CurrentEntry 4 }

mtpSlL3CurrentSlRemoteInhibition OBJECT-TYPE
    SYNTAX PerfCurrentCount
    UNITS "seconds"
    MAX-ACCESS read-only
    STATUS current
    DESCRIPTION
	""
    REFERENCE
	"ITU-T Rec. Q.751.1, (10/95) : slRemoteInhibition.
	 ITU-T Rec. Q.752, (1997) : Table 2/Q.752 2.6"
    ::= { mtpSlL3CurrentEntry 5 }

mtpSlL3CurrentSlFailed OBJECT-TYPE
    SYNTAX PerfCurrentCount
    UNITS "seconds"
    MAX-ACCESS read-only
    STATUS current
    DESCRIPTION
	""
    REFERENCE
	"ITU-T Rec. Q.751.1, (10/95) : slFailed.
	 ITU-T Rec. Q.752, (1997) : Table 2/Q.752 2.7"
    ::= { mtpSlL3CurrentEntry 6 }

mtpSlL3CurrentSlRemoteProcOutage OBJECT-TYPE
    SYNTAX PerfCurrentCount
    UNITS "seconds"
    MAX-ACCESS read-only
    STATUS current
    DESCRIPTION
	""
    REFERENCE
	"ITU-T Rec. Q.751.1, (10/95) : slRemoteProcOutage.
	 ITU-T Rec. Q.752, (1997) : Table 2/Q.752 2.9"
    ::= { mtpSlL3CurrentEntry 7 }

mtpSlL3CurrentLocalMgmtInhibit OBJECT-TYPE
    SYNTAX PerfCurrentCount
    UNITS "seconds"
    MAX-ACCESS read-only
    STATUS current
    DESCRIPTION
	""
    REFERENCE
	"ITU-T Rec. Q.751.1, (10/95) : localMgmtInhibit.
	 ITU-T Rec. Q.752, (1997) : Table 2/Q.752 2.13"
    ::= { mtpSlL3CurrentEntry 8 }

mtpSlL3CurrentLocalMgmtUninhibit OBJECT-TYPE
    SYNTAX PerfCurrentCount
    UNITS "seconds"
    MAX-ACCESS read-only
    STATUS current
    DESCRIPTION
	""
    REFERENCE
	"ITU-T Rec. Q.751.1, (10/95) : localMgmtUninhibit.
	 ITU-T Rec. Q.752, (1997) : Table 2/Q.752 2.14"
    ::= { mtpSlL3CurrentEntry 9 }

mtpSlL3CurrentLocalBusy OBJECT-TYPE
    SYNTAX PerfCurrentCount
    UNITS "SIBs sent"
    MAX-ACCESS read-only
    STATUS current
    DESCRIPTION
	""
    REFERENCE
	"ITU-T Rec. Q.751.1, (10/95) : localBusy.
	 ITU-T Rec. Q.752, (1997) : Table 2/Q.752 2.15"
    ::= { mtpSlL3CurrentEntry 10 }

mtpSlL3CurrentSlCongestedStarts OBJECT-TYPE
    SYNTAX PerfCurrentCount
    UNITS "events"
    MAX-ACCESS read-only
    STATUS current
    DESCRIPTION
	""
    REFERENCE
	"ITU-T Rec. Q.751.1, (10/95) : slCongestedStarts.
	 ITU-T Rec. Q.752, (1997) : Table 3/Q.752 3.6"
    ::= { mtpSlL3CurrentEntry 11 }

mtpSlL3CurrentSlCongestedDuration OBJECT-TYPE
    SYNTAX PerfCurrentCount
    UNITS "seconds"
    MAX-ACCESS read-only
    STATUS current
    DESCRIPTION
	""
    REFERENCE
	"ITU-T Rec. Q.751.1, (10/95) : slCongestedDuration.
	 ITU-T Rec. Q.752, (1997) : Table 3/Q.752 3.7"
    ::= { mtpSlL3CurrentEntry 12 }

mtpSlL3CurrentSlCongestionStops OBJECT-TYPE
    SYNTAX PerfCurrentCount
    UNITS "events"
    MAX-ACCESS read-only
    STATUS current
    DESCRIPTION
	""
    REFERENCE
	"ITU-T Rec. Q.751.1, (10/95) : slCongestionStops.
	 ITU-T Rec. Q.752, (1997) : Table 3/Q.752 3.9"
    ::= { mtpSlL3CurrentEntry 13 }

mtpSlL3CurrentDiscardedMSUs OBJECT-TYPE
    SYNTAX PerfCurrentCount
    UNITS "MSUs"
    MAX-ACCESS read-only
    STATUS current
    DESCRIPTION
	""
    REFERENCE
	"ITU-T Rec. Q.751.1, (10/95) : discardedMSUs.
	 ITU-T Rec. Q.752, (1997) : Table 3/Q.752 3.10"
    ::= { mtpSlL3CurrentEntry 14 }

mtpSlL3CurrentCongestionEventsMSULoss OBJECT-TYPE
    SYNTAX PerfCurrentCount
    UNITS "events"
    MAX-ACCESS read-only
    STATUS current
    DESCRIPTION
	""
    REFERENCE
	"ITU-T Rec. Q.751.1, (10/95) : congestionEventsMSULoss.
	 ITU-T Rec. Q.752, (1997) : Table 3/Q.752 3.11"
    ::= { mtpSlL3CurrentEntry 15 }

mtpSlL3CurrentChangeovers OBJECT-TYPE
    SYNTAX PerfCurrentCount
    MAX-ACCESS read-only
    STATUS current
    DESCRIPTION
	""
    REFERENCE
	"Q.752, 1.10"
    ::= { mtpSlL3CurrentEntry 16 }

mtpSlL3CurrentChangebacks OBJECT-TYPE
    SYNTAX PerfCurrentCount
    MAX-ACCESS read-only
    STATUS current
    DESCRIPTION
	""
    REFERENCE
	"Q.752, 1.11"
    ::= { mtpSlL3CurrentEntry 17 }

mtpSlL3CurrentRestorations OBJECT-TYPE
    SYNTAX PerfCurrentCount
    MAX-ACCESS read-only
    STATUS current
    DESCRIPTION
	""
    REFERENCE
	"Q.752, 1.12"
    ::= { mtpSlL3CurrentEntry 18 }



-- ====================================================================

mtpSlL3Int5minTable OBJECT-TYPE
    SYNTAX SEQUENCE OF MtpSlL3Int5minEntry
    MAX-ACCESS not-accessible
    STATUS current
    DESCRIPTION
	""
    ::= { mtpSl 8 }

mtpSlL3Int5minEntry OBJECT-TYPE
    SYNTAX MtpSlL3Int5minEntry
    MAX-ACCESS not-accessible
    STATUS current
    DESCRIPTION
	""
    INDEX {
	mtpSpId, -- shared index
	mtpLsId, -- shared index
	mtpSlSlCode, -- shared index
	mtpSlL3Int5minInterval
    }
    ::= { mtpSlL3Int5minTable 1 }


MtpSlL3Int5minEntry ::= SEQUENCE {
    mtpSlL3Int5minInterval			Unsigned32,
    mtpSlL3Int5minTimeStamp			TimeStamp,
    mtpSlL3Int5minSlUnavailabilityDuration	PerfIntervalCount, -- Q.752, 2.1
    mtpSlL3Int5minSlLocalInhibition		PerfIntervalCount, -- Q.752, 2.5
    mtpSlL3Int5minSlRemoteInhibition		PerfIntervalCount, -- Q.752, 2.6
    mtpSlL3Int5minSlFailed			PerfIntervalCount, -- Q.752, 2.7
    mtpSlL3Int5minSlRemoteProcOutage		PerfIntervalCount, -- Q.752, 2.9
    mtpSlL3Int5minLocalMgmtInhibit		PerfIntervalCount, -- Q.752, 2.13
    mtpSlL3Int5minLocalMgmtUninhibit		PerfIntervalCount, -- Q.752, 2.14
    mtpSlL3Int5minLocalBusy			PerfIntervalCount, -- Q.752, 2.15
    mtpSlL3Int5minSlCongestedStarts		PerfIntervalCount, -- Q.752, 3.6
    mtpSlL3Int5minSlCongestedDuration		PerfIntervalCount, -- Q.752, 3.7
    mtpSlL3Int5minSlCongestionStops		PerfIntervalCount, -- Q.752, 3.9
    mtpSlL3Int5minDiscardedMSUs			PerfIntervalCount, -- Q.752, 3.10
    mtpSlL3Int5minCongestionEventsMSULoss	PerfIntervalCount, -- Q.752, 3.11
    mtpSlL3Int5minChangeovers			PerfIntervalCount, -- Q.752, 1.10
    mtpSlL3Int5minChangebacks			PerfIntervalCount, -- Q.752, 1.11
    mtpSlL3Int5minRestorations			PerfIntervalCount  -- Q.752, 1.12
}

mtpSlL3Int5minInterval OBJECT-TYPE
    SYNTAX Unsigned32
    MAX-ACCESS not-accessible
    STATUS current
    DESCRIPTION
	""
    ::= { mtpSlL3Int5minEntry 1 }

mtpSlL3Int5minTimeStamp OBJECT-TYPE
    SYNTAX TimeStamp
    MAX-ACCESS read-only
    STATUS current
    DESCRIPTION
	""
    ::= { mtpSlL3Int5minEntry 2 }

mtpSlL3Int5minSlUnavailabilityDuration OBJECT-TYPE
    SYNTAX PerfIntervalCount
    UNITS "seconds"
    MAX-ACCESS read-only
    STATUS current
    DESCRIPTION
	""
    REFERENCE
	"ITU-T Rec. Q.751.1, (10/95) : slUnavailabilityDuration.
	 ITU-T Rec. Q.752, (1997) : Table 2/Q.752 2.1"
    ::= { mtpSlL3Int5minEntry 3 }

mtpSlL3Int5minSlLocalInhibition OBJECT-TYPE
    SYNTAX PerfIntervalCount
    MAX-ACCESS read-only
    STATUS current
    DESCRIPTION
	""
    REFERENCE
	"ITU-T Rec. Q.751.1, (10/95) : slLocalInhibition
	 ITU-T Rec. Q.752, (1997) : Table 2/Q.752 2.5"
    ::= { mtpSlL3Int5minEntry 4 }

mtpSlL3Int5minSlRemoteInhibition OBJECT-TYPE
    SYNTAX PerfIntervalCount
    UNITS "seconds"
    MAX-ACCESS read-only
    STATUS current
    DESCRIPTION
	""
    REFERENCE
	"ITU-T Rec. Q.751.1, (10/95) : slRemoteInhibition.
	 ITU-T Rec. Q.752, (1997) : Table 2/Q.752 2.6"
    ::= { mtpSlL3Int5minEntry 5 }

mtpSlL3Int5minSlFailed OBJECT-TYPE
    SYNTAX PerfIntervalCount
    UNITS "seconds"
    MAX-ACCESS read-only
    STATUS current
    DESCRIPTION
	""
    REFERENCE
	"ITU-T Rec. Q.751.1, (10/95) : slFailed.
	 ITU-T Rec. Q.752, (1997) : Table 2/Q.752 2.7"
    ::= { mtpSlL3Int5minEntry 6 }

mtpSlL3Int5minSlRemoteProcOutage OBJECT-TYPE
    SYNTAX PerfIntervalCount
    UNITS "seconds"
    MAX-ACCESS read-only
    STATUS current
    DESCRIPTION
	""
    REFERENCE
	"ITU-T Rec. Q.751.1, (10/95) : slRemoteProcOutage.
	 ITU-T Rec. Q.752, (1997) : Table 2/Q.752 2.9"
    ::= { mtpSlL3Int5minEntry 7 }

mtpSlL3Int5minLocalMgmtInhibit OBJECT-TYPE
    SYNTAX PerfIntervalCount
    MAX-ACCESS read-only
    STATUS current
    DESCRIPTION
	""
    REFERENCE
	"ITU-T Rec. Q.751.1, (10/95) : localMgmtInhibit.
	 ITU-T Rec. Q.752, (1997) : Table 2/Q.752 2.13"
    ::= { mtpSlL3Int5minEntry 8 }

mtpSlL3Int5minLocalMgmtUninhibit OBJECT-TYPE
    SYNTAX PerfIntervalCount
    MAX-ACCESS read-only
    STATUS current
    DESCRIPTION
	""
    REFERENCE
	"ITU-T Rec. Q.751.1, (10/95) : localMgmtUninhibit.
	 ITU-T Rec. Q.752, (1997) : Table 2/Q.752 2.14"
    ::= { mtpSlL3Int5minEntry 9 }

mtpSlL3Int5minLocalBusy OBJECT-TYPE
    SYNTAX PerfIntervalCount
    UNITS "SIBs sent"
    MAX-ACCESS read-only
    STATUS current
    DESCRIPTION
	""
    REFERENCE
	"ITU-T Rec. Q.751.1, (10/95) : localBusy.
	 ITU-T Rec. Q.752, (1997) : Table 2/Q.752 2.15"
    ::= { mtpSlL3Int5minEntry 10 }

mtpSlL3Int5minSlCongestedStarts OBJECT-TYPE
    SYNTAX PerfIntervalCount
    UNITS "events"
    MAX-ACCESS read-only
    STATUS current
    DESCRIPTION
	""
    REFERENCE
	"ITU-T Rec. Q.751.1, (10/95) : slCongestedStarts.
	 ITU-T Rec. Q.752, (1997) : Table 3/Q.752 3.6"
    ::= { mtpSlL3Int5minEntry 11 }

mtpSlL3Int5minSlCongestedDuration OBJECT-TYPE
    SYNTAX PerfIntervalCount
    UNITS "seconds"
    MAX-ACCESS read-only
    STATUS current
    DESCRIPTION
	""
    REFERENCE
	"ITU-T Rec. Q.751.1, (10/95) : slCongestedDuration.
	 ITU-T Rec. Q.752, (1997) : Table 3/Q.752 3.7"
    ::= { mtpSlL3Int5minEntry 12 }

mtpSlL3Int5minSlCongestionStops OBJECT-TYPE
    SYNTAX PerfIntervalCount
    UNITS "events"
    MAX-ACCESS read-only
    STATUS current
    DESCRIPTION
	""
    REFERENCE
	"ITU-T Rec. Q.751.1, (10/95) : slCongestionStops.
	 ITU-T Rec. Q.752, (1997) : Table 3/Q.752 3.9"
    ::= { mtpSlL3Int5minEntry 13 }

mtpSlL3Int5minDiscardedMSUs OBJECT-TYPE
    SYNTAX PerfIntervalCount
    UNITS "MSUs"
    MAX-ACCESS read-only
    STATUS current
    DESCRIPTION
	""
    REFERENCE
	"ITU-T Rec. Q.751.1, (10/95) : discardedMSUs.
	 ITU-T Rec. Q.752, (1997) : Table 3/Q.752 3.10"
    ::= { mtpSlL3Int5minEntry 14 }

mtpSlL3Int5minCongestionEventsMSULoss OBJECT-TYPE
    SYNTAX PerfIntervalCount
    UNITS "events"
    MAX-ACCESS read-only
    STATUS current
    DESCRIPTION
	""
    REFERENCE
	"ITU-T Rec. Q.751.1, (10/95) : congestionEventsMSULoss.
	 ITU-T Rec. Q.752, (1997) : Table 3/Q.752 3.11"
    ::= { mtpSlL3Int5minEntry 15 }

mtpSlL3Int5minChangeovers OBJECT-TYPE
    SYNTAX PerfIntervalCount
    MAX-ACCESS read-only
    STATUS current
    DESCRIPTION
	""
    REFERENCE
	"Q.752, 1.10"
    ::= { mtpSlL3Int5minEntry 16 }

mtpSlL3Int5minChangebacks OBJECT-TYPE
    SYNTAX PerfIntervalCount
    MAX-ACCESS read-only
    STATUS current
    DESCRIPTION
	""
    REFERENCE
	"Q.752, 1.11"
    ::= { mtpSlL3Int5minEntry 17 }

mtpSlL3Int5minRestorations OBJECT-TYPE
    SYNTAX PerfIntervalCount
    MAX-ACCESS read-only
    STATUS current
    DESCRIPTION
	""
    REFERENCE
	"Q.752, 1.12"
    ::= { mtpSlL3Int5minEntry 18 }

-- ====================================================================

mtpSlL3Int15minTable OBJECT-TYPE
    SYNTAX SEQUENCE OF MtpSlL3Int15minEntry
    MAX-ACCESS not-accessible
    STATUS current
    DESCRIPTION
	""
    ::= { mtpSl 9 }

mtpSlL3Int15minEntry OBJECT-TYPE
    SYNTAX MtpSlL3Int15minEntry
    MAX-ACCESS not-accessible
    STATUS current
    DESCRIPTION
	""
    INDEX {
	mtpSpId, -- shared index
	mtpLsId, -- shared index
	mtpSlSlCode, -- shared index
	mtpSlL3Int15minInterval
    }
    ::= { mtpSlL3Int15minTable 1 }


MtpSlL3Int15minEntry ::= SEQUENCE {
    mtpSlL3Int15minInterval			Unsigned32,
    mtpSlL3Int15minTimeStamp			TimeStamp,
    mtpSlL3Int15minSlUnavailabilityDuration	PerfIntervalCount, -- Q.752, 2.1
    mtpSlL3Int15minSlLocalInhibition		PerfIntervalCount, -- Q.752, 2.5
    mtpSlL3Int15minSlRemoteInhibition		PerfIntervalCount, -- Q.752, 2.6
    mtpSlL3Int15minSlFailed			PerfIntervalCount, -- Q.752, 2.7
    mtpSlL3Int15minSlRemoteProcOutage		PerfIntervalCount, -- Q.752, 2.9
    mtpSlL3Int15minLocalMgmtInhibit		PerfIntervalCount, -- Q.752, 2.13
    mtpSlL3Int15minLocalMgmtUninhibit		PerfIntervalCount, -- Q.752, 2.14
    mtpSlL3Int15minLocalBusy			PerfIntervalCount, -- Q.752, 2.15
    mtpSlL3Int15minSlCongestedStarts		PerfIntervalCount, -- Q.752, 3.6
    mtpSlL3Int15minSlCongestedDuration		PerfIntervalCount, -- Q.752, 3.7
    mtpSlL3Int15minSlCongestionStops		PerfIntervalCount, -- Q.752, 3.9
    mtpSlL3Int15minDiscardedMSUs		PerfIntervalCount, -- Q.752, 3.10
    mtpSlL3Int15minCongestionEventsMSULoss	PerfIntervalCount, -- Q.752, 3.11
    mtpSlL3Int15minChangeovers			PerfIntervalCount, -- Q.752, 1.10
    mtpSlL3Int15minChangebacks			PerfIntervalCount, -- Q.752, 1.11
    mtpSlL3Int15minRestorations			PerfIntervalCount  -- Q.752, 1.12
}

mtpSlL3Int15minInterval OBJECT-TYPE
    SYNTAX Unsigned32
    MAX-ACCESS not-accessible
    STATUS current
    DESCRIPTION
	""
    ::= { mtpSlL3Int15minEntry 1 }

mtpSlL3Int15minTimeStamp OBJECT-TYPE
    SYNTAX TimeStamp
    MAX-ACCESS read-only
    STATUS current
    DESCRIPTION
	""
    ::= { mtpSlL3Int15minEntry 2 }

mtpSlL3Int15minSlUnavailabilityDuration OBJECT-TYPE
    SYNTAX PerfIntervalCount
    UNITS "seconds"
    MAX-ACCESS read-only
    STATUS current
    DESCRIPTION
	""
    REFERENCE
	"ITU-T Rec. Q.751.1, (10/95) : slUnavailabilityDuration.
	 ITU-T Rec. Q.752, (1997) : Table 2/Q.752 2.1"
    ::= { mtpSlL3Int15minEntry 3 }

mtpSlL3Int15minSlLocalInhibition OBJECT-TYPE
    SYNTAX PerfIntervalCount
    MAX-ACCESS read-only
    STATUS current
    DESCRIPTION
	""
    REFERENCE
	"ITU-T Rec. Q.751.1, (10/95) : slLocalInhibition
	 ITU-T Rec. Q.752, (1997) : Table 2/Q.752 2.5"
    ::= { mtpSlL3Int15minEntry 4 }

mtpSlL3Int15minSlRemoteInhibition OBJECT-TYPE
    SYNTAX PerfIntervalCount
    UNITS "seconds"
    MAX-ACCESS read-only
    STATUS current
    DESCRIPTION
	""
    REFERENCE
	"ITU-T Rec. Q.751.1, (10/95) : slRemoteInhibition.
	 ITU-T Rec. Q.752, (1997) : Table 2/Q.752 2.6"
    ::= { mtpSlL3Int15minEntry 5 }

mtpSlL3Int15minSlFailed OBJECT-TYPE
    SYNTAX PerfIntervalCount
    UNITS "seconds"
    MAX-ACCESS read-only
    STATUS current
    DESCRIPTION
	""
    REFERENCE
	"ITU-T Rec. Q.751.1, (10/95) : slFailed.
	 ITU-T Rec. Q.752, (1997) : Table 2/Q.752 2.7"
    ::= { mtpSlL3Int15minEntry 6 }

mtpSlL3Int15minSlRemoteProcOutage OBJECT-TYPE
    SYNTAX PerfIntervalCount
    UNITS "seconds"
    MAX-ACCESS read-only
    STATUS current
    DESCRIPTION
	""
    REFERENCE
	"ITU-T Rec. Q.751.1, (10/95) : slRemoteProcOutage.
	 ITU-T Rec. Q.752, (1997) : Table 2/Q.752 2.9"
    ::= { mtpSlL3Int15minEntry 7 }

mtpSlL3Int15minLocalMgmtInhibit OBJECT-TYPE
    SYNTAX PerfIntervalCount
    MAX-ACCESS read-only
    STATUS current
    DESCRIPTION
	""
    REFERENCE
	"ITU-T Rec. Q.751.1, (10/95) : localMgmtInhibit.
	 ITU-T Rec. Q.752, (1997) : Table 2/Q.752 2.13"
    ::= { mtpSlL3Int15minEntry 8 }

mtpSlL3Int15minLocalMgmtUninhibit OBJECT-TYPE
    SYNTAX PerfIntervalCount
    MAX-ACCESS read-only
    STATUS current
    DESCRIPTION
	""
    REFERENCE
	"ITU-T Rec. Q.751.1, (10/95) : localMgmtUninhibit.
	 ITU-T Rec. Q.752, (1997) : Table 2/Q.752 2.14"
    ::= { mtpSlL3Int15minEntry 9 }

mtpSlL3Int15minLocalBusy OBJECT-TYPE
    SYNTAX PerfIntervalCount
    UNITS "SIBs sent"
    MAX-ACCESS read-only
    STATUS current
    DESCRIPTION
	""
    REFERENCE
	"ITU-T Rec. Q.751.1, (10/95) : localBusy.
	 ITU-T Rec. Q.752, (1997) : Table 2/Q.752 2.15"
    ::= { mtpSlL3Int15minEntry 10 }

mtpSlL3Int15minSlCongestedStarts OBJECT-TYPE
    SYNTAX PerfIntervalCount
    UNITS "events"
    MAX-ACCESS read-only
    STATUS current
    DESCRIPTION
	""
    REFERENCE
	"ITU-T Rec. Q.751.1, (10/95) : slCongestedStarts.
	 ITU-T Rec. Q.752, (1997) : Table 3/Q.752 3.6"
    ::= { mtpSlL3Int15minEntry 11 }

mtpSlL3Int15minSlCongestedDuration OBJECT-TYPE
    SYNTAX PerfIntervalCount
    UNITS "seconds"
    MAX-ACCESS read-only
    STATUS current
    DESCRIPTION
	""
    REFERENCE
	"ITU-T Rec. Q.751.1, (10/95) : slCongestedDuration.
	 ITU-T Rec. Q.752, (1997) : Table 3/Q.752 3.7"
    ::= { mtpSlL3Int15minEntry 12 }

mtpSlL3Int15minSlCongestionStops OBJECT-TYPE
    SYNTAX PerfIntervalCount
    UNITS "events"
    MAX-ACCESS read-only
    STATUS current
    DESCRIPTION
	""
    REFERENCE
	"ITU-T Rec. Q.751.1, (10/95) : slCongestionStops.
	 ITU-T Rec. Q.752, (1997) : Table 3/Q.752 3.9"
    ::= { mtpSlL3Int15minEntry 13 }

mtpSlL3Int15minDiscardedMSUs OBJECT-TYPE
    SYNTAX PerfIntervalCount
    UNITS "MSUs"
    MAX-ACCESS read-only
    STATUS current
    DESCRIPTION
	""
    REFERENCE
	"ITU-T Rec. Q.751.1, (10/95) : discardedMSUs.
	 ITU-T Rec. Q.752, (1997) : Table 3/Q.752 3.10"
    ::= { mtpSlL3Int15minEntry 14 }

mtpSlL3Int15minCongestionEventsMSULoss OBJECT-TYPE
    SYNTAX PerfIntervalCount
    UNITS "events"
    MAX-ACCESS read-only
    STATUS current
    DESCRIPTION
	""
    REFERENCE
	"ITU-T Rec. Q.751.1, (10/95) : congestionEventsMSULoss.
	 ITU-T Rec. Q.752, (1997) : Table 3/Q.752 3.11"
    ::= { mtpSlL3Int15minEntry 15 }

mtpSlL3Int15minChangeovers OBJECT-TYPE
    SYNTAX PerfIntervalCount
    MAX-ACCESS read-only
    STATUS current
    DESCRIPTION
	""
    REFERENCE
	"Q.752, 1.10"
    ::= { mtpSlL3Int15minEntry 16 }

mtpSlL3Int15minChangebacks OBJECT-TYPE
    SYNTAX PerfIntervalCount
    MAX-ACCESS read-only
    STATUS current
    DESCRIPTION
	""
    REFERENCE
	"Q.752, 1.11"
    ::= { mtpSlL3Int15minEntry 17 }

mtpSlL3Int15minRestorations OBJECT-TYPE
    SYNTAX PerfIntervalCount
    MAX-ACCESS read-only
    STATUS current
    DESCRIPTION
	""
    REFERENCE
	"Q.752, 1.12"
    ::= { mtpSlL3Int15minEntry 18 }

-- ====================================================================

mtpSlL2CurrentTable OBJECT-TYPE
    SYNTAX SEQUENCE OF MtpSlL2CurrentEntry
    MAX-ACCESS not-accessible
    STATUS current
    DESCRIPTION
	""
    ::= { mtpSl 10 }

mtpSlL2CurrentEntry OBJECT-TYPE
    SYNTAX MtpSlL2CurrentEntry
    MAX-ACCESS not-accessible
    STATUS current
    DESCRIPTION
	""
    INDEX {
	mtpSpId, -- shared index
	mtpLsId, -- shared index
	mtpSlSlCode -- shared index
    }
    ::= { mtpSlL2CurrentTable 1 }


MtpSlL2CurrentEntry ::= SEQUENCE {
    mtpSlL2CurrentValidIntervals		HCPerfValidIntervals,
    mtpSlL2CurrentTimeDiscontinuity		TimeStamp,
    mtpSlL2CurrentSlInServiceDuration		PerfCurrentCount, -- Q.752, 1.1
    mtpSlL2CurrentSlAlignment			PerfCurrentCount, -- Q.752, 1.7
    mtpSlL2CurrentSignUnitsReceived		PerfCurrentCount, -- Q.752, 1.8
    mtpSlL2CurrentNegAckReceived		PerfCurrentCount, -- Q.752, 1.9
    mtpSlL2CurrentTransmittedOctetsSIFSIO	PerfCurrentCount, -- Q.752, 3.1
    mtpSlL2CurrentRetransmittedOctets		PerfCurrentCount, -- Q.752, 3.2
    mtpSlL2CurrentTransmittedMSUs		PerfCurrentCount, -- Q.752, 3.3
    mtpSlL2CurrentReceivedOctetsSIFSIO		PerfCurrentCount, -- Q.752, 3.4
    mtpSlL2CurrentReceivedMSUs			PerfCurrentCount  -- Q.752, 3.5
}

mtpSlL2CurrentValidIntervals OBJECT-TYPE
    SYNTAX HCPerfValidIntervals
    MAX-ACCESS read-only
    STATUS current
    DESCRIPTION
	""
    ::= { mtpSlL2CurrentEntry 1 }

mtpSlL2CurrentTimeDiscontinuity OBJECT-TYPE
    SYNTAX TimeStamp
    MAX-ACCESS read-only
    STATUS current
    DESCRIPTION
	""
    ::= { mtpSlL2CurrentEntry 2 }

mtpSlL2CurrentSlInServiceDuration OBJECT-TYPE
    SYNTAX PerfCurrentCount
    MAX-ACCESS read-only
    STATUS current
    DESCRIPTION
	""
    REFERENCE
	"ITU-T Rec. Q.752, (1997) : Table 1/Q.752 1.1
	 ITU-T Rec. Q.751.1, (10/95) : slInServiceDuration."
    ::= { mtpSlL2CurrentEntry 3 }

mtpSlL2CurrentSlAlignment OBJECT-TYPE
    SYNTAX PerfCurrentCount
    MAX-ACCESS read-only
    STATUS current
    DESCRIPTION
	""
    REFERENCE
	"ITU-T Rec. Q.752, (1997) : Table 1/Q.752 1.7
	 ITU-T Rec. Q.751.1 (10/95) : slAlignment."
    ::= { mtpSlL2CurrentEntry 4 }

mtpSlL2CurrentSignUnitsReceived OBJECT-TYPE
    SYNTAX PerfCurrentCount
    MAX-ACCESS read-only
    STATUS current
    DESCRIPTION
	""
    REFERENCE
	"ITU-T Rec. Q.752, (1997) : Table 1/Q.752 1.8
	 ITU-T Rec. Q.751.1 (10/95) : signUnitsReceived."
    ::= { mtpSlL2CurrentEntry 5 }

mtpSlL2CurrentNegAckReceived OBJECT-TYPE
    SYNTAX PerfCurrentCount
    MAX-ACCESS read-only
    STATUS current
    DESCRIPTION
	""
    REFERENCE
	"ITU-T Rec. Q.752, (1997) : Table 1/Q.752 1.9
	 ITU-T Rec. Q.751.1 (10/95) : negAckReceived."
    ::= { mtpSlL2CurrentEntry 6 }

mtpSlL2CurrentTransmittedOctetsSIFSIO OBJECT-TYPE
    SYNTAX PerfCurrentCount
    MAX-ACCESS read-only
    STATUS current
    DESCRIPTION
	""
    REFERENCE
	"ITU-T Rec. Q.752, (1997) : Table 3/Q.752 3.1
	 ITU-T Rec. Q.751.1 (10/95) : transmittedOctetsSIFSIO."
    ::= { mtpSlL2CurrentEntry 7 }

mtpSlL2CurrentRetransmittedOctets OBJECT-TYPE
    SYNTAX PerfCurrentCount
    MAX-ACCESS read-only
    STATUS current
    DESCRIPTION
	""
    REFERENCE
	"ITU-T Rec. Q.752, (1997) : Table 3/Q.752 3.2
	 ITU-T Rec. Q.751.1 (10/95) : retransmittedOctets."
    ::= { mtpSlL2CurrentEntry 8 }

mtpSlL2CurrentTransmittedMSUs OBJECT-TYPE
    SYNTAX PerfCurrentCount
    MAX-ACCESS read-only
    STATUS current
    DESCRIPTION
	""
    REFERENCE
	"ITU-T Rec. Q.752, (1997) : Table 3/Q.752 3.3
	 ITU-T Rec. Q.751.1 (10/95) : transmittedMSUs."
    ::= { mtpSlL2CurrentEntry 9 }

mtpSlL2CurrentReceivedOctetsSIFSIO OBJECT-TYPE
    SYNTAX PerfCurrentCount
    MAX-ACCESS read-only
    STATUS current
    DESCRIPTION
	""
    REFERENCE
	"ITU-T Rec. Q.752, (1997) : Table 3/Q.752 3.4
	 ITU-T Rec. Q.751.1 (10/95) : receivedOctetsSIFSIO."
    ::= { mtpSlL2CurrentEntry 10 }

mtpSlL2CurrentReceivedMSUs OBJECT-TYPE
    SYNTAX PerfCurrentCount
    MAX-ACCESS read-only
    STATUS current
    DESCRIPTION
	""
    REFERENCE
	"ITU-T Rec. Q.752, (1997) : Table 3/Q.752 3.5
	 ITU-T Rec. Q.751.1 (10/95) : receivedMSUs."
    ::= { mtpSlL2CurrentEntry 11 }



-- ====================================================================

mtpSlL2Int5minTable OBJECT-TYPE
    SYNTAX SEQUENCE OF MtpSlL2Int5minEntry
    MAX-ACCESS not-accessible
    STATUS current
    DESCRIPTION
	"Provides a 5 minute interval table for MTP Level 2 statistics."
    ::= { mtpSl 11 }

mtpSlL2Int5minEntry OBJECT-TYPE
    SYNTAX MtpSlL2Int5minEntry
    MAX-ACCESS not-accessible
    STATUS current
    DESCRIPTION
	"Each entry in the table represents statistics collected for one 
	 5 minute interval.  The first interval in the table is the most 
	   recent 5 minute interval, beginning with 1."
    INDEX {
	mtpSpId, -- shared index
	mtpLsId, -- shared index
	mtpSlSlCode, -- shared index
	mtpSlL2Int5minInterval
    }
    ::= { mtpSlL2Int5minTable 1 }

MtpSlL2Int5minEntry ::= SEQUENCE {
    mtpSlL2Int5minInterval			Unsigned32,
    mtpSlL2Int5minTimestamp			TimeStamp,
    mtpSlL2Int5minSlInServiceDuration		PerfIntervalCount, -- Q.752, 1.1
    mtpSlL2Int5minSlAlignment			PerfIntervalCount, -- Q.752, 1.7
    mtpSlL2Int5minSignUnitsReceived		PerfIntervalCount, -- Q.752, 1.8
    mtpSlL2Int5minNegAckReceived		PerfIntervalCount, -- Q.752, 1.9
    mtpSlL2Int5minTransmittedOctetsSIFSIO	PerfIntervalCount, -- Q.752, 3.1
    mtpSlL2Int5minRetransmittedOctets		PerfIntervalCount, -- Q.752, 3.2
    mtpSlL2Int5minTransmittedMSUs		PerfIntervalCount, -- Q.752, 3.3
    mtpSlL2Int5minReceivedOctetsSIFSIO		PerfIntervalCount, -- Q.752, 3.4
    mtpSlL2Int5minReceivedMSUs			PerfIntervalCount  -- Q.752, 3.5
}

mtpSlL2Int5minInterval OBJECT-TYPE
    SYNTAX Unsigned32
    MAX-ACCESS not-accessible
    STATUS current
    DESCRIPTION
	""
    ::= { mtpSlL2Int5minEntry 1 }

mtpSlL2Int5minTimestamp OBJECT-TYPE
    SYNTAX TimeStamp
    MAX-ACCESS read-only
    STATUS current
    DESCRIPTION
	""
    ::= { mtpSlL2Int5minEntry 2 }

mtpSlL2Int5minSlInServiceDuration OBJECT-TYPE
    SYNTAX PerfIntervalCount
    MAX-ACCESS read-only
    STATUS current
    DESCRIPTION
	""
    REFERENCE
	"ITU-T Rec. Q.752, (1997) : Table 1/Q.752 1.1"
    ::= { mtpSlL2Int5minEntry 3 }

mtpSlL2Int5minSlAlignment OBJECT-TYPE
    SYNTAX PerfIntervalCount
    MAX-ACCESS read-only
    STATUS current
    DESCRIPTION
	""
    REFERENCE
	"ITU-T Rec. Q.752, (1997) : Table 1/Q.752 1.7
	 ITU-T Rec. Q.751.1 (10/95) : slAlignment."
    ::= { mtpSlL2Int5minEntry 4 }

mtpSlL2Int5minSignUnitsReceived OBJECT-TYPE
    SYNTAX PerfIntervalCount
    MAX-ACCESS read-only
    STATUS current
    DESCRIPTION
	""
    REFERENCE
	"ITU-T Rec. Q.752, (1997) : Table 1/Q.752 1.8
	 ITU-T Rec. Q.751.1 (10/95) : signUnitsReceived."
    ::= { mtpSlL2Int5minEntry 5 }

mtpSlL2Int5minNegAckReceived OBJECT-TYPE
    SYNTAX PerfIntervalCount
    MAX-ACCESS read-only
    STATUS current
    DESCRIPTION
	""
    REFERENCE
	"ITU-T Rec. Q.752, (1997) : Table 1/Q.752 1.9
	 ITU-T Rec. Q.751.1 (10/95) : negAckReceived."
    ::= { mtpSlL2Int5minEntry 6 }

mtpSlL2Int5minTransmittedOctetsSIFSIO OBJECT-TYPE
    SYNTAX PerfIntervalCount
    MAX-ACCESS read-only
    STATUS current
    DESCRIPTION
	""
    REFERENCE
	"ITU-T Rec. Q.752, (1997) : Table 3/Q.752 3.1
	 ITU-T Rec. Q.751.1 (10/95) : transmittedOctetsSIFSIO."
    ::= { mtpSlL2Int5minEntry 7 }

mtpSlL2Int5minRetransmittedOctets OBJECT-TYPE
    SYNTAX PerfIntervalCount
    MAX-ACCESS read-only
    STATUS current
    DESCRIPTION
	""
    REFERENCE
	"ITU-T Rec. Q.752, (1997) : Table 3/Q.752 3.2
	 ITU-T Rec. Q.751.1 (10/95) : retransmittedOctets."
    ::= { mtpSlL2Int5minEntry 8 }

mtpSlL2Int5minTransmittedMSUs OBJECT-TYPE
    SYNTAX PerfIntervalCount
    MAX-ACCESS read-only
    STATUS current
    DESCRIPTION
	""
    REFERENCE
	"ITU-T Rec. Q.752, (1997) : Table 3/Q.752 3.3
	 ITU-T Rec. Q.751.1 (10/95) : transmittedMSUs."
    ::= { mtpSlL2Int5minEntry 9 }

mtpSlL2Int5minReceivedOctetsSIFSIO OBJECT-TYPE
    SYNTAX PerfIntervalCount
    MAX-ACCESS read-only
    STATUS current
    DESCRIPTION
	""
    REFERENCE
	"ITU-T Rec. Q.752, (1997) : Table 3/Q.752 3.4
	 ITU-T Rec. Q.751.1 (10/95) : receivedOctetsSIFSIO."
    ::= { mtpSlL2Int5minEntry 10 }

mtpSlL2Int5minReceivedMSUs OBJECT-TYPE
    SYNTAX PerfIntervalCount
    MAX-ACCESS read-only
    STATUS current
    DESCRIPTION
	""
    REFERENCE
	"ITU-T Rec. Q.752, (1997) : Table 3/Q.752 3.5
	 ITU-T Rec. Q.751.1 (10/95) : receivedMSUs."
    ::= { mtpSlL2Int5minEntry 11 }


-- ====================================================================

mtpSlL2Int15minTable OBJECT-TYPE
    SYNTAX SEQUENCE OF MtpSlL2Int15minEntry
    MAX-ACCESS not-accessible
    STATUS current
    DESCRIPTION
	"Provides a 15 minute interval table for MTP Level 2 
	 statistics."
    ::= { mtpSl 12 }

mtpSlL2Int15minEntry OBJECT-TYPE
    SYNTAX MtpSlL2Int15minEntry
    MAX-ACCESS not-accessible
    STATUS current
    DESCRIPTION
	"Each entry in the table represents statistics collected for one 
	 15 minute interval.  The first interval in the table is the 
	 most recent 15 minute interval, beginning with 1."
    INDEX {
	mtpSpId, -- shared index
	mtpLsId, -- shared index
	mtpSlSlCode, -- shared index
	mtpSlL2Int15minInterval
    }
    ::= { mtpSlL2Int15minTable 1 }

MtpSlL2Int15minEntry ::= SEQUENCE {
    mtpSlL2Int15minInterval			Unsigned32,
    mtpSlL2Int15minTimestamp			TimeStamp,
    mtpSlL2Int15minSlInServiceDuration		PerfIntervalCount, -- Q.752, 1.1
    mtpSlL2Int15minSlAlignment			PerfIntervalCount, -- Q.752, 1.7
    mtpSlL2Int15minSignUnitsReceived		PerfIntervalCount, -- Q.752, 1.8
    mtpSlL2Int15minNegAckReceived		PerfIntervalCount, -- Q.752, 1.9
    mtpSlL2Int15minTransmittedOctetsSIFSIO	PerfIntervalCount, -- Q.752, 3.1
    mtpSlL2Int15minRetransmittedOctets		PerfIntervalCount, -- Q.752, 3.2
    mtpSlL2Int15minTransmittedMSUs		PerfIntervalCount, -- Q.752, 3.3
    mtpSlL2Int15minReceivedOctetsSIFSIO		PerfIntervalCount, -- Q.752, 3.4
    mtpSlL2Int15minReceivedMSUs			PerfIntervalCount  -- Q.752, 3.5
}

mtpSlL2Int15minInterval OBJECT-TYPE
    SYNTAX Unsigned32
    MAX-ACCESS not-accessible
    STATUS current
    DESCRIPTION
	""
    ::= { mtpSlL2Int15minEntry 1 }

mtpSlL2Int15minTimestamp OBJECT-TYPE
    SYNTAX TimeStamp
    MAX-ACCESS read-only
    STATUS current
    DESCRIPTION
	""
    ::= { mtpSlL2Int15minEntry 2 }

mtpSlL2Int15minSlInServiceDuration OBJECT-TYPE
    SYNTAX PerfIntervalCount
    MAX-ACCESS read-only
    STATUS current
    DESCRIPTION
	""
    REFERENCE
	"ITU-T Rec. Q.752, (1997) : Table 1/Q.752 1.1"
    ::= { mtpSlL2Int15minEntry 3 }

mtpSlL2Int15minSlAlignment OBJECT-TYPE
    SYNTAX PerfIntervalCount
    MAX-ACCESS read-only
    STATUS current
    DESCRIPTION
	""
    REFERENCE
	"ITU-T Rec. Q.752, (1997) : Table 1/Q.752 1.7
	 ITU-T Rec. Q.751.1 (10/95) : slAlignment."
    ::= { mtpSlL2Int15minEntry 4 }

mtpSlL2Int15minSignUnitsReceived OBJECT-TYPE
    SYNTAX PerfIntervalCount
    MAX-ACCESS read-only
    STATUS current
    DESCRIPTION
	""
    REFERENCE
	"ITU-T Rec. Q.752, (1997) : Table 1/Q.752 1.8
	 ITU-T Rec. Q.751.1 (10/95) : signUnitsReceived."
    ::= { mtpSlL2Int15minEntry 5 }

mtpSlL2Int15minNegAckReceived OBJECT-TYPE
    SYNTAX PerfIntervalCount
    MAX-ACCESS read-only
    STATUS current
    DESCRIPTION
	""
    REFERENCE
	"ITU-T Rec. Q.752, (1997) : Table 1/Q.752 1.9
	 ITU-T Rec. Q.751.1 (10/95) : negAckReceived."
    ::= { mtpSlL2Int15minEntry 6 }

mtpSlL2Int15minTransmittedOctetsSIFSIO OBJECT-TYPE
    SYNTAX PerfIntervalCount
    MAX-ACCESS read-only
    STATUS current
    DESCRIPTION
	""
    REFERENCE
	"ITU-T Rec. Q.752, (1997) : Table 3/Q.752 3.1
	 ITU-T Rec. Q.751.1 (10/95) : transmittedOctetsSIFSIO."
    ::= { mtpSlL2Int15minEntry 7 }

mtpSlL2Int15minRetransmittedOctets OBJECT-TYPE
    SYNTAX PerfIntervalCount
    MAX-ACCESS read-only
    STATUS current
    DESCRIPTION
	""
    REFERENCE
	"ITU-T Rec. Q.752, (1997) : Table 3/Q.752 3.2
	 ITU-T Rec. Q.751.1 (10/95) : retransmittedOctets."
    ::= { mtpSlL2Int15minEntry 8 }

mtpSlL2Int15minTransmittedMSUs OBJECT-TYPE
    SYNTAX PerfIntervalCount
    MAX-ACCESS read-only
    STATUS current
    DESCRIPTION
	""
    REFERENCE
	"ITU-T Rec. Q.752, (1997) : Table 3/Q.752 3.3
	 ITU-T Rec. Q.751.1 (10/95) : transmittedMSUs."
    ::= { mtpSlL2Int15minEntry 9 }

mtpSlL2Int15minReceivedOctetsSIFSIO OBJECT-TYPE
    SYNTAX PerfIntervalCount
    MAX-ACCESS read-only
    STATUS current
    DESCRIPTION
	""
    REFERENCE
	"ITU-T Rec. Q.752, (1997) : Table 3/Q.752 3.4
	 ITU-T Rec. Q.751.1 (10/95) : receivedOctetsSIFSIO."
    ::= { mtpSlL2Int15minEntry 10 }

mtpSlL2Int15minReceivedMSUs OBJECT-TYPE
    SYNTAX PerfIntervalCount
    MAX-ACCESS read-only
    STATUS current
    DESCRIPTION
	""
    REFERENCE
	"ITU-T Rec. Q.752, (1997) : Table 3/Q.752 3.5
	 ITU-T Rec. Q.751.1 (10/95) : receivedMSUs."
    ::= { mtpSlL2Int15minEntry 11 }


-- ====================================================================

mtpNbTable OBJECT-TYPE
    SYNTAX SEQUENCE OF MtpNbProfileEntry
    MAX-ACCESS not-accessible
    STATUS current
    DESCRIPTION
	"Provides an auxillary table of narrowband specific MTP Level 2 
	 protocol profile information for Signalling Terminals."
    REFERENCE
	""
    ::= { mtpSdt 1 }

mtpNbEntry OBJECT-TYPE
    SYNTAX MtpNbProfileEntry
    MAX-ACCESS not-accessible
    STATUS current
    DESCRIPTION
	"Each entry in this table shares an index with an entry in the 
	 mtpSlL2ProfileTable which provides the common MTP Level 2 
	 protocol profile information whereas each of these entries 
	 provides narrowband signalling link specific information."
    REFERENCE
	""
    INDEX {
	mtpSdtProfileId
    }
    ::= { mtpNbTable 1 }

MtpNbProfileEntry ::= SEQUENCE {
    mtpSdtProfileId				SimpleNameType,
    mtpNbTransmissionRate			MtpTransmissionRate,
    mtpNbTimerT8				MilliSeconds,
    mtpNbTin					Unsigned32,
    mtpNbTie					Unsigned32,
    mtpNbT					Unsigned32,
    mtpNbD					Unsigned32,
    mtpNbTe					Unsigned32,
    mtpNbDe					Unsigned32,
    mtpNbUe					Unsigned32,
    mtpNbN					Unsigned32,
    mtpNbm					Unsigned32,
    mtpNbb					Unsigned32,
    mtpNbf					INTEGER,
    mtpNbRowStatus				RowStatus
}

mtpSdtProfileId OBJECT-TYPE
    SYNTAX SimpleNameType
    MAX-ACCESS not-accessible
    STATUS current
    DESCRIPTION
	"Provides a signalling terminal protocol profile index for the 
	 narrowband, ATM SAAL and M2PA protocol profile tables."
    REFERENCE
	""
    ::= { mtpNbEntry 1 }


mtpNbTransmissionRate OBJECT-TYPE
    SYNTAX MtpTransmissionRate
    MAX-ACCESS read-create
    STATUS current
    DESCRIPTION
	"This attribute specifies the transmissionRate and implies the 
	 transmissionType (i.e. 56 and 64 kbits imply digital, 4.8 kbits 
	 implies analog transmission).  It can have one of the 
	 folllowing values:
	 
	  - kbits4point8(0), the transmission rate is for modem (4800 
	    baud, analog link);
	  - kbits56(1), the transmission rate is for DS0-A (56kbps, 
	    low-speed digital link);
	  - kbits64(2), the transmission rate is for DS0 (64kbps, 
	    low-speed digital link);
	  - kbits1544(3), the transmission rate is for T1 (1536kbps, 
	    high-speed digial link);
	  - kbits2048(4), the transmission rate is for E1 (1984kbps, 
	    high-speed digial link).
	 
	 "
    REFERENCE
	"ITU-T Rec. Q.751.1 (1997), ANSI T1.116.1 (2000), 
	 transmissionRate attribute."
    ::= { mtpNbEntry 2 }

mtpNbTimerT8 OBJECT-TYPE
    SYNTAX MilliSeconds
    UNITS "seconds"
    MAX-ACCESS read-create
    STATUS current
    DESCRIPTION
	"This is the Timer T8 which is used on high speed links (full 
	 E1, T1 or J1).  This timer value is zero (0) for low speed 
	 links.  Conceptual rows in this table that represent analog or 
	 low-speed digital links do not have this column present."
    ::= { mtpNbEntry 3 }

mtpNbTin OBJECT-TYPE
    SYNTAX Unsigned32 (4)
    MAX-ACCESS read-create
    STATUS current
    DESCRIPTION
	"This is the number of iterations of the normal proving period 
	 for low speed links.  This value is always 4.  Some 
	 implementations may permit this value to also be writable."
    DEFVAL { 4 }
    ::= { mtpNbEntry 4 }

mtpNbTie OBJECT-TYPE
    SYNTAX Unsigned32 (1)
    MAX-ACCESS read-create
    STATUS current
    DESCRIPTION
	"This is the number of iterations of the emergency proving 
	 period for low speed links.  This value is always 1.  Some 
	 implementations may permit this value to also be writable."
    DEFVAL { 1 }
    ::= { mtpNbEntry 5 }

mtpNbT OBJECT-TYPE
    SYNTAX Unsigned32 (256)
    MAX-ACCESS read-create
    STATUS current
    DESCRIPTION
	"This is the threshold on the AERM and SUERM for analog and 
	 low-speed digital links.  This value is always 256.  Conceptual 
	 rows in this table that represent high-speed digital links do 
	 not have this column present.  Some implemntations may also 
	 permit this value to also be writable."
    DEFVAL { 256 }
    ::= { mtpNbEntry 6 }

mtpNbD OBJECT-TYPE
    SYNTAX Unsigned32 (64)
    MAX-ACCESS read-create
    STATUS current
    DESCRIPTION
	"This is correct signal unit decrement threshold for the SUERM 
	 leaky bucket algorithm.  This value is always 
	 64."
    DEFVAL { 64 }
    ::= { mtpNbEntry 7 }

mtpNbTe OBJECT-TYPE
    SYNTAX Unsigned32
    MAX-ACCESS read-create
    STATUS current
    DESCRIPTION
	"This is the threshold on the Errored Interval Monitor (EIM) for 
	 high speed links.  The default value depends upon the 
	 transmission rate of the Signalling Data Link."
    ::= { mtpNbEntry 8 }

mtpNbDe OBJECT-TYPE
    SYNTAX Unsigned32
    MAX-ACCESS read-create
    STATUS current
    DESCRIPTION
	"This is the correct interval decrement for the Errored Interval 
	 Monitor (EIM) for high speed links.  The default value depends 
	 upon the transmission rate of the Signalling Data Link."
    ::= { mtpNbEntry 9 }

mtpNbUe OBJECT-TYPE
    SYNTAX Unsigned32
    MAX-ACCESS read-create
    STATUS current
    DESCRIPTION
	"This is the errored interval increment for the Errored Interval 
	 Monitor (EIM) for high speed links.  The default value depends 
	 upon the transmission rate of the Signalling Data Link."
    ::= { mtpNbEntry 10 }

mtpNbN OBJECT-TYPE
    SYNTAX Unsigned32 (16)
    MAX-ACCESS read-create
    STATUS current
    DESCRIPTION
	"This is the number of octets that will be considered as an 
	 signal unit in error when the DAEDR is in octet counting mode.  
	 This is only applicable to low speed links and is always 16."
    DEFVAL { 16 }
    ::= { mtpNbEntry 11 }

mtpNbm OBJECT-TYPE
    SYNTAX Unsigned32 (272 | 4096)
    MAX-ACCESS read-create
    STATUS current
    DESCRIPTION
	"This is the maximum size of the SIF before the DAEDR enters 
	 octet counting mode.  THe value is different for low and high 
	 speed links.  It is always 272 for low speed links and always 
	 4096 for high speed links."
    DEFVAL { 272 }
    ::= { mtpNbEntry 12 }

mtpNbb OBJECT-TYPE
    SYNTAX Unsigned32 (8 | 192 | 256)
    MAX-ACCESS read-create
    STATUS current
    DESCRIPTION
	"This is the maximum number of octets in a transmission block.  
	 It consists of 1 millisecond worth of octets and is 8 for 
	 V.35/DS0/DS0A channels, 192 for T1/J1 high speed links, and 256 
	 for E1 high speed links."
    ::= { mtpNbEntry 13 }

mtpNbf OBJECT-TYPE
    SYNTAX INTEGER {
		one(0), shared(1), two(2), three(3), four(4), five(5), 
		six(6) }
    MAX-ACCESS read-create
    STATUS current
    DESCRIPTION
	"This is the number of transmitted flags between frames counting 
	 the closing flag of the preceding frame and the opening flag of 
	 the following frame.  Some poorly designed equipment is 
	 incapable of receiving one flag between frames when idling 
	 FISUs.  This value should always default to 1.
	 
	 - one(0),
	 - shared(1),
	 - two(2),
	 - three(3),
	 - four(4),
	 - five(5),
	 - six(6)."
    DEFVAL { 0 } -- one
    ::= { mtpNbEntry 14 }

mtpNbRowStatus OBJECT-TYPE
    SYNTAX RowStatus
    MAX-ACCESS read-create
    STATUS current
    DESCRIPTION
	"Provides a mechanism whereby management stations may create and 
	 delete rows in this table.  Rows in this table provide 
	 narrowband information pertaining to the indexed 
	 mtpSlL2ProfileTable entry.  Deleting the corresponding entry in 
	 the mtpSlL2ProfileTable results in deletion of this entry."
    REFERENCE
	"STD 58, SNMPv2-TC RowStatus."
    ::= { mtpNbEntry 15 }


-- ====================================================================

mtpSaalTable OBJECT-TYPE
    SYNTAX SEQUENCE OF MtpSaalEntry
    MAX-ACCESS not-accessible
    STATUS current
    DESCRIPTION
	""
    REFERENCE
	"ITU-T Rec. Q.751.1 (1997), ANSI T1.116.1 (2000), 
	 saalNniProtocolProfile MOC."
    ::= { mtpSdt 2 }

mtpSaalEntry OBJECT-TYPE
    SYNTAX MtpSaalEntry
    MAX-ACCESS not-accessible
    STATUS current
    DESCRIPTION
	""
    REFERENCE
	"ITU-T Rec. Q.751.1 (1997), ANSI T1.116.1 (2000), 
	 saalNniProtocolProfile MO."
    INDEX {
	mtpSdtProfileId -- shared index
    }
    ::= { mtpSaalTable 1 }

MtpSaalEntry ::= SEQUENCE {
    mtpSaalBufferRelease			TruthValue,
    mtpSaalMaxCc				Unsigned32,
    mtpSaalMaxNrp				Unsigned32,
    mtpSaalMaxInformationFieldLength		Unsigned32,
    mtpSaalMaxLengthSscopUuField		Unsigned32,
    mtpSaalMaxPd				Unsigned32,
    mtpSaalMaxSscopCreditToPeer			Unsigned32,
    mtpSaalMaxStat				Unsigned32,
    mtpSaalN1					Unsigned32,
    mtpSaalNniLayerManagementProvingState	INTEGER,
    mtpSaalNniLayerManagementTimerNoCredit	TimeInterval,
    mtpSaalNniLayerManagementTimerRepeatSrec	TimeInterval,
    mtpSaalNniTimerT1				TimeInterval,
    mtpSaalNniTimerT2				TimeInterval,
    mtpSaalNniTimerT3				TimeInterval,
    mtpSaalSscopTimerCc				TimeInterval,
    mtpSaalSscopTimerIdle			TimeInterval,
    mtpSaalSscopTimerKeepAlive			TimeInterval,
    mtpSaalSscopTimerNoResponse			TimeInterval,
    mtpSaalSscopTimerPoll			TimeInterval,
    mtpSaalTransmissionRateIntervalLower	Unsigned32,
    mtpSaalTransmissionRateIntervalUpper	Unsigned32,
    mtpSaalEgressTransmissionRateIntervalLower	Unsigned32,
    mtpSaalEgressTransmissionRateIntervalUpper	Unsigned32,
    mtpSaalPollAfterRetransmission		TruthValue,
    mtpSaalRowStatus				RowStatus
}

mtpSaalBufferRelease OBJECT-TYPE
    SYNTAX TruthValue
    MAX-ACCESS read-create
    STATUS current
    DESCRIPTION
	"This attribute determines whether SSCOP can release its 
	 transmission buffer and transmission queue on connection 
	 release and can selectively release messages from the 
	 transmission buffer when older messages are still outstanding."
    REFERENCE
	"ITU-T Rec. Q.751.1 (1997), ANSI T1.116.1 (2000), bufferRelease 
	 attribute."
    ::= { mtpSaalEntry 1 }

mtpSaalMaxCc OBJECT-TYPE
    SYNTAX Unsigned32
    MAX-ACCESS read-create
    STATUS current
    DESCRIPTION
	"This attribute defines the maximum value [PDUs] of the state 
	 variable VT(CC), corresponding to the maximum number of 
	 transmissions of BGN, END, ER or RS PDUs."
    REFERENCE
	"ITU-T Rec. Q.751.1 (1997), ANSI T1.116.1 (2000), maxCc 
	 attribute."
    DEFVAL { 4 }
    ::= { mtpSaalEntry 2 }

mtpSaalMaxNrp OBJECT-TYPE
    SYNTAX Unsigned32
    MAX-ACCESS read-create
    STATUS current
    DESCRIPTION
	"This attribute defines the maximum number of retransmissions 
	 allowed during proving."
    REFERENCE
	"ITU-T Rec. Q.751.1 (1997), ANSI T1.116.1 (2000), maxNrp 
	 attribute."
    ::= { mtpSaalEntry 3 }

mtpSaalMaxInformationFieldLength OBJECT-TYPE
    SYNTAX Unsigned32
    MAX-ACCESS read-create
    STATUS current
    DESCRIPTION
	"This attribute defines the maximum length of the information 
	 field in SD PDUs, UD PDUs and MD PDUs kh.  The unit of the 
	 INTEGER value is octets."
    REFERENCE
	"ITU-T Rec. Q.751.1 (1997), ANSI T1.116.1 (2000), 
	 maxInformationFieldLength attribute."
    DEFVAL { 4096 }
    ::= { mtpSaalEntry 4 }

mtpSaalMaxLengthSscopUuField OBJECT-TYPE
    SYNTAX Unsigned32
    MAX-ACCESS read-create
    STATUS current
    DESCRIPTION
	"This attribute defines the maximum length of a variable length 
	 SSCOP UU field j.  The SSCOP UU is an optional field of BGN 
	 PDUs, BGAK PDUs, BGREJ PDUs, END PDUs and RS PDUs.  The unit of 
	 the INTEGER value is octets."
    REFERENCE
	"ITU-T Rec. Q.751.1 (1997), ANSI T1.116.1 (2000), 
	 maxLengthSscopUuField attribute."
    DEFVAL { 4 }
    ::= { mtpSaalEntry 5 }

mtpSaalMaxPd OBJECT-TYPE
    SYNTAX Unsigned32
    MAX-ACCESS read-create
    STATUS current
    DESCRIPTION
	"This attribute defines the maximum acceptable value [PDUs] of 
	 the state variable VT(PD) before sending a POLL PDU and 
	 resetting VT(PD) to zero.  The VT(PD) is incremented each time 
	 an SD PDU is transmitted."
    REFERENCE
	"ITU-T Rec. Q.751.1 (1997), ANSI T1.116.1 (2000), maxPd 
	 attribute."
    DEFVAL { 500 }
    ::= { mtpSaalEntry 6 }

mtpSaalMaxSscopCreditToPeer OBJECT-TYPE
    SYNTAX Unsigned32
    MAX-ACCESS read-create
    STATUS current
    DESCRIPTION
	"This attribute defines the absolute value [PDUs] of the size of 
	 the receive window given to the peer.  This value is added to 
	 VR(R) to generate VR(MR).  VR(MR) is mapped to N(MR) by 
	 transmission of STAT, USTAT, RS RSAK, ER, ERAK, BGN or BGAK 
	 PDUs."
    REFERENCE
	"ITU-T Rec. Q.751.1 (1997), ANSI T1.116.1 (2000), 
	 maxSscopCreditToPeer attribute."
    ::= { mtpSaalEntry 7 }

mtpSaalMaxStat OBJECT-TYPE
    SYNTAX Unsigned32
    MAX-ACCESS read-create
    STATUS current
    DESCRIPTION
	"This attribute defines the maximum number of list elements 
	 placed in a STAT PDU."
    REFERENCE
	"ITU-T Rec. Q.751.1 (1997), ANSI T1.116.1 (2000), maxStat 
	 attribute."
    DEFVAL { 67 }
    ::= { mtpSaalEntry 8 }

mtpSaalN1 OBJECT-TYPE
    SYNTAX Unsigned32
    MAX-ACCESS read-create
    STATUS current
    DESCRIPTION
	"This attribute defines the number of PDUs sent during normal 
	 proving."
    REFERENCE
	"ITU-T Rec. Q.751.1 (1997), ANSI T1.116.1 (2000), n1 attribute."
    DEFVAL { 1000 }
    ::= { mtpSaalEntry 9 }

mtpSaalNniLayerManagementProvingState OBJECT-TYPE
    SYNTAX INTEGER {
	normal(0), emergency(1), neutral(2) }
    MAX-ACCESS read-create
    STATUS current
    DESCRIPTION
	"This attribute defines the type of proving required by 
	 management.  The value of the management proving state 
	 overrides the value of proving required by MTP L3.  It can take 
	 the values: Normal, emergency neutral."
    REFERENCE
	"ITU-T Rec. Q.751.1 (1997), ANSI T1.116.1 (2000), 
	 nniLayerManagementProvingState attribute."
    ::= { mtpSaalEntry 10 }

mtpSaalNniLayerManagementTimerNoCredit OBJECT-TYPE
    SYNTAX TimeInterval
    UNITS "centiseconds"
    MAX-ACCESS read-create
    STATUS current
    DESCRIPTION
	"This attribute defines the maximum time interval that the value 
	 of VT(MS) may remain less than or equal VT(S) before the link 
	 is taken out of service.  The unit for the INTEGER value is 
	 milliseconds."
    REFERENCE
	"ITU-T Rec. Q.751.1 (1997), ANSI T1.116.1 (2000), 
	 nniLayerManagementTimerNoCredit attribute."
    ::= { mtpSaalEntry 11 }

mtpSaalNniLayerManagementTimerRepeatSrec OBJECT-TYPE
    SYNTAX TimeInterval
    UNITS "centiseconds"
    MAX-ACCESS read-create
    STATUS current
    DESCRIPTION
	"This attribute defines the minimum time between SSCOP 
	 recoveries which does not result in a release of the 
	 connection.  The unit for the INTEGER value is milliseconds."
    REFERENCE
	"ITU-T Rec. Q.751.1 (1997), ANSI T1.116.1 (2000), 
	 nniLayerManagementTimerRepeatSrec attribute."
    ::= { mtpSaalEntry 12 }

mtpSaalNniTimerT1 OBJECT-TYPE
    SYNTAX TimeInterval
    UNITS "centiseconds"
    MAX-ACCESS read-create
    STATUS current
    DESCRIPTION
	"This attribute defines the time between the link release action 
	 and the next link establish action during alignment.  The unit 
	 for the INTEGER value is milliseconds."
    REFERENCE
	"ITU-T Rec. Q.751.1 (1997), ANSI T1.116.1 (2000), nniTimerT1 
	 attribute."
    DEFVAL { 500 } -- 5 seconds
    ::= { mtpSaalEntry 13 }

mtpSaalNniTimerT2 OBJECT-TYPE
    SYNTAX TimeInterval
    UNITS "centiseconds"
    MAX-ACCESS read-create
    STATUS current
    DESCRIPTION
	"This attribute defines the total time that SSCF NNI will 
	 attempt alignment.  The unit for the INTEGER value is 
	 milliseconds."
    REFERENCE
	"ITU-T Rec. Q.751.1 (1997), ANSI T1.116.1 (2000), nniTimerT2 
	 attribute."
    DEFVAL { 3000 } -- 30 seconds
    ::= { mtpSaalEntry 14 }

mtpSaalNniTimerT3 OBJECT-TYPE
    SYNTAX TimeInterval
    UNITS "centiseconds"
    MAX-ACCESS read-create
    STATUS current
    DESCRIPTION
	"The time between proving PDUs such that proving PDUs are 
	 transmitted with half of the channel bandwidth.  The unit for 
	 the INTEGER value is microseconds."
    REFERENCE
	"ITU-T Rec. Q.751.1 (1997), ANSI T1.116.1 (2000), nniTimerT3 
	 attribute."
    ::= { mtpSaalEntry 15 }

mtpSaalSscopTimerCc OBJECT-TYPE
    SYNTAX TimeInterval
    UNITS "centiseconds"
    MAX-ACCESS read-create
    STATUS current
    DESCRIPTION
	"This attribute defines the time interval between transmissions 
	 of BGN, END, RS and ER PDUs when an acknowledge to these PDUs 
	 has not been received.  The unit for the INTEGER value is 
	 milliseconds."
    REFERENCE
	"ITU-T Rec. Q.751.1 (1997), ANSI T1.116.1 (2000), sscopTimerCc 
	 attribute."
    DEFVAL { 20 } -- 200 milliseconds
    ::= { mtpSaalEntry 16 }

mtpSaalSscopTimerIdle OBJECT-TYPE
    SYNTAX TimeInterval
    UNITS "centiseconds"
    MAX-ACCESS read-create
    STATUS current
    DESCRIPTION
	"This attribute defines the SSCOP timer IDLE.  The SSCOP 
	 connection is partitioned into phases.  The SSCOP timer IDLE 
	 supervises the idle phase.  In this phase the timer NO_RESPONSE 
	 is not running and no POLL PDUs are transmitted.  The unit for 
	 the INTEGER value is milliseconds."
    REFERENCE
	"ITU-T Rec. Q.751.1 (1997), ANSI T1.116.1 (2000), sscopTimerIdle 
	 attribute."
    DEFVAL { 10 } -- 100 milliseconds
    ::= { mtpSaalEntry 17 }

mtpSaalSscopTimerKeepAlive OBJECT-TYPE
    SYNTAX TimeInterval
    UNITS "centiseconds"
    MAX-ACCESS read-create
    STATUS current
    DESCRIPTION
	"This attribute defines the SSCOP timer KEEP_ALIVE.  The SSCOP 
	 connection is partitioned into phases.  The SSCOP timer IDLE 
	 supervises the transient phase.  In this phase there are no 
	 outstanding acknowledgements or new data pending transmission.  
	 The unit for the INTEGER value is milliseconds."
    REFERENCE
	"ITU-T Rec. Q.751.1 (1997), ANSI T1.116.1 (2000), 
	 sscopTimerKeepAlive attribute."
    DEFVAL { 10 } -- 100 milliseconds
    ::= { mtpSaalEntry 18 }

mtpSaalSscopTimerNoResponse OBJECT-TYPE
    SYNTAX TimeInterval
    UNITS "centiseconds"
    MAX-ACCESS read-create
    STATUS current
    DESCRIPTION
	"This attribute defines the SSCOP timer NO_RESPONSE.  This timer 
	 is used to detect a faulty connection.  The timer runs with 
	 either the timer POLL or KEEP_ALIVE simultaneously.  The unit 
	 for the INTEGER value is milliseconds."
    REFERENCE
	"ITU-T Rec. Q.751.1 (1997), ANSI T1.116.1 (2000), 
	 sscopTimerNoResponse attribute."
    DEFVAL { 150 } -- 1.5 seconds
    ::= { mtpSaalEntry 19 }

mtpSaalSscopTimerPoll OBJECT-TYPE
    SYNTAX TimeInterval
    UNITS "centiseconds"
    MAX-ACCESS read-create
    STATUS current
    DESCRIPTION
	"This attribute defines the SSCOP timer POLL.  The SSCOP 
	 connection is partitioned into phases.  The SSCOP timer POLL 
	 supervises the active phase.  In this new data is pending, 
	 transmission or acknowledgements are outstanding.  The unit for 
	 the INTEGER value is milliseconds."
    REFERENCE
	"ITU-T Rec. Q.751.1 (1997), ANSI T1.116.1 (2000), sscopTimerPoll 
	 attribute."
    DEFVAL { 10 } -- 100 milliseconds
    ::= { mtpSaalEntry 20 }

mtpSaalTransmissionRateIntervalLower OBJECT-TYPE
    SYNTAX Unsigned32 (64..4096)
    MAX-ACCESS read-create
    STATUS current
    DESCRIPTION
	"This attribute defines the lower and upper boundaries for the 
	 transmission rate to which the other attributes are set to fit 
	 to.
	 
	 If the conditional egressTransmissionRateInterval attribute is 
	 not present, the value of this attribute refers to both egress 
	 and ingress traffic.  If the egressTransmissionRateInterval 
	 attribute is present, the value of this attribute refers to 
	 ingress traffic only.
	 
	 The unit of the INTEGER values is kbits per second.  The whole 
	 NNI bandwidth range from 64 to 4096 kbit/s should be covered by 
	 several mtpSaalProfile instances."
    REFERENCE
	"ITU-T Rec. Q.751.1 (1997), ANSI T1.116.1 (2000), 
	 transmissionRateInterval attribute."
    DEFVAL { 129 }
    ::= { mtpSaalEntry 21 }

mtpSaalTransmissionRateIntervalUpper OBJECT-TYPE
    SYNTAX Unsigned32 (64..4096)
    MAX-ACCESS read-create
    STATUS current
    DESCRIPTION
	"This attribute defines the lower and upper boundaries for the 
	 transmission rate to which the other attributes are set to fit 
	 to.
	 
	 If the conditional egressTransmissionRateInterval attribute is 
	 not present, the value of this attribute refers to both egress 
	 and ingress traffic.  If the egressTransmissionRateInterval 
	 attribute is present, the value of this attribute refers to 
	 ingress traffic only.
	 
	 The unit of the INTEGER values is kbits per second.  The whole 
	 NNI bandwidth range from 64 to 4096 kbit/s should be covered by 
	 several mtpSaalProfile instances."
    REFERENCE
	"ITU-T Rec. Q.751.1 (1997), ANSI T1.116.1 (2000), 
	 transmissionRateInterval attribute."
    DEFVAL { 256 }
    ::= { mtpSaalEntry 22 }

mtpSaalEgressTransmissionRateIntervalLower OBJECT-TYPE
    SYNTAX Unsigned32
    MAX-ACCESS read-create
    STATUS current
    DESCRIPTION
	"This attribute defines the lower and upper boundaries for the 
	 transmission rate to which the other attributes regarding 
	 egress traffic are set to fit to.
	 
	 The unit of the INTEGER values is kbits per second.  The whole 
	 NNI bandwidth range should be covered by several mtpSaalProfile 
	 instances."
    REFERENCE
	"ITU-T Rec. Q.751.1 (1997), ANSI T1.116.1 (2000), 
	 egressTransmissionRateInterval attribute."
    ::= { mtpSaalEntry 23 }

mtpSaalEgressTransmissionRateIntervalUpper OBJECT-TYPE
    SYNTAX Unsigned32
    MAX-ACCESS read-create
    STATUS current
    DESCRIPTION
	"This attribute defines the lower and upper boundaries for the 
	 transmission rate to which the other attributes regarding 
	 egress traffic are set to fit to.
	 
	 The unit of the INTEGER values is kbits per second.  The whole 
	 NNI bandwidth range should be covered by several mtpSaalProfile 
	 instances."
    REFERENCE
	"ITU-T Rec. Q.751.1 (1997), ANSI T1.116.1 (2000), 
	 egressTransmissionRateInterval attribute."
    ::= { mtpSaalEntry 24 }

mtpSaalPollAfterRetransmission OBJECT-TYPE
    SYNTAX TruthValue
    MAX-ACCESS read-create
    STATUS current
    DESCRIPTION
	"This attribute specifies if a POLL is transmitted each time the 
	 retransmission queue is emptied."
    REFERENCE
	"ITU-T Rec. Q.751.1 (1997), ANSI T1.116.1 (2000), 
	 pollAfterRetransmission attribute."
    ::= { mtpSaalEntry 25 }

mtpSaalRowStatus OBJECT-TYPE
    SYNTAX RowStatus
    MAX-ACCESS read-create
    STATUS current
    DESCRIPTION
	"Provides a mechanism whereby management stations may create and 
	 delete rows in this table.  Asside from several default 
	 entries, entires are only created or deleted from this table by 
	 management stations.  Entries created in this table must 
	 survive an agent reboot."
    REFERENCE
	"ITU-T Rec. Q.751.1 (1997), ANSI T1.116.1 (2000), 
	     mtpSaalProtocolProfileRowStatus attribute.
	 STD 58, SNMPv2-TC RowStatus."
    ::= { mtpSaalEntry 26 }


-- ====================================================================

mtpM2paTable OBJECT-TYPE
    SYNTAX SEQUENCE OF MtpM2paEntry
    MAX-ACCESS not-accessible
    STATUS current
    DESCRIPTION
	"This table provides a table of protocol parameter profiles for 
	 M2PA signalling links.  The entries in this table are used when 
	 creating rows for M2PA signalling links to determine the 
	 initial values of protocol parameters associated with the 
	 link."
    REFERENCE
	"ITU-T Rec. Q.751.1 (1997), ANSI T1.116.1 (2000), 
	     mtpM2paProtocolProfile MOC.
	 RFC 4165, ITU-T Rec. Q.703, ITU-T Rec. Q.751.1, ANSI T1.116.1, 
	 ITU-T Rec. Q.2751.1."
    ::= { mtpSdt 3 }

mtpM2paEntry OBJECT-TYPE
    SYNTAX MtpM2paEntry
    MAX-ACCESS not-accessible
    STATUS current
    DESCRIPTION
	"Each entry in the table provides one profile which may be used 
	 when creating rows in the m2paLinkTable and is used for default 
	 values of the protocol parameters.  Each entry is indexed by 
	 protocol variant."
    REFERENCE
	"ITU-T Rec. Q.751.1 (1997), ANSI T1.116.1 (2000), 
	     mtpM2paProtocolProfile MO.
	 RFC 4165, ITU-T Rec. Q.703, ITU-T Rec. Q.751.1, ANSI T1.116.1, 
	 ITU-T Rec. Q.2751.1."
    INDEX {
	mtpSdtProfileId -- shared index
    }
    ::= { mtpM2paTable 1 }

MtpM2paEntry ::= SEQUENCE {
    mtpM2paN1					Unsigned32,
    mtpM2paProving				TruthValue,
    mtpM2paManagementProvingState		INTEGER,
    mtpM2paLoopDelayLower			MilliSeconds,
    mtpM2paLoopDelayUpper			MilliSeconds,
    mtpM2paTransmissionRateIntervalLower	Unsigned32,
    mtpM2paTransmissionRateIntervalUpper	Unsigned32,
    mtpM2paSctpNoDelay				TruthValue,
    mtpM2paSctpMaxseg				Unsigned32,
    mtpM2paSctpHeartbeatItvl			MilliSeconds,
    mtpM2paSctpHeartbeat			TruthValue,
    mtpM2paSctpRtoInitial			MilliSeconds,
    mtpM2paSctpRtoMin				MilliSeconds,
    mtpM2paSctpRtoMax				MilliSeconds,
    mtpM2paSctpPathMaxRetrans			Unsigned32,
    mtpM2paSctpCookieLife			MilliSeconds,
    mtpM2paSctpCookieInc			MilliSeconds,
    mtpM2paSctpMaxInitRetries			Unsigned32,
    mtpM2paSctpMaxBurst				Unsigned32,
    mtpM2paSctpAssocMaxRetrans			Unsigned32,
    mtpM2paSctpSackDelay			MilliSeconds,
    mtpM2paSctpLifetime				MilliSeconds,
    mtpM2paProvingAttempts			Unsigned32,
    mtpM2paRowStatus				RowStatus
}

mtpM2paN1 OBJECT-TYPE
    SYNTAX Unsigned32
    MAX-ACCESS read-create
    STATUS current
    DESCRIPTION
	"This column defines the number of PDUs sent during normal 
	 proving."
    REFERENCE
	"ITU-T Rec. Q.2751.1 (1997) n1."
    DEFVAL { 1000 }
    ::= { mtpM2paEntry 1 }

mtpM2paProving OBJECT-TYPE
    SYNTAX TruthValue
    MAX-ACCESS read-create
    STATUS current
    DESCRIPTION
	"This column defines whether the M2PA signalling link using this 
	 M2PA protocol profile will, when true(1),  perform proving in 
	 accordance with Q.703, ANSI T1.111.3, and optional Q.2140 
	 procedures, or whether the M2PA signalling link will, when 
	 false(2), forego proving althogether."
    REFERENCE
	""
    DEFVAL { 1 } -- true
    ::= { mtpM2paEntry 2 }

mtpM2paManagementProvingState OBJECT-TYPE
    SYNTAX INTEGER {
	normal(0), emergency(1), neutral(2) }
    MAX-ACCESS read-create
    STATUS current
    DESCRIPTION
	"This column defines the type of proving required by management.  
	 The value of the management proving state overrides the value 
	 of proving required by MTP L3.  It can take the values:
	  - normal: normal proving is always applied to the signalling 
	    link;
	  - emergency: emergency proving is always applied to the 
	    signalling link;
	  - neutral: whichever form of proving is requested by MTP L3 is 
	    applied to the signalling link.
	 This column only takes effect when mtpM2paProving is true(1).  
	 When mtpM2paProving is false(2), no proving is performed."
    REFERENCE
	"ITU-T Rec. Q.2751.1 (1997) nniLayerManagementProvingState."
    ::= { mtpM2paEntry 3 }

mtpM2paLoopDelayLower OBJECT-TYPE
    SYNTAX MilliSeconds
    UNITS "seconds"
    MAX-ACCESS read-create
    STATUS current
    DESCRIPTION
	"This column defines the lower boundary for the loop delay 
	 (round trip time) for which the other attributes in the 
	 conceptual row are applicable.    The lower M2PA loop delay 
	 must be less than the upper M2PA loop delay.  The range defined 
	 by the lower and upper M2PA loop delay and the range defined by 
	 the lower and upper M2PA transmission rate cannot overlap in 
	 conjunction with another pair of ranges belonging to another 
	 entry belonging to the same managed switching system and 
	 network entity."
    REFERENCE
	""
    ::= { mtpM2paEntry 4 }

mtpM2paLoopDelayUpper OBJECT-TYPE
    SYNTAX MilliSeconds
    UNITS "seconds"
    MAX-ACCESS read-create
    STATUS current
    DESCRIPTION
	"This column defines the upper boundary for the loop delay 
	 (round trip time) for which the other attributes in the 
	 conceptual row are applicable.  The upper M2PA loop delay must 
	 be greater than the lower M2PA loop delay.  The range defined 
	 by the lower and upper M2PA loop delay and the range defined by 
	 the lower and upper M2PA transmission rate cannot overlap in 
	 conjunction with another pair of ranges belonging to another 
	 entry belonging to the same managed switching system and 
	 network entity."
    REFERENCE
	""
    ::= { mtpM2paEntry 5 }

mtpM2paTransmissionRateIntervalLower OBJECT-TYPE
    SYNTAX Unsigned32
    UNITS "bits per second"
    MAX-ACCESS read-create
    STATUS current
    DESCRIPTION
	"This column defines the lower boundary for the transmission 
	 rate range for which the other attributes in the conceptual row 
	 are applicable.  The lower M2PA transmission rate must be less 
	 than the upper M2PA transmission rate.  The range defined by 
	 the lower and upper M2PA transmission rates and the range 
	 defined byt he lower and upper M2PA loop delay cannot overlap 
	 in conjunction with another pair of ranges belonging to another 
	 entry belonging to the same managed switching element and 
	 network entity."
    REFERENCE
	""
    ::= { mtpM2paEntry 6 }

mtpM2paTransmissionRateIntervalUpper OBJECT-TYPE
    SYNTAX Unsigned32
    UNITS "bits per second"
    MAX-ACCESS read-create
    STATUS current
    DESCRIPTION
	"This column defines the upper boundary for the transmission 
	 rate range for which the other attributes in the conceptual row 
	 are applicable.  The upper M2PA transmission rate must be 
	 greater than the lower M2PA transmission rate.  The range 
	 defined by the lower and upper M2PA transmission rates and the 
	 range defined byt he lower and upper M2PA loop delay cannot 
	 overlap in conjunction with another pair of ranges belonging to 
	 another entry belonging to the same managed switching element 
	 and network entity."
    REFERENCE
	""
    ::= { mtpM2paEntry 7 }

mtpM2paSctpNoDelay OBJECT-TYPE
    SYNTAX TruthValue
    MAX-ACCESS read-create
    STATUS current
    DESCRIPTION
	"This column defines, under this M2PA profile, whether the Nagle 
	 algorithm should be applied to SCTP associations.  The Nagle 
	 algorithm increases the size of the packets placed on the 
	 network at the expense of delaying the transmission of some 
	 data during congestion episodes.  When set to true(1), the 
	 Nagle algorithm is suppresed; otherwise, set to false(2), the 
	 Nagle algorithm is in effect.
	 
	 The default value is determined by the setting of 
	 mtpM2paDefaultSctpNoDelay."
    REFERENCE
	""
    ::= { mtpM2paEntry 8 }

mtpM2paSctpMaxseg OBJECT-TYPE
    SYNTAX Unsigned32 (1..65536)
    UNITS "octets"
    MAX-ACCESS read-create
    STATUS current
    DESCRIPTION
	"This column defines the maximum SCTP payload size for outgoing 
	 packets.  Values greater than the association MTU are ignored 
	 and have no effect.  The value determines the maximum size (in 
	 octets) above which SCCP will fragment larger DATA chunis into 
	 smaller DATA chunks, and beneath which SCTP will bundle DATA 
	 chunks into a single packate or combine smaller DATA chunks 
	 into larger DATA chunks.  Normally this value is the 
	 association MTU value must the size of the current IP and SCTP 
	 headers, minus the size of one DATA chunk header.  When set to 
	 a lower value, the lower value will be used.
	 
	 The default value is determined by the setting of 
	 mtpM2paDefaultSctpMaxseg."
    REFERENCE
	""
    ::= { mtpM2paEntry 9 }

mtpM2paSctpHeartbeatItvl OBJECT-TYPE
    SYNTAX MilliSeconds
    UNITS "seconds"
    MAX-ACCESS read-create
    STATUS current
    DESCRIPTION
	"This column defines the time interval (in milliseconds) between 
	 successive HEARTBEAT messages used to probe destination 
	 transport addresses for RTT calculation and activity.  Valid 
	 values are zero (0) - do not heartbeat, or a value of 1 
	 millisecond or greater.
	 
	 The default value is determined by the setting of 
	 m2paDefaultHeartbeatItvl."
    REFERENCE
	""
    ::= { mtpM2paEntry 10 }

mtpM2paSctpHeartbeat OBJECT-TYPE
    SYNTAX TruthValue
    MAX-ACCESS read-create
    STATUS current
    DESCRIPTION
	"This column determines whether HEARTBEAT messages used to probe 
	 destination transport addresses for RTT calculation and 
	 activity will be sent periodically.  The default value from RFC 
	 2960 is true(1).
	 
	 Disabling heartbeats reduces the protocol's responsiveness in 
	 detection of failures and redirection of traffic away from 
	 failed paths and interfaces.  This column should normally be 
	 left at its default value.
	 
	 The default value is determined by the setting of 
	 mtpM2paDefaultSctpHeartbeat."
    REFERENCE
	""
    ::= { mtpM2paEntry 11 }

mtpM2paSctpRtoInitial OBJECT-TYPE
    SYNTAX MilliSeconds
    UNITS "seconds"
    MAX-ACCESS read-create
    STATUS current
    DESCRIPTION
	"This column defines the initial time interval (in milliseconds) 
	 that will be used as an initial RTO (retransmission timeout) 
	 value when sending packets to a destination for the first time.  
	 Valid values are zero or greater but must be within the range 
	 mtpM2paSctpRtoMin to mtpM2paSctpRtoMax.  The default value is 
	 the value recommended by RFC 2960 and RFC 4960 (1000 
	 milliseconds, or 1 second).
	 
	 Note that, in general, the RTO initial should not be less than 
	 the peer's maximum SACK delay, otherwise, excessive 
	 retransmission migh occur while the peer is delaying 
	 acknowledgements.
	 
	 The default value is determined by the setting of 
	 mtpM2paDefaultSctpRtoInitial."
    REFERENCE
	""
    ::= { mtpM2paEntry 12 }

mtpM2paSctpRtoMin OBJECT-TYPE
    SYNTAX MilliSeconds
    UNITS "seconds"
    MAX-ACCESS read-create
    STATUS current
    DESCRIPTION
	"This column defines the minimum timer interval (in 
	 milliseconds) that will be used as an RTO (retranmission 
	 timeout) value when sending packets to a destination transport 
	 address and expecting acknowledgements.  Valid values are zero 
	 or greater and must be less than or equal to 
	 mtpM2paSctpRtoInitial and strictly less than and 
	 mtpM2paSctpRtoMax.  The default value is the value recommended 
	 by RFC 2960 and RFC 4960 (1000 milliseconds, or 1 second).
	 
	 Note that, in general, the RTO minimum should not be less than 
	 the peer's maximum SACK delay, otherwise, excessive 
	 retransmission migh occur while the peer is delaying 
	 acknowledgements.
	 
	 The default value is determined by the setting of 
	 mtpM2paDefaultSctpRtoMin."
    REFERENCE
	""
    ::= { mtpM2paEntry 13 }

mtpM2paSctpRtoMax OBJECT-TYPE
    SYNTAX MilliSeconds
    UNITS "seconds"
    MAX-ACCESS read-create
    STATUS current
    DESCRIPTION
	"This column defines the maximum time interval (in milliseconds) 
	 that will be used as an RTO (retransmission timeout) value when 
	 sending packets t a destination transport address and expecting 
	 acknowledgements.  Valid values are zero or greater but must be 
	 greater than or equal to mtpM2paSctpRtoInitial and strictly 
	 greater than mtpM2paSctpRtoMin.  The default value is the value 
	 recommended by RFC 2960 and RFC 4960 (60000 milliseconds, or 60 
	 seconds).
	 
	 Note that, in general, the RTO maximum should not be less than 
	 the peer's maximum SACK delay, otherwise, excessive 
	 retransmission migh occur while the peer is delaying 
	 acknowledgements.
	 
	 The default value is determined by the setting of 
	 mtpM2paDefaultSctpRtoMax."
    REFERENCE
	""
    ::= { mtpM2paEntry 14 }

mtpM2paSctpPathMaxRetrans OBJECT-TYPE
    SYNTAX Unsigned32
    UNITS "retransmissions"
    MAX-ACCESS read-create
    STATUS current
    DESCRIPTION
	"This column defines the number of times that SCTP will attempt 
	 retransmitting a packet to a given detination transport address 
	 before it considers that destination transport address 
	 inactive.  Valid values are zero or greater.  The default value 
	 is the value recommended in RFC 2960 (5 retransmissions).
	 
	 Adjusting this value has an effect on th period of time taken 
	 to fail-over between destinations for multi-homed connections.  
	 Lower values (including zero) will yield faster fail-over 
	 response times.  Lower values, however, may cause thrashing 
	 between destinations contributing to congestion in the network.  
	 Deafult values are applicable to Internet applicaions.
	 
	 The default value is determined by the setting of 
	 mtpM2paDefaultSctpPathMaxRetrans."
    REFERENCE
	""
    ::= { mtpM2paEntry 15 }

mtpM2paSctpCookieLife OBJECT-TYPE
    SYNTAX MilliSeconds
    UNITS "seconds"
    MAX-ACCESS read-create
    STATUS current
    DESCRIPTION
	"This column defines the time interval (in milliseconds) in 
	 conjunction with mtpM2paSctpCookieInc beyond which a 
	 COOKIE-ECHO received with a cookie sent in an INIT-ACK will no 
	 longer be accepted.  For SCTP, this also limits the maximum 
	 time interval for which the HMAC secret key for the cookie will 
	 be valid.  Valid values are zero or greater.  Values of zero 
	 will  be converted to a system clock tick.  The default value 
	 is the value recommended by RFC 2960 (60,000 milliseconds, or 
	 60 seconds).
	 
	 Reducing this value will increase the probability that passive 
	 connection attempts will fail due to expired cookies.  
	 Increasing the value will reduce the overall security of the 
	 system by permitting attackers an increased interval within 
	 which to crack HMACs and guess verification tags.  This value 
	 may be adjusted in conjunction with mtpM2paSctpCookieInc to 
	 meet most objectives for successful passive connection attempts 
	 with the best security afforded by smaller values of 
	 mtpM2paSctpCookieLife.
	 
	 Unfortunately, the mtpM2paSctpCookieLife and 
	 mtpM2paSctpCookieInc must be adjusted to accomodate the slowest 
	 peer on the slowest connection.  The default setting is 
	 adequate for Internet applications.
	 
	 The default value is determined by the setting of 
	 mtpM2paDefaultSctpCookieLife."
    REFERENCE
	""
    ::= { mtpM2paEntry 16 }

mtpM2paSctpCookieInc OBJECT-TYPE
    SYNTAX MilliSeconds
    UNITS "seconds"
    MAX-ACCESS read-create
    STATUS current
    DESCRIPTION
	"This column defines the time increment (in milliseconds) that 
	 will be added to the lifespan of the cookie in an INIT-ACK if 
	 the recieved INIT requests cookie preservative to lengthen the 
	 lifespan of the cookie.  Valid values are zero or greater.  The 
	 default value is the value recommended in RFC 
	 2960 5.2.6 (1000 milliseconds, or 1 second).
	 
	 This value can be adjusted in conjunction with 
	 mtpM2paSctpCookieLife to meet objectives of successful passive 
	 connection attempts and security.  The default setting is 
	 adequate for Internet applications.
	 
	 The default value is determined by the setting of 
	 mtpM2paDefaultSctpCookieInc."
    REFERENCE
	""
    ::= { mtpM2paEntry 17 }

mtpM2paSctpMaxInitRetries OBJECT-TYPE
    SYNTAX Unsigned32
    UNITS "retries"
    MAX-ACCESS read-create
    STATUS current
    DESCRIPTION
	"This column defines the number of times that an INIT or 
	 COOKIE-ECHO will be resent to a given destination before 
	 abandoning an active open attempt.  Value values are zero or 
	 greater.  The default value is the value recommended by RFC 
	 2960 (8 retries).
	 
	 The default value is determined by the setting of 
	 mtpM2paDefaultSctpMaxInitRetries."
    REFERENCE
	""
    ::= { mtpM2paEntry 18 }

mtpM2paSctpMaxBurst OBJECT-TYPE
    SYNTAX Unsigned32
    UNITS "packets"
    MAX-ACCESS read-create
    STATUS current
    DESCRIPTION
	"This column defines the maximum number of MTUs of new data 
	 chunks that will be sent in a burst in accordance with SCTP 
	 Specification Errata and Issues, RFC 4460 and RFC 4960.  The 
	 default value is the value recommended in RFC 4960 (4 MTUs).
	 
	 The default value is determined by the setting of 
	 mtpM2paDefaultSctpMaxBurst."
    REFERENCE
	""
    ::= { mtpM2paEntry 19 }

mtpM2paSctpAssocMaxRetrans OBJECT-TYPE
    SYNTAX Unsigned32
    UNITS "retransmissions"
    MAX-ACCESS read-create
    STATUS current
    DESCRIPTION
	"This column defines the number of times that the sending 
	 endpoint will attempt retransmitting a packet on any active 
	 destination transport address before it aborts the association.  
	 Value values are zero or greater.  The default value is the 
	 value recommended in RFC 2960 (10 retransmissions).
	 
	 This value should be larger  than sum of the path maximum 
	 number of retransmission values of each of the destinations.
	 
	 Setting this value to less than the sum of the path maximum 
	 retransmission values for all of the destinations has the 
	 interesting effect of permitting a connection to persist even 
	 when all destinations have been deemed inactive.
	 
	 The default value is determined by the setting of 
	 m2paDefaultAssocMaxRetrans."
    REFERENCE
	""
    DEFVAL { 20 } -- 200 milliseconds
    ::= { mtpM2paEntry 20 }

mtpM2paSctpSackDelay OBJECT-TYPE
    SYNTAX MilliSeconds (0..50)
    UNITS "seconds"
    MAX-ACCESS read-create
    STATUS current
    DESCRIPTION
	"This column defines the interval of time (in milliseconds) that 
	 will be used as an RTO (retransmission timeout) value when 
	 sending packets to a destination transport address.  Valid 
	 values are zero or to 500 milliseconds (RFC 2960 forbits 
	 setting this value larger than 500 milliseconds).  The default 
	 value is the value recommended in RFC 2960 (200 milliseconds).
	 
	 The default value is determined by the setting of 
	 mtpM2paDefaultSctpSackDelay."
    REFERENCE
	""
    DEFVAL { 20 } -- 200 milliseconds
    ::= { mtpM2paEntry 21 }

mtpM2paSctpLifetime OBJECT-TYPE
    SYNTAX MilliSeconds
    UNITS "seconds"
    MAX-ACCESS read-create
    STATUS current
    DESCRIPTION
	"The default value is determined by the setting of 
	 mtpM2paDefaultSctpLifetime."
    REFERENCE
	""
    ::= { mtpM2paEntry 22 }

mtpM2paProvingAttempts OBJECT-TYPE
    SYNTAX Unsigned32
    MAX-ACCESS read-create
    STATUS current
    DESCRIPTION
	"Defines the number of unsuccesful proving attempts that will be 
	 conducted during link alignment before the alignment procedures 
	 will be considered unsuccessful."
    REFERENCE
	""
    ::= { mtpM2paEntry 23 }

mtpM2paRowStatus OBJECT-TYPE
    SYNTAX RowStatus
    MAX-ACCESS read-create
    STATUS current
    DESCRIPTION
	"Provides a mechanism whereby management stations, following the 
	 RowStatus textual convention from the SNMPv2-TC module, may 
	 create or destroy conceptual rows in this table."
    REFERENCE
	"STD 58, SNMPv2-TC RowStatus."
    ::= { mtpM2paEntry 24 }


-- ====================================================================

mtpSdtTable OBJECT-TYPE
    SYNTAX SEQUENCE OF MtpSdtEntry
    MAX-ACCESS not-accessible
    STATUS current
    DESCRIPTION
	"This is the Signalling Data Terminal table.  Each entry in this 
	 table represents a Signalling Data Terminal.
	 
	 The signTerm MOC defines the management capabilities for the 
	 signalling terminal.  The signalling terminal is defined in 
	 ITU-T Rec. Q.703."
    REFERENCE
	"ITU-T Rec. Q.751.1 (1997), ANSI T1.116.1 (2000), signTerm MOC."
    ::= { mtpSdt 4 }

mtpSdtEntry OBJECT-TYPE
    SYNTAX MtpSdtEntry
    MAX-ACCESS not-accessible
    STATUS current
    DESCRIPTION
	"An entry (row) in the mtpSdtTable."
    REFERENCE
	"ITU-T Rec. Q.751.1 (1997), ANSI T1.116.1 (2000), signTerm MO."
    INDEX {
	mtpSdtId
    }
    ::= { mtpSdtTable 1 }

MtpSdtEntry ::= SEQUENCE {
    mtpSdtId					Unsigned32,
    mtpSdtAdministrativeState			AdministrativeState,
    mtpSdtOperationalState			OperationalState,
    mtpSdtUsageState				UsageState,
    mtpSdtProceduralStatus			ProceduralStatus,
    mtpSdtAvailabilityStatus			AvailabilityStatus,
    mtpSdtEquipmentPointer			RowPointer,
    mtpSdtName					CommonLanguageName,
    mtpSdtProfilePointer			RowPointer,
    mtpSdtRowStatus				RowStatus
}

mtpSdtId OBJECT-TYPE
    SYNTAX Unsigned32
    MAX-ACCESS not-accessible
    STATUS current
    DESCRIPTION
	"This attribute is used for naming instances."
    REFERENCE
	"ITU-T Rec. Q.751.1 (1997), ANSI T1.116.1 (2000), signTermId 
	 attribute."
    ::= { mtpSdtEntry 1 }

mtpSdtAdministrativeState OBJECT-TYPE
    SYNTAX AdministrativeState
    MAX-ACCESS read-create
    STATUS current
    DESCRIPTION
	"Provides the administrative state of the signalling terminal 
	 following the AdministativeState textual convention of the 
	 OPENSS7-SMI-MIB module and ITU-T Rec. X.721 | ISO/IEC 10165-2.

	  - locked(0), 
	  - unlocked(1), 
	  - shuttingDown(2), 
	"
    REFERENCE
	"ITU-T Rec. Q.751.1 (1997), ANSI T1.116.1 (2000) : 
	     administrativeState attribute.
	 ITU-T Rec. Q.751.1 (1997), ANSI T1.116.1 (2000) : 
	     administrativeState attribute."
    DEFVAL { 0 } -- locked
    ::= { mtpSdtEntry 2 }

mtpSdtOperationalState OBJECT-TYPE
    SYNTAX OperationalState
    MAX-ACCESS read-only
    STATUS current
    DESCRIPTION
	"Provides the operational state of the signalling terminal 
	 following the OperationalState textual convention of the 
	 OPENSS7-SMI-MIB module and ITU-T Rec. X.721 | ISO/IEC 10165-2.
	 
	  - disabled(0), 
	  - enabled(1), 
	 "
    REFERENCE
	"ITU-T Rec. X.721 (1992) | ISO/IEC 10165-2 : 1992, 
	     Attribute-ASN1Module.OperationalState.
	 ITU-T Rec. X.731 (1992) | ISO/IEC 10164-2 : 1993, 
	     Section 8.1.1.1.
	 ITU-T Rec. Q.751.1 (1997), ANSI T1.116.1 (2000), 
	     operationalState attribute."
    DEFVAL { 0 } -- disabled
    ::= { mtpSdtEntry 3 }

mtpSdtUsageState OBJECT-TYPE
    SYNTAX UsageState
    MAX-ACCESS read-only
    STATUS current
    DESCRIPTION
	"Provides the usage state of the signalling terminal following 
	 the UsageState textual convention of the OPENSS7-SMI-MIB module 
	 and ITU-T Rec. X.721 | ISO/IEC 10165-2.

	  - idle(0),
	  - active(1),
	  - busy(2),
	 "
    REFERENCE
	"ITU-T Rec. Q.751.1 (1997), ANSI T1.116.1 (2000), usageState 
	     attribute."
    DEFVAL { 0 } -- idle
    ::= { mtpSdtEntry 4 }

mtpSdtProceduralStatus OBJECT-TYPE
    SYNTAX ProceduralStatus
    MAX-ACCESS read-only
    STATUS current
    DESCRIPTION
	"Provides the procedural status of the signalling terminal 
	 following the ProceduralStatus textual convention of the 
	 OPENSS7-SMI-MIB module and ITU-T Rec. X.721 | ISO/IEC 10165-2.
	 
	  - initializationRequired(0),
	  - notInitialized(1),
	  - initializing(2),
	  - reporting(3),
	  - terminating(4),
	 "
    REFERENCE
	"ITU-T Rec. Q.751.1 (1997), ANSI T1.116.1 (2000), 
	 proceduralStatus attribute."
    ::= { mtpSdtEntry 5 }

mtpSdtAvailabilityStatus OBJECT-TYPE
    SYNTAX AvailabilityStatus
    MAX-ACCESS read-only
    STATUS current
    DESCRIPTION
	"Provides the availabilty status of the signalling terminal 
	 following the AvailabilityStatus textual convention of the 
	 OPENSS7-SMI-MIB module and ITU-T Rec. X.721 | ISO/IEC 
	 10165-2.
	 
	  - inTest(0),
	  - failed(1),
	  - powerOff(2),
	  - offLine(3),
	  - offDuty(4),
	  - dependency(5),
	  - degraded(6),
	  - notInstalled(7),
	  - logFull(8),
	"
    REFERENCE
	"ITU-T Rec. X.721 | ISO/IEC 10165-2, availabilityStatus 
	     attribute.
	 ITU-T Rec. Q.751.1 (1997), ANSI T1.116.1 (2000), 
	     availabilityStatus attribute."
    ::= { mtpSdtEntry 6 }

mtpSdtEquipmentPointer OBJECT-TYPE
    SYNTAX RowPointer
    MAX-ACCESS read-create
    STATUS current
    DESCRIPTION
	"This attribute is used to reference physical equipment."
    REFERENCE
	"ITU-T Rec. Q.751.1 (1997), ANSI T1.116.1 (2000), 
	     equipmentPointer attribute."
    DEFVAL { { zeroDotZero } }
    ::= { mtpSdtEntry 7 }

mtpSdtName OBJECT-TYPE
    SYNTAX CommonLanguageName
    MAX-ACCESS read-create
    STATUS current
    DESCRIPTION
	"This attribute is an additional name for instances of the 
	 signTerm managed object class."
    REFERENCE
	"ITU-T Rec. Q.751.1 (1997), ANSI T1.116.1 (2000), signTermName 
	 attribute."
    ::= { mtpSdtEntry 8 }

mtpSdtProfilePointer OBJECT-TYPE
    SYNTAX RowPointer
    MAX-ACCESS read-create
    STATUS current
    DESCRIPTION
	"Provides a pointer to a signalling terminal protocol profile to 
	 be used with the signalling terminal.  This points to an entry 
	 in the mtpNbTable, an entry in the mtpSaalTable or a entry in 
	 the mtpM2paTable, as appropriate."
    REFERENCE
	""
    ::= { mtpSdtEntry 9 }

mtpSdtRowStatus OBJECT-TYPE
    SYNTAX RowStatus
    MAX-ACCESS read-create
    STATUS current
    DESCRIPTION
	"Provides a mechanism whereby management stations may create and 
	 delete rows in this table.
	 
	 A create request is rejected if the equipmentPointer would 
	 reference equipment that does not exist.  If the name package 
	 is supported: a create request with a value for the name 
	 attribute that is already used by another instance of the same 
	 object class will be rejected."
    REFERENCE
	"STD 58, SNMPv2-TC RowStatus.
	 ITU-T Rec. Q.751.1 (1997) : managedSwitchingElement-signTerm 
	     NAME BINDING."
    ::= { mtpSdtEntry 10 }


-- ====================================================================

mtpSdtStatsTable OBJECT-TYPE
    SYNTAX SEQUENCE OF MtpSdtStatsEntry
    MAX-ACCESS not-accessible
    STATUS current
    DESCRIPTION
	"This is the SDT statistics table.  It provides statistics 
	 associated with signalling terminals."
    ::= { mtpSdt 5 }

mtpSdtStatsEntry OBJECT-TYPE
    SYNTAX MtpSdtStatsEntry
    MAX-ACCESS not-accessible
    STATUS current
    DESCRIPTION
	"This is an entry in the SDT statistics table.  Each entry 
	 contains statistics associated with a single signalling 
	 terminal.  The entries are indexed using the same index as is 
	 used for the signalling terminal configuration and state table, 
	 and the statistics are corelated with the signalling terminal 
	 using that index.  Whenever a row exists in the signalling 
	 terminal table, a corresponding row with the same index exists 
	 in this table.
	 
	 A management station may continually walk this table, repeating 
	 every second or so, to collect near real-time statistics on the 
	 OpenSS7 implementations.  Note, however, that for general SS7 
	 implementations, statistics should be collected not more 
	 rapidly than on five minute intervals.  Notifications are 
	 provided for significant events to preclude the need for 
	 polling these tables.."
    AUGMENTS    { mtpSdtEntry }
    ::= { mtpSdtStatsTable 1 }

MtpSdtStatsEntry ::= SEQUENCE {
    mtpSdtStatsTxBytes				Counter32,
    mtpSdtStatsTxSus				Counter32,
    mtpSdtStatsTxSusRepeated			Counter32,
    mtpSdtStatsTxUnderruns			Counter32,
    mtpSdtStatsTxAborts				Counter32,
    mtpSdtStatsTxBufferOverflows		Counter32,
    mtpSdtStatsTxSusInError			Counter32,
    mtpSdtStatsRxBytes				Counter32,
    mtpSdtStatsRxSusCompressed			Counter32,
    mtpSdtStatsRxOverruns			Counter32,
    mtpSdtStatsRxAborts				Counter32,
    mtpSdtStatsRxBufferOverflows		Counter32,
    mtpSdtStatsRxSusInError			Counter32,
    mtpSdtStatsRxSyncTransitions		Counter32,
    mtpSdtStatsRxBitsOctetCounted		Counter32,
    mtpSdtStatsRxCrcErrors			Counter32,
    mtpSdtStatsRxFrameErrors			Counter32,
    mtpSdtStatsRxFrameOverflows			Counter32,
    mtpSdtStatsRxFrameTooLong			Counter32,
    mtpSdtStatsRxFrameTooShort			Counter32,
    mtpSdtStatsRxResidueErrors			Counter32,
    mtpSdtStatsCarrierCtsLost			Counter32,
    mtpSdtStatsCarrierDcdLost			Counter32,
    mtpSdtStatsCarrierLost			Counter32
}

mtpSdtStatsTxBytes OBJECT-TYPE
    SYNTAX Counter32
    UNITS "Octets"
    MAX-ACCESS read-only
    STATUS current
    DESCRIPTION
	"This is the count of the number of octets transmitted by the 
	 signalling terminal.  This count should increase rapidly during 
	 normal operation.  When this count does not increase, it means 
	 that the transmitters are not transmitting data."
    DEFVAL { 0 }
    ::= { mtpSdtStatsEntry 1 }

mtpSdtStatsTxSus OBJECT-TYPE
    SYNTAX Counter32
    UNITS "Signal Units"
    MAX-ACCESS read-only
    STATUS current
    DESCRIPTION
	"This is the number of signal units transmitted by the 
	 signalling terminal, it includes repeated SUs.  This count 
	 should increase rapidly during normal operation.  When this 
	 count does not increase, it means that the signalling terminal 
	 is not transmitting SUs."
    DEFVAL { 0 }
    ::= { mtpSdtStatsEntry 2 }

mtpSdtStatsTxSusRepeated OBJECT-TYPE
    SYNTAX Counter32
    UNITS "Signal Units"
    MAX-ACCESS read-only
    STATUS current
    DESCRIPTION
	"This is the count of the number of signal units repeated.  A 
	 signal unit is repeated when there is no additional signal unit 
	 waiting to be transmitted so the signalling terminal generates 
	 another copy of an LSSU or FISU, or if the last frame 
	 transmitted was an MSUs, a FISU is generated from the MSU 
	 previously sent.  This count should increase rapidly while idle 
	 (e.g. idling FISUs) during normal operation.  It is also normal 
	 for this count to not increase when the line is busy (activiely 
	 carrying a significant traffic load of MSUs."
    DEFVAL { 0 }
    ::= { mtpSdtStatsEntry 3 }

mtpSdtStatsTxUnderruns OBJECT-TYPE
    SYNTAX Counter32
    UNITS "Events"
    MAX-ACCESS read-only
    STATUS current
    DESCRIPTION
	"This is the count of the number of transmitter underrun events.  
	 A transmitter underrun event occurs when an unsufficient number 
	 of bits where provided to the signalling data link when the 
	 time came to transmit bits on the wire.  This count should not 
	 increase past possibly a small number when the link  is 
	 initialized for the first time.  Large counts here represent a 
	 significant problem."
    DEFVAL { 0 }
    ::= { mtpSdtStatsEntry 4 }

mtpSdtStatsTxAborts OBJECT-TYPE
    SYNTAX Counter32
    UNITS "Events"
    MAX-ACCESS read-only
    STATUS current
    DESCRIPTION
	"This is the count of the number of aborts transmitted.  The 
	 drivers do not normally transmit aborts (unless specifically 
	 requested to for test purposes).  This count should be low or 
	 zero.  A significant number here represents a heavy testing or 
	 a significant problem."
    DEFVAL { 0 }
    ::= { mtpSdtStatsEntry 5 }

mtpSdtStatsTxBufferOverflows OBJECT-TYPE
    SYNTAX Counter32
    UNITS "Events"
    MAX-ACCESS read-only
    STATUS current
    DESCRIPTION
	"This is the count of the number of transmit buffer overflow 
	 events.  A transmit  overflow event occurs when the signalling 
	 terminal goes to acquire a buffer to transmit data bits to the 
	 signalling data link and cannot immediately acquire a buffer, 
	 resulting in data loss.  The drivers recycle recieve buffers 
	 into transmit buffers from and to the signalling data link.  
	 There should be no counts in this item.  A significant number 
	 here would represent a significant problem."
    DEFVAL { 0 }
    ::= { mtpSdtStatsEntry 6 }

mtpSdtStatsTxSusInError OBJECT-TYPE
    SYNTAX Counter32
    UNITS "Signal Units"
    MAX-ACCESS read-only
    STATUS current
    DESCRIPTION
	"This is the count of signal units transmitted in error.  The 
	 drivers do not normally transmit signal units in error, unless 
	 requested to do so for testing purposes.  This count should be 
	 low or zero.  A significant number here reflects heavy testing 
	 or a significant error."
    DEFVAL { 0 }
    ::= { mtpSdtStatsEntry 7 }

mtpSdtStatsRxBytes OBJECT-TYPE
    SYNTAX Counter32
    UNITS "Octets"
    MAX-ACCESS read-only
    STATUS current
    DESCRIPTION
	"This count is the number of octets received by the signalling 
	 terminal from the signalling data link.  This number should 
	 increase rapidly under normal operation."
    DEFVAL { 0 }
    ::= { mtpSdtStatsEntry 8 }

mtpSdtStatsRxSusCompressed OBJECT-TYPE
    SYNTAX Counter32
    UNITS "Signal Units"
    MAX-ACCESS read-only
    STATUS current
    DESCRIPTION
	"This count is the number of signal units that were compressed 
	 on input.  Each signal unit that would otherwise have been 
	 delivered but was suppressed due to the SU compression 
	 algorithm is counted in this count.  This number should 
	 increase rapidly during normal operation when the line is idle 
	 (e.g. it is idling FISUs)."
    DEFVAL { 0 }
    ::= { mtpSdtStatsEntry 9 }

mtpSdtStatsRxOverruns OBJECT-TYPE
    SYNTAX Counter32
    UNITS "Events"
    MAX-ACCESS read-only
    STATUS current
    DESCRIPTION
	"This count is the number of receive buffer overruns that have 
	 occurred.  A receive buffer overrun occurs when the signalling 
	 terminal goes to allocate a buffer to deliver an SU to the 
	 signalling link and a buffer is not immediately available.  The 
	 drivers recycle singalling data link receive buffers into 
	 signalling data link transmit buffers and the signalling data 
	 link does the opposite (recycles transmit buffers to receive 
	 buffers).  This number should be low or zero and should not 
	 increase after the first initialization of the siganalling 
	 link.  A significant number here would represent a significant 
	 problem."
    DEFVAL { 0 }
    ::= { mtpSdtStatsEntry 10 }

mtpSdtStatsRxAborts OBJECT-TYPE
    SYNTAX Counter32
    UNITS "Events"
    MAX-ACCESS read-only
    STATUS current
    DESCRIPTION
	"This count is the number of aborts that were received in the 
	 incoming bit stream from the signalling data link.  Signalling 
	 data terminals do not normally send aborts.  A significant 
	 number here indicates that either the signalling data link is 
	 experiencing a fault or the remote signalling terminal is 
	 experiencing difficulties.  When a T1 or E1 span is losing 
	 synchronization, it is not uncommon to see this count rise.  If 
	 there are no group synchronization problems with the signalling 
	 link an increasing count here represends a problem with the 
	 facility or a problem with the remote signalling terminal."
    DEFVAL { 0 }
    ::= { mtpSdtStatsEntry 11 }

mtpSdtStatsRxBufferOverflows OBJECT-TYPE
    SYNTAX Counter32
    UNITS "Events"
    MAX-ACCESS read-only
    STATUS current
    DESCRIPTION
	"This count is the number of receive buffer overflow conditions.  
	 A receive buffer overflow condition occurs when, on the receive 
	 side, the siganlling terminal attempts to allocate a buffer to 
	 transmit data to a signalling link and a buffer is not 
	 immediately available.  Signalling link drivers typically 
	 recycle their buffers from receive to transmit and the 
	 signalling terminal recycles its buffers from transmit to 
	 receive.  Therefore, it is unlikely that a buffer overflow will 
	 occur.  An increasing number here represents a serious 
	 problem."
    DEFVAL { 0 }
    ::= { mtpSdtStatsEntry 12 }

mtpSdtStatsRxSusInError OBJECT-TYPE
    SYNTAX Counter32
    UNITS "Signal Units"
    MAX-ACCESS read-only
    STATUS current
    DESCRIPTION
	"This count is the count of the number of signal units received 
	 in error.  If this number is increasing it is either because 
	 the signalling link is noisy (due to, for example, loss of 
	 synchronization on the group carrier), or the remote signalling 
	 terminal is experiencing difficulties sending correct SUs.  A 
	 significant number here represents a significant problem with 
	 the signalling data link or with the remote signalling 
	 terminal."
    REFERENCE
	"Q.751.1, ANSI T1.116.1, Table 1/1.8"
    DEFVAL { 0 }
    ::= { mtpSdtStatsEntry 13 }

mtpSdtStatsRxSyncTransitions OBJECT-TYPE
    SYNTAX Counter32
    UNITS "Events"
    MAX-ACCESS read-only
    STATUS current
    DESCRIPTION
	"This count is the count of the number of synchronization 
	 transitions on the receive bitstream.  Syncrhonization 
	 transitions occur when the signalling terminal begins hunting 
	 for flags because a flag does not exist where expected and when 
	 the signalling terminal locks on flags and begins to frame 
	 proper HDLC frames.  Both the transition from flag and frame 
	 lock to flag hunting and the transition from flag hunting to 
	 flag and frame lock are counted.  A significant or increasing 
	 number of transitions here normally indicates that the group 
	 carrier providing the signalling link is experiencing 
	 syncrhonization problems (i.e. it is slipping).  For a clean 
	 facility, an increasing number here would indicate a difficulty 
	 with the remote signalling terminal."
    DEFVAL { 0 }
    ::= { mtpSdtStatsEntry 14 }

mtpSdtStatsRxBitsOctetCounted OBJECT-TYPE
    SYNTAX Counter32
    UNITS "Bits"
    MAX-ACCESS read-only
    STATUS current
    DESCRIPTION
	"This count is the number of bits (not bytes) octet counted.  
	 While the signalling terminal is hunting for flags, it counts 
	 the bits that it receives which do not contain a valid flag.  
	 These bits are used to count octets and every 16 octets are 
	 considered to be an SU in error for error monitoring purposes.  
	 An increasing number here indicates that the signalling 
	 terminal is hunting for flags and not finding them.  This can 
	 either be caused by a failed facility or by a serious problem 
	 with the remote signalling terminal."
    DEFVAL { 0 }
    ::= { mtpSdtStatsEntry 15 }

mtpSdtStatsRxCrcErrors OBJECT-TYPE
    SYNTAX Counter32
    UNITS "Events"
    MAX-ACCESS read-only
    STATUS current
    DESCRIPTION
	"This is the count of the number of CRC errors detected in the 
	 received bit stream.  This number should be small.  An 
	 excessive number of CRC errors either indicates that the 
	 signalling data link facility is noisy and is experiencing bit 
	 errors.  This would not normally result from a syncrhonization 
	 problem (framing would likely be lost and octet counting 
	 entered).  CRC errors result from random bit errors that are 
	 unlikely to affect flags.  A increasing or significant number 
	 here indicates a noisy signalling data link."
    DEFVAL { 0 }
    ::= { mtpSdtStatsEntry 16 }

mtpSdtStatsRxFrameErrors OBJECT-TYPE
    SYNTAX Counter32
    UNITS "Events"
    MAX-ACCESS read-only
    STATUS current
    DESCRIPTION
	"This is the count of the number of frame errors in the received 
	 bit stream."
    DEFVAL { 0 }
    ::= { mtpSdtStatsEntry 17 }

mtpSdtStatsRxFrameOverflows OBJECT-TYPE
    SYNTAX Counter32
    UNITS "Events"
    MAX-ACCESS read-only
    STATUS current
    DESCRIPTION
	""
    DEFVAL { 0 }
    ::= { mtpSdtStatsEntry 18 }

mtpSdtStatsRxFrameTooLong OBJECT-TYPE
    SYNTAX Counter32
    UNITS "Frames"
    MAX-ACCESS read-only
    STATUS current
    DESCRIPTION
	"This is the count of the number of frames that were too long 
	 (they had a number of octets between flags and CRC of greater 
	 than the maximum SIF length) in the receive bitstream.  This 
	 number should be zero or very small.  A significant count in 
	 this field indicates a loss of syncrhonization on the carrier 
	 hosting the signalling data link, a noisy signalilng data link, 
	 or a serious problem with the remote signalling terminal."
    DEFVAL { 0 }
    ::= { mtpSdtStatsEntry 19 }

mtpSdtStatsRxFrameTooShort OBJECT-TYPE
    SYNTAX Counter32
    UNITS "Frames"
    MAX-ACCESS read-only
    STATUS current
    DESCRIPTION
	"This is the count of the number of frames that were too short 
	 (they were shorter than a FISU) in the receive bitstream.  This 
	 number should be zero or very small.  A significant number in 
	 this field indicates a loss of syncrhonization on the carrier 
	 hosting the signalling data link, a noisy signalling data link 
	 or a serious problem with the remote signalling terminal."
    DEFVAL { 0 }
    ::= { mtpSdtStatsEntry 20 }

mtpSdtStatsRxResidueErrors OBJECT-TYPE
    SYNTAX Counter32
    UNITS "Frames"
    MAX-ACCESS read-only
    STATUS current
    DESCRIPTION
	"This is the count of frames with residue errors (a non-octet 
	 aligned number of bits) in the receive bitstream.  This number 
	 should be zero or small.  A significant or increasing number in 
	 this column indicates a loss of syncrhonization of the group 
	 carrier containing the signalling data link, a noisy signalling 
	 data link, or a serious problem with the remote signalling 
	 terminal."
    DEFVAL { 0 }
    ::= { mtpSdtStatsEntry 21 }

mtpSdtStatsCarrierCtsLost OBJECT-TYPE
    SYNTAX Counter32
    UNITS "Events"
    MAX-ACCESS read-only
    STATUS current
    DESCRIPTION
	"This is the count of the number of times that the CTS (Clear To 
	 Send) lead was lost (deasserted) on a V.35 interface.  A 
	 significant number in this column indicates a problem with the 
	 modem or channel bank providing access to the signalling data 
	 link over the V.35 interface."
    DEFVAL { 0 }
    ::= { mtpSdtStatsEntry 22 }

mtpSdtStatsCarrierDcdLost OBJECT-TYPE
    SYNTAX Counter32
    UNITS "Events"
    MAX-ACCESS read-only
    STATUS current
    DESCRIPTION
	"This is the count of the number of times that the DCD (Data 
	 Carrier Detect) lead was lost (deasserted) on a V.35 interface.  
	 A significant number in this column indicates a problemw tih 
	 the modem or channel bank providing access to the signalling 
	 data link over the V.35 interface."
    DEFVAL { 0 }
    ::= { mtpSdtStatsEntry 23 }

mtpSdtStatsCarrierLost OBJECT-TYPE
    SYNTAX Counter32
    UNITS "Events"
    MAX-ACCESS read-only
    STATUS current
    DESCRIPTION
	"This is the count of the number of times that the carrier was 
	 lost on a DS0/DS1 interface.  A significant number in this 
	 field indicates that there is a problem with syncrhonization of 
	 the group carrier containing the signalling data link."
    DEFVAL { 0 }
    ::= { mtpSdtStatsEntry 24 }


-- ====================================================================

mtpSdlTable OBJECT-TYPE
    SYNTAX SEQUENCE OF MtpSdlEntry
    MAX-ACCESS not-accessible
    STATUS current
    DESCRIPTION
	"This managed object represents the termination of the 
	 signalling data link within the SP as defined in Q.702.
	 
	 The operational state is enabled in normal operation. In case 
	 of failure of the part of the signalling data link that is 
	 within control of the managed switching element, this state 
	 will be 'disabled'.
	 
	 If the vcTTpPointer attribute is present, then the transmission 
	 rate is determined by the cell rate fixed in the 
	 trafficDescriptorPackages of the vcTTPBidirectional instance 
	 referenced by the signDataLinkTp.
	
	 Note that for a complete view of the status of a signalling 
	 data link a network view is required."
    REFERENCE
	"ITU-T Rec. Q.751.1 (1997), ANSI T1.116.1 (2000), signDataLinkTp 
	     MOC."
    ::= { mtpSdl 1 }

mtpSdlEntry OBJECT-TYPE
    SYNTAX MtpSdlEntry
    MAX-ACCESS not-accessible
    STATUS current
    DESCRIPTION
	"This is an entry (row) in the SDL table."
    REFERENCE
	"ITU-T Rec. Q.751.1 (1997), ANSI T1.116.1 (2000), signDataLinkTp 
	     MO."
    INDEX {
	mtpSdlId
    }
    ::= { mtpSdlTable 1 }

MtpSdlEntry ::= SEQUENCE {
    mtpSdlId					Unsigned32,
    mtpSdlAdjPc					NetworkPointCode,
    mtpSdlTransmissionRate			MtpTransmissionRate,
    mtpSdlLoopDelay				MilliSeconds,
    mtpSdlOperationalState			OperationalState,
    mtpSdlEquipmentPointer			RowPointer,
    mtpSdlCIC					CircuitIdentificationCode,
    mtpSdlName					CommonLanguageName,
    mtpSdlStmChannel				CircuitCode,
    mtpSdlVcTTpPointer				RowPointer,
    mtpSdlRowStatus				RowStatus
}

mtpSdlId OBJECT-TYPE
    SYNTAX Unsigned32
    MAX-ACCESS not-accessible
    STATUS current
    DESCRIPTION
	"This attribute is used for naming instances."
    REFERENCE
	"ITU-T Rec. Q.751.1 (1997), ANSI T1.116.1 (2000), attribute."
    ::= { mtpSdlEntry 1 }

mtpSdlAdjPc OBJECT-TYPE
    SYNTAX NetworkPointCode
    MAX-ACCESS read-create
    STATUS current
    DESCRIPTION
	"This columnar object is an entry of the SDL table that 
	 indicates the signalling point code of the adjacent signalling 
	 point (the signalling point at the opposite end of the link).  
	 Becase the Signalling Point could be operating in multiple 
	 National and International networks, the NetworkPointCode 
	 contains a network identifier."
    REFERENCE
	"ITU-T Rec. Q.751.1 (1997), ANSI T1.116.1 (2000), attribute."
    ::= { mtpSdlEntry 2 }

mtpSdlTransmissionRate OBJECT-TYPE
    SYNTAX MtpTransmissionRate
    MAX-ACCESS read-create
    STATUS current
    DESCRIPTION
	"Specifies or indicates the nominal transmission rate associated 
	 with the narrowband signalling data link."
    REFERENCE
	"ITU-T Rec. Q.751.1 (1997), ANSI T1.116.1 (2000), attribute."
    ::= { mtpSdlEntry 3 }

mtpSdlLoopDelay OBJECT-TYPE
    SYNTAX MilliSeconds
    UNITS "seconds"
    MAX-ACCESS read-create
    STATUS current
    DESCRIPTION
	"Specifies the nominal loop delay (in milliseconds) associated 
	 with the narrowband signalling data link.  The value zero (0), 
	 indicates that the nominal loop delay of the signalling data 
	 link is unknown and unspecified."
    DEFVAL { 0 }
    ::= { mtpSdlEntry 4 }

mtpSdlOperationalState OBJECT-TYPE
    SYNTAX OperationalState
    MAX-ACCESS read-create
    STATUS current
    DESCRIPTION
	"Provides the operational state of the signalling data link 
	 following the OperationalState textual convention of the 
	 OPENSS7-SMI-MIB module, and according to ITU-T Rec. X.721 | 
	 ISO/IEC 10165-2.
	 
	  - disabled(0), 
	  - enabled(1), 
	 "
    REFERENCE
	"ITU-T Rec. X.721 (1992) | ISO/IEC 10165-2 : 1992, 
	     Attribute-ASN1Module.OperationalState.
	 ITU-T Rec. X.731 (1992) | ISO/IEC 10164-2 : 1993, 
	     Section 8.1.1.1.
	 ITU-T Rec. Q.751.1 (1997), ANSI T1.116.1 (2000), 
	     operationalState attribute."
    DEFVAL { 0 } -- disabled
    ::= { mtpSdlEntry 5 }

mtpSdlEquipmentPointer OBJECT-TYPE
    SYNTAX RowPointer
    MAX-ACCESS read-create
    STATUS current
    DESCRIPTION
	"This attribute is used to reference physical equipment."
    REFERENCE
	"ITU-T Rec. Q.751.1 (1997), ANSI T1.116.1 (2000), attribute."
    DEFVAL { { zeroDotZero } }
    ::= { mtpSdlEntry 6 }

mtpSdlCIC OBJECT-TYPE
    SYNTAX CircuitIdentificationCode
    MAX-ACCESS read-create
    STATUS current
    DESCRIPTION
	"This attribute is used to reference the SS No. 7 trunk used by 
	 the datalink.  Its value has to be unique within the SP's 
	 connected by the trunk.
	 
	 This columnar object is an entry of the SDL table that 
	 indicates the circuit identification code (CIC) which 
	 identifies the SDL channel between the local and adjacent 
	 signalling points.  This value is only necessary when the 
	 automatic allocation of signalling data links is supported.  
	 For IUT-T based networks, the CIC can have a value 0..4095, for 
	 ANSI based networks, the CIC can have a value 0..16383."
    REFERENCE
	"ITU-T Rec. Q.751.1 (1997), ANSI T1.116.1 (2000), 
	     signDataLinkTp::cIC ATTRIBUTE."
    DEFVAL { 0 }
    ::= { mtpSdlEntry 7 }

mtpSdlName OBJECT-TYPE
    SYNTAX CommonLanguageName
    MAX-ACCESS read-create
    STATUS current
    DESCRIPTION
	"This attribute is an additional name for instances of the 
	 signDataLinkTp managed object class."
    REFERENCE
	"ITU-T Rec. Q.751.1 (1997), ANSI T1.116.1 (2000), attribute."
    ::= { mtpSdlEntry 8 }

mtpSdlStmChannel OBJECT-TYPE
    SYNTAX CircuitCode
    MAX-ACCESS read-create
    STATUS current
    DESCRIPTION
	"This is a circuit code which uniquely identifies the circuit 
	 group or circuit facility which provides the signalling data 
	 link.
	 
	 This attribute denotes the STM channel which defines the 
	 signalling datalink on the PCM transmission system.  Note that 
	 the range is (1..31) for E1 and (1..24) for T1 and J1.
	 
	 For broadband (SAAL) and SIGTRAN (M2PA) signalling data links, 
	 this column is not present."
    REFERENCE
	"ITU-T Rec. Q.751.1 (1997), ANSI T1.116.1 (2000), 
	    signDataLinkTp::stmChannel ATTRIBUTE.
	 ITU-T Rec. Q.751.1 (1997), ANSI T1.116.1 (2000), 
	    MTPDefinedTypesModule.StmChannel."
    ::= { mtpSdlEntry 9 }

mtpSdlVcTTpPointer OBJECT-TYPE
    SYNTAX RowPointer
    MAX-ACCESS read-create
    STATUS current
    DESCRIPTION
	"This attribute references an object class defined in I.751.  It 
	 must be present for a broadband signalling data link, it must 
	 not be present for a narrowband datalink (the term ebroadband 
	 signalling data linkl signifies a data link using the SAAL 
	 NNI).  The referenced instance has a mandatory relation via its 
	 upstream- and downstreamConnectivityPointers to one instance of 
	 object class vcCTPBidirectional, whose Id represents the VCI of 
	 the virtual channel used by the data link.  This 
	 vcCTPBidirectional is contained in a superior object 
	 vpTTPBidirectional, which has a mandatory relation via its 
	 upstream- and downstreamConnectivityPointers to one instance of 
	 the object class vpTTPBidirectional, whose Id represents the 
	 VPI of the virtual path used by the data link.
	 
	 For narrowband (TDM) and SIGTRAN (M2PA) signalling data links, 
	 this column is not present."
    REFERENCE
	"ITU-T Rec. Q.2751.1 (1997), signDataLinkTp::vcTTpPointer 
	     ATTRIBUTE."
    ::= { mtpSdlEntry 10 }

mtpSdlRowStatus OBJECT-TYPE
    SYNTAX RowStatus
    MAX-ACCESS read-create
    STATUS current
    DESCRIPTION
	"Provides a mechanism whereby management stations may create and 
	 delete entries in this table.
	 
	 A create request is rejected if the equipmentPointer would 
	 reference equipment that does not exist.  If the name package 
	 is supported: a create request with a value for the name 
	 attribute that is already used by another instance of the same 
	 object class will be rejected."
    REFERENCE
	"STD 58, SNMPv2-TC RowStatus.
	 ITU-T Rec. Q.751.1 (1997) : mtpSignPoint-signDataLinkTp NAME 
	     BINDING."
    ::= { mtpSdlEntry 11 }


-- ====================================================================

mtpSdlStatsTable OBJECT-TYPE
    SYNTAX SEQUENCE OF MtpSdlStatsEntry
    MAX-ACCESS not-accessible
    STATUS current
    DESCRIPTION
	"This is the SDL ststistics table.  It provides statistics 
	 associated with signalling data links."
    ::= { mtpSdl 2 }

mtpSdlStatsEntry OBJECT-TYPE
    SYNTAX MtpSdlStatsEntry
    MAX-ACCESS not-accessible
    STATUS current
    DESCRIPTION
	"This is an entry in the SDL statistics table.  Each entry 
	 contains statistics associated with a single signalling data 
	 link.  The entries are indexed using the same index as is used 
	 for the signalling data link configuration and state table, and 
	 the statistics are corelated with the signalling data link 
	 using that index.  Whenever a row exists in the signalling data 
	 link table, a corresponding row with the same index exists in 
	 this table.
	 
	 A management station may continually walk this table, repeating 
	 every second or so, to collect near real-time statistics on the 
	 OpenSS7 implementations.  Note, however, that for general SS7 
	 implementations, statistics should not be collected more 
	 frequently than on five minute intervals.  Notifications are 
	 provided for significant events to preclude the need for 
	 polling these tables."
    AUGMENTS    { mtpSdlEntry }
    ::= { mtpSdlStatsTable 1 }

MtpSdlStatsEntry ::= SEQUENCE {
    mtpSdlStatsRxOctets				Counter32,
    mtpSdlStatsTxOctets				Counter32,
    mtpSdlStatsRXOverruns			Counter32,
    mtpSdlStatsTxUnderruns			Counter32,
    mtpSdlStatsRxBufferOverflows		Counter32,
    mtpSdlStatsTxBufferOverflows		Counter32,
    mtpSdlStatsLeadCtsLost			Counter32,
    mtpSdlStatsLeadDcdLost			Counter32,
    mtpSdlStatsCarrierLost			Counter32,
    mtpSdlStatsBipolarViolations		Counter32
}

mtpSdlStatsRxOctets OBJECT-TYPE
    SYNTAX Counter32
    UNITS "Octets"
    MAX-ACCESS read-only
    STATUS current
    DESCRIPTION
	"This is the count of the number of octets received by the 
	 signalling data link from the line.  This count should increase 
	 rapidly during normal operation.  When this count does not 
	 increase, it means that the receivers are not receiving data.  
	 Monitoring this column over a short period of time is a way of 
	 verifying the bit rate of the signalling data link.  During 
	 normal operation, this column should increase at a fixe rate 
	 equal to the bit rate of the signalling data link."
    ::= { mtpSdlStatsEntry 1 }

mtpSdlStatsTxOctets OBJECT-TYPE
    SYNTAX Counter32
    UNITS "Octets"
    MAX-ACCESS read-only
    STATUS current
    DESCRIPTION
	"This is the count of the number of octets transmitted by the 
	 signalling data link to the line.  This count should increase 
	 rapidly during normal operation.  When this count does not 
	 increase, it means that the transmittters are not transmitting 
	 data.  Monitoring this column over a short period of time is a 
	 way of verifying the transmission rate of the signalling data 
	 link.  During normal operation, this column should increase at 
	 a fixed rate equal to the bit rate of the signalling data 
	 link."
    ::= { mtpSdlStatsEntry 2 }

mtpSdlStatsRXOverruns OBJECT-TYPE
    SYNTAX Counter32
    UNITS "Occurences"
    MAX-ACCESS read-only
    STATUS current
    DESCRIPTION
	"Receive overruns are counted on the receiver between the line 
	 and the signalling data link terminating device.  This occurs 
	 whenever bits were able to be retrieved from the line, but the 
	 driver was too slow in accepting the previously received bit 
	 from the line, and the signalling data link receivers were 
	 forced to drop bits.  This should not occur in normal operation 
	 and this number should be low or zero and not increase after 
	 the first initialization of the signalling data link.  If this 
	 number is increasing, it indicates that there are significant 
	 latencies in some device driver which is performing too many 
	 functions with interrupts suppressed.  (Or the CPU is just too 
	 slow.)"
    ::= { mtpSdlStatsEntry 3 }

mtpSdlStatsTxUnderruns OBJECT-TYPE
    SYNTAX Counter32
    UNITS "Occurences"
    MAX-ACCESS read-only
    STATUS current
    DESCRIPTION
	"Transmit underruns are counted on the transmitter between the 
	 signalling data link and the line.  This occrus whenever bits 
	 were required to be transmitted on the wire and the signalling 
	 data link driver did not supply a sufficient number of bits to 
	 satisfy the requirement.  This should not occur in normal 
	 operation and this number should be low or zero and not 
	 increase after the first initialization of the signalling data 
	 link.  If this number is increasing, it indicates that there 
	 are significant latencies in some device driver which is 
	 performing too many functions with interrupts suppressed.  (Or 
	 the CPU is just too slow.)"
    ::= { mtpSdlStatsEntry 4 }

mtpSdlStatsRxBufferOverflows OBJECT-TYPE
    SYNTAX Counter32
    UNITS "Occurences"
    MAX-ACCESS read-only
    STATUS current
    DESCRIPTION
	"Receive buffer overflows occur between the signalling data link 
	 and the signalling terminal.  When the signalling data link 
	 driver goes to deliver data to the signalling terminal and a 
	 buffer to contain the data is not immediately available, a 
	 receive buffer overflow condition ensues.  Becuase of buffer 
	 recycling, this number should be low or zero and should not 
	 increase after the first initialization of the signalling data 
	 link.  If this number is increasing, it indicates that there 
	 are significant buffer or memory pressure issued or that there 
	 are significant latencies in some device driver which is 
	 performing too many functions with interrupts diabled.  (Or the 
	 CPU is just too slow.)"
    ::= { mtpSdlStatsEntry 5 }

mtpSdlStatsTxBufferOverflows OBJECT-TYPE
    SYNTAX Counter32
    UNITS "Occurences"
    MAX-ACCESS read-only
    STATUS current
    DESCRIPTION
	""
    ::= { mtpSdlStatsEntry 6 }

mtpSdlStatsLeadCtsLost OBJECT-TYPE
    SYNTAX Counter32
    UNITS "Occurences"
    MAX-ACCESS read-only
    STATUS current
    DESCRIPTION
	"This is the count of the number of times that the CTS (Clear To 
	 Send) lead was lost (deasserted) on a V.35 interface.  A 
	 significant number in this column indicates a problem with the 
	 modem or channel bank providing access to the signalling data 
	 link over the V.35 interface."
    ::= { mtpSdlStatsEntry 7 }

mtpSdlStatsLeadDcdLost OBJECT-TYPE
    SYNTAX Counter32
    UNITS "Occurences"
    MAX-ACCESS read-only
    STATUS current
    DESCRIPTION
	"This is the count of the number of times that the DCD (Data 
	 Carrier Detect) lead was lost (deasserted) on a V.35 interface.  
	 A significant number in this column indicates a problemw tih 
	 the modem or channel bank providing access to the signalling 
	 data link over the V.35 interface."
    ::= { mtpSdlStatsEntry 8 }

mtpSdlStatsCarrierLost OBJECT-TYPE
    SYNTAX Counter32
    UNITS "Occurences"
    MAX-ACCESS read-only
    STATUS current
    DESCRIPTION
	"This is the count of the number of times that the carrier was 
	 lost on a DS0/DS1 interface.  A significant number in this 
	 field indicates that there is a problem with syncrhonization of 
	 the group carrier containing the signalling data link."
    ::= { mtpSdlStatsEntry 9 }

mtpSdlStatsBipolarViolations OBJECT-TYPE
    SYNTAX Counter32
    UNITS "Occurences"
    MAX-ACCESS read-only
    STATUS current
    DESCRIPTION
	"This is the count of the number of bipolar violations received 
	 on a T1, J1 or E1 carrier."
    ::= { mtpSdlStatsEntry 10 }

-- ====================================================================
-- DEFAULT VALUES
-- ====================================================================

-- Default values:
--
-- The purpose of these default scalars is two-fold: 1. to provide a 
-- localized set of default values to be applied when creatinging 
-- underspecified entries in the mtpM2paTable; 2. to provide values 
-- where no protocol profile is specified.  These are default-default 
-- values in the sense that the act as default values for management 
-- operations, however, once set by a management station or by internal 
-- system operations, they persist across both agent and system reboots.

mtpM2paDefaultSctpNoDelay OBJECT-TYPE
    SYNTAX TruthValue
    MAX-ACCESS read-write
    STATUS current
    DESCRIPTION
	"This scalar defines, for M2PA, by default whether the Nagle 
	 algorithm should be applied to SCTP associations.  The Nagle 
	 algorithm increases the size of the packets placed on the 
	 network at the expense of delaying the transmission of some 
	 data during congestion episodes.  When set to true(1), the 
	 Nagle algorithm is suppressed; otherwise, set to false(2), the 
	 Nagle algorithm is in effect.
	 
	 The default default is true(1): send packets without delay.  
	 The default default value is only application when never set by 
	 any management station.  When set, the scalar value must 
	 persist across system reboots."
    REFERENCE
	"RFC 4960"
    DEFVAL { 1 } -- true
    ::= { mtpDefaults 1 }

mtpM2paDefaultSctpMaxseg OBJECT-TYPE
    SYNTAX Unsigned32 (1..65536)
    UNITS "octets"
    MAX-ACCESS read-write
    STATUS current
    DESCRIPTION
	"This scalar defines, for M2PA, the default maximum SCTP payload 
	 size for outgoing packets.  Values greater than the association 
	 MTU are ignored and have no effect.  The value determines the 
	 maximum size (in octets) above which SCCP will fragment larger 
	 DATA chunis into smaller DATA chunks, and beneath which SCTP 
	 will bundle DATA chunks into a single packate or combine 
	 smaller DATA chunks into larger DATA chunks.  Normally this 
	 value is the association MTU value must the size of the current 
	 IP and SCTP headers, minus the size of one DATA chunk header.  
	 When set to a lower value, the lower value will be used.
	 
	 The default default allows the prevailing MTU to be controlling 
	 (65536 octets).  The default default value is only application 
	 when never set by any management station.  When set, the scalar 
	 value must persist across system reboots."
    REFERENCE
	"RFC 4960"
    DEFVAL { 65536 }
    ::= { mtpDefaults 2 }

mtpM2paDefaultSctpHeartbeatItvl OBJECT-TYPE
    SYNTAX MilliSeconds
    UNITS "seconds"
    MAX-ACCESS read-write
    STATUS current
    DESCRIPTION
	"This scalar defines, for M2PA, the default time interval (in 
	 milliseconds) between successive HEARTBEAT messages used to 
	 probe destination transport addresses for RTT calculation and 
	 activity.  Valid values are zero (0) - do not heartbeat, or a 
	 value of 1 millisecond or greater.
	 
	 In general this value determines the amount of time that it 
	 takes for an SCTP association to detect a failure on a 
	 association which has no data to transmit or retransmit.  M2PA, 
	 however, is used by MTP Level 3 which generates a test message 
	 every T2, where T2 is defined in ITU-T Rec. Q.707 (1993) or 
	 ANSI T1.111.7 (2000) to have a range from 4 to 12 seconds.  
	 Therefore, for M2PA, unless the SCTP heartbeat interval is set 
	 below Q.707-T2, it will only have effect on multihomed 
	 associations for checking the status of non-primary or non-CMT 
	 destinations.
	 
	 Reducing this value will reduce the amount of time taken to 
	 detect primary and non-primary, non-CMT path, interface and 
	 destination failures, but may only affect primary destinations 
	 if reduced below the coresponding Q.707-T2 value.
	 
	 The default default value is that recommended by RFC 4960 
	 (60,000 milliseconds, or 60 seconds).  The default default 
	 value is only application when never set by any management 
	 station.  When set, the scalar value must persist across system 
	 reboots."
    REFERENCE
	"RFC 4960 15. HB.interval, ITU-T Rec. Q.707 (1993), ANIS 
	 T1.111.7 (2000)."
    DEFVAL { 60000 } -- 60 seconds
    ::= { mtpDefaults 3 }

mtpM2paDefaultSctpHeartbeat OBJECT-TYPE
    SYNTAX TruthValue
    MAX-ACCESS read-write
    STATUS current
    DESCRIPTION
	"This scalar defines, for M2PA, by default whether HEARBEAT 
	 messages used to probe destination transport addresses for RTT 
	 calculation and activity will be sent periodically.
	 
	 Disabling the heart beat mechanism reduces the protocol's 
	 repsonsiveness in detection of failures and redirection of 
	 traffic away from failed paths and interfaces, particularly, 
	 for M2PA, failed non-primary and non-CMT destinations in an 
	 multi-homed association.  This scalar should normally be left 
	 at its default value.
	 
	 The default default value from RFC 4960 is true(1).  The 
	 default default value is only application when never set by any 
	 management station.  When set, the scalar value must persist 
	 across system reboots."
    REFERENCE
	"RFC 4960"
    ::= { mtpDefaults 4 }

mtpM2paDefaultSctpRtoInitial OBJECT-TYPE
    SYNTAX MilliSeconds
    UNITS "seconds"
    MAX-ACCESS read-write
    STATUS current
    DESCRIPTION
	"This scalar defines, for M2PA, the default initial time 
	 interval (in milliseconds) that will be used as an intial RTO 
	 (retransmission time out) value when sending packets to a 
	 destination for the first time.  Valid values are zero or 
	 greater but must be within the range mtpM2paDefaultSctpRtoMin 
	 to mtpM2paDefaultSctpRtoMax.
	 
	 Note that, in general, the default RTO initial values should 
	 not be less than the peer's maximum SACK delay, otherwise, 
	 excessive retransmission might occur while the peer is delaying 
	 acknowledgements.  That is, this value should be greater than 
	 the corresponding mtpM2paDefaultSctpSackDelay at the peer.
	 
	 The default default value is that value recommended by RFC 4960 
	 (3,000 milliseconds, or 3 seconds).  The default default value 
	 is only application when never set by any management station.  
	 When set, the scalar value must persist across system reboots."
    REFERENCE
	"RFC 4960 15. RTO.Initial"
    DEFVAL { 3000 }
    ::= { mtpDefaults 5 }

mtpM2paDefaultSctpRtoMin OBJECT-TYPE
    SYNTAX MilliSeconds
    UNITS "seconds"
    MAX-ACCESS read-write
    STATUS current
    DESCRIPTION
	"This scalar defines, for M2PA, the default minmum time interval 
	 (in milliseconds) that will be used as an RTO (retransmission 
	 time out) value when sending packets to a destination transport 
	 address and expecting acknowledgements.  Valid values are zero 
	 or greater but must be less than or equal to 
	 mtpM2paDefaultSctpRtoInitial and strictly less than 
	 mtpM2paDefaultSctpRtoMax.
	 
	 Note that, in general, the RTO minimum should not be less thatn 
	 the peer's maximum SACK delay, otherwise, excessive 
	 retransmissions might occur while the peer is delaying 
	 acknowledgements.  That is, this value should not be less than 
	 the corresponding mtpM2paDefaultSctpSackDelay at the peer.
	 
	 The default default value is the value recommended by RFC 4960 
	 (1000 milliseconds, or 1 second).  The default default value is 
	 only application when never set by any management station.  
	 When set, the scalar value must persist across system reboots."
    REFERENCE
	"RFC 4960 15. RTO.Min"
    DEFVAL { 1000 } -- 1 second
    ::= { mtpDefaults 6 }

mtpM2paDefaultSctpRtoMax OBJECT-TYPE
    SYNTAX MilliSeconds
    UNITS "seconds"
    MAX-ACCESS read-write
    STATUS current
    DESCRIPTION
	"This scalar defines, for M2PA, the default maximum time 
	 interval (in milliseconds) that will be used as an RTO 
	 (retransmission timeout) value when sending packets t a 
	 destination transport address and expecting acknowledgements.  
	 Valid values are zero or greater but must be greater than or 
	 equal to mtpM2paSctpRtoInitial and strictly greater than 
	 mtpM2paSctpRtoMin.
	 
	 The default default value is the value recommended by RFC 4960 
	 (60000 milliseconds, or 60 seconds).  The default default value 
	 is only application when never set by any management station.  
	 When set, the scalar value must persist across system reboots."
    REFERENCE
	"RFC 4960 15. RTO.Max"
    DEFVAL { 60000 } -- 60 seconds
    ::= { mtpDefaults 7 }

mtpM2paDefaultSctpPathMaxRetrans OBJECT-TYPE
    SYNTAX Unsigned32
    UNITS "retransmissions"
    MAX-ACCESS read-write
    STATUS current
    DESCRIPTION
	"This scalar defines, for M2PA, the default number of times that 
	 SCTP will attempt retransmitting a packet to a given detination 
	 transport address before it considers that destination 
	 transport address inactive.  Valid values are zero or greater.
	 
	 Adjusting this value has an effect on th period of time taken 
	 to fail-over between destinations for multi-homed connections.  
	 Lower values (including zero) will yield faster fail-over 
	 response times.  Lower values, however, may cause thrashing 
	 between destinations contributing to congestion in the network.  
	 Default default values are applicable to Internet applications.
	 
	 The default default value is the value recommended in RFC 4960 
	 (5 retransmissions).  The default default value is only 
	 application when never set by any management station.  When 
	 set, the scalar value must persist across system reboots."
    REFERENCE
	"RFC 4960 15. Path.Max.Retrans"
    DEFVAL { 5 } -- retransmissions
    ::= { mtpDefaults 8 }

mtpM2paDefaultSctpCookieLife OBJECT-TYPE
    SYNTAX MilliSeconds
    UNITS "seconds"
    MAX-ACCESS read-write
    STATUS current
    DESCRIPTION
	"This scalar defines, for M2PA, the default time interval (in 
	 milliseconds) in conjunction with mtpM2paSctpCookieInc beyond 
	 which a COOKIE-ECHO received with a cookie sent in an INIT-ACK 
	 will no longer be accepted.  For SCTP, this also limits the 
	 maximum time interval for which the HMAC secret key for the 
	 cookie will be valid.  Valid values are zero or greater.  
	 Values of zero will  be converted to a system clock tick.
	 
	 Reducing this value will increase the probability that passive 
	 connection attempts will fail due to expired cookies.  
	 Increasing the value will reduce the overall security of the 
	 system by permitting attackers an increased interval within 
	 which to crack HMACs and guess verification tags.  This value 
	 may be adjusted in conjunction with mtpM2paSctpCookieInc to 
	 meet most objectives for successful passive connection attempts 
	 with the best security afforded by smaller values of 
	 mtpM2paSctpCookieLife.
	 
	 Unfortunately, the mtpM2paSctpCookieLife and 
	 mtpM2paSctpCookieInc must be adjusted to accomodate the slowest 
	 peer on the slowest connection.  The default setting is 
	 adequate for Internet applications.
	 
	 The default default value is the value recommended by RFC 4960 
	 (60,000 milliseconds, or 60 seconds).  The default default value 
	 is only application when never set by any management station.  
	 When set, the scalar value must persist across system reboots."
    REFERENCE
	"RFC 4960 15. Valid.Cookie.Life"
    DEFVAL { 60000 } -- 60 seconds
    ::= { mtpDefaults 9 }

mtpM2paDefaultSctpCookieInc OBJECT-TYPE
    SYNTAX MilliSeconds
    UNITS "seconds"
    MAX-ACCESS read-write
    STATUS current
    DESCRIPTION
	"This scalar defines, for M2PA, the default time increment (in 
	 milliseconds) that will be added to the lifespan of the cookie 
	 in an INIT-ACK if the recieved INIT requests cookie 
	 preservative to lengthen the lifespan of the cookie.  Valid 
	 values are zero or greater.
	 
	 This value can be adjusted in conjunction with 
	 mtpM2paSctpCookieLife to meet objectives of successful passive 
	 connection attempts and security.
	 
	 The default default value is the value recommended in RFC 4960 
	 5.2.6 (1000 milliseconds, or 1 second).  The default default 
	 setting is adequate for Internet applications.  The default 
	 default value is only application when never set by any 
	 management station.  When set, the scalar value must persist 
	 across system reboots."
    REFERENCE
	"RFC 4960, 5.2.6, 3)"
    DEFVAL { 1000 } -- 1 second
    ::= { mtpDefaults 10 }

mtpM2paDefaultSctpMaxInitRetries OBJECT-TYPE
    SYNTAX Unsigned32
    UNITS "retries"
    MAX-ACCESS read-write
    STATUS current
    DESCRIPTION
	"This scalar defines, for M2PA, the default number of times that 
	 an INIT or COOKIE-ECHO will be resent to a given destination 
	 before abandoning an active open attempt.  Value values are 
	 zero or greater.
	 
	 The default default value is the value recommended by RFC 4960 
	 (8 retries).  The default default value is only application 
	 when never set by any management station.  When set, the scalar 
	 value must persist across system reboots."
    REFERENCE
	"RFC 4960 15. Max.Init.Retransmits"
    DEFVAL { 8 }
    ::= { mtpDefaults 11 }

mtpM2paDefaultSctpMaxBurst OBJECT-TYPE
    SYNTAX Unsigned32
    UNITS "MTUs"
    MAX-ACCESS read-write
    STATUS current
    DESCRIPTION
	"This scalar defines, for M2PA, the default maximum number of 
	 MTUs of new data chunks that will be sent in a burst in 
	 accordance with SCTP Specification Errata and Issues, RFC 4460 
	 and RFC 4960.
	 
	 The default default value is the value recommended in RFC 4960 
	 (4 MTUs).  The default default value is only application when 
	 never set by any management station.  When set, the scalar 
	 value must persist across system reboots."
    REFERENCE
	"RFC 4960 15. Max.Burst"
    DEFVAL { 4 }
    ::= { mtpDefaults 12 }

mtpM2paDefaultSctpAssocMaxRetrans OBJECT-TYPE
    SYNTAX Unsigned32
    UNITS "retransmissions"
    MAX-ACCESS read-write
    STATUS current
    DESCRIPTION
	"This scalar defines, for M2PA, the default number of times that 
	 the sending endpoint will attempt retransmitting a packet on 
	 any active destination transport address before it aborts the 
	 association.  Value values are zero or greater.
	 
	 This value should be larger than sum of the default path 
	 maximum number of retransmission values of each of the 
	 destinations.
	 
	 Setting this value to less than the sum of the default path 
	 maximum retransmission values for all of the destinations has 
	 the interesting effect of permitting a connection to persist 
	 even when all destinations have been deemed inactive.
	 
	 The default default value is the value recommended in RFC 4960 
	 (10 retransmissions).  The default default value is only 
	 application when never set by any management station.  When 
	 set, the scalar value must persist across system reboots."
    REFERENCE
	"RFC 4960 15. Association.Max.Retrans"
    DEFVAL { 10 }
    ::= { mtpDefaults 13 }

mtpM2paDefaultSctpSackDelay OBJECT-TYPE
    SYNTAX MilliSeconds (0..50)
    UNITS "seconds"
    MAX-ACCESS read-write
    STATUS current
    DESCRIPTION
	"This scalar defines, for M2PA, the default interval of time (in 
	 milliseconds) that will be used as an RTO (retransmission time 
	 out) value when sending packets to a destination transport 
	 address.  Valid values are zero or to 500 milliseconds (RFC 
	 4960 forbids setting this value larger than 500 milliseconds).
	 
	 The default default value is the value recommended in RFC 4960 
	 (200 milliseconds).  The default default value is only 
	 application when never set by any management station.  When 
	 set, the scalar value must persist across system reboots."
    REFERENCE
	"RFC 4960 15. 6.2"
    DEFVAL { 200 }
    ::= { mtpDefaults 14 }

mtpM2paDefaultSctpLifetime OBJECT-TYPE
    SYNTAX MilliSeconds
    UNITS "seconds"
    MAX-ACCESS read-write
    STATUS current
    DESCRIPTION
	"This scalar defines, for M2PA, the default life time assigned 
	 to user data to be sent on the association.
	 
	 The default default value is only application when never set by 
	 any management station.  When set, the scalar value must 
	 persist across system reboots."
    REFERENCE
	"RFC 4960 10.1 E)"
    DEFVAL { 0 }
    ::= { mtpDefaults 15 }


-- ====================================================================
-- NOTIFICATION PARAMETERS
-- ====================================================================

changeInLsToAdjSp OBJECT-TYPE
    SYNTAX NetworkPointCode
    MAX-ACCESS accessible-for-notify
    STATUS current
    DESCRIPTION
	"Contains the network point code of the adjacent signalling 
	 point."
    REFERENCE
	"ITU-T Rec. Q.751.1 (1997), ANSI T1.116.1 (2000), 
	 changeInLsToAdjSp parameter."
    ::= { mtpNotifs 1 }

oldLs OBJECT-TYPE
    SYNTAX RowPointer
    MAX-ACCESS accessible-for-notify
    STATUS current
    DESCRIPTION
	""
    REFERENCE
	"ITU-T Rec. Q.751.1 (1997), ANSI T1.116.1 (2000), 
	 MTPDefinedTypesModule.ChangeInLsToAdjSp.oldSignLinkSetTp."
    DEFVAL { { zeroDotZero } }
    ::= { mtpNotifs 2 }

newLs OBJECT-TYPE
    SYNTAX RowPointer
    MAX-ACCESS accessible-for-notify
    STATUS current
    DESCRIPTION
	""
    REFERENCE
	"ITU-T Rec. Q.751.1 (1997), ANSI T1.116.1 (2000), 
	 MTPDefinedTypesModule.ChangeInLsToAdjSp.newSignLinkSetTp."
    DEFVAL { { zeroDotZero } }
    ::= { mtpNotifs 3 }

inaccessibleSp OBJECT-TYPE
    SYNTAX NetworkPointCode
    MAX-ACCESS accessible-for-notify
    STATUS current
    DESCRIPTION
	""
    REFERENCE
	"ITU-T Rec. Q.751.1 (1997), ANSI T1.116.1 (2000), inaccessibleSp 
	 parameter."
    ::= { mtpNotifs 4 }

-- note this conflicts with ProbableCause of same name
remoteUnavailableUserPart OBJECT-TYPE
    SYNTAX MtpUserPart
    MAX-ACCESS accessible-for-notify
    STATUS current
    DESCRIPTION
	""
    REFERENCE
	"ITU-T Rec. Q.751.1 (1997), ANSI T1.116.1 (2000), 
	 remoteUserPartUnavailable parameter."
    ::= { mtpNotifs 5 }

congestionStatus OBJECT-TYPE
    SYNTAX MtpCongestionLevel
    MAX-ACCESS accessible-for-notify
    STATUS current
    DESCRIPTION
	"This parameter provides an object to use in notifications to 
	 indicate the congestion level along with the notification.  It 
	 is used in qualityOfServiceAlarm notifications that indicate 
	 the change in congestion level of a route set or signalling 
	 link."
    ::= { mtpNotifs 6 }

networkPointCode OBJECT-TYPE
    SYNTAX NetworkPointCode
    MAX-ACCESS accessible-for-notify
    STATUS current
    DESCRIPTION
	"This parameter provides an object to use in notifications to 
	 indicate a network signalling point code along with the 
	 notification."
    ::= { mtpNotifs 7 }

userPart OBJECT-TYPE
    SYNTAX Unsigned32 (3..15)
    MAX-ACCESS accessible-for-notify
    STATUS current
    DESCRIPTION
	"This parameter provides an object to use in notifications to 
	 indicate an MTP user part along with the notification."
    ::= { mtpNotifs 8 }

userPartStatus OBJECT-TYPE
    SYNTAX MtpUserPartStatus
    MAX-ACCESS accessible-for-notify
    STATUS current
    DESCRIPTION
	"This parameter provide an object to use in notifications to 
	 indicate an MTP user part availability along with the 
	 notification."
    ::= { mtpNotifs 9 }

linkFailureReason OBJECT-TYPE
    SYNTAX MtpLinkFailureReason
    MAX-ACCESS accessible-for-notify
    STATUS current
    DESCRIPTION
	"This parameter provides an object to use in notifications to 
	 indicate additional information pertaning to the link failure 
	 indication.  It is intended to be used with the slLinkFailure 
	 communicationsAlarm notification."
    ::= { mtpNotifs 10 }


-- ====================================================================
-- CONFORMANCE OBJECT GROUPS
-- ====================================================================

mtpLsProfilePackage OBJECT-GROUP
    OBJECTS {
	mtpLsProfileTimerT6, mtpLsProfileTimerT8, mtpLsProfileTimerT10, 
	mtpLsProfileRowStatus }
    STATUS current
    DESCRIPTION
	""
    REFERENCE
	"ITU-T Rec. Q.751.1 (1997), ANSI T1.116.1 (2000), 
	 lsTimersProfilePackage."
    ::= { mtpGroups 1 }

-- managedSwitchingElementPackage OBJECT-GROUP
--     OBJECTS {
--         vendorName
--     }
--     STATUS current
--     DESCRIPTION
--         ""
--     REFERENCE
--         "ITU-T Rec. Q.751.1 (1997), ANSI T1.116.1 (2000), 
--         managedSwitchingElementPackage ."
--     ::= { mtpGroups 2 }

mtpSapPkg OBJECT-GROUP
    OBJECTS {
	mtpSap2Address, mtpSapUserEntityNames, mtpSapRowStatus }
    STATUS current
    DESCRIPTION
	""
    REFERENCE
	"ITU-T Rec. Q.751.1 (1997), ANSI T1.116.1 (2000), 
	 mtpAccessPointPkg ."
    ::= { mtpGroups 2 }

mtpSlL2ProfilePkg OBJECT-GROUP
    OBJECTS {
	mtpSlL2ProfileErrorCorrectionMethod, mtpSlL2ProfileTimerT1, 
	mtpSlL2ProfileTimerT2, mtpSlL2ProfileTimerT3, mtpSlL2ProfileTimerT4N, 
	mtpSlL2ProfileTimerT4E, mtpSlL2ProfileTimerT5, mtpSlL2ProfileTimerT6, 
	mtpSlL2ProfileTimerT7, mtpSlL2ProfileTbOnset1, 
	mtpSlL2ProfileTbAbate1, 
	mtpSlL2ProfileRowStatus }
    STATUS current
    DESCRIPTION
	""
    REFERENCE
	"ITU-T Rec. Q.751.1 (1997), ANSI T1.116.1 (2000), 
	 mtpL2ProtocolProfilePkg ."
    ::= { mtpGroups 3 }

mtpL3Package OBJECT-GROUP
    OBJECTS {
	mtpL3AdministrativeState, mtpL3OperationalState, 
	mtpL3UsageState, mtpL3ProceduralStatus, mtpL3RowStatus }
    STATUS current
    DESCRIPTION
	""
    REFERENCE
	"ITU-T Rec. Q.751.1 (1997), ANSI T1.116.1 (2000), 
	 mtpLevel3Package ."
    ::= { mtpGroups 4 }

mtpSpPackage OBJECT-GROUP
    OBJECTS {
	mtpSpPointCode, mtpSpType, mtpSpOperationalState, 
	mtpSpProceduralStatus, mtpSpAvailabilityStatus, mtpSpVersion, 
	mtpSpNetworkIndicator, mtpSpRowStatus }
    STATUS current
    DESCRIPTION
	""
    REFERENCE
	"ITU-T Rec. Q.751.1 (1997), ANSI T1.116.1 (2000), 
	 mtpSignPointPackage ."
    ::= { mtpGroups 5 }

mtpSdlPackage OBJECT-GROUP
    OBJECTS {
	mtpSdlAdjPc, mtpSdlTransmissionRate, mtpSdlLoopDelay, 
	mtpSdlOperationalState, mtpSdlEquipmentPointer, mtpSdlRowStatus }
    STATUS current
    DESCRIPTION
	"This managed object represents the termination of the 
	 signalling data link within the SP as defined in Q.702.  The 
	 operational state is 'enabled' in normal operation.  In case of 
	 failure of the part of the signalling data link that is within 
	 control of the managed switching element, this state will be 
	 'disabled'."
    REFERENCE
	"ITU-T Rec. Q.751.1 (1997), ANSI T1.116.1 (2000), 
	 signDataLinkTpPackage ."
    ::= { mtpGroups 6 }

mtpLsPackage OBJECT-GROUP
    OBJECTS {
	mtpLsAdjPc, mtpLsMaxCapacity, mtpLsCurrentCapacity, 
	mtpLsCongestionControlMethod, mtpLsUsageState, 
	mtpLsOperationalState, mtpLsAvailabilityStatus, 
	mtpLsPeriodicLinkTestFlag, mtpLsRowStatus }
    STATUS current
    DESCRIPTION
	"This managed object class represents the SS No. 7 signalling 
	 link set termination point.  Link sets are defined in 
	 Recommendation Q.704.  The states are directly related to the 
	 set of link termination point's states, except for the optional 
	 administrativeState.
	 
	 General principles on state information:
	 
	 1. The states of the managed object linkset are only readable, 
	    except for the optional administrativeState.
	 
	 2. Activation and deactivation of a linkset may be done via 
	    operations on the links (e.g. by using scoping functions) or 
	    the optional administrativeState can be used for this.
	 
	 Based on these principles the states of a linkset are defined 
	 as follows:
	 
	  - operational state (read-only for the OS).  The operational 
	    state is enabled whenever one link of the linkset is 
	    enabled, i.e. neither FAILED nor DEACTIVATED nor LOCAL 
	    BLOCKED nor REMOTE BLOCKED.
	 
	  - Usage state (read-only for the OS).  The usage state 
	    reflects the usage of the belonging links.  It is ACTIVE if 
	    at least one of the belonging links is ACTIVE and no link is 
	    BUSY.  It contains BUSY if one of the belonging links is 
	    BUSY.  It is IDLE if all links are UNAVAILABLE.
	 
	  - Availability status (read-only for the OS).  The 
	    availability status indicates unavailability or reduced 
	    availability of the belonging links.  It contains DEPENDENCY 
	    if all the belonging links are unavailable for user traffic.  
	    It contains DEGRADED if at least one belonging link is not 
	    available for user traffic.  For the different reasons of 
	    unavailability (failed, deactivated, local blocked, remote 
	    blocked, local inhibited and remote inhibited) see 
	    3.2.1/Q.704.
	 
	 If the 'ITU-T Rec. X.721 (1992) | ISO/IEC 10165-2 : 
	 1992':communicationsAlarm notification is used, the following 
	 probable causes can apply:
	 
	  - Probable Cause=403 (LinkSetFailure), which represents 
	    measurements Q.752/4.3 (PerceivedSeverity=Maj/Min/War) and 
	    Q.752/4.4 (PerceivedSeverity=Cleared).
	 
	 State change notifications are emitted for all state and status 
	 changes."
    REFERENCE
	"ITU-T Rec. Q.751.1 (1997), ANSI T1.116.1 (2000), 
	 signLinkSetTpPackage ."
    ::= { mtpGroups 7 }

mtpSlPackage OBJECT-GROUP
    OBJECTS {
	mtpSlSlsCodeCurrentList, mtpSlMaxCapacitySL, 
	mtpSlCurrentCapacitySL, 
	mtpSlLinkTpStatus, mtpSlAdministrativeState, 
	mtpSlOperationalState, mtpSlUsageState, mtpSlProceduralStatus, 
	mtpSlMtpL2ProtocolProfilePointer, mtpSlSignTermPointer, 
	mtpSlSignDataLinkTpPointer, 
	mtpSlRowStatus, mtpSlLocalInhibit, mtpSlLocalUninhibit, 
	mtpSlReplaceSt }
    STATUS current
    DESCRIPTION
	"This managed object represents the termination of the 
	 signalling link within the signalling point as defined in 
	 Recommendation Q.703.  The signLinkTp object class represents 
	 that part of a signalling link which is located in one NE.
	 
	 The following state and status attributes are supported:
	 
	  1. administrative state:
	 
	   - locked: it is administratively not permitted to transport 
	     traffic on the link termination point.
	 
	   - unlocked: it is administratively permitted to transport 
	     user part traffic or test traffic on the link termination 
	     point.
	 
	  2. operational state:
	 
	   - enabled: the link termination point is operationally able 
	     to transport user part traffic or test traffic.
	 
	   - disabled: the link termination point is operationally 
	     unable to transport user part traffic or test traffic.  The 
	     operational state is disabled whenever the link termination 
	     point status contains Failed, Deactivated, Local Blocked, 
	     Remote Blocked, or the procedural status is Initializing.
	 
	  3. usage state:
	 
	   - idle: the link termination point carries no user part 
	     traffic (test traffic may be present).
	 
	   - 'active': the link termination point is not congested.  
	     Currently the link termination point carries user part 
	     traffic.
	 
	   - busy: the link termination point is congested due to user 
	     part traffic.  The usage state is idle whenever the link 
	     termination point status is not empty i.e. the usage state 
	     immediately reflects the availability of the signLinkTp for 
	     user traffic.
	 
	     For national MTP options applying several congestion levels 
	     an additional attribute indicating these levels may be 
	     added.
	 
	  4. procedural status:
	 
	    The procedural status initializing is valid during initial 
	    alignment procedure.
	 
	    The procedural status not initalized applies when the link 
	    termination point is not aligned and the initial alignment 
	    procedure has not been started.
	 
	  5. Link termination point status.  This is a set-valued 
	     attribute.  The following statusses can exist alone or in 
	     combinations with each other.  The exact definition for 
	     each of the following SS7-functional states is to be gained 
	     from Q.704 local blocked remote blocked local inhibited 
	     remote inhibited failed deactivated.
	 
	 If the 'ITU-T Rec. X.721 (1992) | ISO/IEC 10165-2 : 
	 1992':communicationsAlarm notification is used, the following 
	 probable causes can apply:
	 
	 - Probable C102 (slFailure) which represents measurement 
	   Q.752/1.2 measurement Q.752/1.6 (SpecificProblems=003 
	   abnormalFIBRorBSNR, 004 excessiveAckDelay, 005 
	   excessiveErrorRate, 006 excessiveCongDuration) and 
	   Q.752/1.12.(PerceivedSeverity=cleared)
	 
	 If the ss7OnOccEventPackage is present, the event notifications 
	 with the following probable causes can apply:
	 
	  - Probable Cause = 110 (localChangeOver) which represents 
	    measurement Q.752/1.10 (PerceivedSeverity=Maj/Min/War) and 
	    measurement Q.752/1.11 (PerceivedSeverity=Cleared).
	 
	  - Probable Cause = 210 (remoteProcOutage) which represents 
	    measurements Q.752/2.10 (PerceivedSeverity=Maj/Min/War) and 
	    Q.752/2.11 (PerceivedSeverity=Cleared).
	 
	  - Probable Cause = 216 (start of local inhibition) which 
	    represents measurement Q.752/2.16 
	    (PerceivedSeverity=Maj/Min/War) and Q.752/2.17 
	    (PerceivedSeverity=Cleared).
	 
	  - Probable Cause = 218 (start of remote inhibition) which 
	    represents measurement Q.752/2.18 
	    (PerceivedSeverity=Maj/Min/War) and Q.752/2.19 
	    (PerceivedSeverity=Cleared).
	 
	 A create or set request is rejected, if
	 
	  1. a pointer would reference an instance, which does not 
	     belong to the appropriate object class OR
	 
	  2. a pointer would reference an instance which is not existing 
	     OR
	 
	  3. a signDataLinkTpPointer would reference a signDataLinkTp 
	     which is not in the same mtpSignPoint OR
	 
	  4. a signDataLinkTpPointer would reference a signDataLinkTp 
	     which has a different value of adjPc than the superior 
	     signLinkSetTp OR
	 
	  5. the link would reference a datalink and a 
	     mtpL2ProtocolProfile whose transmissionRates is not the 
	     same OR
	 
	  6. the link would reference a mtpL2ProtocolProfile where the 
	     appropriate packages for the congestionControlMethod of the 
	     superior signLinkSetTp are not present (see B.1.2.9.2) OR
	 
	  7. the spTimersProfilePackage is present in the superior 
	     mtpSignPoint AND the link would reference a 
	     mtpL2ProtocolProfile whose l2TimerT2 is not bigger than the 
	     q704-t17 of the spTimersProfile referenced by the 
	     mtpSignPoint OR
	 
	  8. the spTimersPackage is present in the superior mtpSignPoint 
	     AND the link would reference a mtpL2ProtocolProfile whose 
	     l2TimerT2 is not bigger than the q704-t17 of the 
	     mtpSignPoint.
	 
	  The rejection also takes place if only a single pointer within 
	  the signDataLinkList or the signTermList (if present) is 
	  wrong.
	 
	 A delete request is rejected, if the linkTpStatus does not 
	 contain the value deactivated,"
    REFERENCE
	"ITU-T Rec. Q.751.1 (1997), ANSI T1.116.1 (2000), 
	 signLinkTpPackage ."
    ::= { mtpGroups 8 }

mtpSlL3ProfilePackage OBJECT-GROUP
    OBJECTS {
	mtpSlL3ProfileTimerT1, mtpSlL3ProfileTimerT3, mtpSlL3ProfileTimerT17, 
	mtpSlL3ProfileTimerT24I, mtpSlL3ProfileRowStatus }
    STATUS current
    DESCRIPTION
	"A signalling link timer profile is a set of Q.704 timers which 
	 are related to the characteristics of Signalling Links.  The 
	 managed object class slTimersProfile is a support managed 
	 object class which can be instantiated in order to define a 
	 particular profile.  At creation time of a signLinkTp one of 
	 the slTimersProfiles may be referenced."
    REFERENCE
	"ITU-T Rec. Q.751.1 (1997), ANSI T1.116.1 (2000), 
	 slTimersProfilePackage ."
    ::= { mtpGroups 9 }

mtpSpProfilePackage OBJECT-GROUP
    OBJECTS {
	mtpSpProfileTimerT2, mtpSpProfileTimerT4, mtpSpProfileTimerT5, 
	mtpSpProfileTimerT7, mtpSpProfileTimerT11, mtpSpProfileTimerT12, 
	mtpSpProfileTimerT13, mtpSpProfileTimerT14, mtpSpProfileTimerT15, 
	mtpSpProfileTimerT16, mtpSpProfileTimerT18I, mtpSpProfileTimerT19I, 
	mtpSpProfileTimerT20I, mtpSpProfileTimerT21I, mtpSpProfileTimerT22I, 
	mtpSpProfileTimerT23I, mtpSpProfileTimerT20A, mtpSpProfileTimerT21A, 
	mtpSpProfileTimerT1T, mtpSpProfileTimerT2T, mtpSpProfileRowStatus }
    STATUS current
    DESCRIPTION
	"A signalling link set timer profile is set of Q.704 and Q.707 
	 timers which are related to the characteristics of signalling 
	 points.  The managed object class spTimersProfile is a support 
	 managed object class which can be instantiated in order to 
	 define a particular profile.  At creation time of a signPoint 
	 one of the spTimersProfiles is referenced."
    REFERENCE
	"ITU-T Rec. Q.751.1 (1997), ANSI T1.116.1 (2000), 
	 spTimersProfilePackage ."
    ::= { mtpGroups 10 }

mtpRtPackage OBJECT-GROUP
    OBJECTS {
	mtpRtLsPointer, mtpRtAdministrativeState, mtpRtOperationalState, 
	mtpRtAvailabilityStatus, mtpRtRowStatus }
    STATUS current
    DESCRIPTION
	"A signalling route (A,C,B)i is defined as an ordered sequence 
	 of the near end signalling point A (i.e. the network element), 
	 an adjacent SP C and the destination SP B.  The adjacent SP C 
	 may be identical with the destination B, or it may or may not 
	 be directly interconnected to the destination SP.  The adjacent 
	 SP C must be directly connected to the near end SP by at least 
	 one linkset which is intended to convey MSUs sent from A to B 
	 (hence the use of the term 'adjacent').
	 
	 Two signalling routes (A,C,B)i and (A,C,B)j are distinct if the 
	 adjacent SP is different.
	 
	 The signRouteNePart Managed Object class defines the management 
	 capabilities of the resources which define a specific route 
	 segment (Link Set to be traversed) and its priority within the 
	 routeset as seen from the own SP.  A particular signRouteNePart 
	 is related to one or more Signalling Routes on the network 
	 level.
	 
	 The priority in which the network Signalling Routes are used, 
	 is defined by means of assigning priorities to all involved 
	 route segments.  If from a particular SP two or more route 
	 segments are used with the same priority, loadsharing between 
	 Signalling Routes may occur.
	 
	 A Combined Link Set is a set of Link Sets used with the same 
	 priority by message routing.
	 
	 The signLinkSetTp used for routing is allocated at creation 
	 time and cannot be changed during the existence of a particular 
	 signRouteNePart.
	 
	 The administrativeState attribute describes whether it is 
	 administratively permitted to route messages towards the 
	 respective destination point via the referenced signLinkSetTp.
	 
	 The operationalState attribute is 'enabled' if both the 
	 referenced signLinkSetTp is in the operational state 'enabled' 
	 and no TFP message concerning the respective destination has 
	 been received from the adjPC of the respective signLinkSetTp.
	 
	 The optional usageState attribute is used to cover restriction 
	 of a route.  Its value is set to 'busy', if the route is 
	 restricted ('transfer restricted' is a national option).
	 
	 The availabilityStatus attribute gives additional information 
	 about the availability of the signRouteNePart instance.  It is 
	 furthermore needed to map some of the MTP functional states 
	 (prohibited: availabilityStatus = {dependency}, restricted: 
	 availabilityStatus={degraded}) and is used for the case that 
	 the route is locked not by the OS, but e.g. by a local 
	 administrator (administrativeState=unlocked and 
	 availabilityStatus={off line})."
    REFERENCE
	"ITU-T Rec. Q.751.1 (1997), ANSI T1.116.1 (2000), 
	 signRouteNePartPackage ."
    ::= { mtpGroups 11 }

mtpRsPackage OBJECT-GROUP
    OBJECTS {
	mtpRsAdministrativeState, mtpRsOperationalState, mtpRsRowStatus 
	}
    STATUS current
    DESCRIPTION
	"A Signalling Route Set is a complete set of routes that can be 
	 used to carry traffic toward a specific destination signalling 
	 point.  The signRouteSetNePart Managed Object class defines the 
	 management capabilities of the resources which represent a 
	 specific destination SP and its accessibility as seen from the 
	 own SP.  This SP may be the originating SP of the MTP messages 
	 or an STP.  A particular signRouteSetNePart may be related to 
	 one or more Signalling Route Sets on network level.
	 
	  - The administrativeState attribute describes whether it is 
	    administratively permitted to route SS No. 7 MSUs towards 
	    the respective destination point.  Before the administrative 
	    state of a signRouteSetNePart can be set to 'unlocked', 
	    there must be at least one signRouteNePart contained within 
	    the signRouteSetNePart.
	 
	  - The operationalState attribute describes whether the 
	    respective destination signalling point is accessible - 
	    ('enabled') or not ('disabled').  If the operational states 
	    of all signRouteNePart instances contained in the 
	    signRouteSetNePart are 'disabled', then the operational 
	    state of the signRouteSetNePart is 'disabled', in any other 
	    case it is 'enabled'.
	 
	  - The usageState attribute is used to reflect route set 
	    congestion.  The value is 'busy' in case of route set 
	    congestion.
	 
	 If the 'ITU-T Rec. X.721 (1992) | ISO/IEC 10165-2: 
	 1992':communicationsAlarm notification is present, it indicates 
	 at least the following probable causes:
	 
	  - Probable Cause = 411(RouteSetUnavailable), which represents 
	    measurements Q.752/4.11 (PerceivedSeverity=Maj/Min/War) and 
	    Q.751/4.12 (PerceivedSeverity=Cleared).
	 
	 If the ss7OnOccEventPackage is present, event notifications 
	 with the following probable cause can apply:
	 
	  - Probable Cause = 002 (remoteUserPartUnavailable), with the 
	    involved user part as parameter.  Possible values for 
	    SpecificProblems are: 007 'unknown', 008 'unequipped' and 
	    009 'inaccessibleRemoteUser'.
	 
	 An activation or deactivation of a signRouteSetNePart must lead 
	 to the activation respectively deactivation of all contained 
	 signRouteNeParts."
    REFERENCE
	"ITU-T Rec. Q.751.1 (1997), ANSI T1.116.1 (2000), 
	 signRouteSetNePartPackage ."
    ::= { mtpGroups 12 }

mtpStPackage OBJECT-GROUP
    OBJECTS {
	mtpSdtAdministrativeState, mtpSdtOperationalState, mtpSdtUsageState, 
	mtpSdtProceduralStatus, mtpSdtAvailabilityStatus, mtpSdtEquipmentPointer, 
	mtpSdtRowStatus }
    STATUS current
    DESCRIPTION
	"The signTerm MOC defines the management capabilities for the 
	 signalling terminal.  The signalling terminal is defined in 
	 ITU-T Rec. Q.703."
    REFERENCE
	"ITU-T Rec. Q.751.1 (1997), ANSI T1.116.1 (2000), 
	 signTermPackage ."
    ::= { mtpGroups 13 }

mtpGsPkg OBJECT-GROUP
    OBJECTS {
	mtpGsAdministrativeState, mtpGsTreatmentOfOutsideRanges, 
	mtpGsListMode, mtpGsScreeningByLinkSetOrByOpc, mtpGsRowStatus }
    STATUS current
    DESCRIPTION
	""
    REFERENCE
	"ITU-T Rec. Q.751.1 (1997), ANSI T1.116.1 (2000), 
	 stpScreeningTablePkg ."
    ::= { mtpGroups 14 }

mtpGsLinePkg OBJECT-GROUP
    OBJECTS {
	mtpGsLineContent, mtpGsLineRowStatus, 
	mtpGsLineContentDesignatedDPCLast, 
	mtpGsLineContentMessageTreatment, mtpGsLineContentRowStatus }
    STATUS current
    DESCRIPTION
	"The stpScreeningTableLine together with its superior 
	 stpScreeningTable contains all the information which are 
	 necessary for an STP to identify and to handle unauthorized SS 
	 No. 7 messages as defined in 8.2/Q.705 and 8.3/Q.705.  The 
	 total number of screened DPC's across all stpScreeningTableLine 
	 instances contained by a stpScreeningTable must be less or 
	 equal to maxNoOfScreenedDpcs."
    REFERENCE
	"ITU-T Rec. Q.751.1 (1997), ANSI T1.116.1 (2000), 
	 stpScreeningTableLinePkg ."
    ::= { mtpGroups 15 }

administrativeStatePackage OBJECT-GROUP
    OBJECTS {
	mtpLsAdministrativeState }
    STATUS current
    DESCRIPTION
	"This package can be used for activation and deactivation of 
	 link sets.  Possible values of the administrativeState 
	 attribute are: locked and unlocked.  If transition takes place 
	 from locked to unlocked, this will result in activation of all 
	 links in the set that are unlocked.  If transition takes place 
	 from unlocked to locked, this will result in deactivation of 
	 all links in the set.  This has no effect on the administrative 
	 states of the links themselves"
    REFERENCE
	"ITU-T Rec. Q.751.1 (1997), ANSI T1.116.1 (2000), 
	 administrativeStatePackage ."
    ::= { mtpGroups 16 }

bufferMechanismPackage OBJECT-GROUP
    OBJECTS {
	mtpSlL2ProfileNumberOfThresholdLevels }
    STATUS current
    DESCRIPTION
	""
    REFERENCE
	"ITU-T Rec. Q.751.1 (1997), ANSI T1.116.1 (2000), 
	 bufferMechanismPackage ."
    ::= { mtpGroups 17 }

cICPackage OBJECT-GROUP
    OBJECTS {
	mtpSdlCIC }
    STATUS current
    DESCRIPTION
	""
    REFERENCE
	"ITU-T Rec. Q.751.1 (1997), ANSI T1.116.1 (2000), cICPackage ."
    ::= { mtpGroups 18 }

clsLoadsharingInformationPackage OBJECT-GROUP
    OBJECTS {
	mtpRtInClsLoadsharingAlgorithm, mtpRtLsaNormalSlCode, 
	mtpRtLsaAlternativeSlCodeList }
    STATUS current
    DESCRIPTION
	""
    REFERENCE
	"ITU-T Rec. Q.751.1 (1997), ANSI T1.116.1 (2000), 
	 clsLoadsharingInformationPackage ."
    ::= { mtpGroups 19 }

congestedStatePackage OBJECT-GROUP
    OBJECTS {
	mtpRsCongestedState }
    STATUS current
    DESCRIPTION
	"This package supplies an attribute for the simple congestion 
	 method used e.g. in the international network."
    REFERENCE
	"ITU-T Rec. Q.751.1 (1997), ANSI T1.116.1 (2000), 
	 congestedStatePackage ."
    ::= { mtpGroups 20 }

congestionHandlingPackage OBJECT-GROUP
    OBJECTS {
	mtpSlL2ProfileCongestionCounting, 
	mtpSlL2ProfileCongestionReportingBaseObject }
    STATUS current
    DESCRIPTION
	""
    REFERENCE
	"ITU-T Rec. Q.751.1 (1997), ANSI T1.116.1 (2000), 
	 congestionHandlingPackage ."
    ::= { mtpGroups 21 }

congestionLevelPackage OBJECT-GROUP
    OBJECTS {
	mtpRsCongestionLevel }
    STATUS current
    DESCRIPTION
	"This package supplies an attribute to allow for several 
	 congestion levels for the signRouteSetNePart."
    REFERENCE
	"ITU-T Rec. Q.751.1 (1997), ANSI T1.116.1 (2000), 
	 congestionLevelPackage ."
    ::= { mtpGroups 22 }

getScreenedOpcsOrLinkSetsByDpcActionPackage OBJECT-GROUP
    OBJECTS {
	mtpGsGetScreenedOpcsOrLinkSetsByDpc }
    STATUS current
    DESCRIPTION
	""
    REFERENCE
	"ITU-T Rec. Q.751.1 (1997), ANSI T1.116.1 (2000), 
	 getScreenedOpcsOrLinkSetsByDpcActionPackage ."
    ::= { mtpGroups 23 }

fixedRouteNePartPriorityPackage OBJECT-GROUP
    OBJECTS {
	mtpRtFixedPriority }
    STATUS current
    DESCRIPTION
	""
    REFERENCE
	"ITU-T Rec. Q.751.1 (1997), ANSI T1.116.1 (2000), 
	 fixedRouteNePartPriorityPackage ."
    ::= { mtpGroups 24 }

flexibleRouteNePartPriorityPackage OBJECT-GROUP
    OBJECTS {
	mtpRtFlexiblePriority, mtpRtPriorityMode }
    STATUS current
    DESCRIPTION
	""
    REFERENCE
	"ITU-T Rec. Q.751.1 (1997), ANSI T1.116.1 (2000), 
	 flexibleRouteNePartPriorityPackage ."
    ::= { mtpGroups 25 }

inLsLoadShareAlgorithmPackage OBJECT-GROUP
    OBJECTS {
	mtpLsInLsLoadShareAlgorithm }
    STATUS current
    DESCRIPTION
	""
    REFERENCE
	"ITU-T Rec. Q.751.1 (1997), ANSI T1.116.1 (2000), 
	 inLsLoadShareAlgorithmPackage ."
    ::= { mtpGroups 26 }

linkCongestionLevelPackage OBJECT-GROUP
    OBJECTS {
	mtpSlCongestionLevel }
    STATUS current
    DESCRIPTION
	""
    REFERENCE
	"ITU-T Rec. Q.751.1 (1997), ANSI T1.116.1 (2000), 
	 linkCongestionLevelPackage ."
    ::= { mtpGroups 27 }

loadsharingInformationRouteNePartPackage OBJECT-GROUP
    OBJECTS {
	mtpRtLoadsharingInformation }
    STATUS current
    DESCRIPTION
	""
    REFERENCE
	"ITU-T Rec. Q.751.1 (1997), ANSI T1.116.1 (2000), 
	 loadsharingInformationRouteNePartPackage ."
    ::= { mtpGroups 28 }

loadsharingInformationRouteSetNePartPackage OBJECT-GROUP
    OBJECTS {
	mtpRsLoadsharingInformation }
    STATUS current
    DESCRIPTION
	""
    REFERENCE
	"ITU-T Rec. Q.751.1 (1997), ANSI T1.116.1 (2000), 
	 loadsharingInformationRouteSetNePartPackage ."
    ::= { mtpGroups 29 }

loopDelayPackage OBJECT-GROUP
    OBJECTS {
	mtpSlL2ProfileLoopDelay }
    STATUS current
    DESCRIPTION
	""
    REFERENCE
	"ITU-T Rec. Q.751.1 (1997), ANSI T1.116.1 (2000), 
	 loopDelayPackage ."
    ::= { mtpGroups 30 }

mtpLsProfileNamePackage OBJECT-GROUP
    OBJECTS {
	mtpLsProfileName }
    STATUS current
    DESCRIPTION
	""
    REFERENCE
	"ITU-T Rec. Q.751.1 (1997), ANSI T1.116.1 (2000), 
	 lsTimersProfileNamePackage ."
    ::= { mtpGroups 31 }

mtpLsProfilePointerPackage OBJECT-GROUP
    OBJECTS {
	mtpLsProfilePointer }
    STATUS current
    DESCRIPTION
	""
    REFERENCE
	"ITU-T Rec. Q.751.1 (1997), ANSI T1.116.1 (2000), 
	 lsTimersProfilePointerPackage ."
    ::= { mtpGroups 32 }

-- managedSwitchingElementNamePackage OBJECT-GROUP
--     OBJECTS {
--         managedSwitchingElementName
--     }
--     STATUS current
--     DESCRIPTION
--         ""
--     REFERENCE
--         "ITU-T Rec. Q.751.1 (1997), ANSI T1.116.1 (2000), 
--         managedSwitchingElementNamePackage ."
--     ::= { mtpGroups 33 }

mtpSapNamePackage OBJECT-GROUP
    OBJECTS {
	mtpSapName }
    STATUS current
    DESCRIPTION
	""
    REFERENCE
	"ITU-T Rec. Q.751.1 (1997), ANSI T1.116.1 (2000), 
	 mtpAccessPointNamePackage ."
    ::= { mtpGroups 33 }

mtpSlL2ProfileNamePackage OBJECT-GROUP
    OBJECTS {
	mtpSlL2ProfileName }
    STATUS current
    DESCRIPTION
	""
    REFERENCE
	"ITU-T Rec. Q.751.1 (1997), ANSI T1.116.1 (2000), 
	 mtpL2ProtocolProfileNamePackage ."
    ::= { mtpGroups 34 }

mtpL3NamePackage OBJECT-GROUP
    OBJECTS {
	mtpL3Name }
    STATUS current
    DESCRIPTION
	""
    REFERENCE
	"ITU-T Rec. Q.751.1 (1997), ANSI T1.116.1 (2000), 
	 mtpLevel3NamePackage ."
    ::= { mtpGroups 35 }

mtpLoadsharingObjectForRouteNePartPointerPackage OBJECT-GROUP
    OBJECTS {
	mtpRtLoadsharingObject }
    STATUS current
    DESCRIPTION
	""
    REFERENCE
	"ITU-T Rec. Q.751.1 (1997), ANSI T1.116.1 (2000), 
	 mtpLoadsharingObjectForRouteNePartPointerPackage ."
    ::= { mtpGroups 36 }

mtpLoadsharingObjectForRouteSetNePartPointerPackage OBJECT-GROUP
    OBJECTS {
	mtpRsLoadsharingObject }
    STATUS current
    DESCRIPTION
	""
    REFERENCE
	"ITU-T Rec. Q.751.1 (1997), ANSI T1.116.1 (2000), 
	 mtpLoadsharingObjectForRouteSetNePartPointerPackage ."
    ::= { mtpGroups 37 }

mtpSpNamePackage OBJECT-GROUP
    OBJECTS {
	mtpSpName }
    STATUS current
    DESCRIPTION
	""
    REFERENCE
	"ITU-T Rec. Q.751.1 (1997), ANSI T1.116.1 (2000), 
	 mtpSignPointNamePackage ."
    ::= { mtpGroups 38 }

multipleTransmissionCongestionLevelsPackage OBJECT-GROUP
    OBJECTS {
	mtpSlL2ProfileTbOnset2, 
	mtpSlL2ProfileTbAbate2, 
	mtpSlL2ProfileTbOnset3, 
	mtpSlL2ProfileTbAbate3 
    }
    STATUS current
    DESCRIPTION
	"This package contains the second and third levels of 
	 transmission congestion.  The values of the thresholds 
	 belonging to congestion level 2 have to be bigger than the 
	 respective ones of congestion level 1.  The values of the 
	 thresholds belonging to congestion level 3 have to be bigger 
	 than the respective ones of congestion level 2."
    REFERENCE
	"ITU-T Rec. Q.751.1 (1997), ANSI T1.116.1 (2000), 
	 multipleTransmissionCongestionLevelsPackage ."
    ::= { mtpGroups 39 }

multipleTransmissionCongestionLevelsWithPrioPackage OBJECT-GROUP
    OBJECTS {
	mtpSlL2ProfileTbDiscard1, 
	mtpSlL2ProfileTbDiscard2, 
	mtpSlL2ProfileTbDiscard3 
    }
    STATUS current
    DESCRIPTION
	"This package contains the second and third levels of 
	 transmission congestion.  The values of the thresholds 
	 belonging to congestion level 2 have to be bigger than the 
	 respective ones of congestion level 1.  The values of the 
	 thresholds belonging to congestion level 3 have to be bigger 
	 than the respective ones of congestion level 2."
    REFERENCE
	"ITU-T Rec. Q.751.1 (1997), ANSI T1.116.1 (2000), 
	 multipleTransmissionCongestionLevelsPackage ."
    ::= { mtpGroups 40 }

multipleTransmissionCongestionStatesPackage OBJECT-GROUP
    OBJECTS {
	mtpSlL2ProfileTimerTx, mtpSlL2ProfileTimerTy, 
	mtpSlL2ProfileNumberOfCongestionStates, 
	mtpSlL2ProfileInitialLevelOfCongestion }
    STATUS current
    DESCRIPTION
	"This package contains the attributes related to the management 
	 of 'multiple link congestion states without congestion 
	 priority' method.  This method is described in 3.8.2.3/Q.704.  
	 See also B.1.2.9.2.  The range of initialLevelOfCongestion is 
	 [1, numberOfCongestionStates]."
    REFERENCE
	"ITU-T Rec. Q.751.1 (1997), ANSI T1.116.1 (2000), 
	 multipleTransmissionCongestionStatesPackage ."
    ::= { mtpGroups 41 }

noBasicLinkAllocationPackage OBJECT-GROUP
    OBJECTS {
	mtpLsNumberOfNormallyActiveSignLinks }
    STATUS current
    DESCRIPTION
	""
    REFERENCE
	"ITU-T Rec. Q.751.1 (1997), ANSI T1.116.1 (2000), 
	 noBasicLinkAllocationPackage ."
    ::= { mtpGroups 42 }

pCRPackage OBJECT-GROUP
    OBJECTS {
	mtpSlL2ProfileMaxMSUsRetransN1, mtpSlL2ProfileMaxOctRetransN2 }
    STATUS current
    DESCRIPTION
	"This package contains signLinkTp attributes for the PCR 
	 method."
    REFERENCE
	"ITU-T Rec. Q.751.1 (1997), ANSI T1.116.1 (2000), pCRPackage ."
    ::= { mtpGroups 43 }

receiveCongestionLevelsPackage OBJECT-GROUP
    OBJECTS {
	mtpSlL2ProfileReceiveCongestionThresholdOnset, 
	mtpSlL2ProfileReceiveCongestionThresholdAbate }
    STATUS current
    DESCRIPTION
	""
    REFERENCE
	"ITU-T Rec. Q.751.1 (1997), ANSI T1.116.1 (2000), 
	 receiveCongestionLevelsPackage ."
    ::= { mtpGroups 44 }

relatedLinkGroupNumberPackage OBJECT-GROUP
    OBJECTS {
	mtpSlRelatedLinkGroupNumber }
    STATUS current
    DESCRIPTION
	""
    REFERENCE
	"ITU-T Rec. Q.751.1 (1997), ANSI T1.116.1 (2000), 
	 relatedLinkGroupNumberPackage ."
    ::= { mtpGroups 45 }

remoteExchangeLabelPackage OBJECT-GROUP
    OBJECTS {
	mtpRsRemoteExchangeLabel }
    STATUS current
    DESCRIPTION
	""
    REFERENCE
	"ITU-T Rec. Q.751.1 (1997), ANSI T1.116.1 (2000), 
	 remoteExchangeLabelPackage ."
    ::= { mtpGroups 46 }

mtpSdlListPackage OBJECT-GROUP
    OBJECTS {
	mtpSlSdlList, mtpSlSdlListPointer, mtpSlSdlListRowStatus }
    STATUS current
    DESCRIPTION
	""
    REFERENCE
	"ITU-T Rec. Q.751.1 (1997), ANSI T1.116.1 (2000), 
	 signDataLinkTpListPackage ."
    ::= { mtpGroups 47 }

mtpSdlNamePackage OBJECT-GROUP
    OBJECTS {
	mtpSdlName }
    STATUS current
    DESCRIPTION
	""
    REFERENCE
	"ITU-T Rec. Q.751.1 (1997), ANSI T1.116.1 (2000), 
	 signDataLinkTpNamePackage ."
    ::= { mtpGroups 48 }

mtpLsNamePackage OBJECT-GROUP
    OBJECTS {
	mtpLsName }
    STATUS current
    DESCRIPTION
	""
    REFERENCE
	"ITU-T Rec. Q.751.1 (1997), ANSI T1.116.1 (2000), 
	 signLinkSetTpNamePackage ."
    ::= { mtpGroups 49 }

mtpSignLinkTestPackage OBJECT-GROUP
    OBJECTS {
	mtpSlTest }
    STATUS current
    DESCRIPTION
	""
    REFERENCE
	"ITU-T Rec. Q.751.1 (1997), ANSI T1.116.1 (2000), 
	 signLinkTestPackage ."
    ::= { mtpGroups 50 }

mtpSlNamePackage OBJECT-GROUP
    OBJECTS {
	mtpSlName }
    STATUS current
    DESCRIPTION
	""
    REFERENCE
	"ITU-T Rec. Q.751.1 (1997), ANSI T1.116.1 (2000), 
	 signLinkTpNamePackage ."
    ::= { mtpGroups 51 }

mtpRtNamePackage OBJECT-GROUP
    OBJECTS {
	mtpRtName }
    STATUS current
    DESCRIPTION
	""
    REFERENCE
	"ITU-T Rec. Q.751.1 (1997), ANSI T1.116.1 (2000), 
	 signRouteNePartNamePackage ."
    ::= { mtpGroups 52 }

mtpRsNamePackage OBJECT-GROUP
    OBJECTS {
	mtpRsName }
    STATUS current
    DESCRIPTION
	""
    REFERENCE
	"ITU-T Rec. Q.751.1 (1997), ANSI T1.116.1 (2000), 
	 signRouteSetNePartNamePackage ."
    ::= { mtpGroups 53 }

mtpStListPackage OBJECT-GROUP
    OBJECTS {
	mtpSlSdtList, mtpSlSdtListPointer, mtpSlSdtListRowStatus }
    STATUS current
    DESCRIPTION
	""
    REFERENCE
	"ITU-T Rec. Q.751.1 (1997), ANSI T1.116.1 (2000), 
	 signTermListPackage ."
    ::= { mtpGroups 54 }

mtpStNamePackage OBJECT-GROUP
    OBJECTS {
	mtpSdtName }
    STATUS current
    DESCRIPTION
	""
    REFERENCE
	"ITU-T Rec. Q.751.1 (1997), ANSI T1.116.1 (2000), 
	 signTermNamePackage ."
    ::= { mtpGroups 55 }

slsCodeNormalListPackage OBJECT-GROUP
    OBJECTS {
	mtpSlSlsCodeNormalList }
    STATUS current
    DESCRIPTION
	""
    REFERENCE
	"ITU-T Rec. Q.751.1 (1997), ANSI T1.116.1 (2000), 
	 slsCodeNormalListPackage ."
    ::= { mtpGroups 56 }

slsListPackage OBJECT-GROUP
    OBJECTS {
	mtpRtSlsList }
    STATUS current
    DESCRIPTION
	""
    REFERENCE
	"ITU-T Rec. Q.751.1 (1997), ANSI T1.116.1 (2000), slsListPackage 
	 ."
    ::= { mtpGroups 57 }

mtpSlL3ProfileNamePackage OBJECT-GROUP
    OBJECTS {
	mtpSlL3ProfileName }
    STATUS current
    DESCRIPTION
	""
    REFERENCE
	"ITU-T Rec. Q.751.1 (1997), ANSI T1.116.1 (2000), 
	 slTimersProfileNamePackage ."
    ::= { mtpGroups 58 }

mtpSlL3ProfilePointerPackage OBJECT-GROUP
    OBJECTS {
	mtpSlL3ProfilePointer }
    STATUS current
    DESCRIPTION
	""
    REFERENCE
	"ITU-T Rec. Q.751.1 (1997), ANSI T1.116.1 (2000), 
	 slTimersProfilePointerPackage ."
    ::= { mtpGroups 59 }

mtpRestartingNotification NOTIFICATION-GROUP
    NOTIFICATIONS {
	mtpRestarting }
    STATUS current
    DESCRIPTION
	""
    REFERENCE
	"ITU-T Rec. Q.751.1 (1997), ANSI T1.116.1 (2000), mtpRestaring 
	 notification."
    ::= { mtpGroups 60 }

mtpSpTimersPackage OBJECT-GROUP
    OBJECTS {
	mtpSpMtpT1, mtpSpMtpT2, mtpSpMtpT3, mtpSpMtpT4, mtpSpMtpT5, 
	mtpSpMtpT6, mtpSpMtpT7, mtpSpMtpT8, mtpSpMtpT10, mtpSpMtpT11, 
	mtpSpMtpT12, mtpSpMtpT13, mtpSpMtpT14, mtpSpMtpT15, mtpSpMtpT16, 
	mtpSpMtpT17, mtpSpMtpT19A, mtpSpMtpT31A, mtpSpMtpT32A, 
	mtpSpMtpT33A, mtpSpMtpT34A, mtpSpMtpT18I, mtpSpMtpT19I, 
	mtpSpMtpT20I, mtpSpMtpT21I, mtpSpMtpT22I, mtpSpMtpT23I, 
	mtpSpMtpT20A, mtpSpMtpT21A, mtpSpMtpT24I, mtpSpMtpT1T, 
	mtpSpMtpT2T, mtpSpMtpT1S }
    STATUS current
    DESCRIPTION
	"This package contains the values of the Q.704 and Q.707 or 
	 T1.111.4 and T1.111.7 timers."
    REFERENCE
	"ITU-T Rec. Q.751.1 (1997), ANSI T1.116.1 (2000), 
	 spTimersPackage ."
    ::= { mtpGroups 61 }

mtpSpProfileNamePackage OBJECT-GROUP
    OBJECTS {
	mtpSpProfileName }
    STATUS current
    DESCRIPTION
	""
    REFERENCE
	"ITU-T Rec. Q.751.1 (1997), ANSI T1.116.1 (2000), 
	 spTimersProfileNamePackage ."
    ::= { mtpGroups 62 }

mtpSpProfilePointerPackage OBJECT-GROUP
    OBJECTS {
	mtpSpProfilePointer }
    STATUS current
    DESCRIPTION
	""
    REFERENCE
	"ITU-T Rec. Q.751.1 (1997), ANSI T1.116.1 (2000), 
	 spTimersProfilePointerPackage ."
    ::= { mtpGroups 63 }

ss7OnOccEventPackage NOTIFICATION-GROUP
    NOTIFICATIONS {
	ss7OnOccEvent }
    STATUS current
    DESCRIPTION
	""
    REFERENCE
	"ITU-T Rec. Q.751.1 (1997), ANSI T1.116.1 (2000), 
	 ss7OnOccEventPackage ."
    ::= { mtpGroups 64 }

stmChannelPackage OBJECT-GROUP
    OBJECTS {
	mtpSdlStmChannel }
    STATUS current
    DESCRIPTION
	""
    REFERENCE
	"ITU-T Rec. Q.751.1 (1997), ANSI T1.116.1 (2000), 
	 stmChannelPackage ."
    ::= { mtpGroups 65 }

mtpGsNamePackage OBJECT-GROUP
    OBJECTS {
	mtpGsName }
    STATUS current
    DESCRIPTION
	""
    REFERENCE
	"ITU-T Rec. Q.751.1 (1997), ANSI T1.116.1 (2000), 
	 stpScreeningTableNamePackage ."
    ::= { mtpGroups 66 }

usageStatePackage OBJECT-GROUP
    OBJECTS {
	mtpRtUsageState }
    STATUS current
    DESCRIPTION
	"This package supplies a possibility to cover 'transfer 
	 restricted' for a route."
    REFERENCE
	"ITU-T Rec. Q.751.1 (1997), ANSI T1.116.1 (2000), 
	 usageStatePackage ."
    ::= { mtpGroups 67 }

-- adjPcPackage OBJECT-GROUP
--     OBJECTS {
--         adjPc
--     }
--     STATUS current
--     DESCRIPTION
--         ""
--     REFERENCE
--         "ITU-T Rec. Q.2751.1 (1997), adjPcPackage."
--     ::= { mtpGroups 71 }

broadbandSpecificPackage OBJECT-GROUP
    OBJECTS {
	mtpSdlVcTTpPointer }
    STATUS current
    DESCRIPTION
	""
    REFERENCE
	"ITU-T Rec. Q.2751.1 (1997), broadbandSpecificPackage."
    ::= { mtpGroups 68 }

egressTransmissionRateIntervalPackage OBJECT-GROUP
    OBJECTS {
	mtpSaalEgressTransmissionRateIntervalLower, 
	mtpSaalEgressTransmissionRateIntervalUpper }
    STATUS current
    DESCRIPTION
	"This package should be used, if the attributes of the 
	 saalNniProtocolProfile are designed to fit to SAAL NNI 
	 signalling traffic, where ingress and egress traffic have 
	 significantly different cell rates."
    REFERENCE
	"ITU-T Rec. Q.2751.1 (1997), 
	 egressTransmissionRateIntervalPackage."
    ::= { mtpGroups 69 }

longMessageSupportedPackage OBJECT-GROUP
    OBJECTS {
	mtpSapLongMessageSupported }
    STATUS current
    DESCRIPTION
	""
    REFERENCE
	"ITU-T Rec. Q.2751.1 (1997), longMessageSupportedPackage."
    ::= { mtpGroups 70 }

narrowbandSpecificPackage OBJECT-GROUP
    OBJECTS {
	mtpNbTransmissionRate }
    STATUS current
    DESCRIPTION
	""
    REFERENCE
	"ITU-T Rec. Q.2751.1 (1997), narrowbandSpecificPackage."
    ::= { mtpGroups 71 }

pollAfterRetransmissionPackage OBJECT-GROUP
    OBJECTS {
	mtpSaalPollAfterRetransmission }
    STATUS current
    DESCRIPTION
	"This package should be used, if the poll after retransmission 
	 can be selected at creation time of a saalNniProtocolProfile."
    REFERENCE
	"ITU-T Rec. Q.2751.1 (1997), pollAfterRetransmissionPackage."
    ::= { mtpGroups 72 }

mtpSaalProfilePackage OBJECT-GROUP
    OBJECTS {
	mtpSaalBufferRelease, mtpSaalMaxCc, mtpSaalMaxNrp, 
	mtpSaalMaxInformationFieldLength, mtpSaalMaxLengthSscopUuField, 
	mtpSaalMaxPd, mtpSaalMaxSscopCreditToPeer, mtpSaalMaxStat, 
	mtpSaalN1, mtpSaalNniLayerManagementProvingState, 
	mtpSaalNniLayerManagementTimerNoCredit, 
	mtpSaalNniLayerManagementTimerRepeatSrec, mtpSaalNniTimerT1, 
	mtpSaalNniTimerT2, mtpSaalNniTimerT3, mtpSaalSscopTimerCc, 
	mtpSaalSscopTimerIdle, mtpSaalSscopTimerKeepAlive, 
	mtpSaalSscopTimerNoResponse, mtpSaalSscopTimerPoll, 
	mtpSaalTransmissionRateIntervalLower, 
	mtpSaalTransmissionRateIntervalUpper, mtpSaalRowStatus }
    STATUS current
    DESCRIPTION
	"The saalNniProtocolProfile is a broadband-specific object class 
	 and corresponds to the object class mtpL2ProtocolProfile for 
	 narrow-band.  The MOC comprises attributes required for SSCOP, 
	 SSCF-NNI and Layer Management for NNI."
    REFERENCE
	"ITU-T Rec. Q.2751.1 (1997), saalNniProtocolProfilePackage."
    ::= { mtpGroups 73 }

saalSdlPackage OBJECT-GROUP
    OBJECTS {
	mtpSdlOperationalState, mtpSdlEquipmentPointer }
    STATUS current
    DESCRIPTION
	""
    REFERENCE
	"ITU-T Rec. Q.2751.1 (1997), saalSignDataLinkTpPackage."
    ::= { mtpGroups 74 }

-- saalSlPackage OBJECT-GROUP
--     OBJECTS {
--     }
--     STATUS current
--     DESCRIPTION
--         ""
--     REFERENCE
--         "ITU-T Rec. Q.2751.1 (1997), saalSlPackage."
--     ::= { mtpGroups 80 }

m2paSctpDefaultsPackage OBJECT-GROUP
    OBJECTS {
	mtpM2paDefaultSctpNoDelay, mtpM2paDefaultSctpMaxseg, 
	mtpM2paDefaultSctpHeartbeatItvl, mtpM2paDefaultSctpHeartbeat, 
	mtpM2paDefaultSctpRtoInitial, mtpM2paDefaultSctpRtoMin, 
	mtpM2paDefaultSctpRtoMax, mtpM2paDefaultSctpPathMaxRetrans, 
	mtpM2paDefaultSctpCookieLife, mtpM2paDefaultSctpCookieInc, 
	mtpM2paDefaultSctpMaxInitRetries, mtpM2paDefaultSctpMaxBurst, 
	mtpM2paDefaultSctpAssocMaxRetrans, mtpM2paDefaultSctpSackDelay, 
	mtpM2paDefaultSctpLifetime }
    STATUS current
    DESCRIPTION
	"A collection of SCTP default objects."
    ::= { mtpGroups 75 }

mtpM2paProfilePkg OBJECT-GROUP
    OBJECTS {
	mtpM2paN1, mtpM2paLoopDelayLower, mtpM2paLoopDelayUpper, 
	mtpM2paTransmissionRateIntervalLower, 
	mtpM2paTransmissionRateIntervalUpper, mtpM2paSctpNoDelay, 
	mtpM2paSctpMaxseg, mtpM2paSctpHeartbeatItvl, 
	mtpM2paSctpHeartbeat, mtpM2paSctpRtoInitial, mtpM2paSctpRtoMin, 
	mtpM2paSctpRtoMax, mtpM2paSctpPathMaxRetrans, 
	mtpM2paSctpCookieLife, mtpM2paSctpCookieInc, 
	mtpM2paSctpMaxInitRetries, mtpM2paSctpMaxBurst, 
	mtpM2paSctpAssocMaxRetrans, mtpM2paSctpSackDelay, 
	mtpM2paSctpLifetime, mtpM2paRowStatus }
    STATUS current
    DESCRIPTION
	""
    ::= { mtpGroups 76 }

m2paProvingPackage OBJECT-GROUP
    OBJECTS {
	mtpM2paProving, mtpM2paManagementProvingState, 
	mtpM2paProvingAttempts }
    STATUS current
    DESCRIPTION
	""
    ::= { mtpGroups 77 }

providerEntityNamesPackage OBJECT-GROUP
    OBJECTS {
	mtpSapProviderEntityNames }
    STATUS current
    DESCRIPTION
	""
    REFERENCE
	"ITU-T Rec. Q.751.1 (1997), ANSI T1.116.1 (2000), 
	 providerEntityNamesPackage."
    ::= { mtpGroups 78 }

mtpRestartingParameters OBJECT-GROUP
    OBJECTS {
	networkPointCode }
    STATUS current
    DESCRIPTION
	""
    ::= { mtpGroups 79 }

ss7OnOccEventParameters OBJECT-GROUP
    OBJECTS {
	changeInLsToAdjSp, oldLs, newLs, inaccessibleSp, 
	remoteUnavailableUserPart, congestionStatus, networkPointCode, 
	userPart, userPartStatus, linkFailureReason }
    STATUS current
    DESCRIPTION
	""
    ::= { mtpGroups 80 }

mtpSapAsaPointerPackage OBJECT-GROUP
    OBJECTS {
	mtpSapAsaProfilePointer }
    STATUS current
    DESCRIPTION
	""
    ::= { mtpGroups 81 }

mtpL3AsaPointerPackage OBJECT-GROUP
    OBJECTS {
	mtpL3AsaProfilePointer }
    STATUS current
    DESCRIPTION
	""
    ::= { mtpGroups 82 }

mtpSlAsaPointerPackage OBJECT-GROUP
    OBJECTS {
	mtpSlAsaProfilePointer }
    STATUS current
    DESCRIPTION
	""
    ::= { mtpGroups 83 }

mtpRsAsaPointerPackage OBJECT-GROUP
    OBJECTS {
	mtpRsAsaProfilePointer }
    STATUS current
    DESCRIPTION
	""
    ::= { mtpGroups 84 }

mtpLsAsaPointerPackage OBJECT-GROUP
    OBJECTS {
	mtpLsAsaProfilePointer }
    STATUS current
    DESCRIPTION
	""
    ::= { mtpGroups 85 }

mtpLsProfileCompliance MODULE-COMPLIANCE
    STATUS current
    DESCRIPTION
	""

    MODULE -- this module

    MANDATORY-GROUPS {
	mtpLsProfilePackage }
    GROUP mtpLsProfileNamePackage
    DESCRIPTION
	"PRESENT IF an instance supports it."

    MODULE OPENSS7-SMI-MIB

    GROUP createDeleteNotificationsPackage
    DESCRIPTION
	"PRESENT IF the objectCreation and objectDeletion notifications 
	 defined in 'ITU-T Rec. X.721 (1992) | ISO/IEC 10165-2 : 1992' 
	 are supported by an instance of this class"
    GROUP attributeValueChangeNotificationPackage
    DESCRIPTION
	"PRESENT IF the attributeValueChangeNotification defined in 
	 'ITU-T Rec. X.721 (1992) | ISO/IEC 10165-2 : 1992' is supported 
	 by an instance of this class"

    ::= { mtpCompliance 1 }

mtpSapCompliance MODULE-COMPLIANCE
    STATUS current
    DESCRIPTION
	""

    MODULE -- this module

    MANDATORY-GROUPS {
	mtpSapPkg }
    GROUP providerEntityNamesPackage
    DESCRIPTION
	"PRESENT IF an instance supports it."
    GROUP mtpSapAsaPointerPackage
    DESCRIPTION
	"PRESENT IF an instance supports it."
    GROUP mtpSapNamePackage
    DESCRIPTION
	"PRESENT IF an instance supports it."
    GROUP longMessageSupportedPackage
    DESCRIPTION
	"PRESENT IF an instance supports it."

    ::= { mtpCompliance 2 }

mtpL2ProfocolProfileCompliance MODULE-COMPLIANCE
    STATUS current
    DESCRIPTION
	""

    MODULE -- this module

    MANDATORY-GROUPS {
	mtpSlL2ProfilePkg }
    GROUP bufferMechanismPackage
    DESCRIPTION
	"PRESENT IF an instance supports it."
    GROUP congestionHandlingPackage
    DESCRIPTION
	"PRESENT IF an instance supports it."
    GROUP loopDelayPackage
    DESCRIPTION
	"PRESENT IF an instance supports it."
    GROUP mtpSlL2ProfileNamePackage
    DESCRIPTION
	"PRESENT IF an instance supports it."
    GROUP multipleTransmissionCongestionLevelsPackage
    DESCRIPTION
	"PRESENT IF an instance supports it."
    GROUP multipleTransmissionCongestionLevelsWithPrioPackage
    DESCRIPTION
	"PRESENT IF an instance supports it."
    GROUP multipleTransmissionCongestionStatesPackage
    DESCRIPTION
	"PRESENT IF an instance supports it."
    GROUP pCRPackage
    DESCRIPTION
	"PRESENT IF an instance supports it."
    GROUP receiveCongestionLevelsPackage
    DESCRIPTION
	"PRESENT IF an instance supports it."

    MODULE OPENSS7-SMI-MIB

    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in ITU-T Rec. X.721 (1992) | ISO/IEC 10165-2 : 1992 are 
	 supported by an instance of this class."

    ::= { mtpCompliance 3 }

mtpNbProfileCompliance MODULE-COMPLIANCE
    STATUS current
    DESCRIPTION
	""

    MODULE -- this module

    MANDATORY-GROUPS {
	mtpSlL2ProfilePkg, narrowbandSpecificPackage }

    ::= { mtpCompliance 4 }

mtpSaalProfileCompliance MODULE-COMPLIANCE
    STATUS current
    DESCRIPTION
	""

    MODULE -- this module

    MANDATORY-GROUPS {
	mtpSaalProfilePackage }
    GROUP egressTransmissionRateIntervalPackage
    DESCRIPTION
	"PRESENT IF an instance support it."
    GROUP pollAfterRetransmissionPackage
    DESCRIPTION
	"PRESENT IF an instance supports this national option."

    MODULE OPENSS7-SMI-MIB

    GROUP createDeleteNotificationsPackage
    DESCRIPTION
	"PRESENT IF the objectCreation and objectDeletion notifications 
	 defined in oITU-T Rec. X.721 (1992) | ISO/IEC 10165-2: 1992o 
	 are supported by an instance of this class."
    GROUP attributeValueChangeNotificationPackage
    DESCRIPTION
	"PRESENT IF the attributeValueChangeNotification defined in 
	 nITU-T Rec. X.721 (1992) | ISO/IEC 10165-2: 1992 is supported 
	 by an instance of this class."

    ::= { mtpCompliance 5 }

mtpM2paProfileCompliance MODULE-COMPLIANCE
    STATUS current
    DESCRIPTION
	""

    MODULE -- this module

    MANDATORY-GROUPS {
	mtpM2paProfilePkg }
    GROUP m2paSctpDefaultsPackage
    DESCRIPTION
	"PRESENT IF an instance supports it."
    GROUP m2paProvingPackage
    DESCRIPTION
	"PRESENT IF an instance supports it."

    MODULE OPENSS7-SMI-MIB

    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in ITU-T Rec. X.721 (1992) | ISO/IEC 10165-2 : 1992 are 
	 supported by an instance of this class."

    ::= { mtpCompliance 6 }

mtpL3Compliacne MODULE-COMPLIANCE
    STATUS current
    DESCRIPTION
	""

    MODULE -- this module

    MANDATORY-GROUPS {
	mtpL3Package }
    GROUP mtpL3NamePackage
    DESCRIPTION
	"PRESENT IF an instance supports it."
    GROUP ss7OnOccEventPackage
    DESCRIPTION
	"PRESENT IF an instance supports it."
    GROUP ss7OnOccEventParameters
    DESCRIPTION
	"PRESENT IF an instance supports it."
    GROUP mtpL3AsaPointerPackage
    DESCRIPTION
	"PRESENT IF an instance supports it and the 
	 (communicationsAlarmPackage or ss7OnOccEventPackage) is 
	 present."

    MODULE OPENSS7-SMI-MIB

    GROUP communicationsAlarmPackage
    DESCRIPTION
	"PRESENT IF an instance supports it."
    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in 'ITU-T Rec. X.721 (1992) | ISO/IEC 10165-2 : 1992' 
	 are supported by an instance of this class."

    ::= { mtpCompliance 7 }

mtpSpCompliance MODULE-COMPLIANCE
    STATUS current
    DESCRIPTION
	""

    MODULE -- this module

    MANDATORY-GROUPS {
	mtpSpPackage, mtpRestartingNotification, mtpRestartingParameters 
	}
    OBJECT mtpSpType
    MIN-ACCESS read-only
    DESCRIPTION
	"It is not necessary that the implementation be able to change 
	 the value of the signalling point type."
    GROUP mtpSpNamePackage
    DESCRIPTION
	"PRESENT IF an instance supports it."
    GROUP mtpSpTimersPackage
    DESCRIPTION
	"PRESENT IF the instance does not support the 
	 spTimersProfilePointerPackage."
    GROUP mtpSpProfilePointerPackage
    DESCRIPTION
	"PRESENT IF the instance does not support the spTimersPackage."

    MODULE OPENSS7-SMI-MIB

    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in 'ITU-T Rec. X.721 (1992) | ISO/IEC 10165-2 : 1992' 
	 are supported by an instance of this class."

    ::= { mtpCompliance 8 }

mtpSdlCompliance MODULE-COMPLIANCE
    STATUS current
    DESCRIPTION
	""

    MODULE -- this module

    MANDATORY-GROUPS {
	mtpSdlPackage }
    GROUP cICPackage
    DESCRIPTION
	"PRESENT IF an instance supports it."
    GROUP mtpSdlNamePackage
    DESCRIPTION
	"PRESENT IF an instance supports it."
    GROUP stmChannelPackage
    DESCRIPTION
	"PRESENT IF an instance supports it or the signalling point 
	 supports the automatic allocation of signalling datalinks."
    GROUP narrowbandSpecificPackage
    DESCRIPTION
	"PRESENT IF an instance supports it."
    GROUP broadbandSpecificPackage
    DESCRIPTION
	"PRESENT IF an instance supports it."
    GROUP saalSdlPackage
    DESCRIPTION
	"PRESENT IF an instance supports it."

    MODULE OPENSS7-SMI-MIB

    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in 'ITU-T Rec. X.721 (1992) | ISO/IEC 10165-2 : 1992' 
	 are supported by an instance of this class."

    ::= { mtpCompliance 9 }

mtpLsCompliance MODULE-COMPLIANCE
    STATUS current
    DESCRIPTION
	""

    MODULE -- this module

    MANDATORY-GROUPS {
	mtpLsPackage }
    GROUP administrativeStatePackage
    DESCRIPTION
	"PRESENT IF an instance supports it."
    GROUP inLsLoadShareAlgorithmPackage
    DESCRIPTION
	"PRESENT IF an instance supports it."
    GROUP mtpLsProfilePointerPackage
    DESCRIPTION
	"PRESENT IF the instance of superior class mtpSignPoint does not 
	 support the conditional spTimersPackage."
    GROUP noBasicLinkAllocationPackage
    DESCRIPTION
	"PRESENT IF Basic link allocation is not done."
    GROUP mtpLsNamePackage
    DESCRIPTION
	"PRESENT IF an instance supports it."
    GROUP mtpLsAsaPointerPackage
    DESCRIPTION
	"PRESENT IF an instance supports it and the 
	 communicationsAlarmPackage is present."

    MODULE OPENSS7-SMI-MIB

    GROUP communicationsAlarmPackage
    DESCRIPTION
	"PRESENT IF an instance supports it."
    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in 'ITU-T Rec. X.721 (1992) | ISO/IEC 10165-2 : 1992' 
	 are supported by an instance of this class."

    ::= { mtpCompliance 10 }

mtpSlCompliance MODULE-COMPLIANCE
    STATUS current
    DESCRIPTION
	""

    MODULE -- this module

    MANDATORY-GROUPS {
	mtpSlPackage }
    GROUP linkCongestionLevelPackage
    DESCRIPTION
	"PRESENT IF the exchange support the operation, management and 
	 administration of multiple transmission congestion levels 
	 (national option)."
    GROUP relatedLinkGroupNumberPackage
    DESCRIPTION
	"PRESENT IF an instance supports it."
    GROUP mtpSdlListPackage
    DESCRIPTION
	"PRESENT IF an instance supports it."
    GROUP mtpSignLinkTestPackage
    DESCRIPTION
	"PRESENT IF the on-demand signalling link test as described in 
	 Q.707 is supported."
    GROUP mtpSlNamePackage
    DESCRIPTION
	"PRESENT IF an instance supports it."
    GROUP mtpStListPackage
    DESCRIPTION
	"PRESENT IF an instance supports it or an instance supports the 
	 mtpSignDataLinkTpListPackage."
    GROUP slsCodeNormalListPackage
    DESCRIPTION
	"PRESENT IF an instance supports it."
    GROUP mtpSlL3ProfilePointerPackage
    DESCRIPTION
	"PRESENT IF the instance of superior class mtpSignPoint does not 
	 support the conditional spTimersPackage."
    GROUP ss7OnOccEventPackage
    DESCRIPTION
	"PRESENT IF an instance supports it."
    GROUP ss7OnOccEventParameters
    DESCRIPTION
	"PRESENT IF an instance supports it."
    GROUP mtpSlAsaPointerPackage
    DESCRIPTION
	"PRESENT IF an instance supports it and the 
	 (communicationsAlarmPackage or ss7OnOccEventPackage) is 
	 present."

    MODULE OPENSS7-SMI-MIB

    GROUP communicationsAlarmPackage
    DESCRIPTION
	"PRESENT IF an instance supports it."
    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in 'ITU-T Rec. X.721 (1992) | ISO/IEC 10165-2 : 1992' 
	 are supported by an instance of this class."

    ::= { mtpCompliance 11 }

mtpSlL3ProfileCompliance MODULE-COMPLIANCE
    STATUS current
    DESCRIPTION
	""

    MODULE -- this module

    MANDATORY-GROUPS {
	mtpSlL3ProfilePackage }
    GROUP mtpSlL3ProfileNamePackage
    DESCRIPTION
	"PRESENT IF an instance supports it."

    MODULE OPENSS7-SMI-MIB

    GROUP createDeleteNotificationsPackage
    DESCRIPTION
	"PRESENT IF the objectCreation and objectDeletion notifications 
	 defined in 'ITU-T Rec. X.721 (1992) | ISO/IEC 10165-2 : 1992' 
	 are supported by an instance of this class."
    GROUP attributeValueChangeNotificationPackage
    DESCRIPTION
	"PRESENT IF the attributeValueChangeNotification defined in 
	 'ITU-T Rec. X.721 (1992) | ISO/IEC 10165-2 : 1992' is supported 
	 by an instance of this class."

    ::= { mtpCompliance 12 }

mtpSpProfileCompliance MODULE-COMPLIANCE
    STATUS current
    DESCRIPTION
	""

    MODULE -- this module

    MANDATORY-GROUPS {
	mtpSpProfilePackage }
    GROUP mtpSpProfileNamePackage
    DESCRIPTION
	"PRESENT IF an instance supports it."

    MODULE OPENSS7-SMI-MIB

    GROUP createDeleteNotificationsPackage
    DESCRIPTION
	"PRESENT IF the objectCreation and objectDeletion notifications 
	 defined in ITU-T Rec. X.721 (1992) | ISO/IEC 10165-2 : 1992 are 
	 supported by an instance of this class."
    GROUP attributeValueChangeNotificationPackage
    DESCRIPTION
	"PRESENT IF the attributeValueChangeNotification defined in 
	 ITU-T Rec. X.721 (1992) | ISO/IEC 10165-2 : 1992 is supported 
	 by an instance of this class."

    ::= { mtpCompliance 13 }

mtpRtCompliance MODULE-COMPLIANCE
    STATUS current
    DESCRIPTION
	""

    MODULE -- this module

    MANDATORY-GROUPS {
	mtpRtPackage }

    GROUP clsLoadsharingInformationPackage
    DESCRIPTION
	"PRESENT IF an instance supports it."
    GROUP fixedRouteNePartPriorityPackage
    DESCRIPTION
	"PRESENT IF the instance does not use the 
	 flexibleRouteNePartPriorityPackage."
    GROUP flexibleRouteNePartPriorityPackage
    DESCRIPTION
	"PRESENT IF the instance does not use the 
	 fixedRouteNePartPriorityPackage."
    GROUP loadsharingInformationRouteNePartPackage
    DESCRIPTION
	"PRESENT IF the instance supports it."
    GROUP mtpLoadsharingObjectForRouteNePartPointerPackage
    DESCRIPTION
	"PRESENT IF the instance supports it."
    GROUP mtpRtNamePackage
    DESCRIPTION
	"PRESENT IF an instance supports it."
    GROUP slsListPackage
    DESCRIPTION
	"PRESENT IF the instance supports it."
    GROUP usageStatePackage
    DESCRIPTION
	"PRESENT IF the instance supports 'transfer restricted'."

    MODULE OPENSS7-SMI-MIB

    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in 'ITU-T Rec. X.721 (1992) | ISO/IEC 10165-2 : 1992' 
	 are supported by an instance of this class."

    ::= { mtpCompliance 14 }

mtpSignRouteSetNetPartCompliance MODULE-COMPLIANCE
    STATUS current
    DESCRIPTION
	""

    MODULE -- this module

    MANDATORY-GROUPS {
	mtpRsPackage }
    GROUP congestedStatePackage
    DESCRIPTION
	"PRESENT IF the instance does not use the 
	 congestionLevelPackage."
    GROUP congestionLevelPackage
    DESCRIPTION
	"PRESENT IF the instance does not use the 
	 congestedStatePackage."
    GROUP loadsharingInformationRouteSetNePartPackage
    DESCRIPTION
	"PRESENT IF the instance supports it."
    GROUP mtpLoadsharingObjectForRouteSetNePartPointerPackage
    DESCRIPTION
	"PRESENT IF the instance supports it."
    GROUP remoteExchangeLabelPackage
    DESCRIPTION
	"PRESENT IF the instance supports it."
    GROUP mtpRsNamePackage
    DESCRIPTION
	"PRESENT IF the instance supports it."
    GROUP ss7OnOccEventPackage
    DESCRIPTION
	"PRESENT IF an instance supports it."
    GROUP ss7OnOccEventParameters
    DESCRIPTION
	"PRESENT IF an instance supports it."
    GROUP mtpRsAsaPointerPackage
    DESCRIPTION
	"PRESENT IF an instance supports it and the 
	 (communicationsAlarmPackage or ss7OnOccEventPackage) is 
	 present."

    MODULE OPENSS7-SMI-MIB

    GROUP communicationsAlarmPackage
    DESCRIPTION
	"PRESENT IF an instance supports it."
    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in 'ITU-T Rec. X.721 (1992) | ISO/IEC 10165-2 : 1992' 
	 are supported by an instance of this class."

    ::= { mtpCompliance 15 }

mtpStCompliance MODULE-COMPLIANCE
    STATUS current
    DESCRIPTION
	""

    MODULE -- this module

    MANDATORY-GROUPS {
	mtpStPackage }
    GROUP mtpStNamePackage
    DESCRIPTION
	"PRESENT IF an instance supports it."

    MODULE OPENSS7-SMI-MIB

    GROUP createDeleteNotificationsPackage
    DESCRIPTION
	"PRESENT IF the objectCreation and objectDeletion notifications 
	 defined in 'ITU-T Rec. X.721 (1992) | ISO/IEC 10165-2 : 1992' 
	 are supported by an instance of this class."
    GROUP attributeValueChangeNotificationPackage
    DESCRIPTION
	"PRESENT IF the attributeValueChangeNotification defined in 
	 'ITU-T Rec. X.721 (1992) | ISO/IEC 10165-2 : 1992' is supported 
	 by an instance of this class."

    ::= { mtpCompliance 16 }

mtpGsCompliance MODULE-COMPLIANCE
    STATUS current
    DESCRIPTION
	""

    MODULE -- this module

    MANDATORY-GROUPS {
	mtpGsPkg }
    GROUP getScreenedOpcsOrLinkSetsByDpcActionPackage
    DESCRIPTION
	"PRESENT IF an instance supports it."
    GROUP mtpGsNamePackage
    DESCRIPTION
	"PRESENT IF an instance supports it."

    MODULE OPENSS7-SMI-MIB

    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in 'ITU-T Rec. X.721 (1992) | ISO/IEC 10165-2 : 1992' 
	 are supported by an instance of this class."

    ::= { mtpCompliance 17 }

mtpGsLineCompliance MODULE-COMPLIANCE
    STATUS current
    DESCRIPTION
	""

    MODULE -- this module

    MANDATORY-GROUPS {
	mtpGsLinePkg }

    MODULE OPENSS7-SMI-MIB

    GROUP attributeValueChangeNotificationPackage
    DESCRIPTION
	"PRESENT IF the attributeValueChangeNotification defined in 
	 'ITU-T Rec. X.721 (1992) | ISO/IEC 10165-2 : 1992' is supported 
	 by an instance of this class."
    GROUP createDeleteNotificationsPackage
    DESCRIPTION
	"PRESENT IF the objectCreation and objectDeletion notifications 
	 defined in 'ITU-T Rec. X.721 (1992) | ISO/IEC 10165-2 : 1992' 
	 are supported by an instance of this class."

    ::= { mtpCompliance 18 }

END -- end of module OPENSS7-MTP-MIB.

-- vim: ft=mib comments=\f\:\",\b\:\-\-,\:\-\-,\f\b\:- fo+=tcqlornw tw=72 nocin nosi sts=4 sw=4
