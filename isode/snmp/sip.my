-- smdsip.my - SIP MIB

-- $Header: /xtel/isode/isode/snmp/RCS/sip.my,v 9.0 1992/06/16 12:38:11 isode Rel $
--
-- 
-- $Log: sip.my,v $
-- Revision 9.0  1992/06/16  12:38:11  isode
-- Release 8.0
--
--

--
--				  NOTICE
--
--    Acquisition, use, and distribution of this module and related
--    materials are subject to the restrictions of a license agreement.
--    Consult the Preface in the User's Manual for the full terms of
--    this agreement.
--
--


               RFCxxxx-MIB DEFINITIONS ::= BEGIN

               IMPORTS
                       experimental, Counter, TimeTicks, IpAddress
                               FROM RFC1155-SMI
                       OBJECT-TYPE
                               FROM RFC1212;

               --  This MIB module uses the extended OBJECT-TYPE macro as
               --  defined in [9].

               --  This is the MIB module for the SIP objects.


               sip     OBJECT IDENTIFIER ::= { experimental 16 }

               -- All representations of SMDS addresses in this MIB module use,
               -- as a textual convention (i.e., this convention does not affect
               -- their encoding), the data type:

               SMDSAddress ::= OCTET STRING (SIZE (8))
               -- the 60-bit SMDS address, preceded by 4 bits with the
               -- following values:
               -- "1100" when representing an individual address
               -- "1110" when representing a group address


























          -- The SIP Level 3 group
          -- Implementation of the SIP Level 3 group is mandatory
          -- for all systems implementing SIP Level 3.

          sipL3Table  OBJECT-TYPE
              SYNTAX  SEQUENCE OF SIPL3Entry
              ACCESS  not-accessible
              STATUS  mandatory
              DESCRIPTION
                      "This table contains SIP-L3 parameters and state
                      variables, one entry per SIP port."
              ::= { sip 1 }

          sipL3Entry  OBJECT-TYPE
              SYNTAX  SIPL3Entry
              ACCESS  not-accessible
              STATUS  mandatory
              DESCRIPTION
                      "This list contains SIP L3 parameters and state
                      variables."
              INDEX   { sipL3Index }
              ::= { sipL3Table 1 }

          SIPL3Entry  ::= SEQUENCE {
              sipL3Index
                  INTEGER,
              receivedIndividualDAedSIPL3PDUs
                  Counter,
              receivedGAedSIPL3PDUs
                  Counter,
              sentIndividualDAedSIPL3PDUs
                  Counter,
              sentGAedSIPL3PDUs
                  Counter,
              erroredSIPL3PDUs
                  Counter,
              unrecognizedDestinationAddresses
                  Counter,
              unrecognizedGroupAddresses
                  Counter,
              invalidSMDSAddressTypes
                  Counter,
              versionSupport







                  INTEGER
              }


          sipL3Index  OBJECT-TYPE
              SYNTAX  INTEGER
              ACCESS  read-only
              STATUS  mandatory
              DESCRIPTION
                      "The value of this object identifies the SIP port
                      interface for which this entry contains management
                      information.  The value of this object for a
                      particular interface has the same value as the
                      ifIndex object, defined in [4,6], for the same
                      interface."
              ::= { sipL3Entry 1 }

          receivedIndividualDAedSIPL3PDUs OBJECT-TYPE
              SYNTAX  Counter
              ACCESS  read-only
              STATUS  mandatory
              DESCRIPTION
                      "The total number of SIP Level 3 PDUs received
                      from the remote system across the SNI and
                      containing an individual destination address.  The
                      total includes only unerrored L3-PDUs."
              ::= { sipL3Entry 2 }

          receivedGAedSIPL3PDUs OBJECT-TYPE
              SYNTAX  Counter
              ACCESS  read-only
              STATUS  mandatory
              DESCRIPTION
                      "The total number of SIP Level 3 PDUs received
                      from the remote system across the SNI and
                      containing an group destination address.  The
                      total  includes only unerrored L3-PDUs."
              ::= { sipL3Entry 3 }

          sentIndividualDAedSIPL3PDUs OBJECT-TYPE
              SYNTAX  Counter
              ACCESS  read-only
              STATUS  mandatory
              DESCRIPTION
                      "The number of SIP Level 3 PDUs that have been







                      sent by this system across the SNI and that
                      contain an individual destination address."
              ::= { sipL3Entry 4 }

          sentGAedSIPL3PDUs OBJECT-TYPE
              SYNTAX  Counter
              ACCESS  read-only
              STATUS  mandatory
              DESCRIPTION
                      "The number of group addressed SIP L3-PDUs that
                      have been sent by this system across the SNI."
              ::= { sipL3Entry 5 }


          -- The total number of SIPL3-PDU errors can be calculated as
          -- (Syntactic errors + Semantic Service errors )
          -- Syntactic errors include:
          --    erroredSIPL3PDUs
          -- Latest occurrences of syntactic error types are logged in
          --    sipL3PDUErrorTable.
          -- Semantic Service errors include:
          --    unrecognizedDestinationAddresses
          --    unrecognizedGroupAddresses
          --    invalidSMDSAddressTypes
          -- Note that public networks supporting SMDS may discard
          -- SIPL3-PDUs due to subscription violations. Related
          -- managed objects are defined in [18].

          erroredSIPL3PDUs OBJECT-TYPE
              SYNTAX  Counter
              ACCESS  read-only
              STATUS  mandatory
              DESCRIPTION
                      "The total number of SIP Level 3 PDUs received
                      from the remote system that were discovered to
                      have errors (including protocol processing and bit
                      errors but excluding addressing-related errors)
                      and were discarded.  Includes both group addressed
                      L3-PDUs and L3-PDUs containing an individual
                      destination address."
              ::= { sipL3Entry 6 }

          unrecognizedDestinationAddresses OBJECT-TYPE
              SYNTAX  Counter
              ACCESS  read-only







              STATUS  mandatory
              DESCRIPTION
                      "The number of SIP Level 3 PDUs received from the
                      remote system with invalid or unknown destination
                      addresses (Source or Destination Address Screening
                      violations are not included)."
              ::= { sipL3Entry 7 }

          unrecognizedGroupAddresses OBJECT-TYPE
              SYNTAX  Counter
              ACCESS  read-only
              STATUS  mandatory
              DESCRIPTION
                      "The number of SIP Level 3 PDUs received from the
                      remote system with invalid or unknown group
                      addresses."
              ::= { sipL3Entry 8 }

          invalidSMDSAddressTypes OBJECT-TYPE
              SYNTAX  Counter
              ACCESS  read-only
              STATUS  mandatory
              DESCRIPTION
                      "The number of SIP Level 3 PDUs received from the
                      remote system with invalid or unknown destination
                      addresses (Source or Destination Address Screening
                      violations are not included)."
              ::= { sipL3Entry 9 }

          versionSupport  OBJECT-TYPE
              SYNTAX  INTEGER
              ACCESS  read-only
              STATUS  mandatory
              DESCRIPTION
                      "A value which indicates the version(s) of SIP
                      that this interface supports.  The value is a sum.
                      This sum initially takes the value zero.  For each
                      version, V, that this interface supports, 2 raised
                      to (V - 1) is added to the sum. For example, a
                      port supporting versions 1 and 2 would have a
                      value of (2^(1-1)+2^(2-1))=3."
              ::= { sipL3Entry 10 }











          -- The SIP Level 2 group
          -- Implementation of the SIP Level 2 group is mandatory
          -- for all systems implementing SIP Level 2.


          sipL2Table  OBJECT-TYPE
              SYNTAX  SEQUENCE OF SIPL2Entry
              ACCESS  not-accessible
              STATUS  mandatory
              DESCRIPTION
                      "This table contains SIP-L2 parameters and state
                      variables, one entry per SIP port."
              ::= { sip 2 }

          sipL2Entry  OBJECT-TYPE
              SYNTAX  SIPL2Entry
              ACCESS  not-accessible
              STATUS  mandatory
              DESCRIPTION
                      "This list contains SIP L2 parameters and state
                      variables."
              INDEX   { sipL2Index }
              ::= { sipL2Table 1 }

          SIPL2Entry  ::= SEQUENCE {
              sipL2Index
                  INTEGER,
              receivedSIPL2PDUs
                  Counter,
              sentSIPL2PDUs
                  Counter,
              hcsOrCRCErrors
                  Counter,
              payloadLengthErrors
                  Counter,
              sequenceNumberErrors
                  Counter,
              midCurrentlyActiveErrors
                  Counter,
              bomOrSSMsMIDErrors
                  Counter,
              eomsMIDErrors
                  Counter







              }


          sipL2Index  OBJECT-TYPE
              SYNTAX  INTEGER
              ACCESS  read-only
              STATUS  mandatory
              DESCRIPTION
                      "The value of this object identifies the SIP port
                      interface for which this entry contains management
                      information.  The value of this object for a
                      particular interface has the same value as the
                      ifIndex object, defined in [4,6], for the same
                      interface."
              ::= { sipL2Entry 1 }

          receivedSIPL2PDUs OBJECT-TYPE
              SYNTAX  Counter
              ACCESS  read-only
              STATUS  mandatory
              DESCRIPTION
                      "The number of SIP Level 2 PDUs received from the
                      remote system across the SNI. The total includes
                      only unerrored L2-PDUs."
              ::= { sipL2Entry 2 }

          sentSIPL2PDUs OBJECT-TYPE
              SYNTAX  Counter
              ACCESS  read-only
              STATUS  mandatory
              DESCRIPTION
                      "The number of SIP Level 2 PDUs that have been
                      sent by this system across the SNI."
              ::= { sipL2Entry 3 }

          -- The total number of SIPL2-PDU errors can be calculated as the
          -- sum of:
          --    hcsOrCRCErrors
          --    payloadLengthErrors
          --    sequenceNumberErrors
          --    midCurrentlyActiveErrors
          --    bomOrSSMsMIDErrors
          --    eomsMIDErrors

          hcsOrCRCErrors  OBJECT-TYPE







              SYNTAX  Counter
              ACCESS  read-only
              STATUS  mandatory
              DESCRIPTION
                      "The number of received SIP Level 2 PDUs that were
                      discovered to have either a Header Check Sequence
                      error or a Payload CRC violation."
              ::= { sipL2Entry 4 }

          payloadLengthErrors  OBJECT-TYPE
              SYNTAX  Counter
              ACCESS  read-only
              STATUS  mandatory
              DESCRIPTION
                      "The number of received SIP Level 2 PDUs that had
                      Payload Length errors that fall in the following
                      specifications:
                      - Payload length field value not equal to a
                      - multiple of 4 octets,

                      - SSM L2_PDU payload length field value less
                      - than 28 octets or greater than 44 octets,

                      - BOM or COM L2_PDU payload length field not
                      - equal to 44 octets,

                      - EOM L2_PDU payload length field value less
                      - than 4 octets or greater than 44 octets."
              ::= { sipL2Entry 5 }

          sequenceNumberErrors  OBJECT-TYPE
              SYNTAX  Counter
              ACCESS  read-only
              STATUS  mandatory
              DESCRIPTION
                      "The number of received SIP Level 2 PDUs that had
                      a sequence number within the L2_PDU not equal to
                      the expected sequence number of the SMDS SS
                      receive process."
              ::= { sipL2Entry 6 }

          midCurrentlyActiveErrors  OBJECT-TYPE
              SYNTAX Counter
              ACCESS  read-only
              STATUS  mandatory







              DESCRIPTION
                      "The number of received SIP Level 2 PDUs that are
                      BOMs for which an active receive process is
                      already started."
              ::= { sipL2Entry 7 }

          bomOrSSMsMIDErrors  OBJECT-TYPE
              SYNTAX  Counter
              ACCESS  read-only
              STATUS  mandatory
              DESCRIPTION
                      "The number of received SIP Level 2 PDUs that are
                      SSMs with a MID not equal to zero or are BOMs with
                      MIDs equal to zero."
              ::= { sipL2Entry 8 }

          eomsMIDErrors  OBJECT-TYPE
              SYNTAX  Counter
              ACCESS  read-only
              STATUS  mandatory
              DESCRIPTION
                      "The number of received SIP Level 2 PDUs that are
                      EOMs for which there is no active receive process
                      for the MID (i.e., the receipt of an EOM which
                      does not correspond to a BOM) OR the EOM has a MID
                      equal to zero."
              ::= { sipL2Entry 9 }


























          -- The SIP PLCP group
          -- Implementation of one of these groups is mandatory
          -- if the PLCP is implemented.

          sipPLCP OBJECT IDENTIFIER ::= { sip 3 }














































          -- The SIP DS1 PLCP group
          -- Implementation of this group is mandatory
          -- if the DS1 PLCP is implemented.

          sipDS1PLCPTable  OBJECT-TYPE
              SYNTAX  SEQUENCE OF SIPDS1PLCPEntry
              ACCESS  not-accessible
              STATUS  mandatory
              DESCRIPTION
                      "This table contains SIP DS1-PLCP parameters and
                      state variables, one entry per SIP port."
              ::= { sipPLCP 1 }

          sipDS1PLCPEntry  OBJECT-TYPE
              SYNTAX  SIPDS1PLCPEntry
              ACCESS  not-accessible
              STATUS  mandatory
              DESCRIPTION
                      "This list contains SIP DS1-PLCP parameters and
                      state variables."
              INDEX   { sipDS1PLCPIndex }
              ::= { sipDS1PLCPTable 1 }

          SIPDS1PLCPEntry  ::= SEQUENCE {
              sipDS1PLCPIndex
                  INTEGER,
              ds1PLCPSEFSs
                  Counter,
              ds1PLCPYellowSignal
                  INTEGER,
              ds1PLCPRedAlarm
                  INTEGER,
              ds1PLCPUASs
                  Counter
              }


          sipDS1PLCPIndex  OBJECT-TYPE
              SYNTAX  INTEGER
              ACCESS  read-only
              STATUS  mandatory
              DESCRIPTION
                      "The value of this object identifies the SIP port







                      interface for which this entry contains management
                      information.  The value of this object for a
                      particular interface has the same value as the
                      ifIndex object, defined in [4,6], for the same
                      interface."
              ::= { sipDS1PLCPEntry 1 }


          ds1PLCPSEFSs OBJECT-TYPE
              SYNTAX  Counter
              ACCESS  read-only
              STATUS  mandatory
              DESCRIPTION
                      "A DS1 Severely Errored Framing Second (SEFS) is a
                      count of one-second intervals containing one or
                      more SEF events.  A Severely Errored Framing (SEF)
                      event is declared when an error in the A1 octet
                      and an error in the A2 octet of a framing octet
                      pair (i.e., errors in both framing octets), or two
                      consecutive invalid and/or nonsequential Path
                      Overhead Identifier octets are detected."
              ::= { sipDS1PLCPEntry 2 }

          ds1PLCPYellowSignal OBJECT-TYPE
              SYNTAX  INTEGER {
                          ds1PLCPYellowSignal(1),
                          ds1PLCPNoYellowSignal(2)
                      }
              ACCESS  read-only
              STATUS  mandatory
              DESCRIPTION
                      "This variable indicates if a Yellow Signal is
                      received as defined in [12]."
              ::= { sipDS1PLCPEntry 3 }

          ds1PLCPRedAlarm OBJECT-TYPE
              SYNTAX  INTEGER {
                          ds1PLCPRedAlarm(1),
                          ds1PLCPNoRedAlarm(2)
                      }
              ACCESS  read-only
              STATUS  mandatory
              DESCRIPTION
                      "This variable indicates if a Red Alarm condition
                      exists.  A Red Alarm condition is sent when the







                      declaration of a PLCP Loss of Frame failure
                      condition occurs as defined in [12]."
              ::= { sipDS1PLCPEntry 4 }

          ds1PLCPUASs OBJECT-TYPE
              SYNTAX  Counter
              ACCESS  read-only
              STATUS  mandatory
              DESCRIPTION
                      "The counter associated with the number of
                      Unavailable Seconds, as defined by [12],
                      encountered by the PLCP."
              ::= { sipDS1PLCPEntry 5 }








































          -- The SIP DS3-PLCP group
          -- Implementation of this group is mandatory
          -- if the DS3 PLCP is implemented.

          sipDS3PLCPTable  OBJECT-TYPE
              SYNTAX  SEQUENCE OF SIPDS1PLCPEntry
              ACCESS  not-accessible
              STATUS  mandatory
              DESCRIPTION
                      "This table contains SIP DS3-PLCP parameters and
                      state variables, one entry per SIP port."
              ::= { sipPLCP 2 }

          sipDS3PLCPEntry  OBJECT-TYPE
              SYNTAX  SIPDS3PLCPEntry
              ACCESS  not-accessible
              STATUS  mandatory
              DESCRIPTION
                      "This list contains SIP DS3-PLCP parameters and
                      state variables."
              INDEX   { sipDS3PLCPIndex }
              ::= { sipDS3PLCPTable 1 }

          SIPDS3PLCPEntry  ::= SEQUENCE {
              sipDS3PLCPIndex
                  INTEGER,
              ds3PLCPSEFSs
                  Counter,
              ds3PLCPYellowSignal
                  INTEGER,
              ds3PLCPRedAlarm
                  INTEGER,
              ds3PLCPUASs
                  Counter
              }


          sipDS3PLCPIndex  OBJECT-TYPE
              SYNTAX  INTEGER
              ACCESS  read-only
              STATUS  mandatory
              DESCRIPTION
                      "The value of this object identifies the SIP port







                      interface for which this entry contains management
                      information.  The value of this object for a
                      particular interface has the same value as the
                      ifIndex object, defined in [4,6], for the same
                      interface."
              ::= { sipDS3PLCPEntry 1 }

          ds3PLCPSEFSs OBJECT-TYPE
              SYNTAX  Counter
              ACCESS  read-only
              STATUS  mandatory
              DESCRIPTION
                      "A DS3 Severely Errored Framing Second (SEFS) is a
                      count of one-second intervals containing one or
                      more SEF events.  A Severely Errored Framing (SEF)
                      event is declared when an error in the A1 octet
                      and an error in the A2 octet of a framing octet
                      pair (i.e., errors in both framing octets), or two
                      consecutive invalid and/or nonsequential Path
                      Overhead Identifier octets are detected."
              ::= { sipDS3PLCPEntry 2 }

          ds3PLCPYellowSignal OBJECT-TYPE
              SYNTAX  INTEGER {
                          ds3PLCPYellowSignal(1),
                          ds3PLCPNoYellowSignal(2)
                      }
              ACCESS  read-only
              STATUS  mandatory
              DESCRIPTION
                      "This variable indicates if a Yellow Signal is
                      received as defined in [12]."
              ::= { sipDS3PLCPEntry 3 }

          ds3PLCPRedAlarm OBJECT-TYPE
              SYNTAX  INTEGER {
                          ds3PLCPRedAlarm(1),
                          ds3PLCPNoRedAlarm(2)
                      }
              ACCESS  read-only
              STATUS  mandatory
              DESCRIPTION
                      "This variable indicates if a Red Alarm condition
                      exists.  A Red Alarm condition is sent when the
                      declaration of a PLCP Loss of Frame failure







                      condition occurs as defined in [12]."
              ::= { sipDS3PLCPEntry 4 }

          ds3PLCPUASs OBJECT-TYPE
              SYNTAX  Counter
              ACCESS  read-only
              STATUS  mandatory
              DESCRIPTION
                      "The counter associated with the number of
                      Unavailable Seconds, as defined by [12],
                      encountered by the PLCP."
              ::= { sipDS3PLCPEntry 5 }









































          -- The SMDS Applications group
          -- Applications that have been identified for this group are:
          --          * IP-over-SMDS (details are specified in [15])
          -- Implementation of this group is mandatory for systems
          -- that implement IP over SMDS Interface Protocol.

          smdsApplications OBJECT IDENTIFIER ::= { sip 4 }

          ipOverSMDS OBJECT IDENTIFIER ::= { smdsApplications 1 }

          -- Although the objects in this group are read-only, at the
          -- agent's discretion they may be made read-write so that the
          -- management station, when appropriately authorized, may
          -- change the addressing information related to the configuration
          -- of a logical IP subnetwork over SMDS.

          ipOverSMDSAddressTable OBJECT-TYPE
              SYNTAX  SEQUENCE OF IpOverSMDSAddressEntry
              ACCESS  not-accessible
              STATUS  mandatory
              DESCRIPTION
                      "The table of addressing information relevant to
                      this entity's IP addresses."
              ::= { ipOverSMDS 1 }

          ipOverSMDSAddressEntry OBJECT-TYPE
              SYNTAX  IpOverSMDSAddressEntry
              ACCESS  not-accessible
              STATUS  mandatory
              DESCRIPTION
                      "The addressing information for one of this
                      entity's IP addresses."
              INDEX   { ipEntryAddressIfIndex, ipEntryAddress }
              ::= { ipOverSMDSAddressTable 1 }

          IpOverSMDSAddressEntry ::=
              SEQUENCE {
                 ipEntryAddressIfIndex
                     INTEGER,
                 ipEntryAddress
                     IpAddress,
                 smdsHA
                     SMDSAddress,







                 smdsLISGA
                     SMDSAddress,
                 smdsARPReq
                     SMDSAddress
                 }

          ipEntryAddressIfIndex OBJECT-TYPE
              SYNTAX  INTEGER
              ACCESS  read-only
              STATUS  mandatory
              DESCRIPTION
                      "The value of this object identifies the SIP port
                      interface for which this entry contains management
                      information.  The value of this object for a
                      particular interface has the same value as the
                      ifIndex object, defined in [4,6], for the same
                      interface."
              ::= { ipOverSMDSAddressEntry 1 }

          ipEntryAddress OBJECT-TYPE
               SYNTAX  IpAddress
               ACCESS  read-only
               STATUS  mandatory
               DESCRIPTION
                      "The IP address to which this entry's addressing
                      information pertains."
              ::= { ipOverSMDSAddressEntry 2 }

          smdsHA OBJECT-TYPE
               SYNTAX  SMDSAddress
              ACCESS  read-only
              STATUS  mandatory
              DESCRIPTION
                      "The SMDS Individual address of the IP station."
              ::= { ipOverSMDSAddressEntry 3 }

          smdsLISGA OBJECT-TYPE
              SYNTAX  SMDSAddress
              ACCESS  read-only
              STATUS  mandatory
              DESCRIPTION
                      "The SMDS Group Address that has been configured
                      to identify the SMDS Subscriber Network Interfaces
                      (SNIs) of all members of the Logical IP Subnetwork
                      (LIS) connected to the SMDS Service."







              ::= { ipOverSMDSAddressEntry 4 }

          smdsARPReq OBJECT-TYPE
              SYNTAX  SMDSAddress
              ACCESS  read-only
              STATUS  mandatory
              DESCRIPTION
                      "The SMDS address (individual or group) to which
                      ARP Requests are to be sent."
              ::= { ipOverSMDSAddressEntry 5 }











































          -- The SMDS Carrier Selection group
          -- This group is used as a place holder
          -- for carrier selection objects.

          smdsCarrierSelection OBJECT IDENTIFIER ::= { sip 5}














































          -- The SIP Error Log
          -- Implementation of this group is mandatory
          -- for all systems that implement SIP Level 3.

          sipErrorLog OBJECT IDENTIFIER ::= { sip 6 }

          sipL3PDUErrorTable OBJECT-TYPE
              SYNTAX  SEQUENCE OF SIPL3PDUErrorEntry
              ACCESS  not-accessible
              STATUS  mandatory
              DESCRIPTION
                      "A table that contains the latest occurrence of
                      the following syntactical SIPL3PDU errors:

                      - Destination Address Field Format Error,
                      The following pertains to the 60 least significant
                      bits of the 64 bit address field.  For initial
                      availability of SMDS, the address shall use 10
                      digits.  An error is considered to have occurred
                      if the four most significant bits of the Address
                      subfield are not populated with the value 0001, OR
                      the 40 bits which follow are not Binary Coded
                      Decimal (BCD) encoded values of 10 digits, OR the
                      remaining 16 least significant bits are not
                      populated with 1's.

                      - Source Address Field Format Error,
                      The description of this parameter is the same as
                      the description of the Destination Address Field
                      Format Error parameter.

                      - Invalid BAsize Field Value,
                      An error is considered to have occurred when the
                      BAsize field of an SIPL3PDU contains a value less
                      that 32, greater than 9220 octets without the
                      CRC32 field present, or greater than 9224 octets
                      with the CRC32 field present.

                      - Invalid Header Extension Length Field Value,
                      An error is considered to have occurred when the
                      Header Extension Length field value is not equal
                      3.








                      - Invalid Header Extension - Element Length,
                      An error is considered to have occurred when the
                      Header Extension - Element Length is greater than
                      12.

                      - Invalid Header Extension - Version Element
                      Position, Length, or Value,
                      An error is considered to have occurred when a
                      Version element with Length=3, Type=0, and Value=1
                      does not appear first within the Header Extension,
                      or an element Type=0 appears somewhere other than
                      within the first three octets in the Header
                      Extension.

                      - Invalid Header Extension - Carrier Selection
                      Element Position, Length, Value or Format,
                      An error is considered to have occurred when a
                      Carrier Selection element does not appear second
                      within the Header Extension, if the Element Type
                      does not equal 1, the Element Length does not
                      equal 4, 6, or 8, the Element Value field is not
                      four BCD encoded decimal digits used in specifying
                      the Carrier Identification Code (CIC), or the
                      identified CIC code is invalid.

                      - Header Extension PAD Error
                      An error is considered to have occurred when the
                      Header Extension PAD is 9 octets in length, or if
                      the Header Extension PAD is greater than zero
                      octets in length and the Header Extension PAD does
                      not follow all Header Extension elements or does
                      not begin with at least one octet of all zeros.

                      - BEtag Mismatch Error,
                      An error is considered to have occurred when the
                      Beginning-End Tags in the SIPL3PDU header and
                      trailer are not equal.

                      - BAsize Field not equal to Length Field Error,
                      An error is considered to have occurred when the
                      value of the BAsize Field does not equal the value
                      of the Length Field.

                      - Incorrect Length Error, and
                      An error is considered to have occurred when the







                      the Length field value is not equal to the portion
                      of the SIPL3PDU which extends from the Destination
                      Address field up to and including the CRC32 field
                      (if present) or up to and including the PAD field
                      (if the CRC32 field is not present).

                      - MRI Timeout Error.
                      An error is considered to have occurred when the
                      elapsed time between receipt of BOM and
                      corresponding EOM exceeds the value of the MRI for
                      a particular transport signal format.

                      An entry is indexed by interface number and error
                      type, and contains Source Address, Destination
                      Address and a timestamp. All these errors are
                      counted in the erroredSIPL3PDUs counter.  When
                      sipL3PDUErrorTimeStamp is equal to zero, the
                      sipErrorLog does not contain any information."
              ::= { sipErrorLog 1 }

          sipL3PDUErrorEntry  OBJECT-TYPE
              SYNTAX SIPL3PDUErrorEntry
              ACCESS  not-accessible
              STATUS  mandatory
              DESCRIPTION
                      "An entry in the service disagreement table."
              INDEX   { sipL3PDUErrorIndex, sipL3PDUErrorType }
              ::= { sipL3PDUErrorTable 1 }

          SIPL3PDUErrorEntry ::= SEQUENCE {
              sipL3PDUErrorIndex
                  INTEGER,
              sipL3PDUErrorType
                  INTEGER,
              erroredL3PDUSourceAddress
                  SMDSAddress,
              erroredL3PDUDestinationAddress
                  SMDSAddress,
              sipL3PDUErrorTimeStamp
                  TimeTicks
              }

          sipL3PDUErrorIndex OBJECT-TYPE
              SYNTAX  INTEGER
              ACCESS  read-only







              STATUS  mandatory
              DESCRIPTION
                      "The value of this object identifies the SIP port
                      interface for which this entry contains management
                      information.   The value of this object for a
                      particular interface has the same value as the
                      ifIndex object, defined in [4,6], for the same
                      interface."
              ::= { sipL3PDUErrorEntry 1 }

           sipL3PDUErrorType OBJECT-TYPE
              SYNTAX  INTEGER {
                   erroredDAFieldFormat (1),
                   erroredSAFieldFormat (2),
                   invalidBAsizeFieldValue (3),
                   invalidHdrExtLength (4),
                   invalidHdrExtElementLength (5),
                   invalidHdrExtVersionElementPositionLenthOrValue (6),
                   invalidHdrExtCarSelectElementPositionLenghtValueOrFormat (7),
                   hePADError (8),
                   beTagMismatch (9),
                   baSizeFieldNotEqualToLengthField (10),
                   incorrectLength (11),
                   mriTimeout (12)
              }
              ACCESS  read-only
              STATUS  mandatory
              DESCRIPTION
                      "The type of error."
              ::= { sipL3PDUErrorEntry 2 }

          erroredL3PDUSourceAddress OBJECT-TYPE
              SYNTAX  SMDSAddress
              ACCESS  read-only
              STATUS  mandatory
              DESCRIPTION
                      "A rejected SMDS source address."
              ::= { sipL3PDUErrorEntry 3 }

          erroredL3PDUDestinationAddress OBJECT-TYPE
              SYNTAX  SMDSAddress
              ACCESS  read-only
              STATUS  mandatory
              DESCRIPTION
                      "A rejected SMDS destination address."







              ::= { sipL3PDUErrorEntry 4 }

          sipL3PDUErrorTimeStamp OBJECT-TYPE
              SYNTAX  TimeTicks
              ACCESS  read-only
              STATUS  mandatory
              DESCRIPTION
                      "The timestamp for the service disagreement.  The
                      timestamp contains the value of sysUpTime at the
                      latest occurrence of this type of service
                      disagreement.  See textual description under
                      sipL3PDUErrorTable for boundary conditions."
              ::= { sipL3PDUErrorEntry 5 }

          END
