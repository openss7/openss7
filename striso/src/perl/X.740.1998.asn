--@@ GDMOCHECK $Revision: 0.9.2.2 $
--@@ Copyright (c), 2001-2007 OpenSS7 Corporation  <http://www.openss7.com/>
--@@ Copyright (c), 1999-2000 Brian F. G. Bidulock <bidulock@openss7.org>
--@@ 
--@@ Input File: <(standard input)>
--@@ Special File: <(standard input).specials>
--@@ Date: Sat Sep 15 06:02:55 MDT 2007
--@@ 
--< GDMO.Document "ITU-T Rec. X.740 (1992) | ISO/IEC 10164-8 : 1993"
--  { joint-iso-ccitt ms(9) function(2) part8(8) } >--
MODULE "ITU-T Rec. X.740 (1992) | ISO/IEC 10164-8 : 1993" { joint-iso-ccitt ms(9) function(2) part8(8) }
--< ASN1.Version 1994 SecurityAuditTrailDefinitions
--  { joint-iso-ccitt ms(9) function(2) part8(8) asn1Module(2) 1 } >--
-- A.1 Allocation of object identifiers
-- This Recommendation | International Standard allocates the following object identifiers
SecurityAuditTrailDefinitions { joint-iso-ccitt ms(9) function(2) part8(8) asn1Module(2) 1 }
DEFINITIONS ::=
BEGIN
IMPORTS
ServiceReportCause
	FROM SecurityAuditTrail-ASN1Module { joint-iso-ccitt ms(9) function(2) part8(8) asn1Module(2) 2 };
securityAuditTrail-Object OBJECT IDENTIFIER ::= { joint-iso-ccitt ms(9) function(2) part8(8) managedObjectClass(3) }
securityAuditTrail-Package OBJECT IDENTIFIER ::= { joint-iso-ccitt ms(9) function(2) part8(8) package(4) }
securityAuditTrail-Attribute OBJECT IDENTIFIER ::= { joint-iso-ccitt ms(9) function(2) part8(8) attribute(7) }
securityAuditTrail-Notification OBJECT IDENTIFIER ::= { joint-iso-ccitt ms(9) function(2) part8(8) notification(10) }
serviceReportCause OBJECT IDENTIFIER ::= { joint-iso-ccitt ms(9) function(2) part8(8) standardSpecificExtension(0) 1 }
-- the following OBJECT IDENTIFIER values can be used as values for the service report cause parameter in A.5.
serviceRequest ServiceReportCause ::= { serviceReportCause 1 }
serviceDenial ServiceReportCause ::= { serviceReportCause 2 }
serviceResponse ServiceReportCause ::= { serviceReportCause 3 }
serviceFailure ServiceReportCause ::= { serviceReportCause 4 }
serviceRecovery ServiceReportCause ::= { serviceReportCause 5 }
otherReason ServiceReportCause ::= { serviceReportCause 6 }
END

--< ASN1.Version 1994 SecurityAuditTrail-ASN1Module
--  { joint-iso-ccitt ms(9) function(2) part8(8) asn1Module(2) 2 } >--
-- A.5 Abstract syntax definitions
SecurityAuditTrail-ASN1Module { joint-iso-ccitt ms(9) function(2) part8(8) asn1Module(2) 2 }
DEFINITIONS ::=
BEGIN
IMPORTS
AdditionalText, AdditionalInformation, CorrelatedNotifications, NotificationIdentifier
	FROM Attribute-ASN1Module { joint-iso-ccitt ms(9) smi(3) part2(2) asn1Module(2) 1 };
SecurityAuditInfo ::= SEQUENCE {
	serviceReportCause ServiceReportCause OPTIONAL,
	notificationIdentifier NotificationIdentifier OPTIONAL,
	correlatedNotifications [1] IMPLICIT CorrelatedNotifications OPTIONAL,
	additionalText AdditionalText OPTIONAL,
	additionalInformation [2] IMPLICIT AdditionalInformation OPTIONAL }
ServiceReportCause ::= OBJECT IDENTIFIER
END

END
--< GDMO.EndDocument "ITU-T Rec. X.740 (1992) | ISO/IEC 10164-8 : 1993"
--  { joint-iso-ccitt ms(9) function(2) part8(8) } >--
--@@ 
--@@ end of gdmos
--@@ 
--@@ 
--@@ vim: comments=\b\:\-\-,\:\-\-,\f\b\:- fo+=tcqlornw tw=120 nocin nosi
