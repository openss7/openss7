-- 15 Supporting ASN.1 productions
SDHCSASN1 {itu-t(0) recommendation(0) g(7) g774(774) hyphen(127) cs(05)
informationModel(0) asn1Module(2) sdhcs(0)}
DEFINITIONS IMPLICIT TAGS ::=
BEGIN
-- EXPORTS Everything
IMPORTS
PathTrace FROM SDH {itu-t(0) recommendation(0) g(7) sdhm(774) informationModel(0)
asn1Module(2) sdh(0)};
sdhCS OBJECT IDENTIFIER ::= {itu-t(0) recommendation(0) g(7) g774(774)
hyphen(127) cs(05) informationModel(0)}
g774-05MObjectClass OBJECT IDENTIFIER ::= {sdhCS managedObjectClass(3)}
g774-05Package OBJECT IDENTIFIER ::={sdhCS package(4)}
g774-05NameBinding OBJECT IDENTIFIER ::= {sdhCS nameBinding(6)}
g774-05Attribute OBJECT IDENTIFIER ::={sdhCS attribute(7)}
Boolean ::= BOOLEAN
defaultNull Null ::= NULL
Null ::= NULL
PathTraceRS ::= GraphicString
END
