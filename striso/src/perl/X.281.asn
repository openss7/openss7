--@@ GDMOCHECK $Revision: 0.9.2.1 $
--@@ Copyright (c), 2001-2007 OpenSS7 Corporation  <http://www.openss7.com/>
--@@ Copyright (c), 1999-2000 Brian F. G. Bidulock <bidulock@openss7.org>
--@@ 
--@@ Input File: <(standard input)>
--@@ Special File: <(standard input).specials>
--@@ Date: Sat Sep 15 07:19:20 MDT 2007
--@@ 
--< GDMO.Document "ITU-T Rec. X.281 (1999) | ISO/IEC 13642 : 1999"
--  { joint-iso-itu-t physical-layer(18) management(0) } >--
MODULE "ITU-T Rec. X.281 (1999) | ISO/IEC 13642 : 1999" { joint-iso-itu-t physical-layer(18) management(0) }
--< ASN1.Version 1994 PHLM
--  { joint-iso-itu-t physical-layer(18) management(0) asn1Module(2) 0 } >--
-- 6 ASN.1 Module
PHLM { joint-iso-itu-t physical-layer(18) management(0) asn1Module(2) 0 }
DEFINITIONS IMPLICIT TAGS ::=
BEGIN
IMPORTS
GroupObjects
	FROM Attribute-ASN1Module { joint-iso-itu-t ms(9) smi(3) part2(2) asn1Module(2) 1 }
SetInfoStatus, AttributeId, ObjectInstance
	FROM CMIP-1 { joint-iso-itu-t ms(9) cmip(1) modules(0) protocol(3) };
-- Object identifier definitions
physical-layer OBJECT IDENTIFIER ::= { joint-iso-itu-t physical-layer(18) }
phloi OBJECT IDENTIFIER ::= { physical-layer management(0) }
sseoi OBJECT IDENTIFIER ::= { phloi standardSpecificExtension(0) }
moi OBJECT IDENTIFIER ::= { phloi objectClass(3) }
poi OBJECT IDENTIFIER ::= { phloi package(4) }
proi OBJECT IDENTIFIER ::= { phloi parameter(5) }
nboi OBJECT IDENTIFIER ::= { phloi nameBinding(6) }
aoi OBJECT IDENTIFIER ::= { phloi attribute(7) }
agoi OBJECT IDENTIFIER ::= { phloi attributeGroup(8) }
acoi OBJECT IDENTIFIER ::= { phloi action(9) }
noi OBJECT IDENTIFIER ::= { phloi notification(10) }
-- Other definitions
physicalSubsystemId-Value GraphicString ::= "physicalSubsystem"
BitErrors ::= INTEGER
BitErrorsThreshold ::= SEQUENCE {
	mantissa [1] INTEGER,
	exponent [2] INTEGER }
DataCircuitType ::= ENUMERATED {
	end-system(0),
	relay-system(1) }
PhysicalEntityTitle ::= SET OF GraphicString
PhysicalInterfaceStandard ::= OCTET STRING
PhysicalInterfaceType ::= OCTET STRING
PhysicalMediaNames ::= OCTET STRING
SynchronizationMode ::= ENUMERATED {
	synchronous(0),
	asynchronous(1) }
TransmissionCoding ::= OCTET STRING
TransmissionMode ::= ENUMERATED {
	simplex(0),
	duplex(1) }
TransmissionRate ::= SEQUENCE {
	mantissa [1] INTEGER,
	exponent [2] INTEGER }
PortNumber ::= INTEGER
EndpointIdentifier ::= OCTET STRING
ConnectionError ::= OCTET STRING
ConnectionEstablished ::= OCTET STRING
BitErrorThresholdReached ::= OCTET STRING
LossOfSignal ::= OCTET STRING
LossOfSynchronization ::= OCTET STRING
END

END
--< GDMO.EndDocument "ITU-T Rec. X.281 (1999) | ISO/IEC 13642 : 1999"
--  { joint-iso-itu-t physical-layer(18) management(0) } >--
--@@ 
--@@ end of gdmos
--@@ 
--@@ 
--@@ vim: comments=\b\:\-\-,\:\-\-,\f\b\:- fo+=tcqlornw tw=120 nocin nosi
