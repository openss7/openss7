--< GDMO.Document "ITU-T Rec. X.462 (1996) | ISO/IEC 11588-3 : 1997" { joint-iso-itu-t mhs (6) management (9) } >--
MODULE "ITU-T Rec. X.462 (1996) | ISO/IEC 11588-3 : 1997" { joint-iso-itu-t mhs (6) management (9) }
--< ASN1.Version 1994 MhsAcctObjectIdentifiers { joint-iso-itu-t mhs (6) management (9) accounting (3) modules (8) object-identifiers ( 0 ) } >--
-- Annex A
-- ASN.1 definitions
-- (This annex forms an integral part of this Recommendation | International Standard)
-- A.1 ObjectIdentifiers
-- This subclause contains the ASN.1 module that defines the object identifiers referenced by the REGISTERED AS
-- statements of the GDMO templates in clauses 10 to 17.
MhsAcctObjectIdentifiers { joint-iso-itu-t
mhs (6)
management (9)
accounting (3)
modules (8)
object-identifiers ( 0 ) }
DEFINITIONS IMPLICIT TAGS ::=
BEGIN
-- Prologue
-- EXPORTS everything
IMPORTS -- nothing -- ;
ID ::= OBJECT IDENTIFIER
-- MHS management (definitive)
mhs-management ID ::= { joint-iso-itu-t mhs (6) management (9) } -- this is definitive
-- Document IDs
id-model ID ::= {mhs-management 1} -- Model And Architecture
id-information ID ::= {mhs-management 2} -- Information
id-accounting ID ::= {mhs-management 3} -- Accounting Manag. Func.
id-security ID ::= {mhs-management 4} -- Security Manag. Func.
id-configuration ID ::= {mhs-management 5} -- Configuration Manag. Func.
id-fault ID ::= {mhs-management 6} -- Fault Manag. Func.
id-performance ID ::= {mhs-management 7} -- Performance Manag. Func.
id-mta ID ::= {mhs-management 8} -- MTA Entity
id-ua ID ::= {mhs-management 9} -- UA Entity
id-ms ID ::= {mhs-management 10} -- MS Entity
id-au ID ::= {mhs-management 11} -- AU Entity
-- Template types
id-moc ID ::= {id-accounting 0} -- Managed Object Class templates
id-package ID ::= {id-accounting 1} -- Package templates
id-attribute ID ::= {id-accounting 2} -- Attribute templates
id-attribute-group ID ::= {id-accounting 3} -- Attribute Group templates
id-notification ID ::= {id-accounting 4} -- Notification templates
id-action ID ::= {id-accounting 5} -- Action templates
id-parameter ID ::= {id-accounting 6} -- Parameter templates
id-name-binding ID ::= {id-accounting 7} -- Name Binding templates
id-modules ID ::= {id-accounting 8} -- Modules  Not definitive
-- Managed Object Classes
id-moc-acctRequest ID ::= {id-moc 0}
id-moc-bindEventRecord ID ::= {id-moc 1}
id-moc-contact ID ::= {id-moc 2}
id-moc-customer ID ::= {id-moc 3}
id-moc-customerAcctLog ID ::= {id-moc 4}
id-moc-customerAcctRecord ID ::= {id-moc 5}
id-moc-customerEFD ID ::= {id-moc 6}
id-moc-discardEventRecord ID ::= {id-moc 7}
id-moc-interworkingMD ID ::= {id-moc 8}
id-moc-interworkingMD-EFD ID ::= {id-moc 9}
id-moc-maseEventRecord ID ::= {id-moc 10}
id-moc-mdseEventRecord ID ::= {id-moc 11}
id-moc-mdServiceMgtPOA ID ::= {id-moc 12}
id-moc-messageEventRecord ID ::= {id-moc 13}
id-moc-mhsEventLog ID ::= {id-moc 14}
id-moc-misManagementDomain ID ::= {id-moc 15}
id-moc-mrseEventRecord ID ::= {id-moc 16}
id-moc-msseEventRecord ID ::= {id-moc 17}
id-moc-mtseEventRecord ID ::= {id-moc 18}
id-moc-securityAcctRecord ID ::= {id-moc 19}
id-moc-serviceRequest ID ::= {id-moc 20}
id-moc-settlementAcctRecord ID ::= {id-moc 21}
id-moc-settlementAcctLog ID ::= {id-moc 22}
-- Packages
id-package-acctRequest ID ::= {id-package 0}
id-package-alert ID ::= {id-package 1}
id-package-bindEventRecord ID ::= {id-package 2}
id-package-cancelDeferredDelivery ID ::= {id-package 3}
id-package-changeCredential ID ::= {id-package 4}
id-package-commonBindArguments ID ::= {id-package 5}
id-package-commonCreationDeletion ID ::= {id-package 6}
id-package-contact ID ::= {id-package 7}
id-package-customer ID ::= {id-package 8}
id-package-customerAcctRequest ID ::= {id-package 9}
id-package-customerEFD ID ::= {id-package 10}
id-package-d36-commonAttributes ID ::= {id-package 11}
id-package-d36-deliveryViaAccessUnit ID ::= {id-package 12}
id-package-d36-directDelivery ID ::= {id-package 13}
id-package-delete ID ::= {id-package 14}
id-package-deliveryControl ID ::= {id-package 15}
id-package-destinationDomainDelivery ID ::= {id-package 16}
id-package-discardEventRecord ID ::= {id-package 17}
id-package-fetch ID ::= {id-package 18}
id-package-interworkingMD ID ::= {id-package 19}
id-package-interworkingMD-EFD ID ::= {id-package 20}
id-package-list ID ::= {id-package 21}
id-package-maseEventRecord ID ::= {id-package 22}
id-package-mdseEventRecord ID ::= {id-package 23}
id-package-mdServiceMgtPOA ID ::= {id-package 24}
id-package-messageDelivery ID ::= {id-package 25}
id-package-messageDeliveryEnvelope ID ::= {id-package 26}
id-package-messageEventRecord ID ::= {id-package 27}
id-package-messageSubmission ID ::= {id-package 28}
id-package-messageSubmissionEnvelope ID ::= {id-package 29}
id-package-messageTransfer ID ::= {id-package 30}
id-package-mrseEventRecord ID ::= {id-package 31}
id-package-msBindArguments ID ::= {id-package 32}
id-package-msseEventRecord ID ::= {id-package 33}
id-package-mtaBindArguments ID ::= {id-package 34}
id-package-mtsBindArguments ID ::= {id-package 35}
id-package-mtseEventControl ID ::= {id-package 36}
id-package-originatingDomainTransferOut ID ::= {id-package 37}
id-package-probeSubmission ID ::= {id-package 38}
id-package-probeSubmissionEnvelope ID ::= {id-package 39}
id-package-probeTransfer ID ::= {id-package 40}
id-package-processing ID ::= {id-package 41}
id-package-register ID ::= {id-package 42}
id-package-registerMS ID ::= {id-package 43}
id-package-reportDelivery ID ::= {id-package 44}
id-package-reportDeliveryEnvelope ID ::= {id-package 45}
id-package-reportTransfer ID ::= {id-package 46}
id-package-securityAcctRecord ID ::= {id-package 47}
id-package-serviceRequest ID ::= {id-package 48}
id-package-settlementAcctLog ID ::= {id-package 49}
id-package-settlementAcctRecord ID ::= {id-package 50}
id-package-settlementAcctRequest ID ::= {id-package 51}
id-package-submissionControl ID ::= {id-package 52}
id-package-summarize ID ::= {id-package 53}
id-package-trace ID ::= {id-package 54}
id-package-transitDomainTransferOut ID ::= {id-package 55}
-- Attributes
id-attribute-accessRatePerDeliveryServiceType ID ::= {id-attribute 0}
id-attribute-actualRecipientName ID ::= {id-attribute 1}
id-attribute-administrationError ID ::= {id-attribute 2}
id-attribute-alertArgument ID ::= {id-attribute 3}
id-attribute-alertResult ID ::= {id-attribute 4}
id-attribute-authenticationCheck ID ::= {id-attribute 5}
id-attribute-authenticationGeneration ID ::= {id-attribute 6}
id-attribute-bindAuthenticationCheck ID ::= {id-attribute 7}
id-attribute-bindingError ID ::= {id-attribute 8}
id-attribute-bindToken ID ::= {id-attribute 9}
id-attribute-certificate ID ::= {id-attribute 10}
id-attribute-componentRatesPerOctetsPerDeliveryServiceType ID ::= {id-attribute 11}
id-attribute-consumerOfOperation ID ::= {id-attribute 12}
id-attribute-contactCompany ID ::= {id-attribute 13}
id-attribute-contactDetails ID ::= {id-attribute 14}
id-attribute-contactFunction ID ::= {id-attribute 15}
id-attribute-contactId ID ::= {id-attribute 16}
id-attribute-contactInstance ID ::= {id-attribute 17}
id-attribute-contactName ID ::= {id-attribute 18}
id-attribute-contentConfidentialityAlgorithmIdentifier ID ::= {id-attribute 19}
id-attribute-contentIdentifier ID ::= {id-attribute 20}
id-attribute-contentIntegrityCheck ID ::= {id-attribute 21}
id-attribute-contentType ID ::= {id-attribute 22}
id-attribute-currency ID ::= {id-attribute 23}
id-attribute-customerAcctPolicy ID ::= {id-attribute 24}
id-attribute-customerId ID ::= {id-attribute 25}
id-attribute-customerName ID ::= {id-attribute 26}
id-attribute-decipherment ID ::= {id-attribute 27}
id-attribute-defaultDeliveryControls ID ::= {id-attribute 28}
id-attribute-deleteArgument ID ::= {id-attribute 29}
id-attribute-deleteResult ID ::= {id-attribute 30}
id-attribute-deliverableContentTypes ID ::= {id-attribute 31}
id-attribute-deliverableEncodedInformationTypes ID ::= {id-attribute 32}
id-attribute-deliverableMaximumContentLength ID ::= {id-attribute 33}
id-attribute-deliveryComponentRateToPrmd ID ::= {id-attribute 34}
id-attribute-deliveryComponentRateToUa ID ::= {id-attribute 35}
id-attribute-deliveryControls ID ::= {id-attribute 36}
id-attribute-deliveryError ID ::= {id-attribute 37}
id-attribute-deliveryServiceTypes ID ::= {id-attribute 38}
id-attribute-destinationAdmd ID ::= {id-attribute 39}
id-attribute-destinationDomainDeliveryList ID ::= {id-attribute 40}
id-attribute-electronicMailAddress ID ::= {id-attribute 41}
id-attribute-encipherment ID ::= {id-attribute 42}
id-attribute-encodedInformationTypes ID ::= {id-attribute 43}
id-attribute-entryExitMtaNames ID ::= {id-attribute 44}
id-attribute-envelopeType ID ::= {id-attribute 45}
id-attribute-faxTelephoneNumberList ID ::= {id-attribute 46}
id-attribute-fetchArgument ID ::= {id-attribute 47}
id-attribute-fetchResult ID ::= {id-attribute 48}
id-attribute-globalDomainId ID ::= {id-attribute 49}
id-attribute-initiatorCredentials ID ::= {id-attribute 50}
id-attribute-initiatorName ID ::= {id-attribute 51}
id-attribute-internalTrace ID ::= {id-attribute 52}
id-attribute-interworkingMDId ID ::= {id-attribute 53}
id-attribute-interworkingMDName ID ::= {id-attribute 54}
id-attribute-labelsAndRedirections ID ::= {id-attribute 55}
id-attribute-limitValidityDate ID ::= {id-attribute 56}
id-attribute-listArgument ID ::= {id-attribute 57}
id-attribute-listResult ID ::= {id-attribute 58}
id-attribute-logStartTime ID ::= {id-attribute 59}
id-attribute-logStopTime ID ::= {id-attribute 60}
id-attribute-messageContentSize ID ::= {id-attribute 61}
id-attribute-messageDeliveryEnvelope ID ::= {id-attribute 62}
id-attribute-MTSIdentifier ID ::= {id-attribute 63}
id-attribute-messageOriginAuthenticationCheck ID ::= {id-attribute 64}
id-attribute-messageSecurityLabel ID ::= {id-attribute 65}
id-attribute-messageSize ID ::= {id-attribute 66}
id-attribute-messageSubmissionEnvelope ID ::= {id-attribute 67}
id-attribute-submissionTime ID ::= {id-attribute 68}
id-attribute-messageToken ID ::= {id-attribute 69}
id-attribute-messageTransferEnvelope ID ::= {id-attribute 70}
id-attribute-msBindAuthenticationCheck ID ::= {id-attribute 71}
id-attribute-newCredentials ID ::= {id-attribute 72}
id-attribute-numberOfAddressedPrmds ID ::= {id-attribute 73}
id-attribute-numberOfAddressedUas ID ::= {id-attribute 74}
id-attribute-numberOfMessagesPerDeliveryServiceType ID ::= {id-attribute 75}
id-attribute-oldCredentials ID ::= {id-attribute 76}
id-attribute-operationStatus ID ::= {id-attribute 77}
id-attribute-operationTime ID ::= {id-attribute 78}
id-attribute-originalMtaCertification ID ::= {id-attribute 79}
id-attribute-originatingDomainTransferOutList ID ::= {id-attribute 80}
id-attribute-originatingAdmd ID ::= {id-attribute 81}
id-attribute-originatingMTACertificate ID ::= {id-attribute 82}
id-attribute-originatorCertificate ID ::= {id-attribute 83}
id-attribute-originatorName ID ::= {id-attribute 84}
id-attribute-permissibleSecurityContext ID ::= {id-attribute 85}
id-attribute-priority ID ::= {id-attribute 86}
id-attribute-probeOriginAuthenticationCheck ID ::= {id-attribute 87}
id-attribute-probeSubmissionEnvelope ID ::= {id-attribute 88}
id-attribute-probeTransferEnvelope ID ::= {id-attribute 89}
id-attribute-processingComponentRate ID ::= {id-attribute 90}
id-attribute-processingDetails ID ::= {id-attribute 91}
id-attribute-processingErrorFlag ID ::= {id-attribute 92}
id-attribute-processingSummary ID ::= {id-attribute 93}
id-attribute-proofOfDelivery ID ::= {id-attribute 94}
id-attribute-proofOfDeliveryRequest ID ::= {id-attribute 95}
id-attribute-proofOfSubmission ID ::= {id-attribute 96}
id-attribute-proofOfSubmissionRequest ID ::= {id-attribute 97}
id-attribute-recipientCertificate ID ::= {id-attribute 98}
id-attribute-recipientOnResponsibilityList ID ::= {id-attribute 99}
id-attribute-registerMSArgument ID ::= {id-attribute 100}
id-attribute-registerMSResult ID ::= {id-attribute 101}
id-attribute-reportDeliveryEnvelope ID ::= {id-attribute 102}
id-attribute-reportIdentifier ID ::= {id-attribute 103}
id-attribute-reportingMtaCertificate ID ::= {id-attribute 104}
id-attribute-reportOriginAuthenticationCheck ID ::= {id-attribute 105}
id-attribute-reportTransferEnvelope ID ::= {id-attribute 106}
id-attribute-responderCredentials ID ::= {id-attribute 107}
id-attribute-responderName ID ::= {id-attribute 108}
id-attribute-retrievalError ID ::= {id-attribute 109}
id-attribute-securityContext ID ::= {id-attribute 110}
id-attribute-securityError ID ::= {id-attribute 111}
id-attribute-securityProblem ID ::= {id-attribute 112}
id-attribute-serviceAccessCharge ID ::= {id-attribute 113}
id-attribute-serviceFlag ID ::= {id-attribute 114}
id-attribute-serviceRequestId ID ::= {id-attribute 115}
id-attribute-settlementPolicy ID ::= {id-attribute 116}
id-attribute-signatureCheck ID ::= {id-attribute 117}
id-attribute-signatureGeneration ID ::= {id-attribute 118}
id-attribute-startUpDate ID ::= {id-attribute 119}
id-attribute-status ID ::= {id-attribute 120}
id-attribute-subjectIdentifier ID ::= {id-attribute 121}
id-attribute-subjectSubmissionIdentifier ID ::= {id-attribute 122}
id-attribute-submissionControls ID ::= {id-attribute 123}
id-attribute-submissionError ID ::= {id-attribute 124}
id-attribute-summarizeArgument ID ::= {id-attribute 125}
id-attribute-summarizeResult ID ::= {id-attribute 126}
id-attribute-supplierOfOperation ID ::= {id-attribute 127}
id-attribute-telephoneNumberList ID ::= {id-attribute 128}
id-attribute-thisRecipientName ID ::= {id-attribute 129}
id-attribute-totalNumberOfORAddresses ID ::= {id-attribute 130}
id-attribute-trace ID ::= {id-attribute 131}
id-attribute-transitDomainTransferOutList ID ::= {id-attribute 132}
id-attribute-userAddress ID ::= {id-attribute 133}
id-attribute-userName ID ::= {id-attribute 134}
id-attribute-userSecurityLabel ID ::= {id-attribute 135}
-- Attribute Groups
-- none are defined
-- Notifications
id-notification-objectCreation ID ::= {id-notification 0}
id-notification-objectDeletion ID ::= {id-notification 1}
-- Actions
-- none are defined
-- Parameters
id-parameter-attributeError ID ::= {id-parameter 0}
id-parameter-autoActionRequestError ID ::= {id-parameter 1}
id-parameter-deleteError ID ::= {id-parameter 2}
id-parameter-fetchRestrictionError ID ::= {id-parameter 3}
id-parameter-improperlySpecifiedRecipients ID ::= {id-parameter 4}
id-parameter-rangeError ID ::= {id-parameter 5}
id-parameter-securityError ID ::= {id-parameter 6}
id-parameter-sequenceNumberError ID ::= {id-parameter 7}
id-parameter-serviceError ID ::= {id-parameter 8}
-- Name Bindings
id-name-binding-acctRequest-customer ID ::= {id-name-binding 0}
id-name-binding-acctRequest-interworkingMD ID ::= {id-name-binding 1}
id-name-binding-contact-customer ID ::= {id-name-binding 2}
id-name-binding-contact-interworkingMD ID ::= {id-name-binding 3}
id-name-binding-customer-mdServiceManagementPointOfAccess ID ::= {id-name-binding 4}
id-name-binding-customerAcctLog-customer ID ::= {id-name-binding 5}
id-name-binding-customerEFD-customer ID ::= {id-name-binding 6}
id-name-binding-interworkingMD-EFD-interworkingMD ID ::= {id-name-binding 7}
id-name-binding-interworkingMD-mdServiceManagementPointOfAccess ID ::= {id-name-binding 8}
id-name-binding-mdServiceManagementPointOfAccess-misManagementDomain ID ::= {id-name-binding 9}
id-name-binding-settlementAcctLog-interworkingMD ID ::= {id-name-binding 10}
END
--< ASN1.Version 1994 MhsAcctAsn1Module { joint-iso-itu-t mhs (6) management (9) accounting (3) modules (8) asn1-module ( 1 ) } >--
-- A.2 ASN.1 notations
-- This clause contains the ASN.1 module that defines the attribute syntaxes referenced by the attributes in clause
-- Attributes.
MhsAcctAsn1Module { joint-iso-itu-t
mhs (6)
management (9)
accounting (3)
modules (8)
asn1-module ( 1 ) }
DEFINITIONS IMPLICIT TAGS ::=
BEGIN
-- Prologue
-- EXPORTS everything
IMPORTS
-- MTS abstract service parameters
AdministrationDomainName,
ActualRecipientName,
BindTokenEncryptedData,
BindTokenSignedData,
ContentConfidentialityAlgorithmIdentifier,
ContentIdentifier,
ContentIntegrityCheck,
ContentLength,
ContentType,
Credentials,
DefaultDeliveryControls,
DeferredDeliveryTime,
DeliveryControls,
EncodedInformationTypes,
ExplicitConversion,
GlobalDomainIdentifier,
InitiatorCredentials,
LabelAndRedirection,
MessageDeliveryEnvelope,
MessageOriginAuthenticationCheck,
MessageSecurityLabel,
MessageSubmissionEnvelope,
MessageToken,
MTAName,
MTSIdentifier,
NonDeliveryReasonCode,
NonDeliveryDiagnosticCode,
ObjectName,
ORAddressAndOptionalDirectoryName,
ORName,
OriginatingMTACertificate.
OriginatorCertificate,
OriginatorName,
Priority,
ProbeOriginAuthenticationCheck,
ProbeSubmissionEnvelope,
ProofOfDelivery,
ProofOfDeliveryRequest,
ProofOfSubmission,
ProofOfSubmissionRequest,
RecipientCertificate,
RedirectionReason,
ReportDeliveryEnvelope,
ReportingMTACertificate,
ReportOriginAuthenticationCheck,
ResponderCredentials,
SecurityContext,
SecurityProblem,
SubjectSubmissionIdentifier,
SubmissionControls,
Time,
ThisRecipientName,
UserAddress,
UserName,
FROM MTSAbstractService { joint-iso-ccitt mhs-motis (6) mts (3) modules (0) mts-abstract-service (0) version-1994 (0) }
-- MTA abstract service parameters
InternalTraceInformation,
MTSIdentifier,
MessageTransferEnvelope,
ProbeTransferEnvelope,
ReportIdentifier,
ReportTransferEnvelope,
SubjectIdentifier,
TraceInformation
FROM MTAAbstractService { joint-iso-ccitt mhs-motis (6) mts (3) modules (0) mta-abstract-service (2) version-1994 (0) }
-- MS abstract service
AlertArgument,
AlertResult,
AttributeProblem,
AttributeType,
AutoActionRequestProblem,
AutoActionType,
DeleteArgument,
DeleteProblem,
DeleteResult,
FetchArgument,
FetchRestrictionProblem,
FetchResult,
ListArgument,
ListResult,
MS-EITs,
RangeProblem,
Register-MSArgument,
Register-MSResult,
Restrictions,
SequenceNumber,
SequenceNumberProblem,
ServiceProblem,
SummarizeArgument,
SummarizeResult
FROM MSAbstractService { joint-iso-ccitt mhs-motis (6) mts (3) modules (0) abstract-service (1) version-1994 (0) }
-- MTS upper bounds
ub-content-types,
ub-labels-and-redirections,
ub-recipients
FROM MTSUpperBounds {joint-iso-ccitt mhs-motis (6) mts (3) modules (0) upper-bounds (3) version-1994 (0) }
-- MS upper bounds
ub-attributes-supported,
ub-auto-actions,
ub-auto-registrations,
ub-default-registrations,
ub-messages,
ub-per-entry
FROM MSUpperBounds {joint-iso-ccitt mhs-motis (6) mts (3) modules (0) upper-bounds (3) }
EventTypeId,
ObjectInstance
FROM CMIP-1 {joint-iso-ccitt ms (9) cmip (1) modules (0) protocol (3) }
-- X.721 DMI
SimpleNameType
FROM Attribute-ASN1Module {joint-iso-ccitt ms (9) smi (3) part2 (2) asn1Module (2) 1};
-- In the context of MHS management, the following values are defined for the EventTypeId data type.
affirmation EventTypeId ::= localForm : 1
alert EventTypeId ::= localForm : 2
cancel-deferred-delivery EventTypeId ::= localForm : 3
change-credentials EventTypeId ::= localForm : 4
delete EventTypeId ::= localForm : 5
delivery-control EventTypeId ::= localForm : 6
fetch EventTypeId ::= localForm : 7
list EventTypeId ::= localForm : 8
message-delivery EventTypeId ::= localForm : 9
message-indirect-submission EventTypeId ::= localForm : 10
message-submission EventTypeId ::= localForm : 11
message-transfer-in EventTypeId ::= localForm : 12
message-transfer-out EventTypeId ::= localForm : 13
ms-bind EventTypeId ::= localForm : 14
ms-unbind EventTypeId ::= localForm : 15
mta-bind EventTypeId ::= localForm : 16
mta-unbind EventTypeId ::= localForm : 17
mts-bind EventTypeId ::= localForm : 18
mts-unbind EventTypeId ::= localForm : 19
non-affirmation EventTypeId ::= localForm : 20
non-delivery EventTypeId ::= localForm : 21
probe-indirect-submission EventTypeId ::= localForm : 22
probe-submission EventTypeId ::= localForm : 23
probe-transfer-in EventTypeId ::= localForm : 24
probe-transfer-out EventTypeId ::= localForm : 25
register EventTypeId ::= localForm : 26
register-ms EventTypeId ::= localForm : 27
report-delivery EventTypeId ::= localForm : 28
report-transfer-in EventTypeId ::= localForm : 29
report-transfer-out EventTypeId ::= localForm : 30
submission-control EventTypeId ::= localForm : 31
summarize EventTypeId ::= localForm : 32
AdministrationPortOperations ::= EventTypeId (
change-credentials |
register )
BindingOperations ::= EventTypeId (
ms-bind |
ms-unbind |
mta-bind |
mta-unbind |
mts-bind |
mts-unbind )
DeliveryPortOperations ::= EventTypeId (
delivery-control |
message-delivery |
report-delivery )
DiscardOperations ::= EventTypeId (
affirmation |
non-affirmation |
non-delivery )
RetrievalPortOperations ::= EventTypeId (
alert |
delete |
fetch |
list |
register-ms |
summarize )
SubmissionPortOperations ::= EventTypeId (
message-submission |
probe-submission |
cancel-deferred-delivery |
submission-control )
TransferPortOperations ::= EventTypeId (
message-transfer-in |
message-transfer-out |
probe-transfer-in |
probe-transfer-out |
report-transfer-in |
report-transfer-out )
OperationStatus ::= INTEGER {
in-progress (0),
ok (1),
error (2) }
ServiceFlag ::= BOOLEAN
-- Contact attributes
ContactId ::= SimpleNameType
ContactName ::= UniversalString
ContactCompany ::= UniversalString
ContactFunction ::= UniversalString
ContactDetails ::= UniversalString
ElectronicMailAddress ::= ORAddressAndOptionalDirectoryName
TelephoneNumberList ::= SET OF TelephoneNumber
TelephoneNumber ::= UniversalString
-- Customer attributes
CustomerId ::= SimpleNameType
CustomerName ::= UniversalString
-- InterworkingMD attributes
InterworkingMDId ::= SimpleNameType
InterworkingMDName ::= UniversalString
-- Service request attributes
ServiceRequestId ::= SimpleNameType
Status ::= INTEGER {
indirect-mIS-user-agreement-on-the-request (0),
MIS-provider-agreement-on-the-request (1),
request-in-progress (2),
request-processed (3) }
LimitValidityDate ::= Time
StartUpDate ::= Time
-- Accounting policies
CustomerAcctPolicy ::= CHOICE {
globalForm OBJECT IDENTIFIER,
localForm INTEGER}
SettlementPolicy ::= CHOICE {
globalForm OBJECT IDENTIFIER,
localForm INTEGER}
-- In the context of MHS management, the following values are defined for the
-- SettlementPolicy data type.
d36 SettlementPolicy ::= localForm : 0
-- In the following descriptions, a number of redefinition of material defined in other
-- modules occurs. This was made inevitable for either one of two reasons:
-- Reason 1: There is no specific type to be imported for the concerned attribute.
-- This often occurs when parameters are of the format "SET SIZE (...) OF ...".
-- In those cases, the corresponding description has been copied textually in
-- module, with a specific mention of its origin. Though this introduces maintenance
-- difficulties, no better solution has been found.
-- Reason 2: The corresponding type is unavailable. For instance, the various
-- operation errors already have assigned numbers, but the module in which this
-- is done (MTSAccessProtocol { joint-iso-ccitt mhs-motis (6) protocols (0) modules (0)
-- mts-access-protocol (1) } in ITU-T Rec. X.419 | ISO/IEC 10021-6) does not export
-- them, so they are not available for use in this module. Correspondingly, there
-- are no single "error" type to import from ITU-T Rec. X.411 | ISO/IEC 10021-4 not
-- ITU-T Rec. X.413 | ISO/IEC 10021-5, this is why they were reproduced here.
-- Though this introduces maintenance difficulties, no better solution has been found.
-- Binding Types
BindingError ::= CHOICE {
[0] INTEGER {
busy (0),
authentication-error (2),
unacceptable-dialogue-mode (3),
unacceptable-security-context (4)},
[1] MSBindError }
-- Submission Port Types
SubmissionError ::= INTEGER {
submission-control-violated (1),
element-of-service-not-subscribed (2),
deferred-delivery-cancellation-rejected (3),
originator-invalid (4),
recipient-improperly-specified (5), -- has parameters
message-submission-identifier-invalid (6),
inconsistent-request (7),
security-error (8), -- has parameters
unsupported-critical-function (9),
remote-bind-error (10) }
CancelDeferredDeliverySubmissionErrors ::= SubmissionError (
deferred-delivery-cancellation-rejected |
message-submission-identifier-invalid |
remote-bind-error )
MessageSubmissionErrors ::= SubmissionError (
submission-control-violated |
element-of-service-not-subscribed |
originator-invalid |
recipient-improperly-specified |
inconsistent-request |
security-error |
unsupported-critical-function |
remote-bind-error )
ProbeSubmissionErrors ::= SubmissionError (
submission-control-violated |
element-of-service-not-subscribed |
originator-invalid |
recipient-improperly-specified |
inconsistent-request |
security-error |
unsupported-critical-function |
remote-bind-error )
SubmissionControlErrors ::= SubmissionError (
security-error |
remote-bind-error )
-- definition copied from [ITU-T Rec. X.411 | ISO/IEC 10021-4] Figure 2 --
ImproperlySpecifiedRecipients ::= SEQUENCE SIZE (1..ub-recipients) OF ORAddressAndOptionalDirectoryName
-- Delivery Port Types
DeliveryError ::= INTEGER {
delivery-control-violation (1),
control-violates-registration (2),
security-error (3), -- has parameters
unsupported-critical-function (4) }
MessageDeliveryErrors ::= DeliveryError (
delivery-control-violation |
security-error |
unsupported-critical-function )
ReportDeliveryErrors ::= MessageDeliveryErrors
DeliveryControlErrors ::= DeliveryError (
control-violates-registration |
security-error )
-- Retrieval Port Types
RetrievalError ::= INTEGER {
-- Most of these have parameters
attribute-error (1),
auto-action-request-error (2),
delete-error (3),
fetch-restriction-error (4),
invalid-parameter-error (5),
range-error (6),
security-error (7),
sequence-number-error (8),
service-error (9) }
SummarizeErrors ::= RetrievalError (
attribute-error |
invalid-parameter-error |
range-error |
security-error |
sequence-number-error |
service-error )
ListErrors ::= SummarizeErrors
FetchErrors ::= RetrievalError (
INCLUDES SummarizeErrors |
fetch-restriction-error )
DeleteErrors ::= RetrievalError (
delete-error |
invalid-parameter-error |
range-error |
security-error |
sequence-number-error |
service-error )
RegisterMSErrors ::= RetrievalError (
attribute-error |
auto-action-request-error |
invalid-parameter-error |
security-error |
service-error )
AlertErrors ::= RetrievalError ( security-error )
-- definitions copied from [ITU-T Rec. X.413 | ISO/IEC 10021-5] Annex B --
AttributeError ::= SET {
problems [0] SET SIZE (1..ub-per-entry) OF SET {
problem [0] AttributeProblem,
type [1] AttributeType,
value [3] { . . . } }
AutoActionRequestError ::= SET {
problems [0] SET SIZE (1..ub-auto-registrations) OF SET {
problem [0] AutoActionRequestProblem,
type [1] AutoActionType}}
DeleteError ::= SET {
problems [0] SET SIZE (1..ub-messages) OF SET {
problem [0] DeleteProblem,
sequence-number [1] SequenceNumber}}
FetchRestrictionError ::= SET {
problems [0] SET SIZE (1..ub-default-registrations) OF SET {
problem [3] FetchRestrictionProblem,
restriction CHOICE {
content-type [0] ContentType,
eit [1] MS-EITs,
content-length [2] ContentLength}}}
RangeError ::= SET {
problem [0] RangeProblem}
SequenceNumberError ::= SET {
problems [1] SET SIZE (1..ub-messages) OF SET {
problem [0] SequenceNumberProblem,
sequence-number [1] SequenceNumber}}
ServiceError ::= SET {
problem [0] ServiceProblem}
-- Administration Port Types
AdministrationError ::= INTEGER {
register-rejected (1),
new-credentials-unacceptable (2),
old-credentials-incorrectly-specified (3),
remote-bind-error (10) }
RegisterErrors ::= AdministrationErrors (
register-rejected |
remote-bind-error )
ChangeCredentialsErrors ::= AdministrationError (
new-credentials-unacceptable |
old-credentials-incorrectly-specified |
remote-bind-error )
-- two definitions copied from [ITU-T Rec. X.411 | ISO/IEC 10021-4] Figure 2 --
DeliverableContentTypes ::= SET SIZE (1 .. ub-content-types) OF ContentType
LabelsAndRedirections ::= SET SIZE (1 .. ub-labels-and-redirections) OF LabelAndRedirection
-- Security-related types
AuthenticationCheck ::= INTEGER {
validated (1),
failed (2) }
BindAuthenticationCheck ::= AuthenticationCheck
AuthenticationGeneration ::= INTEGER {
generated (1),
non-generated (2) }
Decipherment ::= INTEGER {
success (1),
failure (2) }
SignatureCheck ::= INTEGER {
valid (1),
failed (2) }
SignatureGeneration ::= INTEGER {
generated (1),
non-generated (2) }
-- Information contained in the notifications
CommonCreationAndDeletionInfo ::= INTEGER {
unknown (0),
ressourceOperation(1),
managementOperation(2) }
-- These are types for the processing history-related attributes
ProcessingErrorFlag ::= BOOLEAN
ProcessingSummary ::= BIT STRING {
idle (0),
processed (1),
rejected (2),
name-resolution (3),
dl-expansion (4),
redirection (5),
deferred-delivery (6),
conversion (7),
securityContextCheck (8)}
-- at most one of idle, processed, and rejected bits shall be one:
-- idle bit nonef means the MPR is waiting to be processed;
-- processed bit  onen means the MPR was successfully processed;
-- rejected bit  onee means that the MTS was not able to deliver the message
-- or the report or affirm the probe.
-- idle, processed, and rejected bits zero means the MPR is
-- currently under process.
-- A rname-resolutiono, sredirection, deferred-delivery,
-- Aconversiono or osecurityContextCheckf bit one means the corresponding
-- function was performed on the MPR.
-- if idle bit is set to  onet (MPR idle), dl-expansion, redirection,
-- deferred-delivery and conversion bits shall be set to rzeroe.
ProcessingDetails ::= SEQUENCE OF ProcessingDetail
ProcessingDetail ::= CHOICE {
name-resolution [3] NameResolutionProcessingInfo,
dl-expansion [4] DLExpansionProcessingInfo,
redirection [5] RedirectionProcessingInfo,
deferred-delivery [6] DeferralOfDeliveryProcessingInfo,
conversion [7] ConversionProcessingInfo,
securityContextCheck [8] SecurityProcessingInfo }
-- These come from X.411: MTS Abstract Service
ProcessingError ::= SET {
non-delivery-reason [0] NonDeliveryReasonCode OPTIONAL,
non-delivery-diagnostics [1] NonDeliveryDiagnosticCode OPTIONAL,
supplementary-info [2] SupplementaryError }
SupplementaryError ::= UniversalString
ConversionProcessingInfo ::= SET OF EMailFromToEIT
EMailFromToEIT ::= CHOICE {
explicitConversion [0] ExplicitConversion,
genericConversion [1] GenericConversion }
GenericConversion ::= OBJECT IDENTIFIER
DLExpansionProcessingInfo ::= SEQUENCE {
dlORName ORAddressAndOptionalDirectoryName,
actions Actions }
Actions ::= BIT STRING {
owner-report (0),
originator-on-previous-dl (1),
secure-dl-operation (2) }
RedirectionProcessingInfo ::= SET {
redirection-reason [0] RedirectionReason,
original [1] ORName OPTIONAL,
redirected-to [2] ORName OPTIONAL }
DeferralOfDeliveryProcessingInfo ::= DeferredDeliveryTime
-- Imported from X.411
SecurityProcessingInfo ::= SET {
action [0] SecurityAction,
security-policy [1] OBJECT IDENTIFIER OPTIONAL }
SecurityAction ::= BIT STRING {
unspecified (0),
origin-authentication (1),
security-label-check (2) }
NameResolutionProcessingInfo ::= DirectoryNameAndOptionalORAddress
DirectoryNameAndOptionalORAddress ::= ORName
DeliveryServiceType ::= INTEGER {
mhs-delivery (0),
physical-delivery (1),
telex-delivery (2),
teletex-delivery (3),
g3-facsimile-delivery (4),
g4-facsimile-delivery (5),
videotex-delivery (6),
telephone-delivery (7),
other-delivery (8) }
MessageContentSize ::= INTEGER
RecipientsOnResponsibilityList ::= RecipientName
RecipientName ::= SET OF ORAddressAndOptionalDirectoryName
BindToken ::= CHOICE {
signed [0] BindTokenSignedData,
encrypted [1] BindTokenEncryptedData}
Encipherment ::= INTEGER {
encrypted (1),
clear (2) }
MsBindAuthenticationCheck ::= AuthenticationCheck
OperationTime ::= Time
PermissibleSecurityContext ::= SET OF SecurityContext
-- related to ITU-T Rec. D.36
AccessRatePerDeliveryServiceType ::= SET OF REAL
ComponentRatesPerOctetsPerDeliveryServiceType ::= SET OF REAL
Currency ::= PrintableString
DeliveryComponentRateToPrmd ::= REAL
DeliveryComponentRateToUa ::= REAL
DestinationADMD ::= AdministrationDomainName
MessageSize ::= INTEGER
NumberOfAddressedPRMDs ::= INTEGER
NumberOfAddressedUas ::= INTEGER
NumberOfMessagesPerDeliveryServiceType ::= SET OF INTEGER
OriginatingADMD ::= AdministrationDomainName
ProcessingComponentRate ::= REAL
TotalNumberOfORAddresses ::= INTEGER
ConversionStatistics ::= SEQUENCE {
oldEit EncodedInformationTypes,
newEit EncodedInformationTypes}
DestinationDomainDeliveryList ::= SET OF DeliveredRecipientField
DeliveredRecipientField ::= SET {
recipient-name  ORAddressAndOptionalDirectoryName,
message-delivery-time  Time,
delivery-service  [1] DeliveryService OPTIONAL,
-- absence means no delivery cost incurred
conversion-statistics  [2] ConversionStatistics OPTIONAL, -- absence means no conversion cost incurred --
edirector-name  [5] ORAddressAndOptionalDirectoryName OPTIONAL }
DeliveryService ::= SET {
delivery-service-type DeliveryServiceType,
per-message-component-rate [1] PerMessageComponentRate OPTIONAL,
per-octet-component-rate [2] PerOctetComponentRate OPTIONAL }
PerMessageComponentRate ::= INTEGER
PerOctetComponentRate ::= INTEGER
OriginatingDomainTransferOutList ::= SET OF TransferRecipientField
ServiceAccessCharge ::= INTEGER
TransitDomainTransferOutList ::= SET OF TransferRecipientField
TransferRecipientField ::= MtaName
EntryExitMTANames ::= SEQUENCE OF MTAName
EnvelopeType ::= INTEGER {
message-delivery-envelope (0),
message-submission-envelope (1),
message-transfer-envelope (2),
probe-submission-envelope (3),
probe-transfer-envelope (4),
report-delivery-envelope (5),
report-transfer-envelope (6)}
InternalTrace ::= InternalTraceInformation
Trace ::= TraceInformation
END
END
--< GDMO.EndDocument "ITU-T Rec. X.462 (1996) | ISO/IEC 11588-3 : 1997" { joint-iso-itu-t mhs (6) management (9) } >--
