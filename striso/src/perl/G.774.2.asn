--15 Supporting ASN.1 productions
SDHConfASN1 {itu-t(0) recommendation(0) g(7) g774(774) hyphen(127) conf(02)
informationModel(0)
asn1Module(2) sdhconf (0)}
DEFINITIONS IMPLICIT TAGS ::=
BEGIN
-- EXPORTS everything --
sdhConf OBJECT IDENTIFIER ::= { itu-t(0) recommendation(0) g(7) g774(774)
hyphen(127) conf(02)
informationModel(0) }
g774-02MObjectClass OBJECT IDENTIFIER ::= { sdhConf managedObjectClass(3) }
g774-02Action OBJECT IDENTIFIER ::= { sdhConf action(9) }
g774-02NameBinding OBJECT IDENTIFIER ::= { sdhConf nameBinding(6) }
g774-02Parameter OBJECT IDENTIFIER ::= { sdhConf parameter(5) }
ClientType ::= ENUMERATED {
-- For more information refer to ITU-T G.803 and G.707. --
noClient (0),
c139264AsynchronousMappingClientType (1),
c44736AsynchronousMappingClientType (2),
c34AsynchronousMappingClientType (3),
c6312AsynchronousMappingClientType (4),
c6312BitSynchronousMappingClientType (5),
c6312ByteSynchronousMappingClientType (6),
c2048AsynchronousMappingClientType (7),
c2048BitSynchronousMappingClientType (8),
c2048ByteSynchronousMappingClientType (9),
c1544AsynchronousMappingClientType (10),
c1544BitSynchronousMappingClientType (11),
c1544ByteSynchronousMappingClientType (12),
aTMClientType (13),
fDDIClientType (14),
mANClientType (15)
}
-- NOTE  The identification of the different type of adaptation functions
-- for a single type of characteristic information is for further study.--
ConnectionInfo ::= ENUMERATED {
crossConnectable (1),
notCrossConnectable (2),
unknown (3)
}
AUGStructureInfo ::= CHOICE {
oneAU4 [0] ConnectionInfo,
threeAU3 [1] SEQUENCE SIZE (1..3) OF ConnectionInfo
}
DefineClientTypeInfo ::= ClientType
DefineSDHStructureError ::= ENUMERATED {
structureNotSupported (0),
tpNotCrossConnectable (1),
tpAlreadyCrossConnected (2),
unknown (3)
}
TUG3StructureInfo ::= CHOICE {
oneTU3 [0] ConnectionInfo,
sevenTUG2 [1] SEQUENCE SIZE (1..7) OF TUG2StructureInfo
} -- ordered according to the time sequence --
TUG2StructureInfo ::= CHOICE {
oneTU2 [0] ConnectionInfo,
threeTU12 [1] SEQUENCE SIZE (1..3) OF ConnectionInfo,
fourTU11 [2] SEQUENCE SIZE (1..4) OF ConnectionInfo
} -- ordered according to the time sequence --
VC4StructureInfo ::= CHOICE {
notSubmultiplexed [0] ClientType,
threeTUG3 [1] SEQUENCE SIZE (1..3) OF TUG3StructureInfo
} -- ordered according to the time sequence --
VC3StructureInfo ::= CHOICE {
notSubmultiplexed [0] ClientType,
sevenTUG2 [1] SEQUENCE SIZE (1..7) OF TUG2StructureInfo
} -- In case of mapping the VC3 into a VC4 only the notSubmultiplexed
choice is permitted. --
END -- end of supporting asn.1 productions --
