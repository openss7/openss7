-- vim: ft=mib comments=\f\:\",\b\:\-\-,\:\-\-,\f\b\:- fo+=tcqlornw tw=72 nocin nosi sts=4 sw=4
-- =============================================================================
-- 
-- @(#) $RCSfile: OPENSS7-X25-LLC-MIB.mib,v $ $Name:  $($Revision: 0.9.2.4 $) $Date: 2008-04-29 00:02:04 $
--
-- -----------------------------------------------------------------------------
--
-- Copyright (c) 2001-2008  OpenSS7 Corporation <http://www.openss7.com/>
-- Copyright (c) 1997-2000  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2008-04-29 00:02:04 $ by $Author: brian $
--
-- -----------------------------------------------------------------------------
--
-- $Log: OPENSS7-X25-LLC-MIB.mib,v $
-- Revision 0.9.2.4  2008-04-29 00:02:04  brian
-- - updated headers for release
--
-- Revision 0.9.2.3  2008/01/15 10:41:42  brian
-- - updated and corrected mibs with smilint
--
-- Revision 0.9.2.2  2007/12/29 22:58:27  brian
-- - updated mibs
--
-- Revision 0.9.2.1  2007/12/15 20:16:53  brian
-- - added new mib files
--
-- =============================================================================

OPENSS7-X25-LLC-MIB DEFINITIONS ::= BEGIN

IMPORTS
    InterfaceIndex
        FROM IF-MIB
    openss7Modules
        FROM OPENSS7-SMI
    AdministrativeState, AlarmStatus, OperationalState, ProceduralStatus, 
    SimpleNameType, UsageState, tmnObjectInstance
        FROM OPENSS7-SMI-MIB
    MODULE-COMPLIANCE, NOTIFICATION-GROUP, OBJECT-GROUP
        FROM SNMPv2-CONF
    Counter32, Gauge32, Integer32, MODULE-IDENTITY, NOTIFICATION-TYPE, 
    OBJECT-TYPE, Unsigned32
        FROM SNMPv2-SMI
    DisplayString, MacAddress, RowPointer, RowStatus, TEXTUAL-CONVENTION, 
    TimeInterval, TimeStamp, TruthValue
        FROM SNMPv2-TC
    Float
        FROM UCD-SNMP-MIB;

x25-LLC-MIB MODULE-IDENTITY
    LAST-UPDATED "200711240129Z"
    ORGANIZATION 
        "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         mailto:bidulock@openss7.org"
    DESCRIPTION 
        "This MIB provides configuration and status information for an 
         X.25 LLC1/LLC2 subsystem."
    REVISION    "200711240129Z"
    DESCRIPTION 
        "First release of this module."
    ::= { openss7Modules 2 }


LLCServices ::= TEXTUAL-CONVENTION
    STATUS      current
    DESCRIPTION 
        "This textual convention represents the LLC services the are 
         available or selected.  Per ISO/IEC 8802-2, the services are 
         type1(0), type2(1), type3Initiate(2), type3ReceiveData(3) and 
         type3ReturnData(4)."
    REFERENCE   
        "IEEE 802.2 | ISO/IEC 8802-2 ASN.1, LLCServices."
    SYNTAX      BITS { type1(0), type2(1), type3Initiate(2), 
                    type3ReceiveData(3), type3ReturnData(4) }

LLCStationStatus ::= TEXTUAL-CONVENTION
    STATUS      current
    DESCRIPTION 
        "This textual convetion represents the status of an LLC station.  
         Per ISO/IEC 8802-2, the status can be up(0), down(1), or other 
         (2)."
    REFERENCE   
        "IEEE 802.2 | ISO/IEC 8802-2 ASN.1, Status."
    SYNTAX      INTEGER { up(0), down(1), other(2) }

STRIndicator ::= TEXTUAL-CONVENTION
    STATUS      current
    DESCRIPTION 
        "This textual convention indicates the type of source routed MAC 
         bridging per ISO/IEC 8802-2 (IEEE 802.2), the types are nsr(0) 
         or ste(1)."
    SYNTAX      BITS { nsr(0), ste(1) }

DLSAPAddress ::= TEXTUAL-CONVENTION
    STATUS      current
    DESCRIPTION 
        "This texutal convention represents a fully qualified DLSAP 
         which consistes of a 6 or 8 octet MacAddress (as described for 
         the MacAddress texutal convention) followed by a one octet 
         DSAP.  When null (zero length octet string) the value 
         represents no specific address."
    SYNTAX      OCTET STRING (SIZE(0 | 7 | 9))

LSAP ::= TEXTUAL-CONVENTION
    STATUS      current
    DESCRIPTION 
        "This textual convention represents an LLC LSAP which consists 
         of a 1-octet value which contains the LLC LSAP.  Note that 
         technically the LSAP could be continued into subsequent octets, 
         however, this is not normally necessary for X.25/ISO 8208 and 
         CLNS."
    REFERENCE   
        "IEEE 802.2 (ISO/IEC 8802-2) ASN.1, LSAP."
    SYNTAX      OCTET STRING (SIZE(1))

x25Notifications OBJECT IDENTIFIER
    ::= { x25-LLC-MIB 0 }

x25Objects OBJECT IDENTIFIER
    ::= { x25-LLC-MIB 1 }

x25Tables OBJECT IDENTIFIER
    ::= { x25Objects 1 }

physicalEntity OBJECT IDENTIFIER
    ::= { x25Tables 1 }

physicalEntityTable OBJECT-TYPE
    SYNTAX      SEQUENCE OF PhysicalEntityEntry
    MAX-ACCESS  not-accessible
    STATUS      current
    DESCRIPTION 
        "Physical Entity Managed Object.  There may be multiple 
         instances of these MOs within a system.  These managed objects 
         can not be created or deleted explicitly by management 
         operation.  They exist inherently in a system; created and 
         deleted as part of system operation.
         
         A physicalEntity is derived from a communicationsEntity.  A 
         physicalEntity is containted by a physicalSubsystem.
         
         A dataCircuit is contained by a physicalEntity.  The name 
         binding which applies when a dataCircuit managed object can be 
         created by management as a subordinate object of a 
         physicalEntity managed object and deleted by management."
    REFERENCE   
        "ITU-T Rec. X.281 | ISO/IEC 13642, physicalEntity."
    ::= { physicalEntity 1 }

physicalEntityEntry OBJECT-TYPE
    SYNTAX      PhysicalEntityEntry
    MAX-ACCESS  not-accessible
    STATUS      current
    DESCRIPTION 
        ""
    REFERENCE   
        "ITU-T Rec. X.281 | ISO/IEC 13642, physicalEntity."
    INDEX       { physicalEntityCommunicationsEntityId }
    ::= { physicalEntityTable 1 }

PhysicalEntityEntry ::= SEQUENCE {
    physicalEntityCommunicationsEntityId    InterfaceIndex,
    physicalEntityLocalSapNames             RowPointer,
    physicalEntityOperationalState          OperationalState,
    physicalEntityPhysicalEntityTitles      RowPointer
}

physicalEntityCommunicationsEntityId OBJECT-TYPE
    SYNTAX      InterfaceIndex
    MAX-ACCESS  not-accessible
    STATUS      current
    DESCRIPTION 
        ""
    REFERENCE   
        "ITU-T Rec. X.723 | ISO/IEC 10165-5, communicationsEntityId."
    ::= { physicalEntityEntry 1 }

physicalEntityLocalSapNames OBJECT-TYPE
    SYNTAX      RowPointer
    MAX-ACCESS  read-write
    STATUS      current
    DESCRIPTION 
        "The localSapNames associated with the physical communications 
         entity are the physicalSAP MOs that represent the user-provider 
         relationship for the physical communications entity.  For 
         normal data circuits, there is at most one physicalSAP 
         associated with the physicalEntity and visa versa."
    REFERENCE   
        "ITU-T Rec. X.723 | ISO/IEC 10165-5, localSapNames."
    ::= { physicalEntityEntry 2 }

physicalEntityOperationalState OBJECT-TYPE
    SYNTAX      OperationalState
    MAX-ACCESS  read-only
    STATUS      current
    DESCRIPTION 
        "Provides the operational state of the physical entity in 
         accordance with the OperaionalState textual convention of the 
         OPENSS7-TMN-TC module, which is based on ITU-T Rec. X.721 | 
         ISO/IEC 10165-2 operationalState."
    REFERENCE   
        "ITU-T Rec. X.721 | ISO/IEC 10165-2, operationalState."
    ::= { physicalEntityEntry 3 }

physicalEntityPhysicalEntityTitles OBJECT-TYPE
    SYNTAX      RowPointer
    MAX-ACCESS  read-write
    STATUS      current
    DESCRIPTION 
        "Provides the names (titles) of the data link entity to which 
         this physical entity provides service.  This is a RowPointer 
         into the appropriate table at which entry the data link entity 
         exists."
    REFERENCE   
        "ITU-T Rec. X.281 | ISO/IEC 13642, physicalEntity."
    ::= { physicalEntityEntry 4 }

physicalSAP OBJECT IDENTIFIER
    ::= { x25Tables 2 }

physicalSAPTable OBJECT-TYPE
    SYNTAX      SEQUENCE OF PhysicalSAPEntry
    MAX-ACCESS  not-accessible
    STATUS      current
    DESCRIPTION 
        "Physical Service Access Point Managed Object.  Physical SAP MO 
         class is used to represent a service access point where the 
         interactions between the phsyical service and the physical 
         service provider take place.  
         
         phSAP managed objects are created automatically as part of 
         system operation when a Physical layer user requests and is 
         granted use of the Physical layer services.  The mechanism by 
         which this happens is system-specific and not subject to OSI 
         standardization."
    REFERENCE   
        "ITU-T Rec. X.281 | ISO/IEC 13642 phsicalSAP MO."
    ::= { physicalSAP 1 }

physicalSAPEntry OBJECT-TYPE
    SYNTAX      PhysicalSAPEntry
    MAX-ACCESS  not-accessible
    STATUS      current
    DESCRIPTION 
        ""
    REFERENCE   
        "ITU-T Rec. X.281 | ISO/IEC 13642 phsicalSAP MO."
    INDEX       { physicalSAPsapId }
    ::= { physicalSAPTable 1 }

PhysicalSAPEntry ::= SEQUENCE {
    physicalSAPsapId            SimpleNameType,
    physicalSAPsap1Address      Integer32,
    physicalSAPuserEntityNames  RowPointer,
    physicalSAPRowStatus        RowStatus
}

physicalSAPsapId OBJECT-TYPE
    SYNTAX      SimpleNameType
    MAX-ACCESS  not-accessible
    STATUS      current
    DESCRIPTION 
        ""
    REFERENCE   
        "ITU-T Rec. X.723 | ISO/IEC 10165-5 sapId."
    ::= { physicalSAPEntry 1 }

physicalSAPsap1Address OBJECT-TYPE
    SYNTAX      Integer32
    MAX-ACCESS  not-accessible
    STATUS      current
    DESCRIPTION 
        ""
    REFERENCE   
        "ITU-T Rec. X.723 | ISO/IEC 10165-5 sap1."
    ::= { physicalSAPEntry 2 }

physicalSAPuserEntityNames OBJECT-TYPE
    SYNTAX      RowPointer
    MAX-ACCESS  not-accessible
    STATUS      current
    DESCRIPTION 
        ""
    REFERENCE   
        "ITU-T Rec. X.723 | ISO/IEC 10165-5 userEntityNames."
    ::= { physicalSAPEntry 3 }

physicalSAPRowStatus OBJECT-TYPE
    SYNTAX      RowStatus
    MAX-ACCESS  not-accessible
    STATUS      current
    DESCRIPTION 
        ""
    REFERENCE   
        "STD 58, SNMPv2-TC RowStatus."
    ::= { physicalSAPEntry 4 }

dataCircuit OBJECT IDENTIFIER
    ::= { x25Tables 3 }

dataCircuitTable OBJECT-TYPE
    SYNTAX      SEQUENCE OF DataCircuitEntry
    MAX-ACCESS  not-accessible
    STATUS      current
    DESCRIPTION 
        "The data-circuit managed object class is used to represent a 
         communication path in the physical media for OSI between two 
         phsysical entities, together with the facilities necessary in 
         the Physical Layer for the transmission of bits on it.
         
         This MOC is derived from the X.723 coProtocolMachine."
    REFERENCE   
        "ITU-T Rec. X.281 | ISO/IEC 13642 dataCircuit MO."
    ::= { dataCircuit 1 }

dataCircuitEntry OBJECT-TYPE
    SYNTAX      DataCircuitEntry
    MAX-ACCESS  not-accessible
    STATUS      current
    DESCRIPTION 
        ""
    REFERENCE   
        "ITU-T Rec. X.281 | ISO/IEC 13642 dataCircuit MO."
    INDEX       { dataCircuitCoProtocolMachineId }
    ::= { dataCircuitTable 1 }

DataCircuitEntry ::= SEQUENCE {
    dataCircuitCoProtocolMachineId          SimpleNameType,
    dataCircuitOperationalState             OperationalState,
    dataCircuitBitErrorsReceived            Counter32,
    dataCircuitBitErrorsTransmitted         Counter32,
    dataCircuitBitErrorsThreshold           Float,
    dataCircuitDataCircuitType              INTEGER,
    dataCircuitPhysicalMediaNames           OCTET STRING,
    dataCircuitPhysicalInterfaceType        OCTET STRING,
    dataCircuitPhysicalInterfaceStandard    OCTET STRING,
    dataCircuitSynchronizationMode          INTEGER,
    dataCircuitTransmissionCoding           OCTET STRING,
    dataCircuitTransmissionMode             INTEGER,
    dataCircuitTransmissionRate             Float,
    dataCircuitRowStatus                    RowStatus
}

dataCircuitCoProtocolMachineId OBJECT-TYPE
    SYNTAX      SimpleNameType
    MAX-ACCESS  not-accessible
    STATUS      current
    DESCRIPTION 
        ""
    REFERENCE   
        "ITU-T Rec. X.723 | ISO/IEC 10165-5 
         coProtocolMachineId."
    ::= { dataCircuitEntry 1 }

dataCircuitOperationalState OBJECT-TYPE
    SYNTAX      OperationalState
    MAX-ACCESS  read-only
    STATUS      current
    DESCRIPTION 
        ""
    REFERENCE   
        "ITU-T Rec. X.721 | ISO/IEC 10165-2 oprationalState."
    ::= { dataCircuitEntry 2 }

dataCircuitBitErrorsReceived OBJECT-TYPE
    SYNTAX      Counter32
    MAX-ACCESS  read-only
    STATUS      current
    DESCRIPTION 
        ""
    REFERENCE   
        "ITU-T Rec. X.281 | ISO/IEC 13642 bitErrorsReceived."
    ::= { dataCircuitEntry 3 }

dataCircuitBitErrorsTransmitted OBJECT-TYPE
    SYNTAX      Counter32
    MAX-ACCESS  read-only
    STATUS      current
    DESCRIPTION 
        ""
    REFERENCE   
        "ITU-T Rec. X.281 | ISO/IEC 13642 bitErrorsTransmitted."
    ::= { dataCircuitEntry 4 }

dataCircuitBitErrorsThreshold OBJECT-TYPE
    SYNTAX      Float
    MAX-ACCESS  read-create
    STATUS      current
    DESCRIPTION 
        ""
    REFERENCE   
        "ITU-T Rec. X.281 | ISO/IEC 13642 bitErrorsThreshold."
    ::= { dataCircuitEntry 5 }

dataCircuitDataCircuitType OBJECT-TYPE
    SYNTAX      INTEGER { endSystem(0), relaySystem(1) }
    MAX-ACCESS  read-create
    STATUS      current
    DESCRIPTION 
        ""
    REFERENCE   
        "ITU-T Rec. X.281 | ISO/IEC 13642 dataCircuitType."
    ::= { dataCircuitEntry 6 }

dataCircuitPhysicalMediaNames OBJECT-TYPE
    SYNTAX      OCTET STRING
    MAX-ACCESS  read-create
    STATUS      current
    DESCRIPTION 
        ""
    REFERENCE   
        "ITU-T Rec. X.281 | ISO/IEC 13642 physicalMediaNames."
    ::= { dataCircuitEntry 7 }

dataCircuitPhysicalInterfaceType OBJECT-TYPE
    SYNTAX      OCTET STRING
    MAX-ACCESS  read-create
    STATUS      current
    DESCRIPTION 
        ""
    REFERENCE   
        "ITU-T Rec. X.281 | ISO/IEC 13642 
         physicalInterfaceType."
    ::= { dataCircuitEntry 8 }

dataCircuitPhysicalInterfaceStandard OBJECT-TYPE
    SYNTAX      OCTET STRING
    MAX-ACCESS  read-create
    STATUS      current
    DESCRIPTION 
        ""
    REFERENCE   
        "ITU-T Rec. X.281 | ISO/IEC 13642 
         physicalInterfaceStandard."
    ::= { dataCircuitEntry 9 }

dataCircuitSynchronizationMode OBJECT-TYPE
    SYNTAX      INTEGER { synchronous(0), asynchronous(1) }
    MAX-ACCESS  read-create
    STATUS      current
    DESCRIPTION 
        ""
    REFERENCE   
        "ITU-T Rec. X.281 | ISO/IEC 13642 synchornizationMode."
    ::= { dataCircuitEntry 10 }

dataCircuitTransmissionCoding OBJECT-TYPE
    SYNTAX      OCTET STRING
    MAX-ACCESS  read-create
    STATUS      current
    DESCRIPTION 
        ""
    REFERENCE   
        "ITU-T Rec. X.281 | ISO/IEC 13642 transmissionCoding."
    ::= { dataCircuitEntry 11 }

dataCircuitTransmissionMode OBJECT-TYPE
    SYNTAX      INTEGER { simplex(0), duplex(1) }
    MAX-ACCESS  read-create
    STATUS      current
    DESCRIPTION 
        ""
    REFERENCE   
        "ITU-T Rec. X.281 | ISO/IEC 13642 transmissionMode."
    ::= { dataCircuitEntry 12 }

dataCircuitTransmissionRate OBJECT-TYPE
    SYNTAX      Float
    MAX-ACCESS  read-create
    STATUS      current
    DESCRIPTION 
        ""
    REFERENCE   
        "ITU-T Rec. X.281 | ISO/IEC 13642 transmissionRate."
    ::= { dataCircuitEntry 13 }

dataCircuitRowStatus OBJECT-TYPE
    SYNTAX      RowStatus
    MAX-ACCESS  read-create
    STATUS      current
    DESCRIPTION 
        ""
    REFERENCE   
        "STD 58, SNMPv2-TC RowStatus."
    ::= { dataCircuitEntry 14 }

physicalConnection OBJECT IDENTIFIER
    ::= { x25Tables 4 }

physicalConnectionTable OBJECT-TYPE
    SYNTAX      SEQUENCE OF PhysicalConnectionEntry
    MAX-ACCESS  not-accessible
    STATUS      current
    DESCRIPTION 
        "Physical Connection Managed Object.  The physical connection 
         managed object class is used to represent an interconnection of 
         data circuits in the physical layer."
    REFERENCE   
        "ITU-T Rec. X.281 | ISO/IEC 13642 physicalConnection."
    ::= { physicalConnection 1 }

physicalConnectionEntry OBJECT-TYPE
    SYNTAX      PhysicalConnectionEntry
    MAX-ACCESS  not-accessible
    STATUS      current
    DESCRIPTION 
        ""
    REFERENCE   
        "ITU-T Rec. X.281 | ISO/IEC 13642 physicalConnection."
    INDEX       { physicalConnectionConnectionId }
    ::= { physicalConnectionTable 1 }

PhysicalConnectionEntry ::= SEQUENCE {
    physicalConnectionConnectionId                  SimpleNameType,
    physicalConnectionUnderlyingConnectionNames     RowPointer,
    physicalConnectionSupportedConnectionNames      RowPointer,
    physicalConnectionEndpointIdentifier            OCTET STRING,
    physicalConnectionPortNumber                    Unsigned32,
    physicalConnectionRowStatus                     RowStatus
}

physicalConnectionConnectionId OBJECT-TYPE
    SYNTAX      SimpleNameType
    MAX-ACCESS  not-accessible
    STATUS      current
    DESCRIPTION 
        ""
    REFERENCE   
        "ITU-T Rec. X.723 | ISO/IEC 10165-5 connectionId."
    ::= { physicalConnectionEntry 1 }

physicalConnectionUnderlyingConnectionNames OBJECT-TYPE
    SYNTAX      RowPointer
    MAX-ACCESS  read-create
    STATUS      current
    DESCRIPTION 
        ""
    REFERENCE   
        "ITU-T Rec. X.723 | ISO/IEC 10165-5 underlyingCOnnectionNames."
    ::= { physicalConnectionEntry 2 }

physicalConnectionSupportedConnectionNames OBJECT-TYPE
    SYNTAX      RowPointer
    MAX-ACCESS  read-create
    STATUS      current
    DESCRIPTION 
        ""
    REFERENCE   
        "ITU-T Rec. X.723 | ISO/IEC 10165-5 supportedConnectionNames."
    ::= { physicalConnectionEntry 3 }

physicalConnectionEndpointIdentifier OBJECT-TYPE
    SYNTAX      OCTET STRING
    MAX-ACCESS  read-create
    STATUS      current
    DESCRIPTION 
        ""
    REFERENCE   
        "ITU-T Rec. X.281 | ISO/IEC 13642 endpointIdentifier."
    ::= { physicalConnectionEntry 4 }

physicalConnectionPortNumber OBJECT-TYPE
    SYNTAX      Unsigned32
    MAX-ACCESS  read-create
    STATUS      current
    DESCRIPTION 
        ""
    REFERENCE   
        "ITU-T Rec. X.281 | ISO/IEC 13642 portNumber."
    ::= { physicalConnectionEntry 5 }

physicalConnectionRowStatus OBJECT-TYPE
    SYNTAX      RowStatus
    MAX-ACCESS  read-create
    STATUS      current
    DESCRIPTION 
        ""
    REFERENCE   
        "STD 58, SNMPv2-TC RowStatus."
    ::= { physicalConnectionEntry 6 }

datalinkEntity OBJECT IDENTIFIER
    ::= { x25Tables 5 }

datalinkEntityTable OBJECT-TYPE
    SYNTAX      SEQUENCE OF DatalinkEntityEntry
    MAX-ACCESS  not-accessible
    STATUS      current
    DESCRIPTION 
        ""
    REFERENCE   
        ""
    ::= { datalinkEntity 1 }

datalinkEntityEntry OBJECT-TYPE
    SYNTAX      DatalinkEntityEntry
    MAX-ACCESS  not-accessible
    STATUS      current
    DESCRIPTION 
        ""
    REFERENCE   
        ""
    INDEX       { datalinkEntityCommunicationsEntityId }
    ::= { datalinkEntityTable 1 }

DatalinkEntityEntry ::= SEQUENCE {
    datalinkEntityCommunicationsEntityId    InterfaceIndex,
    datalinkEntityLocalSapNames             RowPointer,
    datalinkEntityOperationalState          OperationalState,
    datalinkEntityProviderEntityNames       RowPointer,
    datalinkEntityRowStatus                 RowStatus
}

datalinkEntityCommunicationsEntityId OBJECT-TYPE
    SYNTAX      InterfaceIndex
    MAX-ACCESS  not-accessible
    STATUS      current
    DESCRIPTION 
        ""
    REFERENCE   
        "ITU-T Rec. X.723 | ISO/IEC 10165-5, datalinkEntity."
    ::= { datalinkEntityEntry 1 }

datalinkEntityLocalSapNames OBJECT-TYPE
    SYNTAX      RowPointer
    MAX-ACCESS  read-create
    STATUS      current
    DESCRIPTION 
        "The localSapNames attribute identifies the providing entity's 
         SAP objects.  (Note that the providing entity is identified by 
         the providerEntityNames attribute."
    REFERENCE   
        "ITU-T Rec. X.723 | ISO/IEC 10165-5, datalinkEntity."
    ::= { datalinkEntityEntry 2 }

datalinkEntityOperationalState OBJECT-TYPE
    SYNTAX      OperationalState
    MAX-ACCESS  read-only
    STATUS      current
    DESCRIPTION 
        ""
    REFERENCE   
        "ITU-T Rec. X.723 | ISO/IEC 10165-5, datalinkEntity."
    ::= { datalinkEntityEntry 3 }

datalinkEntityProviderEntityNames OBJECT-TYPE
    SYNTAX      RowPointer
    MAX-ACCESS  read-create
    STATUS      current
    DESCRIPTION 
        ""
    REFERENCE   
        "ITU-T Rec. X.723 | ISO/IEC 10165-5, datalinkEntity."
    ::= { datalinkEntityEntry 4 }

datalinkEntityRowStatus OBJECT-TYPE
    SYNTAX      RowStatus
    MAX-ACCESS  read-create
    STATUS      current
    DESCRIPTION 
        ""
    REFERENCE   
        "ITU-T Rec. X.723 | ISO/IEC 10165-5, datalinkEntity."
    ::= { datalinkEntityEntry 5 }

dLSAP OBJECT IDENTIFIER
    ::= { x25Tables 6 }

dLSAPTable OBJECT-TYPE
    SYNTAX      SEQUENCE OF DLSAPEntry
    MAX-ACCESS  not-accessible
    STATUS      current
    DESCRIPTION 
        ""
    REFERENCE   
        "ITU-T Rec. X.282 | ISO/IEC 10742."
    ::= { dLSAP 1 }

dLSAPEntry OBJECT-TYPE
    SYNTAX      DLSAPEntry
    MAX-ACCESS  not-accessible
    STATUS      current
    DESCRIPTION 
        ""
    REFERENCE   
        "ITU-T Rec. X.282 | ISO/IEC 10742."
    INDEX       { dLSAPSapId }
    ::= { dLSAPTable 1 }

DLSAPEntry ::= SEQUENCE {
    dLSAPSapId              SimpleNameType,
    dLSAPSap1Address        Integer32,
    dLSAPUserEntityNames    RowPointer,
    dLSAPRowStatus          RowStatus
}

dLSAPSapId OBJECT-TYPE
    SYNTAX      SimpleNameType
    MAX-ACCESS  not-accessible
    STATUS      current
    DESCRIPTION 
        ""
    REFERENCE   
        "ITU-T Rec. X.723 | ISO/IEC 10165-5, dLSAP."
    ::= { dLSAPEntry 1 }

dLSAPSap1Address OBJECT-TYPE
    SYNTAX      Integer32
    MAX-ACCESS  read-create
    STATUS      current
    DESCRIPTION 
        ""
    REFERENCE   
        "ITU-T Rec. X.723 | ISO/IEC 10165-5, dLSAP."
    ::= { dLSAPEntry 2 }

dLSAPUserEntityNames OBJECT-TYPE
    SYNTAX      RowPointer
    MAX-ACCESS  read-create
    STATUS      current
    DESCRIPTION 
        ""
    REFERENCE   
        "ITU-T Rec. X.723 | ISO/IEC 10165-5, dLSAP."
    ::= { dLSAPEntry 3 }

dLSAPRowStatus OBJECT-TYPE
    SYNTAX      RowStatus
    MAX-ACCESS  read-create
    STATUS      current
    DESCRIPTION 
        ""
    REFERENCE   
        "ITU-T Rec. X.723 | ISO/IEC 10165-5, dLSAP."
    ::= { dLSAPEntry 4 }

mACDLE OBJECT IDENTIFIER
    ::= { x25Tables 7 }

mACDLETable OBJECT-TYPE
    SYNTAX      SEQUENCE OF MACDLEEntry
    MAX-ACCESS  not-accessible
    STATUS      current
    DESCRIPTION 
        "The MAC Data Link Entity managed object class.  There may be 
         multiple instances of the mACDLE managed object in a system.  
         Systems not supported connections to LAN media are not required 
         to support the mACDLE and contained managed objects.
         
         A mACDLE managed object may contain at modes on instance of a 
         mac-specific MO derived from the generic mAC MO.  A mACDLE MO 
         may contain at most one dLSAP MO.  The value of the sap1Address 
         attribute is of no significance.  The cardinality of the 
         userEntityNames attribute is limited to one.
         
         A mACDLE MO may be created and deleted explicitly by management 
         operation or created and deleted automatically as part of 
         system operation.
         
         When the mACDLE MO is operable, the operationalState shall have 
         the value 'enabled'; otherwise, it shall have the value 
         'disabled'.  Transitions of operationalState shall be reported 
         using the stateChange notification.
         
         The mACDLE MOC is derived from the datalinkEntity MOC.  The 
         mACDLE MO contains mAC MOs.
         
         An instance of the mACDLE MO represents an instance of the IEEE 
         802.2 MAC sublayer.  The MAC data link entity can contain mAC 
         MOs.  Each mAC MO instance contained represents a MAC address 
         that belongs to the mACDLE."
    REFERENCE   
        "ITU-T Rec. X.272 | ISO/IEC 10742, mACDLE MOC."
    ::= { mACDLE 1 }

mACDLEEntry OBJECT-TYPE
    SYNTAX      MACDLEEntry
    MAX-ACCESS  not-accessible
    STATUS      current
    DESCRIPTION 
        ""
    REFERENCE   
        ""
    INDEX       { mACDLECommunicationsEntityId }
    ::= { mACDLETable 1 }

MACDLEEntry ::= SEQUENCE {
    mACDLECommunicationsEntityId    InterfaceIndex,
    mACDLELocalSapNames             RowPointer,
    mACDLEOperationalState          OperationalState,
    mACDLEProviderEntityNames       RowPointer,
    mACDLERowStatus                 RowStatus
}

mACDLECommunicationsEntityId OBJECT-TYPE
    SYNTAX      InterfaceIndex
    MAX-ACCESS  not-accessible
    STATUS      current
    DESCRIPTION 
        ""
    REFERENCE   
        "ITU-T Rec. X.282 | ISO/IEC 10742, mACDLE."
    ::= { mACDLEEntry 1 }

mACDLELocalSapNames OBJECT-TYPE
    SYNTAX      RowPointer
    MAX-ACCESS  read-create
    STATUS      current
    DESCRIPTION 
        "The localSapNames attribute identifies the providing entity's 
         SAP objects.  In this case, the providing entity is a Ph-Entity 
         and the Ph-SAP is indicated by the name."
    REFERENCE   
        "ITU-T Rec. X.282 | ISO/IEC 10742, mACDLE."
    ::= { mACDLEEntry 2 }

mACDLEOperationalState OBJECT-TYPE
    SYNTAX      OperationalState
    MAX-ACCESS  read-only
    STATUS      current
    DESCRIPTION 
        ""
    REFERENCE   
        "ITU-T Rec. X.282 | ISO/IEC 10742, mACDLE."
    ::= { mACDLEEntry 3 }

mACDLEProviderEntityNames OBJECT-TYPE
    SYNTAX      RowPointer
    MAX-ACCESS  read-create
    STATUS      current
    DESCRIPTION 
        ""
    REFERENCE   
        "ITU-T Rec. X.282 | ISO/IEC 10742, mACDLE."
    ::= { mACDLEEntry 4 }

mACDLERowStatus OBJECT-TYPE
    SYNTAX      RowStatus
    MAX-ACCESS  read-create
    STATUS      current
    DESCRIPTION 
        ""
    REFERENCE   
        "ITU-T Rec. X.282 | ISO/IEC 10742, mACDLE."
    ::= { mACDLEEntry 5 }

mAC OBJECT IDENTIFIER
    ::= { x25Tables 8 }

mACTable OBJECT-TYPE
    SYNTAX      SEQUENCE OF MACEntry
    MAX-ACCESS  not-accessible
    STATUS      current
    DESCRIPTION 
        ""
    REFERENCE   
        "ITU-T Rec. X.282 | ISO/IEC 10742."
    ::= { mAC 1 }

mACEntry OBJECT-TYPE
    SYNTAX      MACEntry
    MAX-ACCESS  not-accessible
    STATUS      current
    DESCRIPTION 
        ""
    REFERENCE   
        "ITU-T Rec. X.282 | ISO/IEC 10742."
    INDEX       { mACMacId }
    ::= { mACTable 1 }

MACEntry ::= SEQUENCE {
    mACOperationalState     OperationalState,
    mACMacId                MacAddress
}

mACOperationalState OBJECT-TYPE
    SYNTAX      OperationalState
    MAX-ACCESS  read-only
    STATUS      current
    DESCRIPTION 
        ""
    ::= { mACEntry 1 }

mACMacId OBJECT-TYPE
    SYNTAX      MacAddress
    MAX-ACCESS  not-accessible
    STATUS      current
    DESCRIPTION 
        ""
    ::= { mACEntry 2 }

resourceTypeId OBJECT IDENTIFIER
    ::= { x25Tables 9 }

resourceTypeIdTable OBJECT-TYPE
    SYNTAX      SEQUENCE OF ResourceTypeIdEntry
    MAX-ACCESS  not-accessible
    STATUS      current
    DESCRIPTION 
        ""
    REFERENCE   
        "ISO/IEC 10742 but not ITU-T Rec. X.282"
    ::= { resourceTypeId 1 }

resourceTypeIdEntry OBJECT-TYPE
    SYNTAX      ResourceTypeIdEntry
    MAX-ACCESS  not-accessible
    STATUS      current
    DESCRIPTION 
        ""
    REFERENCE   
        "ISO/IEC 10742 but not ITU-T Rec. X.282"
    INDEX       { resourceTypeIdName }
    ::= { resourceTypeIdTable 1 }

ResourceTypeIdEntry ::= SEQUENCE {
    resourceTypeIdName                      SimpleNameType,
    resourceInfoManufacturerOUI             OCTET STRING,
    resourceInfoManufacturerName            DisplayString,
    resourceInfoManufacturerProductName     DisplayString,
    resourceInfoManufacturerProductVersion  DisplayString
}

resourceTypeIdName OBJECT-TYPE
    SYNTAX      SimpleNameType
    MAX-ACCESS  not-accessible
    STATUS      current
    DESCRIPTION 
        ""
    REFERENCE   
        "ISO/IEC 10742 but not ITU-T Rec. X.282"
    ::= { resourceTypeIdEntry 1 }

resourceInfoManufacturerOUI OBJECT-TYPE
    SYNTAX      OCTET STRING
    MAX-ACCESS  read-only
    STATUS      current
    DESCRIPTION 
        "ManufacturerOUI takes the value of an Organizationally Unique 
         Identifier, as defined in secion 5.1 of IEEE 802.1 Overview and 
         Architecture.  When encoded as an OCTET STRING, the encoding of 
         the value field of the OCTET STRING shall comply with the 
         representation defined in sections 5.1.2 of the Overview and 
         Architecture.  Inasmcuh as multiple OUI assignements are 
         possible for a given manufacturer and no public registry of 
         such assigments exists, methods for application of the OUI as a 
         globally unique manufacturer identifier is outside the scope of 
         this standard."
    REFERENCE   
        "ISO/IEC 10742 but not ITU-T Rec. X.282"
    ::= { resourceTypeIdEntry 2 }

resourceInfoManufacturerName OBJECT-TYPE
    SYNTAX      DisplayString (SIZE(0..128))
    MAX-ACCESS  read-only
    STATUS      current
    DESCRIPTION 
        "ManufactererName is a printable string used to identify the 
         manufacturer of the resource.  Global assignment of unique name 
         strngs is outside the scope of this standard.  Maximum string 
         length is 128 octets."
    REFERENCE   
        "ISO/IEC 10742 but not ITU-T Rec. X.282"
    ::= { resourceTypeIdEntry 3 }

resourceInfoManufacturerProductName OBJECT-TYPE
    SYNTAX      DisplayString (SIZE(0..128))
    MAX-ACCESS  read-only
    STATUS      current
    DESCRIPTION 
        "ManufactererProductName is a printable string used to identify 
         the manufacturer's product name of the resource.  Maximum 
         string length is 128 octets."
    REFERENCE   
        "ISO/IEC 10742 but not ITU-T Rec. X.282"
    ::= { resourceTypeIdEntry 4 }

resourceInfoManufacturerProductVersion OBJECT-TYPE
    SYNTAX      DisplayString (SIZE(0..128))
    MAX-ACCESS  read-only
    STATUS      current
    DESCRIPTION 
        "ManufacturerProductVersion is a printable string used to 
         identify the manufacturer's product version of the resource.  
         Maximum string length is 128."
    REFERENCE   
        "ISO/IEC 10742 but not ITU-T Rec. X.282"
    ::= { resourceTypeIdEntry 5 }

lLCDLE OBJECT IDENTIFIER
    ::= { x25Tables 10 }

lLCDLETable OBJECT-TYPE
    SYNTAX      SEQUENCE OF LLCDLEEntry
    MAX-ACCESS  not-accessible
    STATUS      current
    DESCRIPTION 
        "The lLCDLE MOC is derived from the datalinkEntity MOC.  The 
         lLCDLE contains connectionless and connection oriented protocol 
         machines representing LLC1, and LLC2 and/or LLC3 operation.  
         The lLCDLE also contains an LLC station and one or more lLCSAP 
         service access points.
         
         Each lLCDLE MO uses the services of a mACDLE.  The mACDLE 
         provides service to an lLCDLE.  (Note that Ethernet II accesses 
         the MAC sublayer directly, via a dlSAP MO contained by the 
         mACDLE.)
         
         An instance of the lLCDLE MO represents an instance of the IEEE 
         802.2 LLC sublayer.  The LLC data link entity can contain 
         lLCCLPM and lLCCOPM protocol machines MOs, an lLCstation MO, 
         and one or more lLCSAP MOs."
    REFERENCE   
        "ITU-T Rec. X.282 | ISO/IEC 10742."
    ::= { lLCDLE 1 }

lLCDLEEntry OBJECT-TYPE
    SYNTAX      LLCDLEEntry
    MAX-ACCESS  not-accessible
    STATUS      current
    DESCRIPTION 
        ""
    REFERENCE   
        "ITU-T Rec. X.282 | ISO/IEC 10742."
    INDEX       { lLCDLECommunicationsEntityId }
    ::= { lLCDLETable 1 }

LLCDLEEntry ::= SEQUENCE {
    lLCDLECommunicationsEntityId    InterfaceIndex,
    lLCDLELocalSapNames             RowPointer,
    lLCDLEOperationalState          OperationalState,
    lLCDLEProviderEntityNames       RowPointer,
    lLCDELRowStatus                 RowStatus
}

lLCDLECommunicationsEntityId OBJECT-TYPE
    SYNTAX      InterfaceIndex
    MAX-ACCESS  not-accessible
    STATUS      current
    DESCRIPTION 
        ""
    REFERENCE   
        "ITU-T Rec. X.282 | ISO/IEC 10742."
    ::= { lLCDLEEntry 1 }

lLCDLELocalSapNames OBJECT-TYPE
    SYNTAX      RowPointer
    MAX-ACCESS  read-create
    STATUS      current
    DESCRIPTION 
        "The localSapNames attribute identifies the providing entity's 
         SAP objects.  In the case of the lLCDLE, the localSapNames 
         identifies the dLSAP of the mACDLE object which is providing 
         service to the lLCDLE."
    REFERENCE   
        "ITU-T Rec. X.282 | ISO/IEC 10742."
    ::= { lLCDLEEntry 2 }

lLCDLEOperationalState OBJECT-TYPE
    SYNTAX      OperationalState
    MAX-ACCESS  read-only
    STATUS      current
    DESCRIPTION 
        ""
    REFERENCE   
        "ITU-T Rec. X.723 | ISO/IEC 10165-5 datalinkEntity 
         operationalState."
    ::= { lLCDLEEntry 3 }

lLCDLEProviderEntityNames OBJECT-TYPE
    SYNTAX      RowPointer
    MAX-ACCESS  read-create
    STATUS      current
    DESCRIPTION 
        "The providerEntityNames attribute identifies the entities 
         providing service to this datalinkEntity.  In the case of the 
         LLC data link entity, lLCDLE, the provider entity is a MAC data 
         link entity, mACDLE.  At most one mACDLE can provide service to 
         an lLCDLE, and at most one lLCDLE can be provided service by a 
         mACDLE."
    REFERENCE   
        "ITU-T Rec. X.282 | ISO/IEC 10742."
    ::= { lLCDLEEntry 4 }

lLCDELRowStatus OBJECT-TYPE
    SYNTAX      RowStatus
    MAX-ACCESS  read-create
    STATUS      current
    DESCRIPTION 
        "Provides a mechanism whereby management stations, following the 
         RowStatus textual convention of the SNMPv2-TC module, may 
         create and destroy conceptual rows in this table.
         
         Rows must have been created by a management station to be 
         deleted by a management station.  Rows created by system 
         operation must be deleted by system operation."
    REFERENCE   
        "STD 58, SNMPv2-TC RowStatus."
    ::= { lLCDLEEntry 5 }

lLCStation OBJECT IDENTIFIER
    ::= { x25Tables 11 }

lLCStationTable OBJECT-TYPE
    SYNTAX      SEQUENCE OF LLCStationEntry
    MAX-ACCESS  not-accessible
    STATUS      current
    DESCRIPTION 
        "The station component is responsible for processing the events 
         that affect the entire LLC entity.  The station component 
         handles PDUs addressed to the null DSAP address and processes 
         the duplicate address check, if implemented.  One station 
         component shall exist for each MAC service access point present 
         on the local area network.
         
         Provides a table of LLC Stations.  There is in entry in this 
         table for each MAC service access point present on the local 
         area network.
         
         Provides a table of statistics for LLC stations.  There is an 
         entry in this table for each MAC service access point present 
         on a local area network attached to this system."
    REFERENCE   
        "IEEE 802.2 | ISO/IEC 8802-2"
    ::= { lLCStation 1 }

lLCStationEntry OBJECT-TYPE
    SYNTAX      LLCStationEntry
    MAX-ACCESS  not-accessible
    STATUS      current
    DESCRIPTION 
        "The station component is responsible for handling all events 
         that are directed to the LLC as a whole (i.e, events affecting 
         all SAPs and connections serviced by that LLC).  The station 
         component shall begin in the DOWN state, optionally check for a 
         duplicate station address, and potentially enter the UP state; 
         see figure 
         24 and table 1 of IEEE 802.2 (ISO/IEC 8802-2).  The UP state of 
            the LLC station component provides the enabling conditions 
            for the operation of the service access point (SAP) 
            components.
         
         The station component shall be capable of receiving and 
         responding to XID and TEST command PDUs.  It shall optionally 
         be capable of initiating the XID commend PDU, if duplicate 
         address checking is performed by the LLC entity in a particular 
         implementation; see table 2 of IEEE 802.2 (ISO/IEC 8802-2).  
         These PDUs shall used the null DSAP address to denote that the 
         station component is being referenced.
         
         The performance of the duplicate address check requires that 
         the station component be prepared to received its own XID PDUs.  
         The definition of the MAC operation provides for the ability to 
         simultaneously transmit and receive.  Since the DA = SA in the 
         XID PDUs can be used for duplicate address check, the MAC will 
         recognize its own address and pass the PDU to the station 
         component.  The station component will respond to an XID 
         command PDU with an XID responose PDU, regardless of whether it 
         originated from itself or a remote LLC.  The station component 
         provides the duplicate address check by maintaining a count of 
         received XID response PDUs.  If more than one XID response PDU 
         is received, then at least one other identical MAC DA exists on 
         the LAN.  See figure 24 and table 1 in IEEE 802.2 (ISO/IEC 
         8802-2) for details.
         
         Provides an entry in the X.25 LLC2 Station table for one LLC2 
         connection to the media (MAC Access).  Each MAC is indexed by 
         its ifIndex into the interface table.
         
         Provides an enty in the X.25 LLC Station table for one LLC 
         connection to the media (MAC Access).  Each MAC is indexed by 
         its ifIndex into the interface table."
    REFERENCE   
        "IEEE 802.2 | ISO/IEC 8802-2"
    INDEX       { dLSAPSapId }
    ::= { lLCStationTable 1 }

LLCStationEntry ::= SEQUENCE {
    lLCStationLLCName                           SimpleNameType,
    lLCStationMaximumLSAPsConfigured            Integer32,
    lLCStationNumberOfActiveLSAPs               Gauge32,
    lLCStationSupportedServicesTypes            LLCServices,
    lLCStationStatus                            LLCStationStatus,
    lLCStationType1AcknowledgeTimeoutValue      TimeInterval,
    lLCStationType1MaximumRetryCount            Integer32,
    lLCStationMaximumPDUN3                      Integer32,
    lLCStationMaximumRetransmissions4           Integer32,
    lLCStationReceiveVariableLifetime           TimeInterval,
    lLCStationTransmitVariableLifetime          TimeInterval,
    lLCStationType3AcknowledgeTimeoutValue      TimeInterval,
    lLCStationType3Retransmissions              Counter32,
    lLCStationAvgBufferUseSize                  Gauge32,
    lLCStationBufferProblems                    Counter32,
    lLCStationBufferSize                        Integer32,
    lLCStationMaxBufferUseSize                  Gauge32,
    lLCStationInactiveLSAP                      Counter32,
    lLCStationPDUsDiscard                       Counter32,
    lLCStationSTRIndicator                      STRIndicator,
    lLCStationVersionNumber                     Integer32,
    lLCStationType1AcknowledgmentTimerTimeouts  Counter32
}

lLCStationLLCName OBJECT-TYPE
    SYNTAX      SimpleNameType
    MAX-ACCESS  read-write
    STATUS      current
    DESCRIPTION 
        "This attriute is used to name the instance of the lLCStation 
         managed object."
    REFERENCE   
        "IEEE 802.2 | ISO/IEC 8802-2, lLCName"
    ::= { lLCStationEntry 1 }

lLCStationMaximumLSAPsConfigured OBJECT-TYPE
    SYNTAX      Integer32 (1..128)
    UNITS       "LSAPs"
    MAX-ACCESS  read-only
    STATUS      current
    DESCRIPTION 
        "The maximum number of LSAPs that can be supported by this 
         station at any moment in time.  All LLC stations must support 
         at least one LSAP (the null LSAP used for duplicate address 
         detection and station-wide XID and TEST commands).  Station 
         numbers (LSAP IDs) range from 0 to 127.  Therefore, the range 
         of this value is from 1 to 128.  IEEE 802.2F (ISO/IEC 8802-2) 
         does not constrain the range of this attribute.  The number 
         reported is implementation dependent.  This is a read-only 
         column."
    REFERENCE   
        "IEEE 802.2 | ISO/IEC 8802-2, maximumLSAPsConfigured"
    ::= { lLCStationEntry 2 }

lLCStationNumberOfActiveLSAPs OBJECT-TYPE
    SYNTAX      Gauge32 (1..128)
    UNITS       "LSAPs"
    MAX-ACCESS  read-only
    STATUS      current
    DESCRIPTION 
        "The number of active LSAPs that the station currently 
         supports."
    REFERENCE   
        "IEEE 802.2 | ISO/IEC 8802-2, numberOfActiveLSAPs"
    ::= { lLCStationEntry 3 }

lLCStationSupportedServicesTypes OBJECT-TYPE
    SYNTAX      LLCServices
    MAX-ACCESS  read-write
    STATUS      current
    DESCRIPTION 
        "The type or types of service supported (i.e., Type 1, Type 2, 
         Type 3.) The type or types of service supported by this 
         station.  The type are a combination of 
         
         - type1(0),
         - type2(1),
         - type3Initiate(2),
         - kype3ReceiveData(3),
         - type3ReturnData(4).
         
         Implementations supporting this MIB must support at least 
         type1(0) and should support type2(1) if at all possible."
    REFERENCE   
        "IEEE 802.2 | ISO/IEC 8802-2, supportedServicesTypes"
    ::= { lLCStationEntry 4 }

lLCStationStatus OBJECT-TYPE
    SYNTAX      LLCStationStatus
    MAX-ACCESS  read-only
    STATUS      current
    DESCRIPTION 
        "Provides the status of the station.  This attribute allows a 
         manager to determine what state (UP, DOWN, etc.) the LLC 
         Station entity is in.  Note that the only reason that the 
         integer values start at zero (0) here instead of one (1) is 
         that the values are already defined in the GDMO MIBs of IEEE 
         802.2 (ISO/IEC 8802-2)."
    REFERENCE   
        "IEEE 802.2 | ISO/IEC 8802-2, status"
    ::= { lLCStationEntry 5 }

lLCStationType1AcknowledgeTimeoutValue OBJECT-TYPE
    SYNTAX      TimeInterval
    UNITS       "seconds"
    MAX-ACCESS  read-write
    STATUS      current
    DESCRIPTION 
        "The timeout value of the Ack timer, which is measured in 
         centiseconds, displayed in seconds.  THe Ack timer is described 
         in IEEE 802.2 (ISO/IEC 8802-2) 6.9.2.2 and 6.9.2.3.  It is used 
         by the station to supervise the acknowledgement of an XID 
         message sent to detect duplicate MAC addresses.  If no XID 
         response message is received within this time period, the XID 
         message will be reattempted up to the maximum retry count."
    REFERENCE   
        "IEEE 802.2 (ISO/IEC 8802-2), 
         type1AcknowledgeTimeoutValue, 6.9.2.2 and 6.9.2.3."
    ::= { lLCStationEntry 6 }

lLCStationType1MaximumRetryCount OBJECT-TYPE
    SYNTAX      Integer32
    UNITS       "retries"
    MAX-ACCESS  read-write
    STATUS      current
    DESCRIPTION 
        "The maximum number of retries during duplicate address 
         checking.  If the acknowledgement timer expires after sending 
         an XID message for duplicate address checking, the XID message 
         will be retransmitted this number of times, before moving to 
         the UP state."
    REFERENCE   
        "ISO/IEC 8802-2 (IEEE 802.2), type1MaximumRetryCount, 
         6.9.2.2 and 6.9.2.3."
    ::= { lLCStationEntry 7 }

lLCStationMaximumPDUN3 OBJECT-TYPE
    SYNTAX      Integer32
    UNITS       "octets"
    MAX-ACCESS  read-write
    STATUS      current
    DESCRIPTION 
        "The maximum size of a Type 3 command PDU.
         
         Unless Type 3 service is supported on the LLC station, this 
         value is of no significance."
    REFERENCE   
        "IEEE 802.2 | ISO/IEC 8802-2, maximumPDUN3"
    ::= { lLCStationEntry 8 }

lLCStationMaximumRetransmissions4 OBJECT-TYPE
    SYNTAX      Integer32
    UNITS       "retransmissions"
    MAX-ACCESS  read-write
    STATUS      current
    DESCRIPTION 
        "The number of retransmissions of a Type 3 PDU due to error 
         conditions preventing receive of an acknowledgement.
         
         Unless Type 3 service is supported on the LLC station, this 
         value is of no significance."
    REFERENCE   
        "IEEE 802.2 | ISO/IEC 8802-2, maximumRetransmissions4"
    ::= { lLCStationEntry 9 }

lLCStationReceiveVariableLifetime OBJECT-TYPE
    SYNTAX      TimeInterval
    MAX-ACCESS  read-write
    STATUS      current
    DESCRIPTION 
        "The amount of time the Type 3 LLC receive state variables are 
         maintained.
         
         Unless Type 3 service is suported on the LLC station, this 
         value is of no significance."
    REFERENCE   
        "IEEE 802.2 | ISO/IEC 8802-2, receiveVariableLifetime"
    ::= { lLCStationEntry 10 }

lLCStationTransmitVariableLifetime OBJECT-TYPE
    SYNTAX      TimeInterval
    MAX-ACCESS  read-write
    STATUS      current
    DESCRIPTION 
        "The amout of time the Type 3 LLC transmit state variables are 
         maintained.
         
         Unless Type 3 service is supported on the LLC station, this 
         value is of no significance."
    REFERENCE   
        "IEEE 802.2 | ISO/IEC 8802-2, transmitVariableLifetime"
    ::= { lLCStationEntry 11 }

lLCStationType3AcknowledgeTimeoutValue OBJECT-TYPE
    SYNTAX      TimeInterval
    MAX-ACCESS  read-write
    STATUS      current
    DESCRIPTION 
        "Specifies the time interval during which the LLC expects to 
         receive a response to an acknowledged connectionless request.
         
         Unless Type 3 service is supported by the LLC station, this 
         value is of no significance."
    REFERENCE   
        "IEEE 802.2 | ISO/IEC 8802-2, type3AcknowledgeTimeoutValue"
    ::= { lLCStationEntry 12 }

lLCStationType3Retransmissions OBJECT-TYPE
    SYNTAX      Counter32
    UNITS       "octets"
    MAX-ACCESS  read-only
    STATUS      current
    DESCRIPTION 
        "Provides a count of the number of PDUs which were retrasmitted 
         (at least once) by the Type 3 LLC service.
         
         Provides a count of the number of PDUs which were retransmitted 
         (at least once) by the Type 3 LLC service.  This value is of no 
         significance unless the LLC station supports Type 3 operation."
    REFERENCE   
        "IEEE 802.2 | ISO/IEC 8802-2, type3Retransmissions"
    ::= { lLCStationEntry 13 }

lLCStationAvgBufferUseSize OBJECT-TYPE
    SYNTAX      Gauge32
    UNITS       "octets"
    MAX-ACCESS  read-only
    STATUS      current
    DESCRIPTION 
        "Specifies the average amount of buffer space (in octets) in use 
         at the same time by LLC for this station."
    REFERENCE   
        "IEEE 802.2 | ISO/IEC 8802-2, avgBufferUseSize"
    ::= { lLCStationEntry 14 }

lLCStationBufferProblems OBJECT-TYPE
    SYNTAX      Counter32
    UNITS       "PDUs"
    MAX-ACCESS  read-only
    STATUS      current
    DESCRIPTION 
        "This counter provides a count of PDUs discarded due to buffer 
         limitations."
    REFERENCE   
        "IEEE 802.2 | ISO/IEC 8802-2, bufferProblems"
    ::= { lLCStationEntry 15 }

lLCStationBufferSize OBJECT-TYPE
    SYNTAX      Integer32
    UNITS       "octets"
    MAX-ACCESS  read-write
    STATUS      current
    DESCRIPTION 
        "THe amount of buffer space (in octets) for use by LLC."
    REFERENCE   
        "IEEE 802.2 | ISO/IEC 8802-2, bufferSize"
    ::= { lLCStationEntry 16 }

lLCStationMaxBufferUseSize OBJECT-TYPE
    SYNTAX      Gauge32
    UNITS       "octets"
    MAX-ACCESS  read-only
    STATUS      current
    DESCRIPTION 
        "Specifies the maximum amount of buffer space (in octets) in use 
         at the same time by LLC for this station."
    REFERENCE   
        "IEEE 802.2 | ISO/IEC 8802-2, maxBufferUseSize"
    ::= { lLCStationEntry 17 }

lLCStationInactiveLSAP OBJECT-TYPE
    SYNTAX      Counter32
    UNITS       "PDUs"
    MAX-ACCESS  read-only
    STATUS      current
    DESCRIPTION 
        "This counts the number of PDUs discarded due to the 
         specification of an inactive DSAP."
    REFERENCE   
        "IEEE 802.2 | ISO/IEC 8802-2, inactiveLSAP"
    ::= { lLCStationEntry 18 }

lLCStationPDUsDiscard OBJECT-TYPE
    SYNTAX      Counter32
    UNITS       "invalid PDUs"
    MAX-ACCESS  read-only
    STATUS      current
    DESCRIPTION 
        "Provides a total count of invalid PDUs that are discarded.  A 
         discarded (invalid) PDU shall be defined as one that meets at 
         least one of the following coniditions:
         
         1. It is identified by such by the PHY or the MAC sublayer;
         2. It is not an integral number of octets in length;
         3. It does not contain two properly formatted address fields, 
            one control field, and optionally an information field in 
            their proper order.
         4. Its length is less that 3 octets (one-octet control field) 
            or 4 octets (two-octet control field)."
    REFERENCE   
        "IEEE 802.2 | ISO/IEC 8802-2, pDUsDiscard"
    ::= { lLCStationEntry 19 }

lLCStationSTRIndicator OBJECT-TYPE
    SYNTAX      STRIndicator
    MAX-ACCESS  read-write
    STATUS      current
    DESCRIPTION 
        "A value that indicates if the spanning tree will be traversed 
         by a NSR or STE routing."
    REFERENCE   
        "IEEE 802.2 | ISO/IEC 8802-2, sTRIndicator"
    ::= { lLCStationEntry 20 }

lLCStationVersionNumber OBJECT-TYPE
    SYNTAX      Integer32
    MAX-ACCESS  read-write
    STATUS      current
    DESCRIPTION 
        "The version of sap RDE protocol implemented at this station.  
         The value of 1 will be used to represent the current version.  
         The special value zero (0) indicates that RDE is not support at 
         this station."
    REFERENCE   
        "IEEE 802.2 | ISO/IEC 8802-2, versionNumber"
    ::= { lLCStationEntry 21 }

lLCStationType1AcknowledgmentTimerTimeouts OBJECT-TYPE
    SYNTAX      Counter32
    MAX-ACCESS  read-only
    STATUS      current
    DESCRIPTION 
        "Specifies the number of times the ACK timer has expired."
    REFERENCE   
        "ISO/IEC 8802-2 (IEEE 802.2), type1AcknowledgmentTimerTimeouts, 
         6.9.2.2 and 6.9.2.3."
    ::= { lLCStationEntry 22 }

lLCSAP OBJECT IDENTIFIER
    ::= { x25Tables 12 }

lLCSAPTable OBJECT-TYPE
    SYNTAX      SEQUENCE OF LLCSAPEntry
    MAX-ACCESS  not-accessible
    STATUS      current
    DESCRIPTION 
        "The Link Service Access Point (SAP) component  is responsible 
         for processing the events that affect a specific operating 
         service access point.  One SAP component shall exist for each 
         SAP within the LLC entity.
         
         lLCSAP managed object.  This managed object contains attributes 
         associated wtih an LLC SAP that are independent of any 
         paticular type of Operation."
    REFERENCE   
        "IEEE 802.2 (ISO/IEC 8802-2)."
    ::= { lLCSAP 1 }

lLCSAPEntry OBJECT-TYPE
    SYNTAX      LLCSAPEntry
    MAX-ACCESS  not-accessible
    STATUS      current
    DESCRIPTION 
        ""
    REFERENCE   
        "IEEE 802.2 (ISO/IEC 8802-2)."
    INDEX       { lLCDLECommunicationsEntityId, dLSAPSapId }
    ::= { lLCSAPTable 1 }

LLCSAPEntry ::= SEQUENCE {
    lLCSAPName      SimpleNameType,
    lLCSAPAddress   LSAP,
    lLCSAPRDE       TruthValue
}

lLCSAPName OBJECT-TYPE
    SYNTAX      SimpleNameType
    MAX-ACCESS  not-accessible
    STATUS      current
    DESCRIPTION 
        "Used to name the instance of this lLCSAP managed object within 
         the scope of a containing lLCDLE managed object."
    REFERENCE   
        "IEEE 802.2 (ISO/IEC 8802-2), lLCSAPName."
    ::= { lLCSAPEntry 1 }

lLCSAPAddress OBJECT-TYPE
    SYNTAX      LSAP
    MAX-ACCESS  read-only
    STATUS      current
    DESCRIPTION 
        "The individual LLC address identifying this LSAP."
    REFERENCE   
        "IEEE 802.2 (ISO/IEC 8802-2), lLCAddress."
    ::= { lLCSAPEntry 2 }

lLCSAPRDE OBJECT-TYPE
    SYNTAX      TruthValue
    MAX-ACCESS  read-only
    STATUS      current
    DESCRIPTION 
        "A boolean value that, if set to true, means that RDE is 
         supported by this SAP."
    REFERENCE   
        "IEEE 802.2 (ISO/IEC 8802-2), rDE."
    ::= { lLCSAPEntry 3 }

rDESetup OBJECT IDENTIFIER
    ::= { x25Tables 13 }

rDESetupTable OBJECT-TYPE
    SYNTAX      SEQUENCE OF RDESetupEntry
    MAX-ACCESS  not-accessible
    STATUS      current
    DESCRIPTION 
        ""
    REFERENCE   
        "IEEE 802.2 (ISO/IEC 8802-2)."
    ::= { rDESetup 1 }

rDESetupEntry OBJECT-TYPE
    SYNTAX      RDESetupEntry
    MAX-ACCESS  not-accessible
    STATUS      current
    DESCRIPTION 
        ""
    REFERENCE   
        "IEEE 802.2 (ISO/IEC  8802-2)."
    INDEX       { rDESetupIndex }
    ::= { rDESetupTable 1 }

RDESetupEntry ::= SEQUENCE {
    rDESetupIndex                       InterfaceIndex,
    rDESetupAgingEnabled                TruthValue,
    rDESetupAgingValue                  Integer32,
    rDESetupEnableType2Reset            Integer32,
    rDESetupMaximumRouteDescriptors     Integer32,
    rDESetupMaximumResponseTime         TimeInterval,
    rDESetupMinimumPDUSize              Integer32,
    rDESetupRDEHold                     TruthValue,
    rDESetupRDEReplace                  TruthValue,
    rDESetupRDESetupName                Integer32,
    rDESetupResetOnTestEnabled          TruthValue
}

rDESetupIndex OBJECT-TYPE
    SYNTAX      InterfaceIndex
    MAX-ACCESS  not-accessible
    STATUS      current
    DESCRIPTION 
        ""
    REFERENCE   
        "IEEE 802.2 (ISO/IEC 8802-2)."
    ::= { rDESetupEntry 1 }

rDESetupAgingEnabled OBJECT-TYPE
    SYNTAX      TruthValue
    MAX-ACCESS  read-write
    STATUS      current
    DESCRIPTION 
        "A boolean value representing the policy that, when true, allows 
         a manager to age a route."
    REFERENCE   
        "IEEE 802.2 (ISO/IEC 8802-2)."
    ::= { rDESetupEntry 2 }

rDESetupAgingValue OBJECT-TYPE
    SYNTAX      Integer32
    MAX-ACCESS  read-write
    STATUS      current
    DESCRIPTION 
        "A value used to determine if a route should be flushed due to 
         inactivity for a specified time period."
    REFERENCE   
        "IEEE 802.2 (ISO/IEC 8802-2)."
    ::= { rDESetupEntry 3 }

rDESetupEnableType2Reset OBJECT-TYPE
    SYNTAX      Integer32
    MAX-ACCESS  read-write
    STATUS      current
    DESCRIPTION 
        ""
    REFERENCE   
        "IEEE 802.2 (ISO/IEC 8802-2)."
    ::= { rDESetupEntry 4 }

rDESetupMaximumRouteDescriptors OBJECT-TYPE
    SYNTAX      Integer32
    MAX-ACCESS  read-write
    STATUS      current
    DESCRIPTION 
        "The maximum number or route descriptors that an acceptable 
         route may contain."
    REFERENCE   
        "IEEE 802.2 (ISO/IEC 8802-2)."
    ::= { rDESetupEntry 5 }

rDESetupMaximumResponseTime OBJECT-TYPE
    SYNTAX      TimeInterval
    UNITS       "seconds"
    MAX-ACCESS  read-write
    STATUS      current
    DESCRIPTION 
        "The timer value used to limit the maximum route trip response 
         time allowed for route discovery and consequently the maximum 
         time a PDU can reamin in the system."
    REFERENCE   
        "IEEE 802.2 (ISO/IEC 8802-2)."
    ::= { rDESetupEntry 6 }

rDESetupMinimumPDUSize OBJECT-TYPE
    SYNTAX      Integer32
    MAX-ACCESS  read-write
    STATUS      current
    DESCRIPTION 
        "The minimum number of octets that must be supported by an 
         acceptable route as indicated by the LF bits of the routing 
         information field."
    REFERENCE   
        "IEEE 802.2 (ISO/IEC 8802-2)."
    ::= { rDESetupEntry 7 }

rDESetupRDEHold OBJECT-TYPE
    SYNTAX      TruthValue
    MAX-ACCESS  read-write
    STATUS      current
    DESCRIPTION 
        "A boolean value representing the policy that, when true, 
         requires RDE to withhold sending PDUs while changing routes."
    REFERENCE   
        "IEEE 802.2 (ISO/IEC 8802-2)."
    ::= { rDESetupEntry 8 }

rDESetupRDEReplace OBJECT-TYPE
    SYNTAX      TruthValue
    MAX-ACCESS  read-write
    STATUS      current
    DESCRIPTION 
        "A boolean value representing the policy that, when true, 
         enables the RDE to use the route selected by the remote 
         station."
    REFERENCE   
        "IEEE 802.2 (ISO/IEC 8802-2)."
    ::= { rDESetupEntry 9 }

rDESetupRDESetupName OBJECT-TYPE
    SYNTAX      Integer32
    MAX-ACCESS  read-only
    STATUS      current
    DESCRIPTION 
        "Naming attribute for the rDESetup managed object."
    REFERENCE   
        "IEEE 802.2 (ISO/IEC 8802-2)."
    ::= { rDESetupEntry 10 }

rDESetupResetOnTestEnabled OBJECT-TYPE
    SYNTAX      TruthValue
    MAX-ACCESS  read-write
    STATUS      current
    DESCRIPTION 
        "This attribute is a boolean value.  If the attribute is true, 
         then if a test frame is rceieved the source route is reset."
    REFERENCE   
        "IEEE 802.2 (ISO/IEC 8802-2)."
    ::= { rDESetupEntry 11 }

rDEPair OBJECT IDENTIFIER
    ::= { x25Tables 14 }

rDEPairTable OBJECT-TYPE
    SYNTAX      SEQUENCE OF RDEPairEntry
    MAX-ACCESS  not-accessible
    STATUS      current
    DESCRIPTION 
        "Provides a table that lists the pairing of local LSAP and MAC 
         with remote LSAP Id and MAC, as a pair for use by the route 
         determination entity (RDE)."
    REFERENCE   
        "IEEE 802.2 (ISO/IEC 8802-2)."
    ::= { rDEPair 1 }

rDEPairEntry OBJECT-TYPE
    SYNTAX      RDEPairEntry
    MAX-ACCESS  not-accessible
    STATUS      current
    DESCRIPTION 
        "Provides an entry into the rDEPairTable which represets the 
         route determination entity routing information for one local 
         LSAP/MAC and remote LSAPId/MAC pair.  The pair is indexed by 
         the rDEPairIndex which indicates the local LLC station and the 
         rDEPairName which indicates the remote LLC station."
    REFERENCE   
        "IEEE 802.2 (ISO/IEC 8802-2)."
    INDEX       { rDEPairIndex, rDEPairName }
    ::= { rDEPairTable 1 }

RDEPairEntry ::= SEQUENCE {
    rDEPairIndex                InterfaceIndex,
    rDEPairName                 OCTET STRING,
    rDEPairDiscardCounter       Counter32,
    rDEPairNSRPDUCounter        Counter32,
    rDEPairNSRSelectedCounter   Counter32,
    rDEPairRIF                  OCTET STRING,
    rDEPairSRFPDUCounter        Counter32,
    rDEPairQueryCounter         Counter32
}

rDEPairIndex OBJECT-TYPE
    SYNTAX      InterfaceIndex
    MAX-ACCESS  not-accessible
    STATUS      current
    DESCRIPTION 
        "Provides an index into the table.  This index is the same as 
         the ifIndex into the ifTable for the corresponding MAC/LLC LAN 
         station entry in the table.  The same value of ifIndex that 
         indicates the MAC/LLC LAN station in the ifTable table, 
         indicates the corresponding enry in this table."
    REFERENCE   
        "IEEE 802.2 (ISO/IEC 8802-2)."
    ::= { rDEPairEntry 1 }

rDEPairName OBJECT-TYPE
    SYNTAX      OCTET STRING (SIZE(7 | 9))
    MAX-ACCESS  not-accessible
    STATUS      current
    DESCRIPTION 
        "The local LSAP and remote LSAPId and the local and remote MAC 
         Addresses.  Because the local LSAP and local MAC address are 
         implied by this LAN station, only the remote LSAPId and remote 
         MAC are provided in this attribute.  The field is encoded as a 
         MacAddress textual convenstion (6 octet or 8 octet MAC address) 
         except that it is also followed by a single octet inicating the 
         remote LSAPId and can have values between 
         0 and 127."
    REFERENCE   
        "IEEE 802.2 (ISO/IEC 8802-2)."
    ::= { rDEPairEntry 2 }

rDEPairDiscardCounter OBJECT-TYPE
    SYNTAX      Counter32
    MAX-ACCESS  read-only
    STATUS      current
    DESCRIPTION 
        "A value that represents the number of times a new selection has 
         been made."
    REFERENCE   
        "IEEE 802.2 (ISO/IEC 8802-2)."
    ::= { rDEPairEntry 3 }

rDEPairNSRPDUCounter OBJECT-TYPE
    SYNTAX      Counter32
    MAX-ACCESS  read-only
    STATUS      current
    DESCRIPTION 
        "A value that represents the number of frames without a routing 
         field."
    REFERENCE   
        "IEEE 802.2 (ISO/IEC 8802-2)."
    ::= { rDEPairEntry 4 }

rDEPairNSRSelectedCounter OBJECT-TYPE
    SYNTAX      Counter32
    MAX-ACCESS  read-only
    STATUS      current
    DESCRIPTION 
        "A value that represents the number of times that acceptable SRF 
         route existed resulting in the selection of the NSR path."
    REFERENCE   
        "IEEE 802.2 (ISO/IEC 8802-2)."
    ::= { rDEPairEntry 5 }

rDEPairRIF OBJECT-TYPE
    SYNTAX      OCTET STRING (SIZE(0..30))
    MAX-ACCESS  read-write
    STATUS      current
    DESCRIPTION 
        "The routing information field varies in length up to 30 octets.  
         When source routing is not used the RIF is said to be NULL and 
         contains no information.  The first bit of the MAC source 
         address is defined as the Routing Information Indicator (RII). 
         When the RIF is null, the RII is set to zero (0).  When the RIF 
         is not null, the RII is set to 1.  The first two octets are the 
         Routing Control field (RC) and the remainder of the RIF 
         contains Routing Descriptors (RD).  Each RD is two octets in 
         length, therefore a maximum of 14 RDs can exists in a RIF."
    REFERENCE   
        "IEEE 802.2 (ISO/IEC 8802-2)."
    ::= { rDEPairEntry 6 }

rDEPairSRFPDUCounter OBJECT-TYPE
    SYNTAX      Counter32
    MAX-ACCESS  read-only
    STATUS      current
    DESCRIPTION 
        "A value that represents the number of frames with routing 
         field."
    REFERENCE   
        "IEEE 802.2 (ISO/IEC 8802-2)."
    ::= { rDEPairEntry 7 }

rDEPairQueryCounter OBJECT-TYPE
    SYNTAX      Counter32
    MAX-ACCESS  read-only
    STATUS      current
    DESCRIPTION 
        "A value that represents the numer of Route Query commands 
         generated."
    REFERENCE   
        "IEEE 802.2 (ISO/IEC 8802-2)."
    ::= { rDEPairEntry 8 }

lLCCLPM OBJECT IDENTIFIER
    ::= { x25Tables 15 }

lLCCLPMTable OBJECT-TYPE
    SYNTAX      SEQUENCE OF LLCCLPMEntry
    MAX-ACCESS  not-accessible
    STATUS      current
    DESCRIPTION 
        "The LLC Connectionless Protocol Machine managed object.  The 
         generic LLC Connectionless PM MO from which protocol-specific 
         LLC PM MOs bay be derived."
    REFERENCE   
        "ITU-T Rec. X.282 | ISO/IEC 10742"
    ::= { lLCCLPM 1 }

lLCCLPMEntry OBJECT-TYPE
    SYNTAX      LLCCLPMEntry
    MAX-ACCESS  not-accessible
    STATUS      current
    DESCRIPTION 
        "The CL PM is contaned by a datalinkEntity, in this case a 
         lLCDLE."
    REFERENCE   
        "ITU-T Rec. X.282 | ISO/IEC 10742"
    INDEX       { lLCCLPMClProtocolMachineId }
    ::= { lLCCLPMTable 1 }

LLCCLPMEntry ::= SEQUENCE {
    lLCCLPMClProtocolMachineId  SimpleNameType,
    lLCCLPMOperationalState     OperationalState,
    lLCCLPMTotalRemoteSAPs      Integer32
}

lLCCLPMClProtocolMachineId OBJECT-TYPE
    SYNTAX      SimpleNameType
    MAX-ACCESS  not-accessible
    STATUS      current
    DESCRIPTION 
        ""
    ::= { lLCCLPMEntry 1 }

lLCCLPMOperationalState OBJECT-TYPE
    SYNTAX      OperationalState
    MAX-ACCESS  read-only
    STATUS      current
    DESCRIPTION 
        ""
    ::= { lLCCLPMEntry 2 }

lLCCLPMTotalRemoteSAPs OBJECT-TYPE
    SYNTAX      Integer32
    MAX-ACCESS  read-only
    STATUS      current
    DESCRIPTION 
        ""
    ::= { lLCCLPMEntry 3 }

lLCConnectionless OBJECT IDENTIFIER
    ::= { x25Tables 16 }

lLCConnectionlessTable OBJECT-TYPE
    SYNTAX      SEQUENCE OF LLCConnectionlessEntry
    MAX-ACCESS  not-accessible
    STATUS      current
    DESCRIPTION 
        "lLCConnectionless MOC. This clause contains those attributes, 
         actions, and event notifications associated with an LLC 
         connectionless environment.  This managed object class is 
         responsible for processing the attributes, actions and 
         notifications that are associated with the LLC connectionless 
         service.
         
         The managed object class is derived from the lLCCLPM LLC 
         connectionless protocol machine managed object class, and is 
         also contained by an instance of the lLCCLPM with the 
         lLCClessName as the relative name."
    REFERENCE   
        "IEEE 802.2 (ISO/IEC 8802-2), lLCConnectionless MOC"
    ::= { lLCConnectionless 1 }

lLCConnectionlessEntry OBJECT-TYPE
    SYNTAX      LLCConnectionlessEntry
    MAX-ACCESS  not-accessible
    STATUS      current
    DESCRIPTION 
        ""
    REFERENCE   
        "IEEE 802.2 (ISO/IEC 8802-2), lLCConnectionless MO"
    INDEX       { lLCCLPMClProtocolMachineId, lLCCLPMClProtocolMachineId }
    ::= { lLCConnectionlessTable 1 }

LLCConnectionlessEntry ::= SEQUENCE {
    lLCConnectionlessName                               SimpleNameType,
    lLCConnectionlessMaximumLLCInformationFieldSize     Integer32,
    lLCConnectionlessTESTReceivedABBResponse            Counter32,
    lLCConnectionlessTESTReceivedCommand                Counter32,
    lLCConnectionlessTESTReceivedResponse               Counter32,
    lLCConnectionlessTESTSentABBResponse                Counter32,
    lLCConnectionlessTESTSentCommand                    Counter32,
    lLCConnectionlessTESTSentResponse                   Counter32,
    lLCConnectionlessUIReceived                         Counter32,
    lLCConnectionlessUISent                             Counter32,
    lLCConnectionlessXIDReceivedCommand                 Counter32,
    lLCConnectionlessXIDReceivedResponse                Counter32,
    lLCConnectionlessXIDSentCommand                     Counter32,
    lLCConnectionlessXIDSentResponse                    Counter32
}

lLCConnectionlessName OBJECT-TYPE
    SYNTAX      SimpleNameType
    MAX-ACCESS  read-write
    STATUS      current
    DESCRIPTION 
        "Provides the name of the higher level entity associated with 
         this object class.
         
         Because the lLCConnectionlessName is used as a relative name 
         within the containing lLCCLPM table entry, all 
         lLCConnectionless entries with the same indexed lLCCLPM table 
         entry must have unique names."
    REFERENCE   
        "IEEE 802.2 (ISO/IEC 8802-2) lLCClessName."
    ::= { lLCConnectionlessEntry 1 }

lLCConnectionlessMaximumLLCInformationFieldSize OBJECT-TYPE
    SYNTAX      Integer32
    MAX-ACCESS  read-write
    STATUS      current
    DESCRIPTION 
        "The maximum length SDU that the LSAP will accomodate.  For 
         Ethernet 10baseT and 100baseT LANs this is typically the 1500 
         byte MTU minus the SNAP header, minus the address fields and 
         command field, or 1492 bytes."
    REFERENCE   
        "IEEE 802.2 (ISO/IEC 8802-2) maximumLLCInformationFieldSize."
    ::= { lLCConnectionlessEntry 2 }

lLCConnectionlessTESTReceivedABBResponse OBJECT-TYPE
    SYNTAX      Counter32
    MAX-ACCESS  read-only
    STATUS      current
    DESCRIPTION 
        "Provides a count of TEST responses received by this LSAP 
         without the LSDU due to limited resources at the remote 
         station."
    REFERENCE   
        "IEEE 802.2 (ISO/IEC 8802-2) tESTReceivedABBResponse."
    ::= { lLCConnectionlessEntry 3 }

lLCConnectionlessTESTReceivedCommand OBJECT-TYPE
    SYNTAX      Counter32
    MAX-ACCESS  read-only
    STATUS      current
    DESCRIPTION 
        "Provides a count of TEST commands received from the MAC 
         sublayer by this LSAP.  This includes commands recieved with 
         any group address recognized by this LSAP."
    REFERENCE   
        "IEEE 802.2 (ISO/IEC 8802-2) tESTReceivedCommand."
    ::= { lLCConnectionlessEntry 4 }

lLCConnectionlessTESTReceivedResponse OBJECT-TYPE
    SYNTAX      Counter32
    MAX-ACCESS  read-only
    STATUS      current
    DESCRIPTION 
        "Provides a count of TEST responses received from the MAC 
         sublayer by this LSAP."
    REFERENCE   
        "IEEE 802.2 (ISO/IEC 8802-2) tESTReceivedResponse."
    ::= { lLCConnectionlessEntry 5 }

lLCConnectionlessTESTSentABBResponse OBJECT-TYPE
    SYNTAX      Counter32
    MAX-ACCESS  read-only
    STATUS      current
    DESCRIPTION 
        "Provides a count of TEST responses that were delivered to the 
         MAC without the LSDU data due to limited resources."
    REFERENCE   
        "IEEE 802.2 (ISO/IEC 8802-2) tESTSentABBResponse."
    ::= { lLCConnectionlessEntry 6 }

lLCConnectionlessTESTSentCommand OBJECT-TYPE
    SYNTAX      Counter32
    MAX-ACCESS  read-only
    STATUS      current
    DESCRIPTION 
        "Provides a count of TEST command set to the MAC sublayer by 
         this LSAP."
    REFERENCE   
        "IEEE 802.2 (ISO/IEC 8802-2) tESTSentCommand."
    ::= { lLCConnectionlessEntry 7 }

lLCConnectionlessTESTSentResponse OBJECT-TYPE
    SYNTAX      Counter32
    MAX-ACCESS  read-only
    STATUS      current
    DESCRIPTION 
        "Provides a count of TEST responses sent to the MAC sublayer by 
         this LSAP."
    REFERENCE   
        "IEEE 802.2 (ISO/IEC 8802-2) tESTSentResponse."
    ::= { lLCConnectionlessEntry 8 }

lLCConnectionlessUIReceived OBJECT-TYPE
    SYNTAX      Counter32
    MAX-ACCESS  read-only
    STATUS      current
    DESCRIPTION 
        "Provides a count of user data PDUs that were received by the 
         LSAP from the MAC sublayer and passed to the user layer.  This 
         includes commands received with group addresses of which the 
         LSAP is a member."
    REFERENCE   
        "IEEE 802.2 (ISO/IEC 8802-2) uIReceived."
    ::= { lLCConnectionlessEntry 9 }

lLCConnectionlessUISent OBJECT-TYPE
    SYNTAX      Counter32
    MAX-ACCESS  read-only
    STATUS      current
    DESCRIPTION 
        "Provides a count of user data PDUs that were accepted by the 
         LSAP from the user layer and delivered to the MAC sublayer."
    REFERENCE   
        "IEEE 802.2 (ISO/IEC 8802-2) uISent."
    ::= { lLCConnectionlessEntry 10 }

lLCConnectionlessXIDReceivedCommand OBJECT-TYPE
    SYNTAX      Counter32
    MAX-ACCESS  read-only
    STATUS      current
    DESCRIPTION 
        "Proivdes a count of XID commands received from the MAC sublayer 
         by this LSAP.  This includes commands received with any group 
         address recognized by this LSAP."
    REFERENCE   
        "IEEE 802.2 (ISO/IEC 8802-2) xIDReceivedCommand."
    ::= { lLCConnectionlessEntry 11 }

lLCConnectionlessXIDReceivedResponse OBJECT-TYPE
    SYNTAX      Counter32
    MAX-ACCESS  read-only
    STATUS      current
    DESCRIPTION 
        "Provides a count of XID responses received from the MAC 
         sublayer by this LSAP."
    REFERENCE   
        "IEEE 802.2 (ISO/IEC 8802-2) xIDReceivedResponse."
    ::= { lLCConnectionlessEntry 12 }

lLCConnectionlessXIDSentCommand OBJECT-TYPE
    SYNTAX      Counter32
    MAX-ACCESS  read-only
    STATUS      current
    DESCRIPTION 
        "Provides a count of XID commands sent to the MAC sublayer by 
         this LSAP."
    REFERENCE   
        "IEEE 802.2 (ISO/IEC 8802-2) xIDSentCommand."
    ::= { lLCConnectionlessEntry 13 }

lLCConnectionlessXIDSentResponse OBJECT-TYPE
    SYNTAX      Counter32
    MAX-ACCESS  read-only
    STATUS      current
    DESCRIPTION 
        "Provides a count of the XID responses sent to the MAC sublayer 
         by this LSAP."
    REFERENCE   
        "IEEE 802.2 (ISO/IEC 8802-2) xIDSentResponse."
    ::= { lLCConnectionlessEntry 14 }

lLCCOPM OBJECT IDENTIFIER
    ::= { x25Tables 17 }

lLCCOPMTable OBJECT-TYPE
    SYNTAX      SEQUENCE OF LLCCOPMEntry
    MAX-ACCESS  not-accessible
    STATUS      current
    DESCRIPTION 
        "The LLC Connection-mode Protocol Machine managed object.  The 
         generic LLC Connection-mode PM MO from which protocol specific 
         LLC PM MOs may be derived."
    REFERENCE   
        "ITU-T Rec. X.282 | ISO/IEC 10742"
    ::= { lLCCOPM 1 }

lLCCOPMEntry OBJECT-TYPE
    SYNTAX      LLCCOPMEntry
    MAX-ACCESS  not-accessible
    STATUS      current
    DESCRIPTION 
        "The CO PM is contaned by a datalinkEntity, in this case a 
         lLCDLE."
    REFERENCE   
        "ITU-T Rec. X.282 | ISO/IEC 10742"
    INDEX       { lLCCOPMCoProtocolMachineId }
    ::= { lLCCOPMTable 1 }

LLCCOPMEntry ::= SEQUENCE {
    lLCCOPMCoProtocolMachineId  SimpleNameType,
    lLCCOPMOperationalState     OperationalState
}

lLCCOPMCoProtocolMachineId OBJECT-TYPE
    SYNTAX      SimpleNameType
    MAX-ACCESS  not-accessible
    STATUS      current
    DESCRIPTION 
        ""
    ::= { lLCCOPMEntry 1 }

lLCCOPMOperationalState OBJECT-TYPE
    SYNTAX      OperationalState
    MAX-ACCESS  read-only
    STATUS      current
    DESCRIPTION 
        ""
    ::= { lLCCOPMEntry 2 }

lLCConnection2 OBJECT IDENTIFIER
    ::= { x25Tables 18 }

lLCConnection2Table OBJECT-TYPE
    SYNTAX      SEQUENCE OF LLCConnection2Entry
    MAX-ACCESS  not-accessible
    STATUS      current
    DESCRIPTION 
        "The Connection component is responsible for processing the 
         events that affect a specific data link connection for Type 2 
         procedures only.  One connection component shall exist for each 
         data link connection supported in the LLC entity.
         
         LLCConnection2 managed object.  This clause contains those 
         attributes, actions, and event notifications associated with an 
         LLC Type 2 (connection) environment.  This managed object is 
         responsible for processing the events that affect the current 
         data link connection during its lifetime (i.e., timeframe of 
         link established until link disconnect).  One LLC Connection 
         managed object shall exist for each data link (LLC Type 
         2) connection supported in the LLC entity.
         
         The managed object is derived from the iLLCCOPM LLC 
         connection-oriented protocol machine managed object lcass, and 
         is also contained by an instance of the lLCCOPM with the 
         lLCConnection2Name as the relative name.
         
         Provides a table of statistics for each LLC2 connection to a 
         remote LLC2 station.
         
         Provides a table of configuration for each LLC2 connection to a 
         remote LLC2 station.  This table provides the configuration 
         (non-statistical) atribtues for the lLCConnection2 managed 
         object from ISO/IEC 8802-2 (IEEE 802.2).  It includes 
         attributes from both mandatory and conditional packages.  
         Attributes that belong to conditional packages in the GDMOs 
         have a default value that reperesents the feature being 
         disabled.
         
         The table is indexed by the ifIndex into the ifTable that 
         represents the local MAC coupled with the Remote MAC Address 
         and LSAP that represents the specific connection."
    REFERENCE   
        "IEEE 802.2 (ISO/IEC 8802-2), lLCConnection2 MOC."
    ::= { lLCConnection2 1 }

lLCConnection2Entry OBJECT-TYPE
    SYNTAX      LLCConnection2Entry
    MAX-ACCESS  not-accessible
    STATUS      current
    DESCRIPTION 
        "Each entry in this table represents an instance of the 
         lLCConnection2 managed object class.  Each instance oft the 
         lLCConnection2 managed object lcass is responsible  for 
         processing the events that affect the current data link 
         connection during its lifetime (i.e., timeframe of link 
         established until link disconnect).  One lLCConnection2 manged 
         object instance shall exist for each data link (LLC Type 2) 
         conenction supported in the LLC entity.
         
         Provides an entry in the X.25 LLC2 Connection table for one 
         LLC2 connection to a remote station.  Each connection is 
         indexed by its ifIndex into the interface table plus a 
         connection identifier.  Each connection is associated with a 
         unique remote DLSAP (MAC address and LSAP), used as a secondary 
         index into this table.
         
         Provides an entry in the X.25 LLC2 Connection table for one LLC 
         connection to a remote station.  Each connection is indexed by 
         its ifIndex into the interface table plus a connection 
         identifier.  Each connection is associated with a unique remote 
         DLSAP (MAC addres and LSAP)."
    REFERENCE   
        "IEEE 802.2 (ISO/IEC 8802-2), lLCConnection2 MO."
    INDEX       { lLCCOPMCoProtocolMachineId, lLCCOPMCoProtocolMachineId }
    ::= { lLCConnection2Table 1 }

LLCConnection2Entry ::= SEQUENCE {
    lLCConnection2Name                      SimpleNameType,
    lLCConnection2MaximumRetransmissions    Integer32,
    lLCConnection2ReceivedWindowSize        Integer32,
    lLCConnection2SendWindowSize            Integer32,
    lLCConnection2AcknowledgeTimeoutValue   TimeInterval,
    lLCConnection2BusyStateTimeoutValue     TimeInterval,
    lLCConnection2PBitTimeoutValue          TimeInterval,
    lLCConnection2RejectTimeoutValue        TimeInterval,
    lLCConnection2LocalBusy                 Counter32,
    lLCConnection2RemoteBusy                Counter32,
    lLCConnection2RemoteReset               Counter32,
    lLCConnection2LocalReset                Counter32,
    lLCConnection2ProviderReset             Counter32,
    lLCConnection2Route                     OCTET STRING,
    lLCConnection2KStep                     Integer32,
    lLCConnection2MaxSendWindowSize         Integer32,
    lLCConnection2ReceivedI                 Counter32,
    lLCConnection2SentI                     Counter32,
    lLCConnection2SentAcks                  Counter32,
    lLCConnection2ReceivedAcks              Counter32,
    lLCConnection2ReceivedFRMR              Counter32,
    lLCConnection2SentFRMR                  Counter32,
    lLCConnection2ReceivedRR                Counter32,
    lLCConnection2SentRR                    Counter32,
    lLCConnection2ReceivedRNR               Counter32,
    lLCConnection2SentRNR                   Counter32,
    lLCConnection2ReceivedREJ               Counter32,
    lLCConnection2SentREJ                   Counter32,
    lLCConnection2ReceivedSABME             Counter32,
    lLCConnection2SentSABME                 Counter32,
    lLCConnection2ReceivedUA                Counter32,
    lLCConnection2SentUA                    Counter32,
    lLCConnection2ReceivedDISC              Counter32,
    lLCConnection2SentDISC                  Counter32,
    lLCConnection2ReceivedDM                Counter32,
    lLCConnection2SentDM                    Counter32,
    lLCConnection2PDUsDiscarded1            Counter32,
    lLCConnection2PDUsDiscarded2            Counter32,
    lLCConnection2PDURetransmissions        Counter32,
    lLCConnection2OptionalTolerationIPDUs   TruthValue,
    lLCConnection2DuplicateIPDUsReceived    Counter32,
    lLCConnection2Violation                 Counter32,
    lLCConnection2ProtocolState             INTEGER,
    lLCConnection2AdministrativeState       AdministrativeState,
    lLCConnection2OperationalState          OperationalState,
    lLCConnection2UsageState                UsageState,
    lLCConnection2ProceduralStatus          ProceduralStatus,
    lLCConnection2AlarmStatus               AlarmStatus
}

lLCConnection2Name OBJECT-TYPE
    SYNTAX      SimpleNameType
    MAX-ACCESS  read-write
    STATUS      current
    DESCRIPTION 
        "The localLSAP and remoteLSAPId and the local and remote 
         MacAddress.
         
         Because the lLCConnection2Name is used as a relative name 
         within the containing lLCCOPM table entry, all lLCConnection2 
         entries with the same indexed lLCCOPM table entry must have 
         unique names.
         
         Provides an index in to the ifTable that identifies the primary 
         MAC interface through which multilple LLC2 connections are 
         esablished.
         
         Provides a connection identifier that identifies the explicit 
         connection made via the MAC device identified by the 
         lLCConnection2StatsIndex above.  These two fields form the 
         index and identify the specific LLC2 connection within this 
         host."
    REFERENCE   
        "IEEE 802.2 (ISO/IEC 8802-2) lLCConnection2Name."
    ::= { lLCConnection2Entry 1 }

lLCConnection2MaximumRetransmissions OBJECT-TYPE
    SYNTAX      Integer32
    MAX-ACCESS  read-write
    STATUS      current
    DESCRIPTION 
        "The number of times that the LLC Type 2 should attempt to 
         realize a successful PDU transfer."
    REFERENCE   
        "IEEE 802.2 (ISO/IEC 8802-2) maximumRetransmissions."
    ::= { lLCConnection2Entry 2 }

lLCConnection2ReceivedWindowSize OBJECT-TYPE
    SYNTAX      Integer32
    MAX-ACCESS  read-write
    STATUS      current
    DESCRIPTION 
        "The value of the receive window."
    REFERENCE   
        "IEEE 802.2 (ISO/IEC 8802-2) receivedWindowSize."
    ::= { lLCConnection2Entry 3 }

lLCConnection2SendWindowSize OBJECT-TYPE
    SYNTAX      Integer32
    MAX-ACCESS  read-write
    STATUS      current
    DESCRIPTION 
        "The value of the send window."
    REFERENCE   
        "IEEE 802.2 (ISO/IEC 8802-2) sendWindowSize."
    ::= { lLCConnection2Entry 4 }

lLCConnection2AcknowledgeTimeoutValue OBJECT-TYPE
    SYNTAX      TimeInterval
    UNITS       "seconds"
    MAX-ACCESS  read-write
    STATUS      current
    DESCRIPTION 
        "This attribute defines the time interval during which the LLC 
         shall expect to receive an acknowledgment to one or more 
         outstanding I PDUs or an expected response PDU to a sent 
         unnumbered command PDU.  This value is measured in centiseconds 
         and displayed in seconds."
    REFERENCE   
        "IEEE 802.2 (ISO/IEC 8802-2), type2AcknowledgeTimeoutValue, 
         7.4.1, 7.4.3, 7.4.5, 7.5, 7.5.5, 7.5.9, 7.6, 7.8.1.1, 7.9.2, 
         7.9.2.2, and 7.9.2.3."
    ::= { lLCConnection2Entry 5 }

lLCConnection2BusyStateTimeoutValue OBJECT-TYPE
    SYNTAX      TimeInterval
    UNITS       "seconds"
    MAX-ACCESS  read-write
    STATUS      current
    DESCRIPTION 
        "This attribute defines the time interval during which the LLC 
         shall wait for an indication of the clearance of a busy 
         condition at the other LLC.  This time value is measured in 
         centiseconds and displayed in seconds."
    REFERENCE   
        "IEEE 802.2 (ISO/IEC 8802-2), type2BusyStateTimeoutValue, 7.5.7, 
         7.5.9, 7.8.1.4, 7.9.2, 7.9.2.2, and 7.9.2.3."
    ::= { lLCConnection2Entry 6 }

lLCConnection2PBitTimeoutValue OBJECT-TYPE
    SYNTAX      TimeInterval
    UNITS       "seconds"
    MAX-ACCESS  read-write
    STATUS      current
    DESCRIPTION 
        "The P-bit timer defines the time interval during which the LLC 
         shall expect to receive a PDU with the F bit set to '1' in 
         response to a sent Type 2 command with the P bit set to '1'. 
         This value is measured in centiseconds and dsiplayed in 
         seconds."
    REFERENCE   
        "IEEE 802.2 (ISO/IEC 8802-2), type2BitTimeoutValue, 7.5.9, 
         7.8.1.2, 7.9.2, 7.9.2.2, and 7.9.2.3."
    ::= { lLCConnection2Entry 7 }

lLCConnection2RejectTimeoutValue OBJECT-TYPE
    SYNTAX      TimeInterval
    UNITS       "seconds"
    MAX-ACCESS  read-write
    STATUS      current
    DESCRIPTION 
        "The Reject timer defines the time interval during which the LLC 
         shall expect to receive a reply to a sent REJ PDU. This value 
         is measured in centiseconds and displayed in seconds."
    REFERENCE   
        "IEEE 802.2 (ISO/IEC 8802-2), type2RejectTimeoutValue, 
         7.5.4, 7.8.1.3, 7.9.2, 7.9.2.2, and 7.9.2.3."
    ::= { lLCConnection2Entry 8 }

lLCConnection2LocalBusy OBJECT-TYPE
    SYNTAX      Counter32
    MAX-ACCESS  read-only
    STATUS      current
    DESCRIPTION 
        "Provides a count of the occurences of entry into the busy 
         condition."
    REFERENCE   
        "IEEE 802.2 (ISO/IEC 8802-2) localBusy."
    ::= { lLCConnection2Entry 9 }

lLCConnection2RemoteBusy OBJECT-TYPE
    SYNTAX      Counter32
    UNITS       "PDUs"
    MAX-ACCESS  read-only
    STATUS      current
    DESCRIPTION 
        "Provides a count of the RNR PDUs received when the remote busy 
         condition is not already set."
    REFERENCE   
        "IEEE 802.2 (ISO/IEC 8802-2) remoteBusy."
    ::= { lLCConnection2Entry 10 }

lLCConnection2RemoteReset OBJECT-TYPE
    SYNTAX      Counter32
    UNITS       "PDUs"
    MAX-ACCESS  read-only
    STATUS      current
    DESCRIPTION 
        "Provides a count of instances of partner-initiated reset (SABME 
         PDU received in a connected state)."
    REFERENCE   
        "IEEE 802.2 (ISO/IEC 8802-2) remoteReset."
    ::= { lLCConnection2Entry 11 }

lLCConnection2LocalReset OBJECT-TYPE
    SYNTAX      Counter32
    UNITS       "requests"
    MAX-ACCESS  read-only
    STATUS      current
    DESCRIPTION 
        "Provides a count of the instances of user request for reset 
         while in the connected state."
    REFERENCE   
        "IEEE 802.2 (ISO/IEC 8802-2) localReset."
    ::= { lLCConnection2Entry 12 }

lLCConnection2ProviderReset OBJECT-TYPE
    SYNTAX      Counter32
    UNITS       "resets"
    MAX-ACCESS  read-only
    STATUS      current
    DESCRIPTION 
        "Provides a count of the instances of provider-initiated reset 
         due to FRMR PDU sent, FRMR received, or retry exhaustion."
    REFERENCE   
        "IEEE 802.2 (ISO/IEC 8802-2) providerReset."
    ::= { lLCConnection2Entry 13 }

lLCConnection2Route OBJECT-TYPE
    SYNTAX      OCTET STRING (SIZE(4))
    MAX-ACCESS  read-write
    STATUS      current
    DESCRIPTION 
        "This is a conditional part of the LSAP Pair Object. It is 
         present if source routing is used and the LSAP Pair is 
         cognizant of its route. This attribute is used by the LSAP Pair 
         to communicate. Source Routing is described in ISO/IEC 10038 : 
         1993 (IEEE 802.1D 1993).
         
         The syntax of the octet string is as follows:
         
         RoutingControl ::= OCTET STRING(SIZE(2))
         RoutingDescriptors ::= OCTET STRING(SIZE(2))
         Route ::= SEQUENCE {
             routingControl [0] IMPLICIT RoutingControl,
             routingDescriptors [1] IMPLICIT RoutingDescriptors }"
    REFERENCE   
        "IEEE 802.2 (ISO/IEC 8802-2), route, IEEE 802.2D 1993 (ISO/IEC 
         10038 : 1993)."
    ::= { lLCConnection2Entry 14 }

lLCConnection2KStep OBJECT-TYPE
    SYNTAX      Integer32
    MAX-ACCESS  read-write
    STATUS      current
    DESCRIPTION 
        "The value of the flow control parameter."
    REFERENCE   
        "IEEE 802.2 (ISO/IEC 8802-2) kStep."
    ::= { lLCConnection2Entry 15 }

lLCConnection2MaxSendWindowSize OBJECT-TYPE
    SYNTAX      Integer32
    MAX-ACCESS  read-write
    STATUS      current
    DESCRIPTION 
        "The maximum size of the send window."
    REFERENCE   
        "IEEE 802.2 (ISO/IEC 8802-2) sendWindowSize."
    ::= { lLCConnection2Entry 16 }

lLCConnection2ReceivedI OBJECT-TYPE
    SYNTAX      Counter32
    MAX-ACCESS  read-only
    STATUS      current
    DESCRIPTION 
        "Provides a count of the number of I PDUs received from the MAC 
         and passed to the LLC user on this connection."
    REFERENCE   
        "IEEE 802.2 (ISO/IEC 8802-2) type2ReceivedI."
    ::= { lLCConnection2Entry 17 }

lLCConnection2SentI OBJECT-TYPE
    SYNTAX      Counter32
    MAX-ACCESS  read-only
    STATUS      current
    DESCRIPTION 
        "Provides a count of the number of I PDUs delivered to the MAC 
         on this connection."
    REFERENCE   
        "IEEE 802.2 (ISO/IEC 8802-2) type2SentI."
    ::= { lLCConnection2Entry 18 }

lLCConnection2SentAcks OBJECT-TYPE
    SYNTAX      Counter32
    MAX-ACCESS  read-only
    STATUS      current
    DESCRIPTION 
        "Provides a count of the number of acknowledgments sent for 
         received I PDUs on this connection."
    REFERENCE   
        "IEEE 802.2 (ISO/IEC 8802-2) sentAcks."
    ::= { lLCConnection2Entry 19 }

lLCConnection2ReceivedAcks OBJECT-TYPE
    SYNTAX      Counter32
    MAX-ACCESS  read-only
    STATUS      current
    DESCRIPTION 
        "Provides a count of the number of I PDUs acknowledged by 
         connection partner on this connection."
    REFERENCE   
        "IEEE 802.2 (ISO/IEC 8802-2) receivedAcks."
    ::= { lLCConnection2Entry 20 }

lLCConnection2ReceivedFRMR OBJECT-TYPE
    SYNTAX      Counter32
    MAX-ACCESS  read-only
    STATUS      current
    DESCRIPTION 
        "Provides a count of the number of FRMR PDUs received from the 
         MAC and not discarded on this connection."
    REFERENCE   
        "IEEE 802.2 (ISO/IEC 8802-2) type2ReceivedFRMR."
    ::= { lLCConnection2Entry 21 }

lLCConnection2SentFRMR OBJECT-TYPE
    SYNTAX      Counter32
    MAX-ACCESS  read-only
    STATUS      current
    DESCRIPTION 
        "Provides a count of the number of FRMR PDUs delivered to the 
         MAC on this connection."
    REFERENCE   
        "IEEE 802.2 (ISO/IEC 8802-2) type2SentFRMR."
    ::= { lLCConnection2Entry 22 }

lLCConnection2ReceivedRR OBJECT-TYPE
    SYNTAX      Counter32
    MAX-ACCESS  read-only
    STATUS      current
    DESCRIPTION 
        "Provides a count of the number of RR PDUs received from the MAC 
         and not discarded on this connection."
    REFERENCE   
        "IEEE 802.2 (ISO/IEC 8802-2) type2ReceivedRR."
    ::= { lLCConnection2Entry 23 }

lLCConnection2SentRR OBJECT-TYPE
    SYNTAX      Counter32
    MAX-ACCESS  read-only
    STATUS      current
    DESCRIPTION 
        "Provides a count of the number of RR PDUs delivered to  the MAC 
         on this connection."
    REFERENCE   
        "IEEE 802.2 (ISO/IEC 8802-2) type2SentRR."
    ::= { lLCConnection2Entry 24 }

lLCConnection2ReceivedRNR OBJECT-TYPE
    SYNTAX      Counter32
    MAX-ACCESS  read-only
    STATUS      current
    DESCRIPTION 
        "Provides a count of the number of RNR PDUs received from the 
         MAC and not discarded on this connection."
    REFERENCE   
        "IEEE 802.2 (ISO/IEC 8802-2) type2ReceivedRNR."
    ::= { lLCConnection2Entry 25 }

lLCConnection2SentRNR OBJECT-TYPE
    SYNTAX      Counter32
    MAX-ACCESS  read-only
    STATUS      current
    DESCRIPTION 
        "Provides a count of the number of RNR PDUs delivered to  the 
         MAC on this connection."
    REFERENCE   
        "IEEE 802.2 (ISO/IEC 8802-2) type2SentRNR."
    ::= { lLCConnection2Entry 26 }

lLCConnection2ReceivedREJ OBJECT-TYPE
    SYNTAX      Counter32
    MAX-ACCESS  read-only
    STATUS      current
    DESCRIPTION 
        "Provides a count of the number of REJ PDUs received from the 
         MAC and not discarded on this connection."
    REFERENCE   
        "IEEE 802.2 (ISO/IEC 8802-2) type2ReceivedREJ."
    ::= { lLCConnection2Entry 27 }

lLCConnection2SentREJ OBJECT-TYPE
    SYNTAX      Counter32
    MAX-ACCESS  read-only
    STATUS      current
    DESCRIPTION 
        "Provides a count of the number of REJ PDUs delivered to  the 
         MAC on this connection."
    REFERENCE   
        "IEEE 802.2 (ISO/IEC 8802-2) type2SentREJ."
    ::= { lLCConnection2Entry 28 }

lLCConnection2ReceivedSABME OBJECT-TYPE
    SYNTAX      Counter32
    MAX-ACCESS  read-only
    STATUS      current
    DESCRIPTION 
        "Provides a count of the number of SABME PDUs received from the 
         MAC and not discarded on this connection."
    REFERENCE   
        "IEEE 802.2 (ISO/IEC 8802-2) type2ReceivedSABME."
    ::= { lLCConnection2Entry 29 }

lLCConnection2SentSABME OBJECT-TYPE
    SYNTAX      Counter32
    MAX-ACCESS  read-only
    STATUS      current
    DESCRIPTION 
        "Provides a count of the number of SABME PDUs delivered to the 
         MAC  on this connection."
    REFERENCE   
        "IEEE 802.2 (ISO/IEC 8802-2) type2SentSABME."
    ::= { lLCConnection2Entry 30 }

lLCConnection2ReceivedUA OBJECT-TYPE
    SYNTAX      Counter32
    MAX-ACCESS  read-only
    STATUS      current
    DESCRIPTION 
        "Provides a count of the number of UA PDUs received from the MAC 
         and not discarded on this connection."
    REFERENCE   
        "IEEE 802.2 (ISO/IEC 8802-2) type2ReceivedUA."
    ::= { lLCConnection2Entry 31 }

lLCConnection2SentUA OBJECT-TYPE
    SYNTAX      Counter32
    MAX-ACCESS  read-only
    STATUS      current
    DESCRIPTION 
        "Provides a count of the number of UA PDUs delivered to  the MAC 
         on this connection."
    REFERENCE   
        "IEEE 802.2 (ISO/IEC 8802-2) type2SentUA."
    ::= { lLCConnection2Entry 32 }

lLCConnection2ReceivedDISC OBJECT-TYPE
    SYNTAX      Counter32
    MAX-ACCESS  read-only
    STATUS      current
    DESCRIPTION 
        "Provides a count of the number of DISC PDUs received from the 
         MAC and not discarded on this connection."
    REFERENCE   
        "IEEE 802.2 (ISO/IEC 8802-2) type2ReceivedDISC."
    ::= { lLCConnection2Entry 33 }

lLCConnection2SentDISC OBJECT-TYPE
    SYNTAX      Counter32
    MAX-ACCESS  read-only
    STATUS      current
    DESCRIPTION 
        "Provides a count of the number of DISC PDUs delivered to the 
         MAC  on this connection."
    REFERENCE   
        "IEEE 802.2 (ISO/IEC 8802-2) type2SentDISC."
    ::= { lLCConnection2Entry 34 }

lLCConnection2ReceivedDM OBJECT-TYPE
    SYNTAX      Counter32
    MAX-ACCESS  read-only
    STATUS      current
    DESCRIPTION 
        "Provides a count of the number of DM PDUs received from the MAC 
         and not discarded on this connection."
    REFERENCE   
        "IEEE 802.2 (ISO/IEC 8802-2) type2ReceivedDM."
    ::= { lLCConnection2Entry 35 }

lLCConnection2SentDM OBJECT-TYPE
    SYNTAX      Counter32
    MAX-ACCESS  read-only
    STATUS      current
    DESCRIPTION 
        "Provides a count of the number of DM PDUs delivered to  the MAC 
         on this connection."
    REFERENCE   
        "IEEE 802.2 (ISO/IEC 8802-2) type2SentDM."
    ::= { lLCConnection2Entry 36 }

lLCConnection2PDUsDiscarded1 OBJECT-TYPE
    SYNTAX      Counter32
    MAX-ACCESS  read-only
    STATUS      current
    DESCRIPTION 
        "Provides a count of the number of PDUs discarded due to 
         insufficient resources for this connection."
    REFERENCE   
        "IEEE 802.2 (ISO/IEC 8802-2) pDUsDiscarded1."
    ::= { lLCConnection2Entry 37 }

lLCConnection2PDUsDiscarded2 OBJECT-TYPE
    SYNTAX      Counter32
    MAX-ACCESS  read-only
    STATUS      current
    DESCRIPTION 
        "Provides a count of the number of PDUs discarded due to 
         unexpected or invalid sequence numberfor this connection."
    REFERENCE   
        "IEEE 802.2 (ISO/IEC 8802-2) pDUsDiscarded2."
    ::= { lLCConnection2Entry 38 }

lLCConnection2PDURetransmissions OBJECT-TYPE
    SYNTAX      Counter32
    MAX-ACCESS  read-only
    STATUS      current
    DESCRIPTION 
        "Provides a count of the number of times the Type 2 LLC service 
         retransmitted PDUs for this connection."
    REFERENCE   
        "IEEE 802.2 (ISO/IEC 8802-2) pDURetransmissions."
    ::= { lLCConnection2Entry 39 }

lLCConnection2OptionalTolerationIPDUs OBJECT-TYPE
    SYNTAX      TruthValue
    MAX-ACCESS  read-write
    STATUS      current
    DESCRIPTION 
        "Indicates if the Toleration of Duplicate I PDUs is on or off."
    REFERENCE   
        "IEEE 802.2 (ISO/IEC 8802-2) optionalTolerationIPDUs."
    ::= { lLCConnection2Entry 40 }

lLCConnection2DuplicateIPDUsReceived OBJECT-TYPE
    SYNTAX      Counter32
    MAX-ACCESS  read-only
    STATUS      current
    DESCRIPTION 
        "Provides a count of the number of duplicated I PDUs received on 
         this connection.  Duplication I PDUs are those that have a 
         sequence number within the current window and which have 
         already been received."
    REFERENCE   
        "IEEE 802.2 (ISO/IEC 8802-2) duplicatePDUsReceived, (also 
         dupIPDUsReceived)."
    ::= { lLCConnection2Entry 41 }

lLCConnection2Violation OBJECT-TYPE
    SYNTAX      Counter32
    MAX-ACCESS  read-only
    STATUS      current
    DESCRIPTION 
        "Provides a count of the number of LLC Type 2 protocol 
         violations detected by this connection. Protocol violations 
         include the following:
         1. those that result in the LLC entity sending an FRMR frame;
         2. those that result in a data link resetting action to be 
            initiated by the receiving LLC entity itself."
    REFERENCE   
        "IEEE 802.2 (ISO/IEC 8802-2) type2Violation."
    ::= { lLCConnection2Entry 42 }

lLCConnection2ProtocolState OBJECT-TYPE
    SYNTAX      INTEGER { disconnectedPhase(0), linkdiconnectionPhase(1), 
                    linkSetUpPhase(2), informationTransferPhase(3), 
                    frameRejectCondition(4), busyCondition(5), 
                    sentRejectCondition(6), 
                    systemParametersAndErrorRecovery(7) }
    MAX-ACCESS  read-only
    STATUS      current
    DESCRIPTION 
        "Local state of an LLC2 connection."
    REFERENCE   
        ""
    ::= { lLCConnection2Entry 43 }

lLCConnection2AdministrativeState OBJECT-TYPE
    SYNTAX      AdministrativeState
    MAX-ACCESS  read-write
    STATUS      current
    DESCRIPTION 
        "Provides the X.731 administrative status of the LLC2 
         connection.  When locked(0), the LLC2 connection is 
         administratively prohibitted from forming and when set to 
         locked(0) will be abruptly disconnected if already formed.  
         When unlocked(1) the LLC2 connection is administratively 
         permitted to form.  When set to shuttingDown(2), the LLC2 
         connection will be gracefully withdrawn from service and will 
         enter the locked(0) state when shut down."
    REFERENCE   
        ""
    ::= { lLCConnection2Entry 44 }

lLCConnection2OperationalState OBJECT-TYPE
    SYNTAX      OperationalState
    MAX-ACCESS  read-only
    STATUS      current
    DESCRIPTION 
        "Provides the X.731 operational state of this LAPB connection."
    REFERENCE   
        ""
    ::= { lLCConnection2Entry 45 }

lLCConnection2UsageState OBJECT-TYPE
    SYNTAX      UsageState
    MAX-ACCESS  read-only
    STATUS      current
    DESCRIPTION 
        "Provides the X.731 usage state of this LLC2 connection.  When 
         idle(0), the LLC2 connection is not currently in use (although 
         it may still be formed).  When active(1), the resource is being 
         used and has sufficient spare operating capacity to provide for 
         additional users simultaneously.  When busy(2), the resource is 
         in use, but it has no spare capacity to provide additional 
         users at this instant."
    REFERENCE   
        ""
    ::= { lLCConnection2Entry 46 }

lLCConnection2ProceduralStatus OBJECT-TYPE
    SYNTAX      ProceduralStatus
    MAX-ACCESS  read-only
    STATUS      current
    DESCRIPTION 
        "Provides the X.731 procedural status of this LLC2 connection.  
         The procedural status contains initializationRequired(0) when 
         the LLC2 requires initiation action to form or reform a 
         connection.  It contains notInitialized(1) when the LLC2 
         connection is in disconnected mode (ADM); initializing(2) when 
         forming connection (SABM) and terminating(3) when disconnecting 
         (DISC)."
    REFERENCE   
        ""
    ::= { lLCConnection2Entry 47 }

lLCConnection2AlarmStatus OBJECT-TYPE
    SYNTAX      AlarmStatus
    MAX-ACCESS  read-write
    STATUS      current
    DESCRIPTION 
        "Provides the alarm status of this LLC2 connection."
    REFERENCE   
        ""
    ::= { lLCConnection2Entry 48 }

lLCConnection2IVMO OBJECT IDENTIFIER
    ::= { x25Tables 19 }

lLCConnection2IVMOTable OBJECT-TYPE
    SYNTAX      SEQUENCE OF LLCConnection2IVMOEntry
    MAX-ACCESS  not-accessible
    STATUS      current
    DESCRIPTION 
        "lLCConnection2IVMO managed object.  A lLCConnection2IVMO may be 
         used to supply initial values for the attributes of 
         lLCConnection2 MOs.  Different instances of lLCConnection2IVMO 
         may contain different initial values.
         
         Provides a table of configuration defaults for LLC2 connections 
         to remote LLC2 stations from this LLC station.
         
         This table provides initial values for connection associated 
         with the MAC/LLC stations indicated by the index into the 
         table.  Note that if the management station does not assign 
         values ot a MAC/LLC station, the agent or implementation will 
         assign default values or values specified by local 
         configuration.  These are only default values for new 
         connections formed to or from the LLC station.  The management 
         station can alter the operational values via the 
         lLCConnection2Table.  The agent or implementation may also 
         alter operational values.  
         
         Changes made to values in this table will not necessarily 
         affect operational connections, but will be used as default 
         values for new connection formed subsequent to the change.  
         Note that managements stations may not add rows to or delete 
         rows from this table.  Rows are allocated by the implementation 
         and correspond each to available LLC stations."
    REFERENCE   
        "IEEE 802.2 (ISO/IEC 8802-2)"
    ::= { lLCConnection2IVMO 1 }

lLCConnection2IVMOEntry OBJECT-TYPE
    SYNTAX      LLCConnection2IVMOEntry
    MAX-ACCESS  not-accessible
    STATUS      current
    DESCRIPTION 
        ""
    REFERENCE   
        "IEEE 802.2 (ISO/IEC 8802-2)"
    INDEX       { lLCConnection2IVMOName }
    ::= { lLCConnection2IVMOTable 1 }

LLCConnection2IVMOEntry ::= SEQUENCE {
    lLCConnection2IVMOName                      SimpleNameType,
    lLCConnection2IVMOMaximumRetransmissions    Unsigned32,
    lLCConnection2IVMOReceivedWindowSize        Unsigned32,
    lLCConnection2IVMOSendWindowSize            Unsigned32,
    lLCConnection2IVMOAcknowledgeTimeoutValue   TimeInterval,
    lLCConnection2IVMOBusyStateTimeoutValue     TimeInterval,
    lLCConnection2IVMOBitTimeoutValue           TimeInterval,
    lLCConnection2IVMORejectTimeoutValue        TimeInterval,
    lLCConnection2IVMORoute                     OCTET STRING,
    lLCConnection2IVMOKStep                     Unsigned32,
    lLCConnection2IVMOMaxSendWindowSize         Unsigned32,
    lLCConnection2IVMOOptionalTolerationIPDUs   TruthValue
}

lLCConnection2IVMOName OBJECT-TYPE
    SYNTAX      SimpleNameType
    MAX-ACCESS  not-accessible
    STATUS      current
    DESCRIPTION 
        ""
    REFERENCE   
        "IEEE 802.2 (ISO/IEC 8802-2)."
    ::= { lLCConnection2IVMOEntry 1 }

lLCConnection2IVMOMaximumRetransmissions OBJECT-TYPE
    SYNTAX      Unsigned32
    MAX-ACCESS  read-write
    STATUS      current
    DESCRIPTION 
        "The default value, when not explicity specified by a management 
         station, is derived from the 
         lLCConnection2DefaultMaximumRetransmissions scalar."
    REFERENCE   
        "IEEE 802.2 (ISO/IEC 8802-2)."
    ::= { lLCConnection2IVMOEntry 2 }

lLCConnection2IVMOReceivedWindowSize OBJECT-TYPE
    SYNTAX      Unsigned32
    MAX-ACCESS  read-write
    STATUS      current
    DESCRIPTION 
        "The default value, when not explicity specified by a management 
         station, is derived from the 
         lLCConnection2DefaultReceivedWindowSize scalar."
    REFERENCE   
        "IEEE 802.2 (ISO/IEC 8802-2)."
    ::= { lLCConnection2IVMOEntry 3 }

lLCConnection2IVMOSendWindowSize OBJECT-TYPE
    SYNTAX      Unsigned32
    MAX-ACCESS  read-write
    STATUS      current
    DESCRIPTION 
        "The default value, when not explicity specified by a management 
         station, is derived from the 
         lLCConnection2DefaultSendWindowSize scalar."
    REFERENCE   
        "IEEE 802.2 (ISO/IEC 8802-2)."
    ::= { lLCConnection2IVMOEntry 4 }

lLCConnection2IVMOAcknowledgeTimeoutValue OBJECT-TYPE
    SYNTAX      TimeInterval
    UNITS       "seconds"
    MAX-ACCESS  read-write
    STATUS      current
    DESCRIPTION 
        "The default value, when not explicity specified by a management 
         station, is derived from the 
         lLCConnection2DefaultAcknowledgeTimeoutValue scalar."
    REFERENCE   
        "IEEE 802.2 (ISO/IEC 8802-2)."
    ::= { lLCConnection2IVMOEntry 5 }

lLCConnection2IVMOBusyStateTimeoutValue OBJECT-TYPE
    SYNTAX      TimeInterval
    UNITS       "seconds"
    MAX-ACCESS  read-write
    STATUS      current
    DESCRIPTION 
        "The default value, when not explicity specified by a management 
         station, is derived from the 
         lLCConnection2DefaultBusyStateTimeoutValue scalar."
    REFERENCE   
        "IEEE 802.2 (ISO/IEC 8802-2)."
    ::= { lLCConnection2IVMOEntry 6 }

lLCConnection2IVMOBitTimeoutValue OBJECT-TYPE
    SYNTAX      TimeInterval
    UNITS       "seconds"
    MAX-ACCESS  read-write
    STATUS      current
    DESCRIPTION 
        "The default value, when not explicity specified by a management 
         station, is derived from the 
         lLCConnection2DefaultPBitTimeoutValue scalar."
    REFERENCE   
        "IEEE 802.2 (ISO/IEC 8802-2)."
    ::= { lLCConnection2IVMOEntry 7 }

lLCConnection2IVMORejectTimeoutValue OBJECT-TYPE
    SYNTAX      TimeInterval
    UNITS       "seconds"
    MAX-ACCESS  read-write
    STATUS      current
    DESCRIPTION 
        "The default value, when not explicity specified by a management 
         station, is derived from the 
         lLCConnection2DefaultRejectTimeoutValue scalar."
    REFERENCE   
        "IEEE 802.2 (ISO/IEC 8802-2)."
    ::= { lLCConnection2IVMOEntry 8 }

lLCConnection2IVMORoute OBJECT-TYPE
    SYNTAX      OCTET STRING
    MAX-ACCESS  read-write
    STATUS      current
    DESCRIPTION 
        "The default value, when not explicity specified by a management 
         station, is derived from the lLCConnection2DefaultRoute 
         scalar."
    REFERENCE   
        "IEEE 802.2 (ISO/IEC 8802-2)."
    ::= { lLCConnection2IVMOEntry 9 }

lLCConnection2IVMOKStep OBJECT-TYPE
    SYNTAX      Unsigned32
    MAX-ACCESS  read-write
    STATUS      current
    DESCRIPTION 
        "The default value, when not explicity specified by a management 
         station, is derived from the lLCConnection2DefaultKStep 
         scalar."
    REFERENCE   
        "IEEE 802.2 (ISO/IEC 8802-2)."
    ::= { lLCConnection2IVMOEntry 10 }

lLCConnection2IVMOMaxSendWindowSize OBJECT-TYPE
    SYNTAX      Unsigned32
    MAX-ACCESS  read-write
    STATUS      current
    DESCRIPTION 
        "The default value, when not explicity specified by a management 
         station, is derived from the 
         lLCConnection2DefaultMaxSendWindowSize scalar."
    REFERENCE   
        "IEEE 802.2 (ISO/IEC 8802-2)."
    ::= { lLCConnection2IVMOEntry 11 }

lLCConnection2IVMOOptionalTolerationIPDUs OBJECT-TYPE
    SYNTAX      TruthValue
    MAX-ACCESS  read-write
    STATUS      current
    DESCRIPTION 
        "The default value, when not explicity specified by a management 
         station, is derived from the 
         lLCConnection2DefaultOptionalTolerationIPDUs scalar."
    REFERENCE   
        "IEEE 802.2 (ISO/IEC 8802-2)."
    ::= { lLCConnection2IVMOEntry 12 }

lLCConnectionlessAck OBJECT IDENTIFIER
    ::= { x25Tables 20 }

lLCConnectionlessAckTable OBJECT-TYPE
    SYNTAX      SEQUENCE OF LLCConnectionlessAckEntry
    MAX-ACCESS  not-accessible
    STATUS      current
    DESCRIPTION 
        "The Type 3 Received component is responsible for processing 
         Type 3 commands as they are received from the medium access 
         control sublayer, and for returning Type 3 responses to the 
         originators of the commands.  At a given station there is 
         potentially a separate Type 3 Receiver component for each 
         possible combination of remote address (SA and SSAP), and MAC 
         priority.  In most applications, however, only a subset of the 
         possible Receiver components will exist, since a component is 
         needed only for those address and priority combinations for 
         which Type 3 commands are actually received.
         
         The Type 3 Sender component is responsible for sending Type 3 
         commands upon request of the network layer, and for processing 
         of Type 3 responses when they are received from the medium 
         access control sublayer.  At any given station there is 
         potentially a spearate Type 3 Sender component for each 
         possible combination of local LSAP, DA portion of the remote 
         address, and MAC priority.  In most applications, however, only 
         a subset of the possible Sender components will exist, since a 
         component is needed only for those address and priority 
         combinations for which Type 3 commands are actually sent."
    REFERENCE   
        "IEEE 802.2 (ISO/IEC 8802-2)"
    ::= { lLCConnectionlessAck 1 }

lLCConnectionlessAckEntry OBJECT-TYPE
    SYNTAX      LLCConnectionlessAckEntry
    MAX-ACCESS  not-accessible
    STATUS      current
    DESCRIPTION 
        ""
    REFERENCE   
        "IEEE 802.2 (ISO/IEC 8802-2)"
    INDEX       { lLCCOPMCoProtocolMachineId, lLCCOPMCoProtocolMachineId }
    ::= { lLCConnectionlessAckTable 1 }

LLCConnectionlessAckEntry ::= SEQUENCE {
    lLCConnectionlessAckName                            SimpleNameType,
    lLCConnectionlessAckMaximumLLCInformationFieldSize  Unsigned32,
    lLCConnectionlessAckMaximumRetransmissions          Unsigned32,
    lLCConnectionlessAckTESTReceivedABBResponse         Counter32,
    lLCConnectionlessAckTESTReceivedCommand             Counter32,
    lLCConnectionlessAckTESTReceivedResponse            Counter32,
    lLCConnectionlessAckTESTSentABBResponse             Counter32,
    lLCConnectionlessAckTESTSentCommand                 Counter32,
    lLCConnectionlessAckTESTSentResponse                Counter32,
    lLCConnectionlessAckReceiveResources                Counter32,
    lLCConnectionlessAckUIReceived                      Counter32,
    lLCConnectionlessAckUISent                          Counter32,
    lLCConnectionlessAckXIDReceivedCommand              Counter32,
    lLCConnectionlessAckXIDReceivedResponse             Counter32,
    lLCConnectionlessAckXIDSentCommand                  Counter32,
    lLCConnectionlessAckXIDSentResponse                 Counter32,
    lLCConnectionlessAckRetransmissions                 Counter32,
    lLCConnectionlessAckNoResponse                      Counter32,
    lLCConnectionlessAckCommandIP                       Counter32,
    lLCConnectionlessAckCommandIT                       Counter32,
    lLCConnectionlessAckCommandOK                       Counter32,
    lLCConnectionlessAckCommandPE                       Counter32,
    lLCConnectionlessAckCommandRS                       Counter32,
    lLCConnectionlessAckCommandUE                       Counter32,
    lLCConnectionlessAckCommandUN                       Counter32,
    lLCConnectionlessAckReceivedACCommand               Counter32,
    lLCConnectionlessAckSentACCommand                   Counter32,
    lLCConnectionlessAckResponseIP                      Counter32,
    lLCConnectionlessAckResponseIT                      Counter32,
    lLCConnectionlessAckResponseNE                      Counter32,
    lLCConnectionlessAckResponseNR                      Counter32,
    lLCConnectionlessAckResponseOK                      Counter32,
    lLCConnectionlessAckResponseRS                      Counter32,
    lLCConnectionlessAckResponseUE                      Counter32,
    lLCConnectionlessAckResponseUN                      Counter32,
    lLCConnectionlessAckViolation                       Counter32
}

lLCConnectionlessAckName OBJECT-TYPE
    SYNTAX      SimpleNameType
    MAX-ACCESS  read-only
    STATUS      current
    DESCRIPTION 
        "The localLSAP and remoteLSAPId and the local and remote MAC 
         Address."
    REFERENCE   
        "IEEE 802.2 (ISO/IEC 8802-2), lLCConnectionlessAckName."
    ::= { lLCConnectionlessAckEntry 1 }

lLCConnectionlessAckMaximumLLCInformationFieldSize OBJECT-TYPE
    SYNTAX      Unsigned32
    MAX-ACCESS  read-write
    STATUS      current
    DESCRIPTION 
        "The maximum length SDU that the LSAP will accomodate."
    REFERENCE   
        "IEEE 802.2 (ISO/IEC 8802-2), 
         maximumLLCInformationFieldSize."
    ::= { lLCConnectionlessAckEntry 2 }

lLCConnectionlessAckMaximumRetransmissions OBJECT-TYPE
    SYNTAX      Unsigned32
    MAX-ACCESS  read-write
    STATUS      current
    DESCRIPTION 
        "The number of times that the LLC Type 2 should attempt to 
         realize a successful PDU transfer."
    REFERENCE   
        "IEEE 802.2 (ISO/IEC 8802-2), maximumRetransmissions."
    ::= { lLCConnectionlessAckEntry 3 }

lLCConnectionlessAckTESTReceivedABBResponse OBJECT-TYPE
    SYNTAX      Counter32
    MAX-ACCESS  read-only
    STATUS      current
    DESCRIPTION 
        "Provides a count of TEST responses received by this LSAP 
         without the LSDU due to limited resources at the remote 
         station."
    REFERENCE   
        "IEEE 802.2 (ISO/IEC 8802-2), tESTReceivedABBResponse."
    ::= { lLCConnectionlessAckEntry 4 }

lLCConnectionlessAckTESTReceivedCommand OBJECT-TYPE
    SYNTAX      Counter32
    MAX-ACCESS  read-only
    STATUS      current
    DESCRIPTION 
        "Provides a count of TEST commands received from the MAC 
         sublayer by this LSAP.  This includes commands recieved with 
         any group address recognized by this LSAP."
    REFERENCE   
        "IEEE 802.2 (ISO/IEC 8802-2), tESTReceivedCommand."
    ::= { lLCConnectionlessAckEntry 5 }

lLCConnectionlessAckTESTReceivedResponse OBJECT-TYPE
    SYNTAX      Counter32
    MAX-ACCESS  read-only
    STATUS      current
    DESCRIPTION 
        "Provides a count of TEST responses received from the MAC 
         sublayer by this LSAP."
    REFERENCE   
        "IEEE 802.2 (ISO/IEC 8802-2), tESTReceivedResponse."
    ::= { lLCConnectionlessAckEntry 6 }

lLCConnectionlessAckTESTSentABBResponse OBJECT-TYPE
    SYNTAX      Counter32
    MAX-ACCESS  read-only
    STATUS      current
    DESCRIPTION 
        "Provides a count of TEST responses that were delivered to the 
         MAC without the LSDU data due to limited resources."
    REFERENCE   
        "IEEE 802.2 (ISO/IEC 8802-2), tESTSentABBResponse."
    ::= { lLCConnectionlessAckEntry 7 }

lLCConnectionlessAckTESTSentCommand OBJECT-TYPE
    SYNTAX      Counter32
    MAX-ACCESS  read-only
    STATUS      current
    DESCRIPTION 
        "Provides a count of TEST command set to the MAC sublayer by 
         this LSAP."
    REFERENCE   
        "IEEE 802.2 (ISO/IEC 8802-2), tESTSentCommand."
    ::= { lLCConnectionlessAckEntry 8 }

lLCConnectionlessAckTESTSentResponse OBJECT-TYPE
    SYNTAX      Counter32
    MAX-ACCESS  read-only
    STATUS      current
    DESCRIPTION 
        "Provides a count of TEST responses sent to the MAC sublayer by 
         this LSAP."
    REFERENCE   
        "IEEE 802.2 (ISO/IEC 8802-2), tESTSentResponse."
    ::= { lLCConnectionlessAckEntry 9 }

lLCConnectionlessAckReceiveResources OBJECT-TYPE
    SYNTAX      Counter32
    MAX-ACCESS  read-only
    STATUS      current
    DESCRIPTION 
        "Causes the LSAP entity to either enable or disable the 
         resources for reception of the data field of Type 3 command 
         PDUs sent to this LSAP.  If a Type 3 PDU containing data is 
         received while disabled, the UN status code is returned in the 
         CCCC field of the response PDU."
    REFERENCE   
        "IEEE 802.2 (ISO/IEC 8802-2), type3ReceiveResources."
    ::= { lLCConnectionlessAckEntry 10 }

lLCConnectionlessAckUIReceived OBJECT-TYPE
    SYNTAX      Counter32
    MAX-ACCESS  read-only
    STATUS      current
    DESCRIPTION 
        "Provides a count of user data PDUs that were received by the 
         LSAP from the MAC sublayer and passed to the user layer.  This 
         includes commands received with group addresses of which the 
         LSAP is a member."
    REFERENCE   
        "IEEE 802.2 (ISO/IEC 8802-2), uIReceived."
    ::= { lLCConnectionlessAckEntry 11 }

lLCConnectionlessAckUISent OBJECT-TYPE
    SYNTAX      Counter32
    MAX-ACCESS  read-only
    STATUS      current
    DESCRIPTION 
        "Provides a count of user data PDUs that were accepted by the 
         LSAP from the user layer and delivered to the MAC sublayer."
    REFERENCE   
        "IEEE 802.2 (ISO/IEC 8802-2), uISent."
    ::= { lLCConnectionlessAckEntry 12 }

lLCConnectionlessAckXIDReceivedCommand OBJECT-TYPE
    SYNTAX      Counter32
    MAX-ACCESS  read-only
    STATUS      current
    DESCRIPTION 
        "Proivdes a count of XID commands received from the MAC sublayer 
         by this LSAP.  This includes commands received with any group 
         address recognized by this LSAP."
    REFERENCE   
        "IEEE 802.2 (ISO/IEC 8802-2), xIDReceivedCommand."
    ::= { lLCConnectionlessAckEntry 13 }

lLCConnectionlessAckXIDReceivedResponse OBJECT-TYPE
    SYNTAX      Counter32
    MAX-ACCESS  read-only
    STATUS      current
    DESCRIPTION 
        "Provides a count of XID responses received from the MAC 
         sublayer by this LSAP."
    REFERENCE   
        "IEEE 802.2 (ISO/IEC 8802-2), xIDReceivedResponse."
    ::= { lLCConnectionlessAckEntry 14 }

lLCConnectionlessAckXIDSentCommand OBJECT-TYPE
    SYNTAX      Counter32
    MAX-ACCESS  read-only
    STATUS      current
    DESCRIPTION 
        "Provides a count of XID commands sent to the MAC 
         sublayer by this LSAP."
    REFERENCE   
        "IEEE 802.2 (ISO/IEC 8802-2), xIDSentCommand."
    ::= { lLCConnectionlessAckEntry 15 }

lLCConnectionlessAckXIDSentResponse OBJECT-TYPE
    SYNTAX      Counter32
    MAX-ACCESS  read-only
    STATUS      current
    DESCRIPTION 
        "Provides a count of the XID responses sent to the MAC sublayer 
         by this LSAP."
    REFERENCE   
        "IEEE 802.2 (ISO/IEC 8802-2), xIDSentResponse."
    ::= { lLCConnectionlessAckEntry 16 }

lLCConnectionlessAckRetransmissions OBJECT-TYPE
    SYNTAX      Counter32
    MAX-ACCESS  read-only
    STATUS      current
    DESCRIPTION 
        "Provides a count of the number of PDUs which were retrasmitted 
         (at least once) by the Type 3 LLC service."
    REFERENCE   
        "IEEE 802.2 (ISO/IEC 8802-2), type3Retransmissions."
    ::= { lLCConnectionlessAckEntry 17 }

lLCConnectionlessAckNoResponse OBJECT-TYPE
    SYNTAX      Counter32
    MAX-ACCESS  read-only
    STATUS      current
    DESCRIPTION 
        "Provides a count of failures to obtain a response from the 
         destination associated with this LSAP pair, after exhausting 
         the retry counter MaximumRetransmissions4."
    REFERENCE   
        "IEEE 802.2 (ISO/IEC 8802-2), type3NoResponse."
    ::= { lLCConnectionlessAckEntry 18 }

lLCConnectionlessAckCommandIP OBJECT-TYPE
    SYNTAX      Counter32
    MAX-ACCESS  read-only
    STATUS      current
    DESCRIPTION 
        "Provides a count of the received responses with the command 
         status field set to indicate 'Permanent implementation 
         dependent error,' as defined in 5.4.3.2."
    REFERENCE   
        "IEEE 802.2 (ISO/IEC 8802-2), type3CommandIP."
    ::= { lLCConnectionlessAckEntry 19 }

lLCConnectionlessAckCommandIT OBJECT-TYPE
    SYNTAX      Counter32
    MAX-ACCESS  read-only
    STATUS      current
    DESCRIPTION 
        "Provides a count of the received responses with the command 
         status field set to indicate 'Temporarily implementation 
         dependent error,' as defined in 5.4.3.2."
    REFERENCE   
        "IEEE 802.2 (ISO/IEC 8802-2), type3CommandIT."
    ::= { lLCConnectionlessAckEntry 20 }

lLCConnectionlessAckCommandOK OBJECT-TYPE
    SYNTAX      Counter32
    MAX-ACCESS  read-only
    STATUS      current
    DESCRIPTION 
        "Provides a count of the received responses with the command 
         status field set to indicate 'Command accepted,' as defined in 
         5.4.3.2."
    REFERENCE   
        "IEEE 802.2 (ISO/IEC 8802-2), type3CommandOK."
    ::= { lLCConnectionlessAckEntry 21 }

lLCConnectionlessAckCommandPE OBJECT-TYPE
    SYNTAX      Counter32
    MAX-ACCESS  read-only
    STATUS      current
    DESCRIPTION 
        "Provides a count of the received responses with the command 
         status field set to indicate 'Protocol error,' as defined in 
         5.4.3.2."
    REFERENCE   
        "IEEE 802.2 (ISO/IEC 8802-2), type3CommandPE."
    ::= { lLCConnectionlessAckEntry 22 }

lLCConnectionlessAckCommandRS OBJECT-TYPE
    SYNTAX      Counter32
    MAX-ACCESS  read-only
    STATUS      current
    DESCRIPTION 
        "Provides a count of the received responses with the command 
         status field set to indicate 'Unimplemented or inactivated 
         service,' as defined in 5.4.3.2."
    REFERENCE   
        "IEEE 802.2 (ISO/IEC 8802-2), type3CommandRS."
    ::= { lLCConnectionlessAckEntry 23 }

lLCConnectionlessAckCommandUE OBJECT-TYPE
    SYNTAX      Counter32
    MAX-ACCESS  read-only
    STATUS      current
    DESCRIPTION 
        "Provides a count of the received responses with the command 
         status field set to indicate 'LLC user interface error,' as 
         defined in 5.4.3.2."
    REFERENCE   
        "IEEE 802.2 (ISO/IEC 8802-2), type3CommandUE."
    ::= { lLCConnectionlessAckEntry 24 }

lLCConnectionlessAckCommandUN OBJECT-TYPE
    SYNTAX      Counter32
    MAX-ACCESS  read-only
    STATUS      current
    DESCRIPTION 
        "Provides a count of the received responses with the command 
         status field set to indicate 'Resources temporarily 
         unavailable,' as defined in 5.4.3.2."
    REFERENCE   
        "IEEE 802.2 (ISO/IEC 8802-2), type3CommandUN."
    ::= { lLCConnectionlessAckEntry 25 }

lLCConnectionlessAckReceivedACCommand OBJECT-TYPE
    SYNTAX      Counter32
    MAX-ACCESS  read-only
    STATUS      current
    DESCRIPTION 
        "Provides a count of AC command PDUs received from the other 
         LSAP of the connection (LSAP PAIR)."
    REFERENCE   
        "IEEE 802.2 (ISO/IEC 8802-2), type3ReceivedACCommand."
    ::= { lLCConnectionlessAckEntry 26 }

lLCConnectionlessAckSentACCommand OBJECT-TYPE
    SYNTAX      Counter32
    MAX-ACCESS  read-only
    STATUS      current
    DESCRIPTION 
        "Provides a count of AC command PDUs sent to the other LSAP of 
         the connection (LSAP PAIR)."
    REFERENCE   
        "IEEE 802.2 (ISO/IEC 8802-2), type3SentACCommand."
    ::= { lLCConnectionlessAckEntry 27 }

lLCConnectionlessAckResponseIP OBJECT-TYPE
    SYNTAX      Counter32
    MAX-ACCESS  read-only
    STATUS      current
    DESCRIPTION 
        "Provides a count of the received responses with the response 
         status field set to indicate 'Permanent implementation 
         dependent error,' as defined in 5.4.3.2."
    REFERENCE   
        "IEEE 802.2 (ISO/IEC 8802-2), type3ResponseIP."
    ::= { lLCConnectionlessAckEntry 28 }

lLCConnectionlessAckResponseIT OBJECT-TYPE
    SYNTAX      Counter32
    MAX-ACCESS  read-only
    STATUS      current
    DESCRIPTION 
        "Provides a count of the received responses with the response 
         status field set to indicate 'Temporary implementation 
         dependent error,' as defined in 5.4.3.2."
    REFERENCE   
        "IEEE 802.2 (ISO/IEC 8802-2), type3ResponseIT."
    ::= { lLCConnectionlessAckEntry 29 }

lLCConnectionlessAckResponseNE OBJECT-TYPE
    SYNTAX      Counter32
    MAX-ACCESS  read-only
    STATUS      current
    DESCRIPTION 
        "Provides a count of the received responses with the response 
         status field set to indicate 'Response LSDU never submitted,' 
         as defined in 5.4.3.2."
    REFERENCE   
        "IEEE 802.2 (ISO/IEC 8802-2), type3ResponseNE."
    ::= { lLCConnectionlessAckEntry 30 }

lLCConnectionlessAckResponseNR OBJECT-TYPE
    SYNTAX      Counter32
    MAX-ACCESS  read-only
    STATUS      current
    DESCRIPTION 
        "Provides a count of the received responses with the response 
         status field set to indicate 'Response LSDU not requested,' as 
         defined in 5.4.3.2."
    REFERENCE   
        "IEEE 802.2 (ISO/IEC 8802-2), type3ResponseNR."
    ::= { lLCConnectionlessAckEntry 31 }

lLCConnectionlessAckResponseOK OBJECT-TYPE
    SYNTAX      Counter32
    MAX-ACCESS  read-only
    STATUS      current
    DESCRIPTION 
        "Provides a count of the received responses with the response 
         status field set to indicate 'Response LSDU present,' as 
         defined in 5.4.3.2."
    REFERENCE   
        "IEEE 802.2 (ISO/IEC 8802-2), type3ResponseOK."
    ::= { lLCConnectionlessAckEntry 32 }

lLCConnectionlessAckResponseRS OBJECT-TYPE
    SYNTAX      Counter32
    MAX-ACCESS  read-only
    STATUS      current
    DESCRIPTION 
        "Provides a count of the received responses with the response 
         status field set to indicate 'Unimplemented or inactivated 
         service,' as defined in 5.4.3.2."
    REFERENCE   
        "IEEE 802.2 (ISO/IEC 8802-2), type3ResponseRS."
    ::= { lLCConnectionlessAckEntry 33 }

lLCConnectionlessAckResponseUE OBJECT-TYPE
    SYNTAX      Counter32
    MAX-ACCESS  read-only
    STATUS      current
    DESCRIPTION 
        "Provides a count of the received responses with the response 
         status field set to indicate 'LLC user interface error,' as 
         defined in 5.4.3.2."
    REFERENCE   
        "IEEE 802.2 (ISO/IEC 8802-2), type3ResponseUE."
    ::= { lLCConnectionlessAckEntry 34 }

lLCConnectionlessAckResponseUN OBJECT-TYPE
    SYNTAX      Counter32
    MAX-ACCESS  read-only
    STATUS      current
    DESCRIPTION 
        "Provides a count of the received responses with the response 
         status field set to indicate 'Resources temporarily 
         unavailable,' as defined in 5.4.3.2."
    REFERENCE   
        "IEEE 802.2 (ISO/IEC 8802-2), type3ResponseUN."
    ::= { lLCConnectionlessAckEntry 35 }

lLCConnectionlessAckViolation OBJECT-TYPE
    SYNTAX      Counter32
    MAX-ACCESS  read-only
    STATUS      current
    DESCRIPTION 
        "Provides a count of the number of protocol violations detected 
         by this connection."
    REFERENCE   
        "IEEE 802.2 (ISO/IEC 8802-2), type3Violation."
    ::= { lLCConnectionlessAckEntry 36 }

lLCConnectionlessAckIVMO OBJECT IDENTIFIER
    ::= { x25Tables 21 }

lLCConnectionlessAckIVMOTable OBJECT-TYPE
    SYNTAX      SEQUENCE OF LLCConnectionlessAckIVMOEntry
    MAX-ACCESS  not-accessible
    STATUS      current
    DESCRIPTION 
        ""
    REFERENCE   
        "IEEE 802.2 (ISO/IEC 8802-2)"
    ::= { lLCConnectionlessAckIVMO 1 }

lLCConnectionlessAckIVMOEntry OBJECT-TYPE
    SYNTAX      LLCConnectionlessAckIVMOEntry
    MAX-ACCESS  not-accessible
    STATUS      current
    DESCRIPTION 
        ""
    REFERENCE   
        "IEEE 802.2 (ISO/IEC 8802-2)"
    INDEX       { lLCConnectionlessAckIVMOName }
    ::= { lLCConnectionlessAckIVMOTable 1 }

LLCConnectionlessAckIVMOEntry ::= SEQUENCE {
    lLCConnectionlessAckIVMOName                            SimpleNameType,
    lLCConnectionlessAckIVMOMaximumLLCInformationFieldSize  Unsigned32,
    lLCConnectionlessAckIVMOMaximumRetransmissions          Unsigned32,
    lLCConnectionlessAckIVMORowStatus                       RowStatus
}

lLCConnectionlessAckIVMOName OBJECT-TYPE
    SYNTAX      SimpleNameType
    MAX-ACCESS  not-accessible
    STATUS      current
    DESCRIPTION 
        ""
    REFERENCE   
        "IEEE 802.2 (ISO/IEC 8802-2), lLCConnecionlessAckIVMOName."
    ::= { lLCConnectionlessAckIVMOEntry 1 }

lLCConnectionlessAckIVMOMaximumLLCInformationFieldSize OBJECT-TYPE
    SYNTAX      Unsigned32
    MAX-ACCESS  read-create
    STATUS      current
    DESCRIPTION 
        "The maximum length SDU that the LSAP will accomodate."
    REFERENCE   
        "IEEE 802.2 (ISO/IEC 8802-2), maximumLLCInformationFieldSize."
    ::= { lLCConnectionlessAckIVMOEntry 2 }

lLCConnectionlessAckIVMOMaximumRetransmissions OBJECT-TYPE
    SYNTAX      Unsigned32
    MAX-ACCESS  read-create
    STATUS      current
    DESCRIPTION 
        "The number of times that the LLC Type 3 should attempt to 
         realize a successful PDU transfer."
    REFERENCE   
        "IEEE 802.2 (ISO/IEC 8802-2), maximumRetransmissions."
    ::= { lLCConnectionlessAckIVMOEntry 3 }

lLCConnectionlessAckIVMORowStatus OBJECT-TYPE
    SYNTAX      RowStatus
    MAX-ACCESS  read-create
    STATUS      current
    DESCRIPTION 
        ""
    REFERENCE   
        "STD 58, SNMPv2-TC RowStatus."
    ::= { lLCConnectionlessAckIVMOEntry 4 }

lAPBDLE OBJECT IDENTIFIER
    ::= { x25Tables 22 }

lAPBDLETable OBJECT-TYPE
    SYNTAX      SEQUENCE OF LAPBDLEEntry
    MAX-ACCESS  not-accessible
    STATUS      current
    DESCRIPTION 
        "The LAPB Data Link Entity managed object.  There may be 
         multiple instancs of the lAPBDLE managed object in a system.  
         Systems not supporting the LAPB Data Link proceudres defined in 
         ISO/IEC 7776 are not required to support the lAPBDLE and 
         contained managed objects.
         
         The lAPBDLE managed object has a conditional mlp package.  
         There amy be multiple instances of lAPBDLE MO in a system, both 
         with and without the mlp package.  For those instances in which 
         the package is absent, the mlp procedures do not apply and the 
         lAPBDLE MO may contain at most one sLPPM MO.  For those 
         instances in which the package is present, the mlp procedures 
         do apply and the lAPBDLE MO may contain multiple instances of 
         sLPPM MO.
         
         A lAPBDLE MO may contain at most one dLSAP MO.  The value of 
         the sap1Address attribute is of no significance.  The 
         cardinality of the userEntityNames attribute is limited to one.
         
         A lAPBDLE MO may be created and deleted explicitly by 
         management operation or created and deleted automatically as a 
         part of ystem operation.
         
         When the lAPBDLE MO is operable, the operationalState shall 
         have the value 'enabled'; otherwise, it shall have the value 
         'disabled'.  Transitions of operationalState shall be reported 
         using the stateChange notification."
    REFERENCE   
        "ITU-T Rec. X.282 | ISO/IEC 10742."
    ::= { lAPBDLE 1 }

lAPBDLEEntry OBJECT-TYPE
    SYNTAX      LAPBDLEEntry
    MAX-ACCESS  not-accessible
    STATUS      current
    DESCRIPTION 
        "This entry is derived from the datalinkEntity and uses the same 
         primary index."
    REFERENCE   
        "ITU-T Rec. X.282 | ISO/IEC 10742."
    INDEX       { lAPBDLECommunicationsEntityId }
    ::= { lAPBDLETable 1 }

LAPBDLEEntry ::= SEQUENCE {
    lAPBDLECommunicationsEntityId           InterfaceIndex,
    lAPBDLELocalSapNames                    RowPointer,
    lAPBDLEOperationalState                 OperationalState,
    lAPBDLEProviderEntityNames              RowPointer,
    lAPBDLEmT1Timer                         TimeInterval,
    lAPBDLEmT3Timer                         TimeInterval,
    lAPBDLEmW                               Unsigned32,
    lAPBDLEmXSend                           Unsigned32,
    lAPBDLEmXReceive                        Unsigned32,
    lAPBDLEmT2Timer                         TimeInterval,
    lAPBDLEReceivedMlpResets                Counter32,
    lAPBDLETimesMT1Expired                  Counter32,
    lAPBDLEIFramesReassignments             Counter32,
    lAPBDLEMlpFramesReceived                Counter32,
    lAPBDLEMlpFramesSent                    Counter32,
    lAPBDLEMlpFramesOutsideWindowGuard      Counter32,
    lAPBDLEReceivedMlpFramesInGuardRegion   Counter32,
    lAPBDLERowStatus                        RowStatus
}

lAPBDLECommunicationsEntityId OBJECT-TYPE
    SYNTAX      InterfaceIndex
    MAX-ACCESS  not-accessible
    STATUS      current
    DESCRIPTION 
        ""
    REFERENCE   
        "ITU-T Rec. X.723 | ISO/IEC 10165-5 communicationsEntityId."
    ::= { lAPBDLEEntry 1 }

lAPBDLELocalSapNames OBJECT-TYPE
    SYNTAX      RowPointer
    MAX-ACCESS  read-create
    STATUS      current
    DESCRIPTION 
        "The localSapNames attribute identifies the providing entitie's 
         SAP objects.  In the case of the lAPBDLE, the localSapNames 
         identifies the Ph-SAP of the Ph-Entity object which is 
         providing service to the lAPBDLE."
    REFERENCE   
        "ITU-T Rec. X.723 | ISO/IEC 10165-5 localSapNames."
    ::= { lAPBDLEEntry 2 }

lAPBDLEOperationalState OBJECT-TYPE
    SYNTAX      OperationalState
    MAX-ACCESS  read-create
    STATUS      current
    DESCRIPTION 
        ""
    REFERENCE   
        "ITU-T Rec. X.721 | ISO/IEC 10165-2 operationalState."
    ::= { lAPBDLEEntry 3 }

lAPBDLEProviderEntityNames OBJECT-TYPE
    SYNTAX      RowPointer
    MAX-ACCESS  read-create
    STATUS      current
    DESCRIPTION 
        "The providerEntityNames attribute identifies the entities 
         providing service to this datalinkEntity.  In the case of the 
         LAPB data link entity, lAPBDLE, the provider entity is a 
         Ph-Entity.  At most one Ph-Entity  can provide service to an 
         lAPBDLE can be provided service by a Ph-Entity."
    REFERENCE   
        "ITU-T Rec. X.282 | ISO/IEC 10742 providerEntityNames."
    ::= { lAPBDLEEntry 4 }

lAPBDLEmT1Timer OBJECT-TYPE
    SYNTAX      TimeInterval
    UNITS       "seconds"
    MAX-ACCESS  read-create
    STATUS      current
    DESCRIPTION 
        "Value of the ISO/IEC 7776 parameter MT1 (lost frame timer).  
         Unit is seconds."
    REFERENCE   
        "ITU-T Rec. X.282 | ISO/IEC 10742, ISO/IEC 7776."
    ::= { lAPBDLEEntry 5 }

lAPBDLEmT3Timer OBJECT-TYPE
    SYNTAX      TimeInterval
    UNITS       "seconds"
    MAX-ACCESS  read-create
    STATUS      current
    DESCRIPTION 
        "Value of the ISO/IEC 7776 parameter MT3 (mlp reset confirmation 
         timer).  Unit is seconds."
    REFERENCE   
        "ITU-T Rec. X.282 | ISO/IEC 10742, ISO/IEC 7776."
    ::= { lAPBDLEEntry 6 }

lAPBDLEmW OBJECT-TYPE
    SYNTAX      Unsigned32 (1..127)
    MAX-ACCESS  read-create
    STATUS      current
    DESCRIPTION 
        "MLP window size."
    REFERENCE   
        "ITU-T Rec. X.282 | ISO/IEC 10742, ISO/IEC 7776."
    ::= { lAPBDLEEntry 7 }

lAPBDLEmXSend OBJECT-TYPE
    SYNTAX      Unsigned32 (0..4095)
    MAX-ACCESS  read-create
    STATUS      current
    DESCRIPTION 
        "Receive MLP window in the Guard Region."
    REFERENCE   
        "ITU-T Rec. X.282 | ISO/IEC 10742, ISO/IEC 7776."
    ::= { lAPBDLEEntry 8 }

lAPBDLEmXReceive OBJECT-TYPE
    SYNTAX      Unsigned32 (0..4095)
    MAX-ACCESS  read-create
    STATUS      current
    DESCRIPTION 
        "Receive MLP window in the Guard Region."
    REFERENCE   
        "ITU-T Rec. X.282 | ISO/IEC 10742, ISO/IEC 7776."
    ::= { lAPBDLEEntry 9 }

lAPBDLEmT2Timer OBJECT-TYPE
    SYNTAX      TimeInterval
    UNITS       "seconds"
    MAX-ACCESS  read-create
    STATUS      current
    DESCRIPTION 
        "Value of the ISO/IEC 7776 parameter MT2 (group busy 
         timer).  Unit is seconds."
    REFERENCE   
        "ITU-T Rec. X.282 | ISO/IEC 10742, ISO/IEC 7776."
    ::= { lAPBDLEEntry 10 }

lAPBDLEReceivedMlpResets OBJECT-TYPE
    SYNTAX      Counter32
    MAX-ACCESS  read-only
    STATUS      current
    DESCRIPTION 
        "Count of the number of received MLP Resets."
    REFERENCE   
        "ITU-T Rec. X.282 | ISO/IEC 10742, receivedMlpResets."
    ::= { lAPBDLEEntry 11 }

lAPBDLETimesMT1Expired OBJECT-TYPE
    SYNTAX      Counter32
    MAX-ACCESS  read-only
    STATUS      current
    DESCRIPTION 
        "Count of the number of lost multilink frames."
    REFERENCE   
        "ITU-T Rec. X.282 | ISO/IEC 10742, timesMT1Expired."
    ::= { lAPBDLEEntry 12 }

lAPBDLEIFramesReassignments OBJECT-TYPE
    SYNTAX      Counter32
    MAX-ACCESS  read-only
    STATUS      current
    DESCRIPTION 
        "Count of the number of reassignments of IFrames on 
         another slp."
    REFERENCE   
        "ITU-T Rec. X.282 | ISO/IEC 10742, iFrameReassignments."
    ::= { lAPBDLEEntry 13 }

lAPBDLEMlpFramesReceived OBJECT-TYPE
    SYNTAX      Counter32
    MAX-ACCESS  read-only
    STATUS      current
    DESCRIPTION 
        "Count of the total number of MLP frames received."
    REFERENCE   
        "ITU-T Rec. X.282 | ISO/IEC 10742, mlpFramesReceived."
    ::= { lAPBDLEEntry 14 }

lAPBDLEMlpFramesSent OBJECT-TYPE
    SYNTAX      Counter32
    MAX-ACCESS  read-only
    STATUS      current
    DESCRIPTION 
        "Count of the total number of MLP frames sent."
    REFERENCE   
        "ITU-T Rec. X.282 | ISO/IEC 10742, mlpFramesSent."
    ::= { lAPBDLEEntry 15 }

lAPBDLEMlpFramesOutsideWindowGuard OBJECT-TYPE
    SYNTAX      Counter32
    MAX-ACCESS  read-only
    STATUS      current
    DESCRIPTION 
        "Count of the total number of MLP frames outwide the window 
         guard that have been received."
    REFERENCE   
        "ITU-T Rec. X.282 | ISO/IEC 10742, mlpFramesOutsideWindowGuard."
    ::= { lAPBDLEEntry 16 }

lAPBDLEReceivedMlpFramesInGuardRegion OBJECT-TYPE
    SYNTAX      Counter32
    MAX-ACCESS  read-only
    STATUS      current
    DESCRIPTION 
        "Count of the number of MLP frames received in the Guard 
         Region."
    REFERENCE   
        "ITU-T Rec. X.282 | ISO/IEC 10742, 
         receivedMlpFramesInGuardRegion."
    ::= { lAPBDLEEntry 17 }

lAPBDLERowStatus OBJECT-TYPE
    SYNTAX      RowStatus
    MAX-ACCESS  read-create
    STATUS      current
    DESCRIPTION 
        "Provides a mechanism whereby management stations, following the 
         RowStatus textual convention of the SNMPv2-TC module, to create 
         and delete conceptual rows in this table."
    REFERENCE   
        "ITU-T Rec. X.282 | ISO/IEC 10742, STD 58, SNMPv2-TC RowStatus."
    ::= { lAPBDLEEntry 18 }

sLPPM OBJECT IDENTIFIER
    ::= { x25Tables 23 }

sLPPMTable OBJECT-TYPE
    SYNTAX      SEQUENCE OF SLPPMEntry
    MAX-ACCESS  not-accessible
    STATUS      current
    DESCRIPTION 
        "The LAPB Signle Link Protoocol Machine managed object.  The 
         sLPPM managed object represents the operation of the LAPB Data 
         Link layer protoocl mahcine described in ISO/IEC 7776 over a 
         single physical link.  An sLPPM managed object may contain at 
         moset on sLPConnection MO and one or more sLPConnectionIVMO.
         
         An sLPPM MO may be crated and deleted explicitly by management 
         operation or created and deleted automatically a part of system 
         oepration.
         
         When the sLPPM MO is operable, the operationalState shall have 
         the value 'enabled'; otherwise, it shall have the value 
         'disabled'.  Transitions of operationalState shall be reported 
         using the stateChange notification."
    REFERENCE   
        "ITU-T Rec. X.282 | ISO/IEC 10742, sLPPM MOC."
    ::= { sLPPM 1 }

sLPPMEntry OBJECT-TYPE
    SYNTAX      SLPPMEntry
    MAX-ACCESS  not-accessible
    STATUS      current
    DESCRIPTION 
        "The sLPPM MO is contained by a lAPBDLE MO.  The name binding 
         which applies when a sLPPM managed object (or an instance of a 
         subclass of the sLPPM MO class) can be created by management as 
         a subordiante object of a lAPBDLE managed object (or subclass), 
         and deleted by amangement."
    REFERENCE   
        "ITU-T Rec. X.282 | ISO/IEC 10742, sLPPM MOC."
    INDEX       { sLPPMCoProtooclMachineId }
    ::= { sLPPMTable 1 }

SLPPMEntry ::= SEQUENCE {
    sLPPMCoProtooclMachineId    SimpleNameType,
    sLPPMOperationalState       OperationalState
}

sLPPMCoProtooclMachineId OBJECT-TYPE
    SYNTAX      SimpleNameType
    MAX-ACCESS  not-accessible
    STATUS      current
    DESCRIPTION 
        ""
    ::= { sLPPMEntry 1 }

sLPPMOperationalState OBJECT-TYPE
    SYNTAX      OperationalState
    MAX-ACCESS  read-only
    STATUS      current
    DESCRIPTION 
        ""
    ::= { sLPPMEntry 2 }

sLPConnection OBJECT IDENTIFIER
    ::= { x25Tables 24 }

sLPConnectionTable OBJECT-TYPE
    SYNTAX      SEQUENCE OF SLPConnectionEntry
    MAX-ACCESS  not-accessible
    STATUS      current
    DESCRIPTION 
        "The LAPB Single Link Protocol Connection managed object.  The 
         sLPConnection managed object represents the local view of a 
         connection between LAPB DLEs over a single physical link.
         
         An sLPConnection MO is created automatically as part of a 
         system operation.
         
         An sLPConnection MO may be deleted automatically as a part of 
         system operation or may be deleted as a result of the 
         deactivate or delete management operations.
         
         An sLPConnectionIVMO may be used as the source of initial 
         values of attributes of an sLPConnection MO.
         
         This table provides the state of all LAPB connections.
         
         This table provides the statistics associated with a given LAPB 
         connection which is associated with a specific LAPB interface."
    REFERENCE   
        "ITU-T Rec. X.282 | ISO/IEC 10742, sLPConnection."
    ::= { sLPConnection 1 }

sLPConnectionEntry OBJECT-TYPE
    SYNTAX      SLPConnectionEntry
    MAX-ACCESS  not-accessible
    STATUS      current
    DESCRIPTION 
        "This is an entry in the state table representing a single LAPB 
         data link connection.
         
         This table entry provides detailed statistics for a given LAPB 
         connection associatedw with a given LAPB interface."
    REFERENCE   
        "ITU-T Rec. X.282 | ISO/IEC 10742."
    INDEX       { sLPConnectionConnectionId }
    ::= { sLPConnectionTable 1 }

SLPConnectionEntry ::= SEQUENCE {
    sLPConnectionConnectionId                       SimpleNameType,
    sLPConnectionUnderlyingConnectionNames          RowPointer,
    sLPConnectionSupportedConnectionNames           RowPointer,
    sLPConnectionInterfaceType                      INTEGER,
    sLPConnectionK                                  Unsigned32,
    sLPConnectionN1                                 Unsigned32,
    sLPConnectionN2                                 Unsigned32,
    sLPConnectionSequenceModulus                    Unsigned32,
    sLPConnectionT1Timer                            TimeInterval,
    sLPConnectionT2Timer                            TimeInterval,
    sLPConnectionFCSErrorsReceived                  Counter32,
    sLPConnectionFRMRsReceived                      Counter32,
    sLPConnectionFRMRsSent                          Counter32,
    sLPConnectionIFrameDataOctetsReceived           Counter32,
    sLPConnectionIFrameDataOctetsSent               Counter32,
    sLPConnectionIFramesReceived                    Counter32,
    sLPConnectionIFramesSent                        Counter32,
    sLPConnectionPollsReceived                      Counter32,
    sLPConnectionREJsReceived                       Counter32,
    sLPConnectionREJsSent                           Counter32,
    sLPConnectionRNRsReceived                       Counter32,
    sLPConnectionRNRsSent                           Counter32,
    sLPConnectionSABMsReceived                      Counter32,
    sLPConnectionSABMsSent                          Counter32,
    sLPConnectionProtocolState                      INTEGER,
    sLPConnectionTimesT1Expired                     Counter32,
    sLPConnectionT3Timer                            TimeInterval,
    sLPConnectionTimesT3Expired                     Counter32,
    sLPConnectionT4Timer                            TimeInterval,
    sLPConnectionTimesT4Expired                     Counter32,
    sLPConnectionAbnormalLinkDisconnectsReceived    Counter32,
    sLPConnectionAbnormalLinkDisconnectsSent        Counter32,
    sLPConnectionLinkResetsReceived                 Counter32,
    sLPConnectionLinkResetsSent                     Counter32,
    sLPConnectionTimesN2Reached                     Counter32,
    sLPConnectionAdministrativeState                AdministrativeState,
    sLPConnectionOperationalState                   OperationalState,
    sLPConnectionUsageState                         UsageState,
    sLPConnectionProceduralStatus                   ProceduralStatus,
    sLPConnectionAlarmStatus                        AlarmStatus,
    sLPConnectionRowStatus                          RowStatus
}

sLPConnectionConnectionId OBJECT-TYPE
    SYNTAX      SimpleNameType
    MAX-ACCESS  not-accessible
    STATUS      current
    DESCRIPTION 
        ""
    REFERENCE   
        "ITU-T Rec. X.723 | ISO/IEC 10165-5"
    ::= { sLPConnectionEntry 1 }

sLPConnectionUnderlyingConnectionNames OBJECT-TYPE
    SYNTAX      RowPointer
    MAX-ACCESS  read-create
    STATUS      current
    DESCRIPTION 
        ""
    REFERENCE   
        "ITU-T Rec. X.723 | ISO/IEC 10165-5"
    ::= { sLPConnectionEntry 2 }

sLPConnectionSupportedConnectionNames OBJECT-TYPE
    SYNTAX      RowPointer
    MAX-ACCESS  read-create
    STATUS      current
    DESCRIPTION 
        ""
    REFERENCE   
        "ITU-T Rec. X.282 | ISO/IEC 10742"
    ::= { sLPConnectionEntry 3 }

sLPConnectionInterfaceType OBJECT-TYPE
    SYNTAX      INTEGER { dTE(0), dCE(1) }
    MAX-ACCESS  read-create
    STATUS      current
    DESCRIPTION 
        "Determines the address mode used by the local DTE."
    REFERENCE   
        "ITU-T Rec. X.282 | ISO/IEC 10742, interfaceType."
    ::= { sLPConnectionEntry 4 }

sLPConnectionK OBJECT-TYPE
    SYNTAX      Unsigned32
    MAX-ACCESS  read-create
    STATUS      current
    DESCRIPTION 
        "Value of the ISO/IEC 7776 parameter k.  The maximum number of 
         sequentially numbered I frames that a DTE may have outstanding 
         (i.e. unacknowledged) at any fiven time."
    REFERENCE   
        "ITU-T Rec. X.282 | ISO/IEC 10742, k."
    ::= { sLPConnectionEntry 5 }

sLPConnectionN1 OBJECT-TYPE
    SYNTAX      Unsigned32
    MAX-ACCESS  read-create
    STATUS      current
    DESCRIPTION 
        "Value of the ISO/IEC 7776 parameter N1.  The maximum number of 
         bits in an I frame (excluding flags and 0 bits inserted for 
         transparency."
    REFERENCE   
        "ITU-T Rec. X.282 | ISO/IEC 10742, n1."
    ::= { sLPConnectionEntry 6 }

sLPConnectionN2 OBJECT-TYPE
    SYNTAX      Unsigned32
    MAX-ACCESS  read-create
    STATUS      current
    DESCRIPTION 
        "Value of the ISO/IEC 7776 parameter N2.  The maximum number of 
         attempts that shall be made to complete the successful 
         transmission of a frame."
    REFERENCE   
        "ITU-T Rec. X.282 | ISO/IEC 10742, n2."
    ::= { sLPConnectionEntry 7 }

sLPConnectionSequenceModulus OBJECT-TYPE
    SYNTAX      Unsigned32 (8 | 128)
    MAX-ACCESS  read-create
    STATUS      current
    DESCRIPTION 
        "Determines basic (modulo 8) or extended (modulo 128) 
         operation."
    REFERENCE   
        "ITU-T Rec. X.282 | ISO/IEC 10742, sequenceModulus."
    ::= { sLPConnectionEntry 8 }

sLPConnectionT1Timer OBJECT-TYPE
    SYNTAX      TimeInterval
    UNITS       "seconds"
    MAX-ACCESS  read-create
    STATUS      current
    DESCRIPTION 
        "Value of the ISO/IEC 7776 parameter Timer T1.  Unit is 
         centiseconds."
    REFERENCE   
        "ITU-T Rec. X.282 | ISO/IEC 10742, t1Timer."
    ::= { sLPConnectionEntry 9 }

sLPConnectionT2Timer OBJECT-TYPE
    SYNTAX      TimeInterval
    UNITS       "seconds"
    MAX-ACCESS  read-create
    STATUS      current
    DESCRIPTION 
        "Value of the ISO/IEC 7776 parameter T2.  Units is 
         centiseconds."
    REFERENCE   
        "ITU-T Rec. X.282 | ISO/IEC 10742, t2Timer."
    ::= { sLPConnectionEntry 10 }

sLPConnectionFCSErrorsReceived OBJECT-TYPE
    SYNTAX      Counter32
    MAX-ACCESS  read-only
    STATUS      current
    DESCRIPTION 
        "Counter.  Total number of frames received with a bad checksum."
    REFERENCE   
        "ITU-T Rec. X.282 | ISO/IEC 10742, fCSErrorsReceived."
    ::= { sLPConnectionEntry 11 }

sLPConnectionFRMRsReceived OBJECT-TYPE
    SYNTAX      Counter32
    MAX-ACCESS  read-only
    STATUS      current
    DESCRIPTION 
        "Counter.  Total number of FRMR frames received."
    REFERENCE   
        "ITU-T Rec. X.282 | ISO/IEC 10742, fRMRsReceived."
    ::= { sLPConnectionEntry 12 }

sLPConnectionFRMRsSent OBJECT-TYPE
    SYNTAX      Counter32
    MAX-ACCESS  read-only
    STATUS      current
    DESCRIPTION 
        "Counter.  Total number of FRMR frames sent."
    REFERENCE   
        "ITU-T Rec. X.282 | ISO/IEC 10742, fRMRsSent."
    ::= { sLPConnectionEntry 13 }

sLPConnectionIFrameDataOctetsReceived OBJECT-TYPE
    SYNTAX      Counter32
    MAX-ACCESS  read-only
    STATUS      current
    DESCRIPTION 
        "Counter Total number of data octets received in I frames.  Only 
         data octets in new I frames are counted, i.e. retransmitted 
         frames that are received do not cause the counter to be 
         incremented."
    REFERENCE   
        "ITU-T Rec. X.282 | ISO/IEC 10742, iFrameDataOctetsReceived."
    ::= { sLPConnectionEntry 14 }

sLPConnectionIFrameDataOctetsSent OBJECT-TYPE
    SYNTAX      Counter32
    MAX-ACCESS  read-only
    STATUS      current
    DESCRIPTION 
        "Counter.  Total number of data octets sent in I frames.  Only 
         data octets in new I frames are counted, i.e., retransmitted 
         frames that are sent do not cause the counter to be 
         incremented."
    REFERENCE   
        "ITU-T Rec. X.282 | ISO/IEC 10742, iFrameDataOctetsSent."
    ::= { sLPConnectionEntry 15 }

sLPConnectionIFramesReceived OBJECT-TYPE
    SYNTAX      Counter32
    MAX-ACCESS  read-only
    STATUS      current
    DESCRIPTION 
        "Counter.  Total number of I frames received.  Only new I frames 
         are counted, i.e. retransmitted frames that are received do not 
         cause the counter to be incremented."
    REFERENCE   
        "ITU-T Rec. X.282 | ISO/IEC 10742, iFramesReceived."
    ::= { sLPConnectionEntry 16 }

sLPConnectionIFramesSent OBJECT-TYPE
    SYNTAX      Counter32
    MAX-ACCESS  read-only
    STATUS      current
    DESCRIPTION 
        "Counter.  Total number of I frame sent.  Only new I frames are 
         counted, i.e., retransmitted frames that are sent do not cause 
         the counter to be incremented."
    REFERENCE   
        "ITU-T Rec. X.282 | ISO/IEC 10742, iFramesSent."
    ::= { sLPConnectionEntry 17 }

sLPConnectionPollsReceived OBJECT-TYPE
    SYNTAX      Counter32
    MAX-ACCESS  read-only
    STATUS      current
    DESCRIPTION 
        "Counter.  Total number of command frames received with P-bit 
         set."
    REFERENCE   
        "ITU-T Rec. X.282 | ISO/IEC 10742, pollsReceived."
    ::= { sLPConnectionEntry 18 }

sLPConnectionREJsReceived OBJECT-TYPE
    SYNTAX      Counter32
    MAX-ACCESS  read-only
    STATUS      current
    DESCRIPTION 
        "Counter.  Total number of REJ frames received."
    REFERENCE   
        "ITU-T Rec. X.282 | ISO/IEC 10742, rEJsReceived."
    ::= { sLPConnectionEntry 19 }

sLPConnectionREJsSent OBJECT-TYPE
    SYNTAX      Counter32
    MAX-ACCESS  read-only
    STATUS      current
    DESCRIPTION 
        "Counter.  Total number of REJ frames sent."
    REFERENCE   
        "ITU-T Rec. X.282 | ISO/IEC 10742, rEJsSent."
    ::= { sLPConnectionEntry 20 }

sLPConnectionRNRsReceived OBJECT-TYPE
    SYNTAX      Counter32
    MAX-ACCESS  read-only
    STATUS      current
    DESCRIPTION 
        "Counter Total number of RNR frames received."
    REFERENCE   
        "ITU-T Rec. X.282 | ISO/IEC 10742, rNRsReceived."
    ::= { sLPConnectionEntry 21 }

sLPConnectionRNRsSent OBJECT-TYPE
    SYNTAX      Counter32
    MAX-ACCESS  read-only
    STATUS      current
    DESCRIPTION 
        "Counter.  Total number of RNR frames sent."
    REFERENCE   
        "ITU-T Rec. X.282 | ISO/IEC 10742, rNRsSent."
    ::= { sLPConnectionEntry 22 }

sLPConnectionSABMsReceived OBJECT-TYPE
    SYNTAX      Counter32
    MAX-ACCESS  read-only
    STATUS      current
    DESCRIPTION 
        "Counter.  Total number of SABM/SABME frames received."
    REFERENCE   
        "ITU-T Rec. X.282 | ISO/IEC 10742, sABMsReceived."
    ::= { sLPConnectionEntry 23 }

sLPConnectionSABMsSent OBJECT-TYPE
    SYNTAX      Counter32
    MAX-ACCESS  read-only
    STATUS      current
    DESCRIPTION 
        "Counter.  Total number of SABM/SABME frames sent."
    REFERENCE   
        "ITU-T Rec. X.282 | ISO/IEC 10742, sABMsSent."
    ::= { sLPConnectionEntry 24 }

sLPConnectionProtocolState OBJECT-TYPE
    SYNTAX      INTEGER { disconnectedPhase(0), linkdisconnectionhase(1), 
                    linkSetUpPhase(2), informationTransferPhase(3), 
                    frameRejectCondition(4), busyCondition(5), 
                    sentRejectCondition(6), 
                    systemParametersAndErrorRecovery(7) }
    MAX-ACCESS  read-only
    STATUS      current
    DESCRIPTION 
        "Local state of a LAPB (SLP) connection."
    REFERENCE   
        "ITU-T Rec. X.282 | ISO/IEC 10742, sLPProtocolState."
    ::= { sLPConnectionEntry 25 }

sLPConnectionTimesT1Expired OBJECT-TYPE
    SYNTAX      Counter32
    MAX-ACCESS  read-only
    STATUS      current
    DESCRIPTION 
        "Counter.  Total number of times the local Timer T1 expired."
    REFERENCE   
        "ITU-T Rec. X.282 | ISO/IEC 10742, timesT1Expired."
    ::= { sLPConnectionEntry 26 }

sLPConnectionT3Timer OBJECT-TYPE
    SYNTAX      TimeInterval
    UNITS       "seconds"
    MAX-ACCESS  read-create
    STATUS      current
    DESCRIPTION 
        "Value of the ISO/IEC 7776 parameter or ITU-T X.25 mandatory 
         parameter T3.  Unit is centiseconds."
    REFERENCE   
        "ITU-T Rec. X.282 | ISO/IEC 10742, t3Timer."
    ::= { sLPConnectionEntry 27 }

sLPConnectionTimesT3Expired OBJECT-TYPE
    SYNTAX      Counter32
    MAX-ACCESS  read-only
    STATUS      current
    DESCRIPTION 
        "Counter.  Total number of times local Timer T3 expired."
    REFERENCE   
        "ITU-T Rec. X.282 | ISO/IEC 10742, timesT3Expired."
    ::= { sLPConnectionEntry 28 }

sLPConnectionT4Timer OBJECT-TYPE
    SYNTAX      TimeInterval
    UNITS       "seconds"
    MAX-ACCESS  read-create
    STATUS      current
    DESCRIPTION 
        "Value of the ISO/IEC 7776 parameter T4.  The maximum time a DTE 
         or a DCE will allow without frames being exchangd on the data 
         link.  Units is centiseconds."
    REFERENCE   
        "ITU-T Rec. X.282 | ISO/IEC 10742, t4Timer."
    ::= { sLPConnectionEntry 29 }

sLPConnectionTimesT4Expired OBJECT-TYPE
    SYNTAX      Counter32
    MAX-ACCESS  read-only
    STATUS      current
    DESCRIPTION 
        "Counter.  Total number of times local Timer T4 expired."
    REFERENCE   
        "ITU-T Rec. X.282 | ISO/IEC 10742, timesT4Expired."
    ::= { sLPConnectionEntry 30 }

sLPConnectionAbnormalLinkDisconnectsReceived OBJECT-TYPE
    SYNTAX      Counter32
    MAX-ACCESS  read-only
    STATUS      current
    DESCRIPTION 
        "Counter.  Total number of received abnormal Link Disconnects."
    REFERENCE   
        "ITU-T Rec. X.282 | ISO/IEC 10742."
    ::= { sLPConnectionEntry 31 }

sLPConnectionAbnormalLinkDisconnectsSent OBJECT-TYPE
    SYNTAX      Counter32
    MAX-ACCESS  read-only
    STATUS      current
    DESCRIPTION 
        "Counter.  Total number of sent abnormal Link Disconnects."
    REFERENCE   
        "ITU-T Rec. X.282 | ISO/IEC 10742."
    ::= { sLPConnectionEntry 32 }

sLPConnectionLinkResetsReceived OBJECT-TYPE
    SYNTAX      Counter32
    MAX-ACCESS  read-only
    STATUS      current
    DESCRIPTION 
        "Counter.  Total number of received Link Resets."
    REFERENCE   
        "ITU-T Rec. X.282 | ISO/IEC 10742."
    ::= { sLPConnectionEntry 33 }

sLPConnectionLinkResetsSent OBJECT-TYPE
    SYNTAX      Counter32
    MAX-ACCESS  read-only
    STATUS      current
    DESCRIPTION 
        "Counter.  Total number of sent Link Resets."
    REFERENCE   
        "ITU-T Rec. X.282 | ISO/IEC 10742."
    ::= { sLPConnectionEntry 34 }

sLPConnectionTimesN2Reached OBJECT-TYPE
    SYNTAX      Counter32
    MAX-ACCESS  read-only
    STATUS      current
    DESCRIPTION 
        "Counter.  Total number of times N2 was reached."
    REFERENCE   
        "ITU-T Rec. X.282 | ISO/IEC 10742."
    ::= { sLPConnectionEntry 35 }

sLPConnectionAdministrativeState OBJECT-TYPE
    SYNTAX      AdministrativeState
    MAX-ACCESS  read-create
    STATUS      current
    DESCRIPTION 
        "Provides the X.731 administrative status of the LAPB 
         connection.  When locked(0), the LAPB connection is 
         administratively prohibitted from forming and when set to 
         locked(0) will be abruptly disconnected if already formed.  
         When unlocked(1) the LAPB connection is administratively 
         permitted to form.  When set to
         shuttingDown(2), the LAPB connection will be gracefully 
         withdrawn from service and will enter the locked(0) state when 
         shut down."
    REFERENCE   
        "ITU-T Rec. X.282 | ISO/IEC 10742,
         ITU-T Rec. X.721 (1992)."
    ::= { sLPConnectionEntry 36 }

sLPConnectionOperationalState OBJECT-TYPE
    SYNTAX      OperationalState
    MAX-ACCESS  read-only
    STATUS      current
    DESCRIPTION 
        "Provides the X.731 operational state of this LAPB connection."
    REFERENCE   
        "ITU-T Rec. X.282 | ISO/IEC 10742,
         ITU-T Rec. X.721 (1992)."
    ::= { sLPConnectionEntry 37 }

sLPConnectionUsageState OBJECT-TYPE
    SYNTAX      UsageState
    MAX-ACCESS  read-only
    STATUS      current
    DESCRIPTION 
        "Provides the X.731 usage state of this LAPB connection.  When 
         idle(0), the LABP connection is not currently in use (although 
         it may still be formed).  When active(1), the resource is being 
         used and has sufficient spare operating capacity to provide for 
         additional users simultaneously.  When busy(2), the resource is 
         in use, but it has no spare capacity to provide additional 
         users at this instant."
    REFERENCE   
        "ITU-T Rec. X.282 | ISO/IEC 10742,
         ITU-T Rec. X.721 (1992)."
    ::= { sLPConnectionEntry 38 }

sLPConnectionProceduralStatus OBJECT-TYPE
    SYNTAX      ProceduralStatus
    MAX-ACCESS  read-only
    STATUS      current
    DESCRIPTION 
        "Provides the X.731 procedural status of this LAPB connection.  
         The procedural status contains initializationRequired(0) when 
         the LAPB requires initiation action to form or reform a 
         connection.  It contains notInitialized(1) when the LAPB 
         connection is in disconnected mode (ADM); initializing(2) when 
         forming connection (SABM) and terminating(3) when disconnecting 
         (DISC)."
    REFERENCE   
        "ITU-T Rec. X.282 | ISO/IEC 10742,
         ITU-T Rec. X.721 (1992)."
    ::= { sLPConnectionEntry 39 }

sLPConnectionAlarmStatus OBJECT-TYPE
    SYNTAX      AlarmStatus
    MAX-ACCESS  read-only
    STATUS      current
    DESCRIPTION 
        "Provides the alarm status of this LAPB connection."
    REFERENCE   
        "ITU-T Rec. X.282 | ISO/IEC 10742,
         ITU-T Rec. X.721 (1992)."
    ::= { sLPConnectionEntry 40 }

sLPConnectionRowStatus OBJECT-TYPE
    SYNTAX      RowStatus
    MAX-ACCESS  read-create
    STATUS      current
    DESCRIPTION 
        "Provides a mechanism whereby management stations, following the 
         RowStatus textual convetion of the SNMPv2-TC module, may create 
         or destroy conceptual rows in this table."
    REFERENCE   
        "STD 58, SNMPv2-TC RowStatus."
    ::= { sLPConnectionEntry 41 }

sLPConnectionIVMO OBJECT IDENTIFIER
    ::= { x25Tables 25 }

sLPConnectionIVMOTable OBJECT-TYPE
    SYNTAX      SEQUENCE OF SLPConnectionIVMOEntry
    MAX-ACCESS  not-accessible
    STATUS      current
    DESCRIPTION 
        ""
    REFERENCE   
        "ITU-T Rec. X.282 | ISO/IEC 10742."
    ::= { sLPConnectionIVMO 1 }

sLPConnectionIVMOEntry OBJECT-TYPE
    SYNTAX      SLPConnectionIVMOEntry
    MAX-ACCESS  not-accessible
    STATUS      current
    DESCRIPTION 
        ""
    REFERENCE   
        "ITU-T Rec. X.282 | ISO/IEC 10742."
    INDEX       { sLPConnectionIVMOName }
    ::= { sLPConnectionIVMOTable 1 }

SLPConnectionIVMOEntry ::= SEQUENCE {
    sLPConnectionIVMOName               SimpleNameType,
    sLPConnectionIVMOInterfaceType      INTEGER,
    sLPConnectionIVMOK                  Integer32,
    sLPConnectionIVMON1                 Integer32,
    sLPConnectionIVMON2                 Integer32,
    sLPConnectionIVMOSequenceModulus    Integer32,
    sLPConnectionIVMOT1Timer            TimeInterval,
    sLPConnectionIVMOT2Timer            TimeInterval,
    sLPConnectionIVMOT3Timer            TimeInterval,
    sLPConnectionIVMOT4Timer            TimeInterval,
    sLPConnectionIVMORowStatus          RowStatus
}

sLPConnectionIVMOName OBJECT-TYPE
    SYNTAX      SimpleNameType
    MAX-ACCESS  not-accessible
    STATUS      current
    DESCRIPTION 
        ""
    REFERENCE   
        "IEEE 802.2 (ISO/IEC 10742)."
    ::= { sLPConnectionIVMOEntry 1 }

sLPConnectionIVMOInterfaceType OBJECT-TYPE
    SYNTAX      INTEGER { dTE(0), dCE(1) }
    MAX-ACCESS  read-create
    STATUS      current
    DESCRIPTION 
        "Sets the default interface type for this profile.  The default 
         is the value of sLPConnectionDefaultInterfaceType."
    REFERENCE   
        "IEEE 802.2 (ISO/IEC 10742)."
    ::= { sLPConnectionIVMOEntry 2 }

sLPConnectionIVMOK OBJECT-TYPE
    SYNTAX      Integer32
    MAX-ACCESS  read-create
    STATUS      current
    DESCRIPTION 
        "Sets the default k value for this profile.  The default is the 
         value of sLPConnectionDefaultK."
    REFERENCE   
        "IEEE 802.2 (ISO/IEC 10742)."
    ::= { sLPConnectionIVMOEntry 3 }

sLPConnectionIVMON1 OBJECT-TYPE
    SYNTAX      Integer32
    MAX-ACCESS  read-create
    STATUS      current
    DESCRIPTION 
        "Sets the default n1 value for this profile.  The default is the 
         value of sLPConnectionDefaultN1."
    REFERENCE   
        "IEEE 802.2 (ISO/IEC 10742)."
    ::= { sLPConnectionIVMOEntry 4 }

sLPConnectionIVMON2 OBJECT-TYPE
    SYNTAX      Integer32
    MAX-ACCESS  read-create
    STATUS      current
    DESCRIPTION 
        "Sets the default n2 value for this profile.  The default is the 
         value of sLPConnectionDefaultN2."
    REFERENCE   
        "IEEE 802.2 (ISO/IEC 10742)."
    ::= { sLPConnectionIVMOEntry 5 }

sLPConnectionIVMOSequenceModulus OBJECT-TYPE
    SYNTAX      Integer32 (8 | 128)
    MAX-ACCESS  read-create
    STATUS      current
    DESCRIPTION 
        "Sets the default sequence modulus for this profile.  The 
         default is the value of sLPConnectionDefaultSequenceModulus."
    REFERENCE   
        "IEEE 802.2 (ISO/IEC 10742)."
    ::= { sLPConnectionIVMOEntry 6 }

sLPConnectionIVMOT1Timer OBJECT-TYPE
    SYNTAX      TimeInterval
    MAX-ACCESS  read-create
    STATUS      current
    DESCRIPTION 
        "Sets the default initial t1Timer value for this profile.  The 
         default is the value of sLPConnectionDefaultT1Timer."
    REFERENCE   
        "IEEE 802.2 (ISO/IEC 10742)."
    ::= { sLPConnectionIVMOEntry 7 }

sLPConnectionIVMOT2Timer OBJECT-TYPE
    SYNTAX      TimeInterval
    MAX-ACCESS  read-create
    STATUS      current
    DESCRIPTION 
        "Sets the default initial t2Timer value for this profile.  The 
         default is the value of sLPConnectionDefaultT2Timer."
    REFERENCE   
        "IEEE 802.2 (ISO/IEC 10742)."
    ::= { sLPConnectionIVMOEntry 8 }

sLPConnectionIVMOT3Timer OBJECT-TYPE
    SYNTAX      TimeInterval
    MAX-ACCESS  read-create
    STATUS      current
    DESCRIPTION 
        "Sets the default initial t3Timer value for this profile.  The 
         default is the value of sLPConnectionDefaultT3Timer."
    REFERENCE   
        "IEEE 802.2 (ISO/IEC 10742)."
    ::= { sLPConnectionIVMOEntry 9 }

sLPConnectionIVMOT4Timer OBJECT-TYPE
    SYNTAX      TimeInterval
    MAX-ACCESS  read-create
    STATUS      current
    DESCRIPTION 
        "Sets the default initial t4Timer value for this profile.  The 
         default is the value of sLPConnectionDefaultT4Timer."
    REFERENCE   
        "IEEE 802.2 (ISO/IEC 10742)."
    ::= { sLPConnectionIVMOEntry 10 }

sLPConnectionIVMORowStatus OBJECT-TYPE
    SYNTAX      RowStatus
    MAX-ACCESS  read-create
    STATUS      current
    DESCRIPTION 
        "Provides a mechanism whereby management stations, following the 
         RowStatus textual convention of the SNMPv2-TC module, may 
         create or destroy conceptual rows in this table."
    REFERENCE   
        "IEEE 802.2 (ISO/IEC 10742)."
    ::= { sLPConnectionIVMOEntry 11 }

x25Scalars OBJECT IDENTIFIER
    ::= { x25Objects 2 }

x25Globals OBJECT IDENTIFIER
    ::= { x25Scalars 1 }

x25DiscontinuityTime OBJECT-TYPE
    SYNTAX      TimeStamp
    MAX-ACCESS  read-only
    STATUS      current
    DESCRIPTION 
        "Provides the time since the last reboot at which a 
         discontinuity in counters and gauges occurred possibly 
         resulting in the reset of counters and gauges to zero."
    REFERENCE   
        "SMIv2"
    ::= { x25Globals 1 }

x25SubsystemId OBJECT-TYPE
    SYNTAX      DisplayString
    MAX-ACCESS  read-only
    STATUS      current
    DESCRIPTION 
        "The subsystem managed object class represents a portion of a 
         system where components are named independently of the 
         components of other subsystems.  The datalinkSubsystem managed 
         object.  There shall be exactly one of these managed objects 
         within a system.  It exists to provide a container for all 
         managed objects in a system, that related to the operation of 
         the Datalink layer.  The datalinkSubsystem managed object 
         cannot be created or deleted explicitly by management 
         operation.  It exists inherently in a system; created and 
         deleted as part of system operation."
    REFERENCE   
        "ITU-T Rec. X.282 | ISO/IEC 10742, datalinkSubsystem."
    DEFVAL      { "datalinkSubsystem" }
    ::= { x25Globals 2 }

x25Defaults OBJECT IDENTIFIER
    ::= { x25Scalars 2 }

sLPConnectionDefaults OBJECT IDENTIFIER
    ::= { x25Defaults 1 }

sLPConnectionDefaultInterfaceType OBJECT-TYPE
    SYNTAX      INTEGER { dTE(0), dCE(1) }
    MAX-ACCESS  read-write
    STATUS      current
    DESCRIPTION 
        "Sets the default value for the sLPConnectionInterfaceType 
         element of the sLPConnectionTable.  When set by a management 
         station, the value set should persist across agent and system 
         reboots.  The DEFVAL, therefore, is only applicable when this 
         default has never been set by a management station."
    REFERENCE   
        "ITU-T Rec. X.282 | ISO/IEC 10742."
    DEFVAL      { dTE }
    ::= { sLPConnectionDefaults 1 }

sLPConnectionDefaultK OBJECT-TYPE
    SYNTAX      Integer32
    MAX-ACCESS  read-write
    STATUS      current
    DESCRIPTION 
        "Sets the default value for the sLPConnectionK element of the 
         sLPConnectionTable.  When set by a management station, the 
         value set should persist across agent and system reboots.  The 
         DEFVAL, therefore, is only applicable when this default has 
         never been set by a management station."
    REFERENCE   
        "ITU-T Rec. X.282 | ISO/IEC 10742."
    ::= { sLPConnectionDefaults 2 }

sLPConnectionDefaultN1 OBJECT-TYPE
    SYNTAX      Integer32
    MAX-ACCESS  read-write
    STATUS      current
    DESCRIPTION 
        "Sets the default value for the sLPConnectionN1 element of the 
         sLPConnectionTable.  When set by a management station, the 
         value set should persist across agent and system reboots.  The 
         DEFVAL, therefore, is only applicable when this default has 
         never been set by a management station."
    REFERENCE   
        "ITU-T Rec. X.282 | ISO/IEC 10742."
    ::= { sLPConnectionDefaults 3 }

sLPConnectionDefaultN2 OBJECT-TYPE
    SYNTAX      Integer32
    MAX-ACCESS  read-write
    STATUS      current
    DESCRIPTION 
        "Sets the default value for the sLPConnectionN2 element of the 
         sLPConnectionTable.  When set by a management station, the 
         value set should persist across agent and system reboots.  The 
         DEFVAL, therefore, is only applicable when this default has 
         never been set by a management station."
    REFERENCE   
        "ITU-T Rec. X.282 | ISO/IEC 10742."
    ::= { sLPConnectionDefaults 4 }

sLPConnectionDefaultSequenceModulus OBJECT-TYPE
    SYNTAX      Integer32 (8 | 128)
    MAX-ACCESS  read-write
    STATUS      current
    DESCRIPTION 
        "Sets the default value for the sLPConnectionModulus element of 
         the sLPConnectionTable.  When set by a management station, the 
         value set should persist across agent and system reboots.  The 
         DEFVAL, therefore, is only applicable when this default has 
         never been set by a management station."
    REFERENCE   
        "ITU-T Rec. X.282 | ISO/IEC 10742."
    ::= { sLPConnectionDefaults 5 }

sLPConnectionDefaultT1Timer OBJECT-TYPE
    SYNTAX      TimeInterval
    MAX-ACCESS  read-write
    STATUS      current
    DESCRIPTION 
        "Sets the default value for the sLPConnectionT1Timer element of 
         the sLPConnectionTable.  When set by a management station, the 
         value set should persist across agent and system reboots.  The 
         DEFVAL, therefore, is only applicable when this default has 
         never been set by a management station."
    REFERENCE   
        "ITU-T Rec. X.282 | ISO/IEC 10742."
    ::= { sLPConnectionDefaults 6 }

sLPConnectionDefaultT2Timer OBJECT-TYPE
    SYNTAX      TimeInterval
    MAX-ACCESS  read-write
    STATUS      current
    DESCRIPTION 
        "Sets the default value for the sLPConnectionT2Timer element of 
         the sLPConnectionTable.  When set by a management station, the 
         value set should persist across agent and system reboots.  The 
         DEFVAL, therefore, is only applicable when this default has 
         never been set by a management station."
    REFERENCE   
        "ITU-T Rec. X.282 | ISO/IEC 10742."
    ::= { sLPConnectionDefaults 7 }

sLPConnectionDefaultT3Timer OBJECT-TYPE
    SYNTAX      TimeInterval
    MAX-ACCESS  read-write
    STATUS      current
    DESCRIPTION 
        "Sets the default value for the sLPConnectionT3Timer element of 
         the sLPConnectionTable.  When set by a management station, the 
         value set should persist across agent and system reboots.  The 
         DEFVAL, therefore, is only applicable when this default has 
         never been set by a management station."
    REFERENCE   
        "ITU-T Rec. X.282 | ISO/IEC 10742."
    ::= { sLPConnectionDefaults 8 }

sLPConnectionDefaultT4Timer OBJECT-TYPE
    SYNTAX      TimeInterval
    MAX-ACCESS  read-write
    STATUS      current
    DESCRIPTION 
        "Sets the default value for the sLPConnectionT4Timer element of 
         the sLPConnectionTable.  When set by a management station, the 
         value set should persist across agent and system reboots.  The 
         DEFVAL, therefore, is only applicable when this default has 
         never been set by a management station."
    REFERENCE   
        "ITU-T Rec. X.282 | ISO/IEC 10742."
    ::= { sLPConnectionDefaults 9 }

lLCConnection2Defaults OBJECT IDENTIFIER
    ::= { x25Defaults 2 }

lLCConnection2DefaultMaximumRetransmissions OBJECT-TYPE
    SYNTAX      Integer32
    MAX-ACCESS  read-write
    STATUS      current
    DESCRIPTION 
        "Sets the default value for the 
         lLCConnection2MaximumRetransmissions element of the 
         lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 1 }

lLCConnection2DefaultReceivedWindowSize OBJECT-TYPE
    SYNTAX      Integer32
    MAX-ACCESS  read-write
    STATUS      current
    DESCRIPTION 
        "Sets the default value for the lLCConnection2ReceivedWindowSize 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 2 }

lLCConnection2DefaultSendWindowSize OBJECT-TYPE
    SYNTAX      Integer32
    MAX-ACCESS  read-write
    STATUS      current
    DESCRIPTION 
        "Sets the default value for the lLCConnection2SendWindowSize 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 3 }

lLCConnection2DefaultAcknowledgeTimeoutValue OBJECT-TYPE
    SYNTAX      TimeInterval
    MAX-ACCESS  read-write
    STATUS      current
    DESCRIPTION 
        "Sets the default value for the 
         lLCConnection2AcknowleTimeoutValue element of the 
         lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 4 }

lLCConnection2DefaultBusyStateTimeoutValue OBJECT-TYPE
    SYNTAX      TimeInterval
    MAX-ACCESS  read-write
    STATUS      current
    DESCRIPTION 
        "Sets the default value for the 
         lLCConnection2BusyStateTimeoutValue element of the 
         lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 5 }

lLCConnection2DefaultPBitTimeoutValue OBJECT-TYPE
    SYNTAX      TimeInterval
    MAX-ACCESS  read-write
    STATUS      current
    DESCRIPTION 
        "Sets the default value for the lLCConnection2BitTImeoutValue 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 6 }

lLCConnection2DefaultRejectTimeoutValue OBJECT-TYPE
    SYNTAX      TimeInterval
    MAX-ACCESS  read-write
    STATUS      current
    DESCRIPTION 
        "Sets the default value for the lLCConnection2RejectTimeoutValue 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 7 }

lLCConnection2DefaultRoute OBJECT-TYPE
    SYNTAX      OCTET STRING
    MAX-ACCESS  read-write
    STATUS      current
    DESCRIPTION 
        "Sets the default value for the lLCConnection2Route element of 
         the lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 8 }

lLCConnection2DefaultKStep OBJECT-TYPE
    SYNTAX      Integer32
    MAX-ACCESS  read-write
    STATUS      current
    DESCRIPTION 
        "Sets the default value for the lLCConnection2KStep element of 
         the lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 9 }

lLCConnection2DefaultMaxSendWindowSize OBJECT-TYPE
    SYNTAX      Integer32
    MAX-ACCESS  read-write
    STATUS      current
    DESCRIPTION 
        "Sets the default value for the lLCConnection2MaxSendWindowSize 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 10 }

lLCConnection2DefaultOptionalTolerationIPDUs OBJECT-TYPE
    SYNTAX      TruthValue
    MAX-ACCESS  read-write
    STATUS      current
    DESCRIPTION 
        "Sets the default value for the 
         lLCConnection2OptionalTolerationIPDUs element of the 
         lLCConnection2Table.  When set by a management station, the 
         value set should persist across agent and system reboots.  The 
         DEFVAL, therefore, is only applicable when this default has 
         never been set by a  management station."
    REFERENCE   
        "IEEE 802.2 (ISO/IEC 8802-2)."
    ::= { lLCConnection2Defaults 11 }

lLCConnectionlessAckDefaults OBJECT IDENTIFIER
    ::= { x25Defaults 3 }

lLCConnectionlessAckDefaultMaximumLLCInformationFieldSize OBJECT-TYPE
    SYNTAX      Integer32
    MAX-ACCESS  read-write
    STATUS      current
    DESCRIPTION 
        "Set the default value for the 
         lLCConnectionlessAckMaximumLLCInformationFieldSize element of 
         the lLCConnectionlessAckTable.  When set by a management 
         station, the value set should persist across the agen and 
         system reboots.  The DEFVAL, therefore, is only applicable when 
         this default has never been set by a management station."
    REFERENCE   
        "IEEE 802.2 (ISO/IEC 8802-2)"
    ::= { lLCConnectionlessAckDefaults 1 }

lLCConnectionlessAckDefaultMaximumRetransmissions OBJECT-TYPE
    SYNTAX      Integer32
    MAX-ACCESS  read-write
    STATUS      current
    DESCRIPTION 
        "Set the default value for the 
         lLCConnectionlessAckMaximumRetransmissions element of the 
         lLCConnectionlessAckTable.  When set by a management station, 
         the value set should persist across the agen and system 
         reboots.  The DEFVAL, therefore, is only applicable when this 
         default has never been set by a management station."
    REFERENCE   
        "IEEE 802.2 (ISO/IEC 8802-2)"
    ::= { lLCConnectionlessAckDefaults 2 }

x25Notifs OBJECT IDENTIFIER
    ::= { x25Objects 3 }

pdusDiscarded OBJECT-TYPE
    SYNTAX      Gauge32
    MAX-ACCESS  accessible-for-notify
    STATUS      current
    DESCRIPTION 
        "For use with lLCStationEvent notification."
    REFERENCE   
        "IEEE 802.2 (ISO/IEC 8802-2)."
    ::= { x25Notifs 1 }

bufferProblems OBJECT-TYPE
    SYNTAX      Gauge32
    MAX-ACCESS  accessible-for-notify
    STATUS      current
    DESCRIPTION 
        "For use with llCStationEvent notification."
    REFERENCE   
        "IEEE 802.2 (ISO/IEC 8802-2)."
    ::= { x25Notifs 2 }

pdusDiscarded1 OBJECT-TYPE
    SYNTAX      Gauge32
    MAX-ACCESS  accessible-for-notify
    STATUS      current
    DESCRIPTION 
        "For use with lLCConnection2Event notification."
    REFERENCE   
        "IEEE 802.2 (ISO/IEC 8802-2)."
    ::= { x25Notifs 3 }

pdusDiscarded2 OBJECT-TYPE
    SYNTAX      Gauge32
    MAX-ACCESS  accessible-for-notify
    STATUS      current
    DESCRIPTION 
        "For use with lLCConnection2Event notification."
    REFERENCE   
        "IEEE 802.2 (ISO/IEC 8802-2)."
    ::= { x25Notifs 4 }

pduRetransmissions OBJECT-TYPE
    SYNTAX      Gauge32
    MAX-ACCESS  accessible-for-notify
    STATUS      current
    DESCRIPTION 
        "For use with lLCConnection2Event notification."
    REFERENCE   
        "IEEE 802.2 (ISO/IEC 8802-2)."
    ::= { x25Notifs 5 }

acknowledgeTimeout OBJECT-TYPE
    SYNTAX      TimeInterval
    MAX-ACCESS  accessible-for-notify
    STATUS      current
    DESCRIPTION 
        "For use with lLCConnection2Event notification."
    REFERENCE   
        "IEEE 802.2 (ISO/IEC 8802-2)."
    ::= { x25Notifs 6 }

busyStateTimeout OBJECT-TYPE
    SYNTAX      TimeInterval
    MAX-ACCESS  accessible-for-notify
    STATUS      current
    DESCRIPTION 
        "For use with lLCConnection2Event notification."
    REFERENCE   
        "IEEE 802.2 (ISO/IEC 8802-2)."
    ::= { x25Notifs 7 }

rejectTimeout OBJECT-TYPE
    SYNTAX      TimeInterval
    MAX-ACCESS  accessible-for-notify
    STATUS      current
    DESCRIPTION 
        "For use with lLCConnection2Event notification."
    REFERENCE   
        "IEEE 802.2 (ISO/IEC 8802-2)."
    ::= { x25Notifs 8 }

pBitTimeout OBJECT-TYPE
    SYNTAX      TimeInterval
    MAX-ACCESS  accessible-for-notify
    STATUS      current
    DESCRIPTION 
        "For use with lLCConnection2Event notification."
    REFERENCE   
        "IEEE 802.2 (ISO/IEC 8802-2)."
    ::= { x25Notifs 9 }

type2Violation OBJECT-TYPE
    SYNTAX      Gauge32
    MAX-ACCESS  accessible-for-notify
    STATUS      current
    DESCRIPTION 
        "For use with lLCConnection2Event notification."
    REFERENCE   
        "IEEE 802.2 (ISO/IEC 8802-2)."
    ::= { x25Notifs 10 }

retransmissions OBJECT-TYPE
    SYNTAX      Gauge32
    MAX-ACCESS  accessible-for-notify
    STATUS      current
    DESCRIPTION 
        "For use with lLCConnection2Event and lLCClessACKEvent notification."
    REFERENCE   
        "IEEE 802.2 (ISO/IEC 8802-2)."
    ::= { x25Notifs 11 }

type3Violation OBJECT-TYPE
    SYNTAX      Gauge32
    MAX-ACCESS  accessible-for-notify
    STATUS      current
    DESCRIPTION 
        "For use with lLCClessACKEvent notification."
    REFERENCE   
        "IEEE 802.2 (ISO/IEC 8802-2)."
    ::= { x25Notifs 12 }

noResponse OBJECT-TYPE
    SYNTAX      Gauge32
    MAX-ACCESS  accessible-for-notify
    STATUS      current
    DESCRIPTION 
        "For use with lLCClessACKEvent notification."
    REFERENCE   
        "IEEE 802.2 (ISO/IEC 8802-2)."
    ::= { x25Notifs 13 }

x25Oids OBJECT IDENTIFIER
    ::= { x25Objects 4 }

x25Conformance OBJECT IDENTIFIER
    ::= { x25-LLC-MIB 2 }

x25Compliances OBJECT IDENTIFIER
    ::= { x25Conformance 1 }

x25Groups OBJECT IDENTIFIER
    ::= { x25Conformance 2 }

lLCStationEvent NOTIFICATION-TYPE
    OBJECTS     { tmnObjectInstance }
    STATUS      current
    DESCRIPTION 
        "This notification will be sent for either PDUs discarded, 
         buffer problems, or type 3 retransmissions.
         
          Additional paramters include:
         
            - pdusDiscarded
            - bufferProblems
            - retransmissions"
    REFERENCE   
        "IEEE 802.2 (ISO/IEC 8802-3), lLCStationEvent-N."
    ::= { x25Notifications 1 }

lLCConnection2Event NOTIFICATION-TYPE
    OBJECTS     { tmnObjectInstance }
    STATUS      current
    DESCRIPTION 
        "This event will be sent for the following conditions: duplicate 
         IPDUs received, PDUs discarded 1, PDUs discarded 2, PDU 
         retransmissions, type2 violations, type2 acknowledgement 
         timeout value, type 2 reject timeout value, type 2 busy state, 
         timeout value type 2, p-bit timeout value, retransmissions.  
         For each condition, there is an appropriate parameter to be 
         included in the notification.
         
          Additional paramters include:
         
            - pdusDiscarded1
            - pdusDiscarded2
            - pduRetransmissions
            - acknowledgeTimeout
            - busyStateTimeout
            - rejectTimeout
            - pBitTimeout
            - type2Violation
            - retransmissions"
    REFERENCE   
        "IEEE 802.2 (ISO/IEC 8802-3), lLCConnection2Event-N."
    ::= { x25Notifications 2 }

lLCClessACKEvent NOTIFICATION-TYPE
    OBJECTS     { tmnObjectInstance }
    STATUS      current
    DESCRIPTION 
        "This event will be sent for the following conditions: 
         retransmissions, no response, type 3 violation.  For each 
         condition, there is an appropriate parameter to be included in 
         the notification.
         
          Additional paramters include:
         
            - type3Violation
            - retransmissions
            - noResponse"
    REFERENCE   
        "IEEE 802.2 (ISO/IEC 8802-3), lLCClessACKEvent-N."
    ::= { x25Notifications 3 }

datalinkEntityMandatoryGroup OBJECT-GROUP
    OBJECTS     { dLSAPSap1Address }
    STATUS      current
    DESCRIPTION 
        ""
    ::= { x25Groups 1 }

dLSAPMandatoryGroup OBJECT-GROUP
    OBJECTS     { dLSAPSap1Address }
    STATUS      current
    DESCRIPTION 
        ""
    ::= { x25Groups 2 }

dLSAPOptionalGroup OBJECT-GROUP
    OBJECTS     { dLSAPSap1Address, dLSAPUserEntityNames }
    STATUS      current
    DESCRIPTION 
        ""
    ::= { x25Groups 3 }

mACDLEConditionalGroup OBJECT-GROUP
    OBJECTS     { mACDLELocalSapNames, mACDLEOperationalState, 
                  mACDLEProviderEntityNames, mACDLERowStatus }
    STATUS      current
    DESCRIPTION 
        ""
    ::= { x25Groups 4 }

mACConditionalGroup OBJECT-GROUP
    OBJECTS     { mACOperationalState }
    STATUS      current
    DESCRIPTION 
        ""
    ::= { x25Groups 5 }

resourceTypeIdConditionalGroup OBJECT-GROUP
    OBJECTS     { resourceInfoManufacturerOUI, 
                  resourceInfoManufacturerName, 
                  resourceInfoManufacturerProductName, 
                  resourceInfoManufacturerProductVersion }
    STATUS      current
    DESCRIPTION 
        ""
    ::= { x25Groups 6 }

lLCDLEConditionalGroup OBJECT-GROUP
    OBJECTS     { lLCDLELocalSapNames }
    STATUS      current
    DESCRIPTION 
        ""
    ::= { x25Groups 7 }

lLCDLEOptionalGroup OBJECT-GROUP
    OBJECTS     { lLCDLELocalSapNames, lLCDLEProviderEntityNames }
    STATUS      current
    DESCRIPTION 
        ""
    ::= { x25Groups 8 }

lLCStationConditionalGroup OBJECT-GROUP
    OBJECTS     { lLCStationLLCName, lLCStationMaximumLSAPsConfigured, 
                  lLCStationSupportedServicesTypes, lLCStationStatus, 
                  lLCStationType1AcknowledgeTimeoutValue, 
                  lLCStationType1MaximumRetryCount, 
                  lLCStationMaximumPDUN3, 
                  lLCStationMaximumRetransmissions4, 
                  lLCStationReceiveVariableLifetime, 
                  lLCStationTransmitVariableLifetime, 
                  lLCStationType3AcknowledgeTimeoutValue, 
                  lLCStationBufferSize, lLCStationSTRIndicator, 
                  lLCStationVersionNumber }
    STATUS      current
    DESCRIPTION 
        ""
    ::= { x25Groups 9 }

lLCStationStatisticsGroup OBJECT-GROUP
    OBJECTS     { lLCStationNumberOfActiveLSAPs, 
                  lLCStationType3Retransmissions, 
                  lLCStationAvgBufferUseSize, lLCStationBufferProblems, 
                  lLCStationMaxBufferUseSize, lLCStationInactiveLSAP, 
                  lLCStationPDUsDiscard, 
                  lLCStationType1AcknowledgmentTimerTimeouts }
    STATUS      current
    DESCRIPTION 
        ""
    ::= { x25Groups 10 }

lLCSAPConditionalGroup OBJECT-GROUP
    OBJECTS     { lLCSAPAddress, lLCSAPRDE }
    STATUS      current
    DESCRIPTION 
        ""
    ::= { x25Groups 11 }

rDESetupConditionalGroup OBJECT-GROUP
    OBJECTS     { rDESetupAgingEnabled, rDESetupAgingValue, 
                  rDESetupEnableType2Reset, 
                  rDESetupMaximumRouteDescriptors, 
                  rDESetupMaximumResponseTime, rDESetupMinimumPDUSize, 
                  rDESetupRDEHold, rDESetupRDEReplace, 
                  rDESetupRDESetupName, rDESetupResetOnTestEnabled }
    STATUS      current
    DESCRIPTION 
        ""
    ::= { x25Groups 12 }

rDEPairConditionalGroup OBJECT-GROUP
    OBJECTS     { rDEPairDiscardCounter, rDEPairNSRPDUCounter, 
                  rDEPairNSRSelectedCounter, rDEPairRIF, 
                  rDEPairSRFPDUCounter, rDEPairQueryCounter }
    STATUS      current
    DESCRIPTION 
        ""
    ::= { x25Groups 13 }

lLCCLPMConditionalGroup OBJECT-GROUP
    OBJECTS     { lLCCLPMOperationalState, lLCCLPMTotalRemoteSAPs }
    STATUS      current
    DESCRIPTION 
        ""
    ::= { x25Groups 14 }

lLCCOPMConditionalGroup OBJECT-GROUP
    OBJECTS     { lLCCOPMOperationalState }
    STATUS      current
    DESCRIPTION 
        ""
    ::= { x25Groups 15 }

lLCConnectionlessConditionalGroup OBJECT-GROUP
    OBJECTS     { lLCConnectionlessName, 
                  lLCConnectionlessMaximumLLCInformationFieldSize }
    STATUS      current
    DESCRIPTION 
        ""
    ::= { x25Groups 16 }

lLCConnectionlessStatisticsGroup OBJECT-GROUP
    OBJECTS     { lLCConnectionlessTESTReceivedABBResponse, 
                  lLCConnectionlessTESTReceivedCommand, 
                  lLCConnectionlessTESTReceivedResponse, 
                  lLCConnectionlessTESTSentABBResponse, 
                  lLCConnectionlessTESTSentCommand, 
                  lLCConnectionlessTESTSentResponse, 
                  lLCConnectionlessUIReceived, lLCConnectionlessUISent, 
                  lLCConnectionlessXIDReceivedCommand, 
                  lLCConnectionlessXIDReceivedResponse, 
                  lLCConnectionlessXIDSentCommand, 
                  lLCConnectionlessXIDSentResponse }
    STATUS      current
    DESCRIPTION 
        ""
    ::= { x25Groups 17 }

lLCConnection2ConditionalGroup OBJECT-GROUP
    OBJECTS     { lLCConnection2Name, 
                  lLCConnection2MaximumRetransmissions, 
                  lLCConnection2ReceivedWindowSize, 
                  lLCConnection2SendWindowSize, 
                  lLCConnection2AcknowledgeTimeoutValue, 
                  lLCConnection2BusyStateTimeoutValue, 
                  lLCConnection2PBitTimeoutValue, 
                  lLCConnection2RejectTimeoutValue, lLCConnection2Route, 
                  lLCConnection2KStep, lLCConnection2MaxSendWindowSize, 
                  lLCConnection2OptionalTolerationIPDUs }
    STATUS      current
    DESCRIPTION 
        ""
    ::= { x25Groups 18 }

lLCConnection2StatisticsGroup OBJECT-GROUP
    OBJECTS     { lLCConnection2LocalBusy, lLCConnection2RemoteBusy, 
                  lLCConnection2RemoteReset, lLCConnection2LocalReset, 
                  lLCConnection2ProviderReset, lLCConnection2ReceivedI, 
                  lLCConnection2SentI, lLCConnection2SentAcks, 
                  lLCConnection2ReceivedAcks, lLCConnection2ReceivedFRMR, 
                  lLCConnection2SentFRMR, lLCConnection2ReceivedRR, 
                  lLCConnection2SentRR, lLCConnection2ReceivedRNR, 
                  lLCConnection2SentRNR, lLCConnection2ReceivedREJ, 
                  lLCConnection2SentREJ, lLCConnection2ReceivedSABME, 
                  lLCConnection2SentSABME, lLCConnection2ReceivedUA, 
                  lLCConnection2SentUA, lLCConnection2ReceivedDISC, 
                  lLCConnection2SentDISC, lLCConnection2ReceivedDM, 
                  lLCConnection2SentDM, lLCConnection2PDUsDiscarded1, 
                  lLCConnection2PDUsDiscarded2, 
                  lLCConnection2PDURetransmissions, 
                  lLCConnection2DuplicateIPDUsReceived, 
                  lLCConnection2Violation }
    STATUS      current
    DESCRIPTION 
        ""
    ::= { x25Groups 19 }

lLCConnectionlessAckConditionalGroup OBJECT-GROUP
    OBJECTS     { lLCConnectionlessAckName, 
                  lLCConnectionlessAckMaximumLLCInformationFieldSize, 
                  lLCConnectionlessAckMaximumRetransmissions }
    STATUS      current
    DESCRIPTION 
        ""
    ::= { x25Groups 20 }

lLCConnectionlessAckStatisticsGroup OBJECT-GROUP
    OBJECTS     { lLCConnectionlessAckTESTReceivedABBResponse, 
                  lLCConnectionlessAckTESTReceivedCommand, 
                  lLCConnectionlessAckTESTReceivedResponse, 
                  lLCConnectionlessAckTESTSentABBResponse, 
                  lLCConnectionlessAckTESTSentCommand, 
                  lLCConnectionlessAckTESTSentResponse, 
                  lLCConnectionlessAckReceiveResources, 
                  lLCConnectionlessAckUIReceived, 
                  lLCConnectionlessAckUISent, 
                  lLCConnectionlessAckXIDReceivedCommand, 
                  lLCConnectionlessAckXIDReceivedResponse, 
                  lLCConnectionlessAckXIDSentCommand, 
                  lLCConnectionlessAckXIDSentResponse, 
                  lLCConnectionlessAckRetransmissions, 
                  lLCConnectionlessAckNoResponse, 
                  lLCConnectionlessAckCommandIP, 
                  lLCConnectionlessAckCommandIT, 
                  lLCConnectionlessAckCommandOK, 
                  lLCConnectionlessAckCommandPE, 
                  lLCConnectionlessAckCommandRS, 
                  lLCConnectionlessAckCommandUE, 
                  lLCConnectionlessAckCommandUN, 
                  lLCConnectionlessAckReceivedACCommand, 
                  lLCConnectionlessAckSentACCommand, 
                  lLCConnectionlessAckResponseIP, 
                  lLCConnectionlessAckResponseIT, 
                  lLCConnectionlessAckResponseNE, 
                  lLCConnectionlessAckResponseNR, 
                  lLCConnectionlessAckResponseOK, 
                  lLCConnectionlessAckResponseRS, 
                  lLCConnectionlessAckResponseUE, 
                  lLCConnectionlessAckResponseUN, 
                  lLCConnectionlessAckViolation }
    STATUS      current
    DESCRIPTION 
        ""
    ::= { x25Groups 21 }

lAPBDLEConditionalGroup OBJECT-GROUP
    OBJECTS     { lAPBDLEmT1Timer, lAPBDLEmT3Timer, lAPBDLEmW, 
                  lAPBDLEmXSend, lAPBDLEmXReceive, lAPBDLEmT2Timer, 
                  lAPBDLERowStatus }
    STATUS      current
    DESCRIPTION 
        ""
    ::= { x25Groups 22 }

lAPBDLEStatisticsGroup OBJECT-GROUP
    OBJECTS     { lAPBDLEReceivedMlpResets, lAPBDLETimesMT1Expired, 
                  lAPBDLEIFramesReassignments, lAPBDLEMlpFramesReceived, 
                  lAPBDLEMlpFramesSent, 
                  lAPBDLEMlpFramesOutsideWindowGuard, 
                  lAPBDLEReceivedMlpFramesInGuardRegion }
    STATUS      current
    DESCRIPTION 
        ""
    ::= { x25Groups 23 }

sLPPMConditionalGroup OBJECT-GROUP
    OBJECTS     { sLPPMOperationalState }
    STATUS      current
    DESCRIPTION 
        ""
    ::= { x25Groups 24 }

sLPConnectionConditionalGroup OBJECT-GROUP
    OBJECTS     { sLPConnectionUnderlyingConnectionNames, 
                  sLPConnectionSupportedConnectionNames, 
                  sLPConnectionInterfaceType, sLPConnectionK, 
                  sLPConnectionN1, sLPConnectionN2, 
                  sLPConnectionSequenceModulus, sLPConnectionT1Timer, 
                  sLPConnectionT2Timer, sLPConnectionProtocolState, 
                  sLPConnectionT3Timer, sLPConnectionT4Timer, 
                  sLPConnectionRowStatus }
    STATUS      current
    DESCRIPTION 
        ""
    ::= { x25Groups 25 }

sLPConnectionStatisticsGroup OBJECT-GROUP
    OBJECTS     { sLPConnectionFCSErrorsReceived, 
                  sLPConnectionFRMRsReceived, sLPConnectionFRMRsSent, 
                  sLPConnectionIFrameDataOctetsReceived, 
                  sLPConnectionIFrameDataOctetsSent, 
                  sLPConnectionIFramesReceived, sLPConnectionIFramesSent, 
                  sLPConnectionPollsReceived, sLPConnectionREJsReceived, 
                  sLPConnectionREJsSent, sLPConnectionRNRsReceived, 
                  sLPConnectionRNRsSent, sLPConnectionSABMsReceived, 
                  sLPConnectionSABMsSent, sLPConnectionTimesT1Expired, 
                  sLPConnectionTimesT3Expired, 
                  sLPConnectionTimesT4Expired }
    STATUS      current
    DESCRIPTION 
        ""
    ::= { x25Groups 26 }

sLPConnectionDefaultsConditionalGroup OBJECT-GROUP
    OBJECTS     { sLPConnectionDefaultInterfaceType, 
                  sLPConnectionDefaultK, sLPConnectionDefaultN1, 
                  sLPConnectionDefaultN2, 
                  sLPConnectionDefaultSequenceModulus, 
                  sLPConnectionDefaultT1Timer, 
                  sLPConnectionDefaultT2Timer, 
                  sLPConnectionDefaultT3Timer, 
                  sLPConnectionDefaultT4Timer }
    STATUS      current
    DESCRIPTION 
        "This group provides default values for protocol attributes for 
         SLP connections.  These default values act as the default 
         values associated with newly created data link entires created 
         as a part of system operations.  Also, when data link entries 
         are created by management stations and columns are left 
         unspecified, these default vlaues will be used to set the 
         initial value of the underspecified columns.
         
         These defaults may be implemented read-only if it is difficult 
         to change them (i.e., requireing exceptional reconfiguration 
         such a recompilation or relinking).  When implemented 
         read-write, the values set by management stations for these 
         scalars must survive both an agent and a system reboot."
    ::= { x25Groups 27 }

lLCConnection2DefaultsConditionalGroup OBJECT-GROUP
    OBJECTS     { lLCConnection2DefaultMaximumRetransmissions, 
                  lLCConnection2DefaultReceivedWindowSize, 
                  lLCConnection2DefaultSendWindowSize, 
                  lLCConnection2DefaultAcknowledgeTimeoutValue, 
                  lLCConnection2DefaultBusyStateTimeoutValue, 
                  lLCConnection2DefaultPBitTimeoutValue, 
                  lLCConnection2DefaultRejectTimeoutValue, 
                  lLCConnection2DefaultRoute, lLCConnection2DefaultKStep, 
                  lLCConnection2DefaultMaxSendWindowSize, 
                  lLCConnection2DefaultOptionalTolerationIPDUs }
    STATUS      current
    DESCRIPTION 
        "This group provides default values for protocol attributes for 
         LLC2 connections.  Because LLC2 data links are formed 
         dynamically, even with previously unknown remote LLC stations, 
         these defaults act as the default values associated with newly 
         created data link entries created as a part of system 
         operations.  Also, when data link entries are created by 
         management stations and columns are left unspecified, these 
         default values will be used to set the initial value of the 
         underspecified columns.
         
         These defaults may be implemented read-only if it is difficult 
         to change them (i.e., requireing exceptional reconfiguration 
         such a recompilation or relinking).  When implemented 
         read-write, the values set by management stations for these 
         scalars must survive both an agent and a system reboot."
    ::= { x25Groups 28 }

x25TMNConditionalGroup OBJECT-GROUP
    OBJECTS     { datalinkEntityOperationalState, mACDLEOperationalState, 
                  mACOperationalState, lLCCLPMOperationalState, 
                  lLCCOPMOperationalState, 
                  lLCConnection2OperationalState, sLPPMOperationalState, 
                  sLPConnectionOperationalState, 
                  lLCConnection2AdministrativeState, 
                  sLPConnectionAdministrativeState, 
                  lLCConnection2UsageState, sLPConnectionUsageState, 
                  lLCConnection2ProceduralStatus, 
                  sLPConnectionProceduralStatus, 
                  lLCConnection2AlarmStatus, sLPConnectionAlarmStatus }
    STATUS      current
    DESCRIPTION 
        "This group provides states and status columns following the 
         OperationalState, AdministrativeState, UsageState, 
         ProceduralStatus and AlarmStatus textual conventions from the 
         OPENSS7-TMN-TC module.  These are ITU-T Rec.  X.271 | ISO/IEC 
         10165-2 states and status.  Note that these columns are only 
         implemented if the corresponding tables are implemented."
    ::= { x25Groups 29 }

x25TMNNotificationObjectGroup OBJECT-GROUP
    OBJECTS     { pdusDiscarded, bufferProblems, pdusDiscarded1, 
                  pdusDiscarded2, pduRetransmissions, acknowledgeTimeout, 
                  busyStateTimeout, rejectTimeout, pBitTimeout, 
                  type2Violation, retransmissions, type3Violation, 
                  noResponse }
    STATUS      current
    DESCRIPTION 
        "A collection of notification objects used in this module."
    ::= { x25Groups 30 }

x25TMNNotificationGroup NOTIFICATION-GROUP
    NOTIFICATIONS { lLCStationEvent, lLCConnection2Event, 
                  lLCClessACKEvent }
    STATUS      current
    DESCRIPTION 
        "A collection of notifications used in this module."
    ::= { x25Groups 31 }

x25TMNScalarsGroup OBJECT-GROUP
    OBJECTS     { x25DiscontinuityTime }
    STATUS      current
    DESCRIPTION 
        "A collection of scalars used in this module."
    ::= { x25Groups 32 }

x25TMNOptionalGroup OBJECT-GROUP
    OBJECTS     { x25SubsystemId, 
                  lLCConnectionlessAckDefaultMaximumLLCInformationFieldSize, 
                  lLCConnectionlessAckDefaultMaximumRetransmissions, 
                  physicalEntityLocalSapNames, 
                  physicalEntityOperationalState, 
                  physicalEntityPhysicalEntityTitles, 
                  dataCircuitOperationalState, 
                  dataCircuitBitErrorsReceived, 
                  dataCircuitBitErrorsTransmitted, 
                  dataCircuitBitErrorsThreshold, 
                  dataCircuitDataCircuitType, 
                  dataCircuitPhysicalMediaNames, 
                  dataCircuitPhysicalInterfaceType, 
                  dataCircuitPhysicalInterfaceStandard, 
                  dataCircuitSynchronizationMode, 
                  dataCircuitTransmissionCoding, 
                  dataCircuitTransmissionMode, 
                  dataCircuitTransmissionRate, dataCircuitRowStatus, 
                  physicalConnectionUnderlyingConnectionNames, 
                  physicalConnectionSupportedConnectionNames, 
                  physicalConnectionEndpointIdentifier, 
                  physicalConnectionPortNumber, 
                  physicalConnectionRowStatus, 
                  datalinkEntityLocalSapNames, 
                  datalinkEntityProviderEntityNames, 
                  datalinkEntityRowStatus, dLSAPRowStatus, 
                  lLCDLEOperationalState, lLCDELRowStatus, 
                  lLCConnection2ProtocolState, 
                  lLCConnection2IVMOMaximumRetransmissions, 
                  lLCConnection2IVMOReceivedWindowSize, 
                  lLCConnection2IVMOSendWindowSize, 
                  lLCConnection2IVMOAcknowledgeTimeoutValue, 
                  lLCConnection2IVMOBusyStateTimeoutValue, 
                  lLCConnection2IVMOBitTimeoutValue, 
                  lLCConnection2IVMORejectTimeoutValue, 
                  lLCConnection2IVMORoute, lLCConnection2IVMOKStep, 
                  lLCConnection2IVMOMaxSendWindowSize, 
                  lLCConnection2IVMOOptionalTolerationIPDUs, 
                  lLCConnectionlessAckIVMOMaximumLLCInformationFieldSize, 
                  lLCConnectionlessAckIVMOMaximumRetransmissions, 
                  lLCConnectionlessAckIVMORowStatus, 
                  lAPBDLELocalSapNames, lAPBDLEOperationalState, 
                  lAPBDLEProviderEntityNames, 
                  sLPConnectionAbnormalLinkDisconnectsReceived, 
                  sLPConnectionAbnormalLinkDisconnectsSent, 
                  sLPConnectionLinkResetsReceived, 
                  sLPConnectionLinkResetsSent, 
                  sLPConnectionTimesN2Reached, 
                  sLPConnectionIVMOInterfaceType, sLPConnectionIVMOK, 
                  sLPConnectionIVMON1, sLPConnectionIVMON2, 
                  sLPConnectionIVMOSequenceModulus, 
                  sLPConnectionIVMOT1Timer, sLPConnectionIVMOT2Timer, 
                  sLPConnectionIVMOT3Timer, sLPConnectionIVMOT4Timer, 
                  sLPConnectionIVMORowStatus }
    STATUS      current
    DESCRIPTION 
        "A collection of remaining objects."
    ::= { x25Groups 33 }

x25MIBCompliance MODULE-COMPLIANCE
    STATUS      current
    DESCRIPTION 
        "Provides the module compliance rquirements for the 
         X25-LLC-MIB."
    REFERENCE   
        ""

    MODULE      -- this module

        MANDATORY-GROUPS        { datalinkEntityMandatoryGroup, 
                  dLSAPMandatoryGroup }

        GROUP   x25TMNConditionalGroup
        DESCRIPTION   
              "Mandatory where the operational state, administrative 
               state, usage state, procedural status and alarm status 
               may be reported."

        GROUP   mACDLEConditionalGroup
        DESCRIPTION   
              "Mandatory when the MAC data link entity is supported."

        GROUP   mACConditionalGroup
        DESCRIPTION   
              "Mandatory when the MAC data link entity and service 
               access point is supported."

        GROUP   resourceTypeIdConditionalGroup
        DESCRIPTION   
              "Mandatory when the MAC data link entity is supported."

        GROUP   lLCDLEConditionalGroup
        DESCRIPTION   
              "Mandatory when the LLC data link entity is supported."

        GROUP   lLCStationConditionalGroup
        DESCRIPTION   
              "Mandatory when the LLC data link entity is supported."

        GROUP   lLCSAPConditionalGroup
        DESCRIPTION   
              "Mandatory when the LLC data link entity and LLC station 
               is supported."

        GROUP   rDESetupConditionalGroup
        DESCRIPTION   
              "Mandatory when the optional RDE is supported."

        GROUP   rDEPairConditionalGroup
        DESCRIPTION   
              "Mandatory when the optional RDE is supported."

        GROUP   lLCCLPMConditionalGroup
        DESCRIPTION   
              "Mandatory when LLC is supported at all."

        GROUP   lLCCOPMConditionalGroup
        DESCRIPTION   
              "Mandatory when LLC2 is supported."

        GROUP   lLCConnectionlessConditionalGroup
        DESCRIPTION   
              "Mandatory when LLC is supported at all."

        GROUP   lLCConnection2ConditionalGroup
        DESCRIPTION   
              "Mandatory when LLC2 is supported."

        GROUP   lLCConnectionlessAckConditionalGroup
        DESCRIPTION   
              "Mandatory when LLC3 is supported."

        GROUP   lAPBDLEConditionalGroup
        DESCRIPTION   
              "Mandatory when LAPB data link entity is supported."

        GROUP   sLPPMConditionalGroup
        DESCRIPTION   
              "Mandatory when LAPB data link entity is supported."

        GROUP   sLPConnectionConditionalGroup
        DESCRIPTION   
              "Mandatory when LAPB data link entity is supported."

        GROUP   sLPConnectionDefaultsConditionalGroup
        DESCRIPTION   
              "Mandatory when LAPB data link connections are supported 
               and management station defined defaults for LAPB data 
               link connections is supported."

        GROUP   lLCConnection2DefaultsConditionalGroup
        DESCRIPTION   
              "Mandatory when LLC2 data link connections are supported 
               and management staiton defined defaults for LLC2 data 
               link connections is supported."

        GROUP   dLSAPOptionalGroup
        DESCRIPTION   
              "More optional groups."

        GROUP   lLCDLEOptionalGroup
        DESCRIPTION   
              "More optional groups."

        GROUP   lLCStationStatisticsGroup
        DESCRIPTION   
              "More optional groups."

        GROUP   lLCConnectionlessStatisticsGroup
        DESCRIPTION   
              "More optional groups."

        GROUP   lLCConnection2StatisticsGroup
        DESCRIPTION   
              "More optional groups."

        GROUP   lLCConnectionlessAckStatisticsGroup
        DESCRIPTION   
              "More optional groups."

        GROUP   lAPBDLEStatisticsGroup
        DESCRIPTION   
              "More optional groups."

        GROUP   sLPConnectionStatisticsGroup
        DESCRIPTION   
              "More optional groups."

        GROUP   x25TMNNotificationObjectGroup
        DESCRIPTION   
              "More optional groups."

        GROUP   x25TMNNotificationGroup
        DESCRIPTION   
              "More optional groups."

        GROUP   x25TMNScalarsGroup
        DESCRIPTION   
              "More optional groups."

        GROUP   x25TMNOptionalGroup
        DESCRIPTION   
              "More optional groups."

        OBJECT  datalinkEntityOperationalState
        MIN-ACCESS  read-only
        DESCRIPTION   
              "Where provided, must be read-only."

        OBJECT  mACDLEOperationalState
        MIN-ACCESS  read-only
        DESCRIPTION   
              "Where provided, must be read-only."

        OBJECT  mACOperationalState
        MIN-ACCESS  read-only
        DESCRIPTION   
              "Where provided, must be read-only."

        OBJECT  lLCCLPMOperationalState
        MIN-ACCESS  read-only
        DESCRIPTION   
              "Where provided, must be read-only."

        OBJECT  lLCCOPMOperationalState
        MIN-ACCESS  read-only
        DESCRIPTION   
              "Where provided, must be read-only."

        OBJECT  lLCConnection2OperationalState
        MIN-ACCESS  read-only
        DESCRIPTION   
              "Where provided, must be read-only."

        OBJECT  sLPPMOperationalState
        MIN-ACCESS  read-only
        DESCRIPTION   
              "Where provided, must be read-only."

        OBJECT  sLPConnectionOperationalState
        MIN-ACCESS  read-only
        DESCRIPTION   
              "Where provided, must be read-only."

        OBJECT  lLCConnection2AdministrativeState
        MIN-ACCESS  read-write
        DESCRIPTION   
              "Where provided, the administrative state must provide for 
               write access to allow management stations to affect the 
               administrative target of the managed object instance."

        OBJECT  sLPConnectionAdministrativeState
        MIN-ACCESS  read-write
        DESCRIPTION   
              "Where provided, the administrative state must provide for 
               write access to allow management stations to affect the 
               administrative target of the managed object instance."

        OBJECT  lLCConnection2UsageState
        MIN-ACCESS  read-only
        DESCRIPTION   
              "Where provided, must be read-only."

        OBJECT  sLPConnectionUsageState
        MIN-ACCESS  read-only
        DESCRIPTION   
              "Where provided, must be read-only."

        OBJECT  lLCConnection2ProceduralStatus
        MIN-ACCESS  read-only
        DESCRIPTION   
              "Where provided, must be read-only."

        OBJECT  sLPConnectionProceduralStatus
        MIN-ACCESS  read-only
        DESCRIPTION   
              "Where provided, must be read-only."

        OBJECT  lLCConnection2AlarmStatus
        MIN-ACCESS  read-write
        DESCRIPTION   
              "Where provided, the alarm status must provide for write 
               access for explicit manual alarm clearing by a management 
               station."

        OBJECT  sLPConnectionAlarmStatus
        MIN-ACCESS  read-write
        DESCRIPTION   
              "Where provided, the alarm status must provide for write 
               access for explicit manual alarm clearing by a management 
               station."

        OBJECT  sLPConnectionDefaultInterfaceType
        MIN-ACCESS  read-only
        DESCRIPTION   
              "It is permitted to provide this default as read-only 
               where the agent or data link subsystems is incapable of 
               changing it without exceptional actions such as 
               recompilation or link editing.
               
               Note that this object is only required when the 
               sLPConnectionDefaultConditionalGroup is mandatory."

        OBJECT  sLPConnectionDefaultK
        MIN-ACCESS  read-only
        DESCRIPTION   
              "It is permitted to provide this default as read-only 
               where the agent or data link subsystems is incapable of 
               changing it without exceptional actions such as 
               recompilation or link editing.
               
               Note that this object is only required when the 
               sLPConnectionDefaultConditionalGroup is mandatory."

        OBJECT  sLPConnectionDefaultN1
        MIN-ACCESS  read-only
        DESCRIPTION   
              "It is permitted to provide this default as read-only 
               where the agent or data link subsystems is incapable of 
               changing it without exceptional actions such as 
               recompilation or link editing.
               
               Note that this object is only required when the 
               sLPConnectionDefaultConditionalGroup is mandatory."

        OBJECT  sLPConnectionDefaultN2
        MIN-ACCESS  read-only
        DESCRIPTION   
              "It is permitted to provide this default as read-only 
               where the agent or data link subsystems is incapable of 
               changing it without exceptional actions such as 
               recompilation or link editing.
               
               Note that this object is only required when the 
               sLPConnectionDefaultConditionalGroup is mandatory."

        OBJECT  sLPConnectionDefaultSequenceModulus
        MIN-ACCESS  read-only
        DESCRIPTION   
              "It is permitted to provide this default as read-only 
               where the agent or data link subsystems is incapable of 
               changing it without exceptional actions such as 
               recompilation or link editing.
               
               Note that this object is only required when the 
               sLPConnectionDefaultConditionalGroup is mandatory."

        OBJECT  sLPConnectionDefaultT1Timer
        MIN-ACCESS  read-only
        DESCRIPTION   
              "It is permitted to provide this default as read-only 
               where the agent or data link subsystems is incapable of 
               changing it without exceptional actions such as 
               recompilation or link editing.
               
               Note that this object is only required when the 
               sLPConnectionDefaultConditionalGroup is mandatory."

        OBJECT  sLPConnectionDefaultT2Timer
        MIN-ACCESS  read-only
        DESCRIPTION   
              "It is permitted to provide this default as read-only 
               where the agent or data link subsystems is incapable of 
               changing it without exceptional actions such as 
               recompilation or link editing.
               
               Note that this object is only required when the 
               sLPConnectionDefaultConditionalGroup is mandatory."

        OBJECT  sLPConnectionDefaultT3Timer
        MIN-ACCESS  read-only
        DESCRIPTION   
              "It is permitted to provide this default as read-only 
               where the agent or data link subsystems is incapable of 
               changing it without exceptional actions such as 
               recompilation or link editing.
               
               Note that this object is only required when the 
               sLPConnectionDefaultConditionalGroup is mandatory."

        OBJECT  sLPConnectionDefaultT4Timer
        MIN-ACCESS  read-only
        DESCRIPTION   
              "It is permitted to provide this default as read-only 
               where the agent or data link subsystems is incapable of 
               changing it without exceptional actions such as 
               recompilation or link editing.
               
               Note that this object is only required when the 
               sLPConnectionDefaultConditionalGroup is mandatory."

        OBJECT  lLCConnection2DefaultMaximumRetransmissions
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultReceivedWindowSize
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultSendWindowSize
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultAcknowledgeTimeoutValue
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultBusyStateTimeoutValue
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultPBitTimeoutValue
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultRejectTimeoutValue
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultRoute
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultKStep
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultMaxSendWindowSize
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

        OBJECT  lLCConnection2DefaultOptionalTolerationIPDUs
        MIN-ACCESS  read-only
        DESCRIPTION   
              "It is permitted to provide this default as read-only 
               where the agent or data link subsystems is incapable of 
               changing it without exceptional actions such as 
               recompilation or link editing.
               
               Note that this object is only required when the 
               lLCConnection2DefaultConditionalGroup is mandatory."

    ::= { x25Compliances 1 }

END -- end of module OPENSS7-X25-LLC-MIB.

-- vim: ft=mib comments=\f\:\",\b\:\-\-,\:\-\-,\f\b\:- fo+=tcqlornw tw=72 nocin nosi sts=4 sw=4
