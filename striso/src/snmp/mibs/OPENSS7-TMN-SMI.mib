-- vim: ft=mib comments=\f\:\",\b\:\-\-,\:\-\-,\f\b\:- fo+=tcqlornw tw=72 nocin nosi sts=4 sw=4
-- =============================================================================
-- 
-- @(#) $RCSfile: OPENSS7-TMN-SMI.mib,v $ $Name: OpenSS7-0_9_2 $($Revision: 0.9.2.13 $) $Date: 2008-12-27 10:01:51 $
--
-- -----------------------------------------------------------------------------
--
-- Copyright (c) 2001-2008  OpenSS7 Corporation <http://www.openss7.com/>
-- Copyright (c) 1997-2000  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2008-12-27 10:01:51 $ by $Author: brian $
--
-- -----------------------------------------------------------------------------
--
-- $Log: OPENSS7-TMN-SMI.mib,v $
-- Revision 0.9.2.13  2008-12-27 10:01:51  brian
-- - updated mibs and stubs
--
-- Revision 0.9.2.12  2008-10-07 13:23:50  brian
-- - corrections
--
-- Revision 0.9.2.11  2008-07-28 08:51:42  brian
-- - SNMP updates
--
-- Revision 0.9.2.10  2008-04-29 07:11:22  brian
-- - updating headers for release
--
-- Revision 0.9.2.8  2008/01/13 00:25:23  brian
-- - updated mibs
--
-- Revision 0.9.2.7  2008/01/10 19:55:43  brian
-- - updating mibs
--
-- Revision 0.9.2.6  2008/01/01 13:59:39  brian
-- - added new mibs
--
-- Revision 0.9.2.5  2007/12/29 21:57:41  brian
-- - updates
--
-- Revision 0.9.2.4  2007/12/15 20:19:14  brian
-- - updates
--
-- Revision 0.9.2.3  2007/11/06 09:47:06  brian
-- - updated mibs
--
-- Revision 0.9.2.2  2007/10/15 01:14:28  brian
-- - updated MIBs
--
-- Revision 0.9.2.1  2007/09/29 14:31:39  brian
-- - added new mib files
--
-- =============================================================================

OPENSS7-TMN-SMI DEFINITIONS ::= BEGIN

IMPORTS
	MODULE-IDENTITY, OBJECT-TYPE, NOTIFICATION-TYPE
		FROM SNMPv2-SMI
	RowPointer, RowStatus, TimeStamp
		FROM SNMPv2-TC
	openss7Modules
		FROM OPENSS7-SMI
	ProbableCause, SimpleNameType
		FROM OPENSS7-TMN-TC;

tmnMIB MODULE-IDENTITY
    LAST-UPDATED
	"200801011353Z"
    ORGANIZATION
	"OpenSS7 Corporation"
    CONTACT-INFO
	"Brian Bidulock
	 OpenSS7 Corporation
	 1469 Jefferys Crescent
	 Edmonton, Alberta T6L 6T1
	 CANADA
	 Tel: +1 780 490 1141
	 Fax: +1 780 490 1241
	 Mob: +1 780 953 0557
	 E-mail: bidulock@openss7.org"
    DESCRIPTION
	"This is a basic MIB module providing definitions of 
	 objects based on the TMN (ITU-T Rec. X.721 (1992))."
    ::= { openss7 9 3 2 }

--
-- Top level organization of the MIB
--

tmnNotifications	OBJECT IDENTIFIER ::= { tmnMIB       0 }
tmnObjects		OBJECT IDENTIFIER ::= { tmnMIB       1 }
tmnConformance		OBJECT IDENTIFIER ::= { tmnMIB       2 }

tmnScalars		OBJECT IDENTIFIER ::= { tmnObjects   1 }
tmnTables		OBJECT IDENTIFIER ::= { tmnObjects   2 }
tmnNotifObjects		OBJECT IDENTIFIER ::= { tmnObjects   3 }

tmnCompliances		OBJECT IDENTIFIER ::= { tmnConformance   1 }
tmnGroups		OBJECT IDENTIFIER ::= { tmnConformance   2 }

tmnSeverityMapping	OBJECT IDENTIFIER ::= { tmnTables    1 }
tmnAlarmSummary		OBJECT IDENTIFIER ::= { tmnTables    2 }
tmnAlarmSummaryControl	OBJECT IDENTIFIER ::= { tmnTables    3 }

managementOperationsSchedule		OBJECT IDENTIFIER ::= { tmnTables    4 }
enhancedCurrentAlarmSummaryControl	OBJECT IDENTIFIER ::= { tmnTables    5 }
discriminator				OBJECT IDENTIFIER ::= { tmnTables    6 }
discriminatorDuration			OBJECT IDENTIFIER ::= { tmnTables    7 }
discriminatorDailySchedule		OBJECT IDENTIFIER ::= { tmnTables    8 }
discriminatorWeeklyScheduling		OBJECT IDENTIFIER ::= { tmnTables    9 }
discriminatorExternalScheduler		OBJECT IDENTIFIER ::= { tmnTables   10 }
eventForwardingDiscriminator		OBJECT IDENTIFIER ::= { tmnTables   11 }
efdDestination				OBJECT IDENTIFIER ::= { tmnTables   12 }
log					OBJECT IDENTIFIER ::= { tmnTables   13 }
logDuration				OBJECT IDENTIFIER ::= { tmnTables   14 }
logDailyScheduling			OBJECT IDENTIFIER ::= { tmnTables   15 }
logWeeklyScheduling			OBJECT IDENTIFIER ::= { tmnTables   16 }
logExternalScheduler			OBJECT IDENTIFIER ::= { tmnTables   17 }
logRecord				OBJECT IDENTIFIER ::= { tmnTables   18 }
eventLogRecord				OBJECT IDENTIFIER ::= { tmnTables   19 }
alarmRecord				OBJECT IDENTIFIER ::= { tmnTables   20 }
attributeValueChangeRecord		OBJECT IDENTIFIER ::= { tmnTables   21 }
objectCreationRecord			OBJECT IDENTIFIER ::= { tmnTables   22 }
objectDeletionRecord			OBJECT IDENTIFIER ::= { tmnTables   23 }
relationshipChangeRecord		OBJECT IDENTIFIER ::= { tmnTables   24 }
securityAlarmReportRecord		OBJECT IDENTIFIER ::= { tmnTables   25 }
stateChangeRecord			OBJECT IDENTIFIER ::= { tmnTables   26 }
system					OBJECT IDENTIFIER ::= { tmnTables   27 }

-- =====================================================================
--
-- NOTIFICATION OBJECTS
--
-- =====================================================================
-- Definition of some notification objects is required so that we can 
-- use these types in notifications.  Basically we need a notification 
-- object for each textual convention that we want to use in the 
-- notification.

objectInstance OBJECT-TYPE
    SYNTAX ObjectInstance
    MAX-ACCESS accessible-for-notify
    STATUS current
    DESCRIPTION
	"Provides an object for use with notifications.  This is a 
	 pointer to an object instance to be included in notifications 
	 where the generating object instances needs be included."
    REFERENCE
	"ITU-T Rec. X.721 (1992) | ISO/IEC 10165-2 : 1992, 
	    objectInstance."
    ::= { tmnNotifObjects 1 }

notificationIdentifier OBJECT-TYPE
    SYNTAX NotificationIdentifier
    MAX-ACCESS accessible-for-notify
    STATUS current
    DESCRIPTION
	"Provides an object for use with notifications."
    REFERENCE
	"ITU-T Rec. X.721 (1992) | ISO/IEC 10165-2 : 1992, 
	 notificationIdentifier."
    ::= { tmnNotifObjects 2 }

correlatedNotifications OBJECT-TYPE
    SYNTAX CorrelatedNotifications
    MAX-ACCESS accessible-for-notify
    STATUS current
    DESCRIPTION
	"Provides an object for use with notifications."
    REFERENCE
	"ITU-T Rec. X.721 (1992) | ISO/IEC 10165-2 : 1992, 
	    correlatedNotifications."
    ::= { tmnNotifObjects 3 }

probableCause OBJECT-TYPE
    SYNTAX ProbableCause
    MAX-ACCESS accessible-for-notify
    STATUS current
    DESCRIPTION
	"This is the probable cause of the alarm condition in accordance 
	 with TMN SMI defintions.  The probable cause is a required 
	 parameter of the communications alarm, environmental alarm, 
	 equipment alarm, processing error alarm and quality of service 
	 alarm notification.  It also appears in the alarm record entry.  
	 It contains an object identity which indicates the probable 
	 cause of the alarm in accordance with the ProbableCause textual 
	 convention.

	 The meaning and purpose of object identifiers that are used to 
	 populate this parameter for the communications alarm, 
	 environmental alarm, equipment alarm, processingError alarm and 
	 qualityofService alarm notification must be specified in the 
	 DESCRIPTION clause of an OBJECT-IDENTITY macro defining the 
	 object identifier associated with the probable cause.  The 
	 precise conditions under which the alarm is raised and cleared 
	 (see perceivedSeverity) must also be defined in the DESCRIPTION 
	 clause whenever the value is used to raise generic alarms such 
	 as the communications alarm.  When used with a specific 
	 notification, the use of the probable cause parameter must be 
	 defined in the NOTIFICATION-TYPE macro's DESCRIPTION clause.

	 In all cases, the object identifier defined by the 
	 corresponding standard (i.e.  TMN specification) should be used 
	 as specified in the corresponding standard.  Private values of 
	 the probable cause may also be defined in OBJECT-IDENTITY 
	 macros within a private or enterprise module definition.  Where 
	 possible, however, a standard values should be used."
    REFERENCE
	"ITU-T Rec. X.721 (1992) | ISO/IEC 10165-2 : 1992, 
	    probableCause."
    ::= { tmnNotifObjects 4 }

specificProblems OBJECT-TYPE
    SYNTAX SpecificProblems
    MAX-ACCESS accessible-for-notify
    STATUS current
    DESCRIPTION
	"This is a specific problem of an alarm condition in accordance 
	 with the TMN SMI definitions.  It is an optional parameter of 
	 the communications alarm, environmental alarm, equipment alarm, 
	 processing error alarm or quality of service alarm 
	 notifications and may occur multiply in that notification when 
	 an alarm condition is set (it is not normally included when an 
	 alarm condition is cleared).  This is a specific problem 
	 indication that supplements the probable cause.  It contains a 
	 single object identity which indiates the specific problem in 
	 accordance with the SpecificProblems textual convention.

	 The meaning and purpose of the object identifiers that are used 
	 to populate this parameter for the communications alarm, 
	 environmental alarm, equipment alarm, processing error alarm or 
	 quality of service alarm notification must be specified in the 
	 DESCRIPTION clause of an OBJECT-IDENTITY macro defining the 
	 object identifier associated with the specific problem.  The 
	 precise conditions under which the alarm is raised and cleared 
	 (see perceivedSeverity) must also be defined in the DESCRIPTION 
	 clause whenever the value is used to raise generic alarms such 
	 as the communications alarm.  When used with a specific 
	 notification, the use of the specific problem parameter must be 
	 defined in the NOTIFICATION-TYPE macro's DESCRIPTION clause.

	 In all cases, the object identifier defined by the 
	 corresponding standard (i.e.  TMN specification) should be used 
	 as specified in the corresponding standard.  Private values of 
	 the specific problem may also be defined in OBJECT-IDENTITY 
	 marcos within a private or enterprise module definition.  Where 
	 possible, however, standard values should be used."
    REFERENCE
	"ITU-T Rec. X.721 (1992) | ISO/IEC 10165-2 : 1992, 
	    specificProblems."
    ::= { tmnNotifObjects 5 }

perceivedSeverity OBJECT-TYPE
    SYNTAX PerceivedSeverity
    MAX-ACCESS accessible-for-notify
    STATUS current
    DESCRIPTION
	"This is the perceived severity level which is set according to 
	 the PerceiveSeverity textual convention.  This value is used 
	 along with a probableCause and specificProblem identifiers with 
	 a generic alarm such as the communications alarm, or is used 
	 with a specifically defined alarm.  The value of the parameter 
	 to the notification should be set to other than cleared(5) to 
	 indicate that onset or assertion of an alarm condition and set 
	 to cleared(5) to indicate the cessation or deassertion of the 
	 alarm condition.
	 
	 The DESCRIPTION of the OBJECT-IDENTITY associated with this 
	 perceived severity, such as the probableCause paraemter, should 
	 describe the conditions under which the alarm is asserted and 
	 cleared, as well a specifying the applicable severities."
    REFERENCE
	"ITU-T Rec. X.721 (1992) | ISO/IEC 10165-2 : 1992, 
	    perceivedSeverity."
    ::= { tmnNotifObjects 6 }

backedUpStatus OBJECT-TYPE
    SYNTAX BackedUpStatus
    MAX-ACCESS accessible-for-notify
    STATUS current
    DESCRIPTION
	"Provides an object for use with notifications."
    REFERENCE
	"ITU-T Rec. X.721 (1992) | ISO/IEC 10165-2 : 1992, 
	    backedUpStatus."
    ::= { tmnNotifObjects 7 }

backUpObject OBJECT-TYPE
    SYNTAX ObjectInstance
    MAX-ACCESS accessible-for-notify
    STATUS current
    DESCRIPTION
	"Provides an object for use with notifications."
    REFERENCE
	"ITU-T Rec. X.721 (1992) | ISO/IEC 10165-2 : 1992, 
	    backUpObject."
    ::= { tmnNotifObjects 8 }

trendIndication OBJECT-TYPE
    SYNTAX TrendIndication
    MAX-ACCESS accessible-for-notify
    STATUS current
    DESCRIPTION
	"Provides an object for use with notifications."
    REFERENCE
	"ITU-T Rec. X.721 (1992) | ISO/IEC 10165-2 : 1992, 
	    trendIndication."
    ::= { tmnNotifObjects 9 }

thresholdInfo OBJECT-TYPE
    SYNTAX ThresholdInfo
    MAX-ACCESS accessible-for-notify
    STATUS current
    DESCRIPTION
	"Provides an object for use with notifications."
    REFERENCE
	"ITU-T Rec. X.721 (1992) | ISO/IEC 10165-2 : 1992, 
	    thresholdInfo."
    ::= { tmnNotifObjects 10 }

stateChangeDefinition OBJECT-TYPE
    SYNTAX AttributeValueChangeDefinition
    MAX-ACCESS accessible-for-notify
    STATUS current
    DESCRIPTION
	"Provides an object for use with notifications."
    REFERENCE
	"ITU-T Rec. X.721 (1992) | ISO/IEC 10165-2 : 1992, 
	    stateChangeDefinition."
    ::= { tmnNotifObjects 11 }

monitoredAttributes OBJECT-TYPE
    SYNTAX MonitoredAttributes
    MAX-ACCESS accessible-for-notify
    STATUS current
    DESCRIPTION
	"Provides an object for use with notifications."
    REFERENCE
	"ITU-T Rec. X.721 (1992) | ISO/IEC 10165-2 : 1992, 
	    monitoredAttributes."
    ::= { tmnNotifObjects 12 }

proposedRepairActions OBJECT-TYPE
    SYNTAX ProposedRepairActions
    MAX-ACCESS accessible-for-notify
    STATUS current
    DESCRIPTION
	"Provides an object for use with notifications."
    REFERENCE
	"ITU-T Rec. X.721 (1992) | ISO/IEC 10165-2 : 1992, 
	    proposedRepairActions."
    ::= { tmnNotifObjects 13 }

sourceIndicator OBJECT-TYPE
    SYNTAX SourceIndicator
    MAX-ACCESS accessible-for-notify
    STATUS current
    DESCRIPTION
	"Provides an object for use with notifications.

	 This is the source indicator which indicates the source of the 
	 change for notifications according to the SourceIndicator 
	 textual convention.
	 
	 This is optionally added tot he attributeValueChange, 
	 objectCreation, objectDeletion, relationshipChange or 
	 stateChange notifications."
    REFERENCE
	"ITU-T Rec. X.721 (1992) | ISO/IEC 10165-2 : 1992, 
	    sourceIndicator."
    ::= { tmnNotifObjects 14 }

attributeIdentifierList OBJECT-TYPE
    SYNTAX AttributeIdentifierList
    MAX-ACCESS accessible-for-notify
    STATUS current
    DESCRIPTION
	"Provides an object for use with notifications."
    REFERENCE
	"ITU-T Rec. X.721 (1992) | ISO/IEC 10165-2 : 1992, 
	    attributeIdentifierList."
    ::= { tmnNotifObjects 15 }

attributeValueChangeDefinition OBJECT-TYPE
    SYNTAX AttributeValueChangeDefinition
    MAX-ACCESS accessible-for-notify
    STATUS current
    DESCRIPTION
	"Provides an object for use with notifications."
    REFERENCE
	"ITU-T Rec. X.721 (1992) | ISO/IEC 10165-2 : 1992, 
	    attributeValueChangeDefinition."
    ::= { tmnNotifObjects 16 }

additionalText OBJECT-TYPE
    SYNTAX AdditionalText
    MAX-ACCESS accessible-for-notify
    STATUS current
    DESCRIPTION
	"Provides an object for use with notifications.  This is the 
	 additional text for an alarm notification following the 
	 AdditionalText textual convention."
    REFERENCE
	"ITU-T Rec. X.721 (1992) | ISO/IEC 10165-2 : 1992, 
	    additionalText."
    ::= { tmnNotifObjects 17 }

additionalInformation OBJECT-TYPE
    SYNTAX AdditionalInformation
    MAX-ACCESS accessible-for-notify
    STATUS current
    DESCRIPTION
	"Provides an object for use with notifications.  This is the 
	 additional information for an alarm notification following the 
	 AdditionalInformation textual convention."
    REFERENCE
	"ITU-T Rec. X.721 (1992) | ISO/IEC 10165-2 : 1992, 
	    additionalInformation."
    ::= { tmnNotifObjects 18 }

securityAlarmCause OBJECT-TYPE
    SYNTAX SecurityAlarmCause
    MAX-ACCESS accessible-for-notify
    STATUS current
    DESCRIPTION
	"This is the security alarm cause of the security alarm 
	 condition in accordance with TMN SMI defintions.  The security 
	 alarm cause is a required parameter of the intergrity 
	 violation, operational violation, physical violation, security 
	 service or mechanism violation, and time domain violation 
	 notifications.  It contains an object identity which indicates 
	 the cause of the alarm in accordance with SecurityAlarmCause 
	 textual convention.

	 The meaning and purpose of object identifiers that are used to 
	 populate this parameter for these alarm notifications must be 
	 specified in the DESCRIPTION clause of an OBJECT-IDENTITY macro 
	 defining the object identifier associated with the security 
	 alarm cause.  The precise conditions under which the alarm is 
	 raised and cleared (see perceivedSeverity) must also be defined 
	 in the DESCRIPTION clause whenever the value is used to raise 
	 generic alarms such as the integrity violation.  When used with 
	 a specific notification, the use of the security alarm cause 
	 parameter must be defined in the NOTIFICATION-TYPE marco's 
	 DESCRIPTION clause.

	 In all cases, the object identifier defined by the 
	 corresponding standard (i.e.  TMN specification) should be used 
	 as specified in the corresponding standard.  Private values of 
	 the probable cuase may also be defined in OBJECT-IDENTITY 
	 marcos within a private or enterprise module definition.  Where 
	 possible, however, a standard value should be used."
    REFERENCE
	"ITU-T Rec. X.721 (1992) | ISO/IEC 10165-2 : 1992, 
	    securityAlarmCause."
    ::= { tmnNotifObjects 19 }

securityAlarmSeverity OBJECT-TYPE
    SYNTAX SecurityAlarmSeverity
    MAX-ACCESS accessible-for-notify
    STATUS current
    DESCRIPTION
	"This is the same as perceivedSeverity but for security alarms.  
	 Security alarms do not clear and this has no cleared(5) value."
    REFERENCE
	"ITU-T Rec. X.721 (1992) | ISO/IEC 10165-2 : 1992, 
	    securityAlarmSeverity."
    ::= { tmnNotifObjects 20 }

securityAlarmDetector OBJECT-TYPE
    SYNTAX SecurityAlarmDetector
    MAX-ACCESS accessible-for-notify
    STATUS current
    DESCRIPTION
	"Provides an object for use with notifications.  This is an 
	 identifier of the detector following the SecurityAlarmDetector 
	 textual convention."
    REFERENCE
	"ITU-T Rec. X.721 (1992) | ISO/IEC 10165-2 : 1992, 
	    securityAlarmDetector."
    ::= { tmnNotifObjects 21 }

serviceUser OBJECT-TYPE
    SYNTAX ServiceUser
    MAX-ACCESS accessible-for-notify
    STATUS current
    DESCRIPTION
	"Provides an object for use with notifications.  This is the 
	 identification of the service user following the ServiceUser 
	 textual convention."
    REFERENCE
	"ITU-T Rec. X.721 (1992) | ISO/IEC 10165-2 : 1992, serviceUser."
    ::= { tmnNotifObjects 22 }

serviceProvider OBJECT-TYPE
    SYNTAX ServiceProvider
    MAX-ACCESS accessible-for-notify
    STATUS current
    DESCRIPTION
	"Provides an object for use with notifications.  This is the 
	 identification of the service provider following the 
	 ServiceProvider textual convention."
    REFERENCE
	"ITU-T Rec. X.721 (1992) | ISO/IEC 10165-2 : 1992, 
	    serviceProvider."
    ::= { tmnNotifObjects 23 }

attributeList OBJECT-TYPE
    SYNTAX AttributeList
    MAX-ACCESS accessible-for-notify
    STATUS current
    DESCRIPTION
	"Provides an object for use with notifications."
    REFERENCE
	"ITU-T Rec. X.721 (1992) | ISO/IEC 10165-2 : 1992, 
	    attributeList."
    ::= { tmnNotifObjects 24 }

relationshipChangeDefinition OBJECT-TYPE
    SYNTAX AttributeValueChangeDefinition
    MAX-ACCESS accessible-for-notify
    STATUS current
    DESCRIPTION
	"Provides an object for use with notifications."
    REFERENCE
	"ITU-T Rec. X.721 (1992) | ISO/IEC 10165-2 : 1992, 
	    relationshipChangeDefinition."
    ::= { tmnNotifObjects 25 }

informationType OBJECT-TYPE
    SYNTAX InformationType
    MAX-ACCESS accessible-for-notify
    STATUS current
    DESCRIPTION
	"This is the information type of an information event in 
	 accordacne with the TMN SMI definitions.  It is an required 
	 parameter of the communicationInformation notification. It 
	 contains an object identity which indicates the information 
	 type of the event in according with the InformationType textual 
	 convention.

	 The meaning and purpose of object identifiers that are used to 
	 populate this parameter for the communicationsInformation 
	 notification must be specified in the DESCRIPTION clause of an 
	 OBJECT-IDENTITY macro defining the object identifiers 
	 associated with the information type.  The precise conditions 
	 under which the event is notified must also be defined in the 
	 DESCRIPTION clause whenever the value is used to raise generic 
	 information notifications such as the communicationsInformation 
	 notification.  When used with a specific notification, the use 
	 of the information type parameter must be defined inthe 
	 NOTIFICATION-TYPE macro's DESCRIPTION clause.

	 In all cases, the object identifier defined by the 
	 corresponding standard (i.e. TMN specification) should be used 
	 as specified in the corresponding standard.  Private values of 
	 the information type may also be defined in OBJECT-IDENTITY 
	 macros within a private or enterprise module definition.  Where 
	 possible, however, a standard value should be used."
    REFERENCE
	"ITU-T Recommendation X.723 (1993) | ISO/IEC 10165-5 : 1993, 
	 informationType."
    ::= { tmnNotifObjects 26 }

informationData OBJECT-TYPE
    SYNTAX InformationData
    MAX-ACCESS accessible-for-notify
    STATUS current
    DESCRIPTION
	"This is the information data for an information notification 
	 following the InformationData textual convention."
    REFERENCE
	"ITU-T Recommendation X.723 (1993) | ISO/IEC 10165-5 : 1993, 
	 informationData."
    ::= { tmnNotifObjects 27 }

-- =====================================================================
--
-- NOTIFICATION
--
-- =====================================================================
-- These are general purpose notifications taken from X.721.  They rely 
-- on the definition of some Scalars from this module and some textual 
-- conventions from the OPENSS7-TMN-TC module.

attributeValueChange NOTIFICATION-TYPE
    OBJECTS {
	objectInstance,
	-- sourceIndicator SourceIndicator OPTIONAL,
	-- attributeIdentifierList [1] AttributeIdentifierList OPTIONAL,
	attributeValueChangeDefinition -- AttributeValueChangeDefinition,
	-- notificationIdentifier NotificationIdentifier OPTIONAL,
	-- correlatedNotifications [2] CorrelatedNotifications OPTIONAL,
	-- additionalText AdditionalText OPTIONAL,
	-- additionalInformation [3] AdditionalInformation OPTIONAL }
    }
    STATUS current
    DESCRIPTION
	"This notification type is used to report changes to the 
	 attribute such as addition or deletion of members to one or 
	 more set valued attributes, replacement of the value of one or 
	 more attributes and setting attribute values to their defaults.
	 
	 The attribute value changes specification in TMN is a 
	 complicated thing.  Here it is required that the issuer of the 
	 notification include the attributes whose values have changed, 
	 first the attribute with the old value and next the attribute 
	 with the new value for each attribute reported."
    REFERENCE
	"ITU-T Rec. X.721 (1992) | ISO/IEC 10165-2 : 1992 
	    attributeValueChange NOTIFICATION."
    ::= { tmnNotifications 1 }

communicationsAlarm NOTIFICATION-TYPE
    OBJECTS {
	objectInstance,
	probableCause, -- ProbableCause,
	-- specificProblems [1] SpecificProblems OPTIONAL,
	perceivedSeverity -- PerceivedSeverity,
	-- backedUpStatus BackedUpStatus OPTIONAL,
	-- backUpObject [2] ObjectInstance OPTIONAL,
	-- trendIndication [3] TrendIndication OPTIONAL,
	-- thresholdInfo [4] ThresholdInfo OPTIONAL,
	-- notificationIdentifier [5] NotificationIdentifier OPTIONAL,
	-- correlatedNotifications [6] CorrelatedNotifications OPTIONAL,
	-- stateChangeDefinition [7] AttributeValueChangeDefinition OPTIONAL,
	-- monitoredAttributes [8] MonitoredAttributes OPTIONAL,
	-- proposedRepairActions [9] ProposedRepairActions OPTIONAL,
	-- additionalText AdditionalText OPTIONAL,
	-- additionalInformation [10] AdditionalInformation OPTIONAL }
    }
    STATUS current
    DESCRIPTION
	"This notification type is used to report when the object 
	 detects a communications error.

	 This is one of two mechanisms of providing communications 
	 alarms corresponding to TMN alarms.  One method is to provide a 
	 single notification which is parameterized in a similar fashion 
	 to TMN.  The other method is providing indepdendent 
	 notifications for each cause.  The advantages of providing a 
	 single notification for communications alarms is that the 
	 management station need only monitor a single trap to receive 
	 all alarm indications.  On a managed system with thousands of 
	 unique alarms, this has scale benefits.

	 The communicationsAlarm is modelled on the TMN notification of 
	 the same name.  TMN too has the ability to provide independent 
	 notifications and chose a similar unified alarm notification.

	 The first parameter of the communicationsAlarm is the probable 
	 cause, which is an object identifier defined with the 
	 OBJECT-IDENTITY macro.  The probable cause identifies the 
	 alarm.  The third parameter (second object in SNMP) is the 
	 perceived severity.  Following the PerceivedSeverity textual 
	 convention, this parameter indicates when the alarm has onset 
	 or cleared, and when indicating onset, the relative severity in 
	 telecommunications terms (warning, minor, major, critical).  
	 The second parameter (optional additional object in SNMP) is a 
	 sequence of specific problems that refined the alarm 
	 indication.

	 Because their values are defined by an OBJECT-IDENTITY macro, 
	 the DESCRIPTION clause in that macro defining a probable cause 
	 or specific problem should clearly identify the purpose of the 
	 alarm, when it is generated, when it is cleared, and how a 
	 specific problem refines the probable cause.  This makes this 
	 information available to managers via the MIB generating the 
	 alarms.  Where a generic value is not used, the probable cause 
	 and specific problems should be defined within the MIB module 
	 that use them.

	 State changes and attribute value changes can be reported by 
	 simply including the object with the old value and the object 
	 with the new value for each object reported."
    REFERENCE
	"ITU-T Rec. X.721 (1992) | ISO/IEC 10165-2 : 1992 
	    communicationsAlarm NOTIFICATION."
    ::= { tmnNotifications 2 }

environmentalAlarm NOTIFICATION-TYPE
    OBJECTS {
	objectInstance,
	probableCause, -- ProbableCause,
	-- specificProblems [1] SpecificProblems OPTIONAL,
	perceivedSeverity -- PerceivedSeverity,
	-- backedUpStatus BackedUpStatus OPTIONAL,
	-- backUpObject [2] ObjectInstance OPTIONAL,
	-- trendIndication [3] TrendIndication OPTIONAL,
	-- thresholdInfo [4] ThresholdInfo OPTIONAL,
	-- notificationIdentifier [5] NotificationIdentifier OPTIONAL,
	-- correlatedNotifications [6] CorrelatedNotifications OPTIONAL,
	-- stateChangeDefinition [7] AttributeValueChangeDefinition OPTIONAL,
	-- monitoredAttributes [8] MonitoredAttributes OPTIONAL,
	-- proposedRepairActions [9] ProposedRepairActions OPTIONAL,
	-- additionalText AdditionalText OPTIONAL,
	-- additionalInformation [10] AdditionalInformation OPTIONAL }
    }
    STATUS current
    DESCRIPTION
	"This notification type is used to report a problem in the 
	 environment.

	 This is similar to the communicationsAlarm. The first parameter 
	 is the probable cause which follows the ProbableCause textual 
	 convention.  The second parameter is the perceived severity 
	 which follows the PerceivedSeverity textual convention.  
	 Additional specificProblems parameters may be added along with 
	 other information.  See communicationsAlarm for more 
	 information."
    REFERENCE
	"ITU-T Rec. X.721 (1992) | ISO/IEC 10165-2 : 1992 
	    environmentalAlarm NOTIFICATION."
    ::= { tmnNotifications 3 }

equipmentAlarm NOTIFICATION-TYPE
    OBJECTS {
	objectInstance,
	probableCause, -- ProbableCause,
	-- specificProblems [1] SpecificProblems OPTIONAL,
	perceivedSeverity -- PerceivedSeverity,
	-- backedUpStatus BackedUpStatus OPTIONAL,
	-- backUpObject [2] ObjectInstance OPTIONAL,
	-- trendIndication [3] TrendIndication OPTIONAL,
	-- thresholdInfo [4] ThresholdInfo OPTIONAL,
	-- notificationIdentifier [5] NotificationIdentifier OPTIONAL,
	-- correlatedNotifications [6] CorrelatedNotifications OPTIONAL,
	-- stateChangeDefinition [7] AttributeValueChangeDefinition OPTIONAL,
	-- monitoredAttributes [8] MonitoredAttributes OPTIONAL,
	-- proposedRepairActions [9] ProposedRepairActions OPTIONAL,
	-- additionalText AdditionalText OPTIONAL,
	-- additionalInformation [10] AdditionalInformation OPTIONAL }
    }
    STATUS current
    DESCRIPTION
	"This notification type is used to report failure in the 
	 equipment.

	 This is similar to both the environmentalAlarm and the 
	 communicationsAlarm.  The first parameter is the probaable 
	 cause which follows the ProbableCause textual convention.  The 
	 second parameter is the perceived severity which follows the 
	 PerceivedSeverity textual convention.  Additional 
	 SpecificProblems parameters may be added along with other 
	 information.  See communicationsAlarm for more information."
    REFERENCE
	"ITU-T Rec. X.721 (1992) | ISO/IEC 10165-2 : 1992 
	    equipmentAlarm NOTIFICATION."
    ::= { tmnNotifications 4 }

integrityViolation NOTIFICATION-TYPE
    OBJECTS {
	objectInstance,
	securityAlarmCause, -- SecurityAlarmCause,
	securityAlarmSeverity, -- SecurityAlarmSeverity,
	securityAlarmDetector, -- SecurityAlarmDetector,
	serviceUser, -- ServiceUser,
	serviceProvider -- ServiceProvider,
	-- notificationIdentifier NotificationIdentifier OPTIONAL,
	-- correlatedNotifications [1] CorrelatedNotifications OPTIONAL,
	-- additionalText AdditionalText OPTIONAL,
	-- additionalInformation [2] AdditionalInformation OPTIONAL }
    }
    STATUS current
    DESCRIPTION
	"This notification is used to report that a potential 
	 interruption in information flow has occurred such that 
	 information may have been illegally modified, inserted or 
	 deleted."
    REFERENCE
	"ITU-T Rec. X.721 (1992) | ISO/IEC 10165-2 : 1992 
	    integrityViolation NOTIFICATION."
    ::= { tmnNotifications 5 }

objectCreation NOTIFICATION-TYPE
    OBJECTS {
	objectInstance
	-- sourceIndicator SourceIndicator OPTIONAL,
	-- attributeList AttributeList OPTIONAL,
	-- notificationIdentifier NotificationIdentifier OPTIONAL,
	-- correlatedNotifications [1] CorrelatedNotifications OPTIONAL,
	-- additionalText AdditionalText OPTIONAL,
	-- additionalInformation [2] AdditionalInformation OPTIONAL }
    }
    STATUS current
    DESCRIPTION
	"This notification type is used to report the creation of a 
	 managed object to another open system.

	 Note that the reporting agent should include a RowPointer 
	 identification of the object instance that has been created."
    REFERENCE
	"ITU-T Rec. X.721 (1992) | ISO/IEC 10165-2 : 1992 
	    objectCreation NOTIFICATION."
    ::= { tmnNotifications 6 }

objectDeletion NOTIFICATION-TYPE
    OBJECTS {
	objectInstance
	-- sourceIndicator SourceIndicator OPTIONAL,
	-- attributeList AttributeList OPTIONAL,
	-- notificationIdentifier NotificationIdentifier OPTIONAL,
	-- correlatedNotifications [1] CorrelatedNotifications OPTIONAL,
	-- additionalText AdditionalText OPTIONAL,
	-- additionalInformation [2] AdditionalInformation OPTIONAL }
    }
    STATUS current
    DESCRIPTION
	"This notification type is used to report the deletion of a 
	 managed object to another open system.

	 Note that the reporting agent should include a RowPointer 
	 identification and all the previous attributes in the 
	 notification."
    REFERENCE
	"ITU-T Rec. X.721 (1992) | ISO/IEC 10165-2 : 1992 
	    objectDeletion NOTIFICATION."
    ::= { tmnNotifications 7 }

operationalViolation NOTIFICATION-TYPE
    OBJECTS {
	objectInstance,
	securityAlarmCause, -- SecurityAlarmCause,
	securityAlarmSeverity, -- SecurityAlarmSeverity,
	securityAlarmDetector, -- SecurityAlarmDetector,
	serviceUser, -- ServiceUser,
	serviceProvider -- ServiceProvider,
	-- notificationIdentifier NotificationIdentifier OPTIONAL,
	-- correlatedNotifications [1] CorrelatedNotifications OPTIONAL,
	-- additionalText AdditionalText OPTIONAL,
	-- additionalInformation [2] AdditionalInformation OPTIONAL }
    }
    STATUS current
    DESCRIPTION
	"This notification is used to report that the provision of the 
	 requested service was not possible due to the unavailability, 
	 malfunction or incorrect invocation of the service."
    REFERENCE
	"ITU-T Rec. X.721 (1992) | ISO/IEC 10165-2 : 1992 
	    operationalViolation NOTIFICATION."
    ::= { tmnNotifications 8 }

physicalViolation NOTIFICATION-TYPE
    OBJECTS {
	objectInstance,
	securityAlarmCause, -- SecurityAlarmCause,
	securityAlarmSeverity, -- SecurityAlarmSeverity,
	securityAlarmDetector, -- SecurityAlarmDetector,
	serviceUser, -- ServiceUser,
	serviceProvider -- ServiceProvider,
	-- notificationIdentifier NotificationIdentifier OPTIONAL,
	-- correlatedNotifications [1] CorrelatedNotifications OPTIONAL,
	-- additionalText AdditionalText OPTIONAL,
	-- additionalInformation [2] AdditionalInformation OPTIONAL }
    }
    STATUS current
    DESCRIPTION
	"This notification is used to report that a physical resource 
	 has been violated in a way that indicates a potential security 
	 attack."
    REFERENCE
	"ITU-T Rec. X.721 (1992) | ISO/IEC 10165-2 : 1992 
	    physicalViolation NOTIFICATION."
    ::= { tmnNotifications 9 }

processingErrorAlarm NOTIFICATION-TYPE
    OBJECTS {
	objectInstance,
	probableCause, -- ProbableCause,
	-- specificProblems [1] SpecificProblems OPTIONAL,
	perceivedSeverity -- PerceivedSeverity,
	-- backedUpStatus BackedUpStatus OPTIONAL,
	-- backUpObject [2] ObjectInstance OPTIONAL,
	-- trendIndication [3] TrendIndication OPTIONAL,
	-- thresholdInfo [4] ThresholdInfo OPTIONAL,
	-- notificationIdentifier [5] NotificationIdentifier OPTIONAL,
	-- correlatedNotifications [6] CorrelatedNotifications OPTIONAL,
	-- stateChangeDefinition [7] AttributeValueChangeDefinition OPTIONAL,
	-- monitoredAttributes [8] MonitoredAttributes OPTIONAL,
	-- proposedRepairActions [9] ProposedRepairActions OPTIONAL,
	-- additionalText AdditionalText OPTIONAL,
	-- additionalInformation [10] AdditionalInformation OPTIONAL }
    }
    STATUS current
    DESCRIPTION
	"This notification type is used to report processing failure in 
	 a managed object.

	 The agent should include the identification of the row or 
	 variable generating the alarm."
    REFERENCE
	"ITU-T Rec. X.721 (1992) | ISO/IEC 10165-2 : 1992 
	    processingErrorAlarm NOTIFICATION."
    ::= { tmnNotifications 10 }

qualityofServiceAlarm NOTIFICATION-TYPE
    OBJECTS {
	objectInstance,
	probableCause, -- ProbableCause,
	-- specificProblems [1] SpecificProblems OPTIONAL,
	perceivedSeverity -- PerceivedSeverity,
	-- backedUpStatus BackedUpStatus OPTIONAL,
	-- backUpObject [2] ObjectInstance OPTIONAL,
	-- trendIndication [3] TrendIndication OPTIONAL,
	-- thresholdInfo [4] ThresholdInfo OPTIONAL,
	-- notificationIdentifier [5] NotificationIdentifier OPTIONAL,
	-- correlatedNotifications [6] CorrelatedNotifications OPTIONAL,
	-- stateChangeDefinition [7] AttributeValueChangeDefinition OPTIONAL,
	-- monitoredAttributes [8] MonitoredAttributes OPTIONAL,
	-- proposedRepairActions [9] ProposedRepairActions OPTIONAL,
	-- additionalText AdditionalText OPTIONAL,
	-- additionalInformation [10] AdditionalInformation OPTIONAL }
    }
    STATUS current
    DESCRIPTION
	"This notification type is used to report a failure in the 
	 quality of service of the managed object."
    REFERENCE
	"ITU-T Rec. X.721 (1992) | ISO/IEC 10165-2 : 1992 
	    qualityofServiceAlarm NOTIFICATION."
    ::= { tmnNotifications 11 }

relationshipChange NOTIFICATION-TYPE
    OBJECTS {
	objectInstance,
	-- sourceIndicator SourceIndicator OPTIONAL,
	-- attributeIdentifierList [1] AttributeIdentifierList OPTIONAL,
	relationshipChangeDefinition -- AttributeValueChangeDefinition,
	-- notificationIdentifier NotificationIdentifier OPTIONAL,
	-- correlatedNotifications [2] CorrelatedNotifications OPTIONAL,
	-- additionalText AdditionalText OPTIONAL,
	-- additionalInformation [3] AdditionalInformation OPTIONAL }
    }
    STATUS current
    DESCRIPTION
	"This notification type is used to report the change in the 
	 value of one or more relationship attributes of a managed 
	 object, that result through either internal operation of the 
	 managed object or via management operation."
    REFERENCE
	"ITU-T Rec. X.721 (1992) | ISO/IEC 10165-2 : 1992 
	    relationshipChange NOTIFICATION."
    ::= { tmnNotifications 12 }

securityServiceOrMechanismViolation NOTIFICATION-TYPE
    OBJECTS {
	objectInstance,
	securityAlarmCause, -- SecurityAlarmCause,
	securityAlarmSeverity, -- SecurityAlarmSeverity,
	securityAlarmDetector, -- SecurityAlarmDetector,
	serviceUser, -- ServiceUser,
	serviceProvider -- ServiceProvider,
	-- notificationIdentifier NotificationIdentifier OPTIONAL,
	-- correlatedNotifications [1] CorrelatedNotifications OPTIONAL,
	-- additionalText AdditionalText OPTIONAL,
	-- additionalInformation [2] AdditionalInformation OPTIONAL }
    }
    STATUS current
    DESCRIPTION
	"This notification is used to report that a security attack has 
	 been detected by a security service or mechanism."
    REFERENCE
	"ITU-T Rec. X.721 (1992) | ISO/IEC 10165-2 : 1992 
	    securityServiceOrMechanismViolation NOTIFICATION."
    ::= { tmnNotifications 13 }

stateChange NOTIFICATION-TYPE
    OBJECTS {
	objectInstance,
	-- sourceIndicator SourceIndicator OPTIONAL,
	-- attributeIdentifierList [1] AttributeIdentifierList OPTIONAL,
	stateChangeDefinition -- AttributeValueChangeDefinition,
	-- notificationIdentifier NotificationIdentifier OPTIONAL,
	-- correlatedNotifications [2] CorrelatedNotifications OPTIONAL,
	-- additionalText AdditionalText OPTIONAL,
	-- additionalInformation [3] AdditionalInformation OPTIONAL }
    }
    STATUS current
    DESCRIPTION
	"This notification type is used to report the change in the 
	 value of one or more state attributes of a managed object, that 
	 result through either internal operation of the managed object 
	 or via management operation.
	 
	 The stateChangeDefinition in TMN is a complicated thing.  Here 
	 the issuer of this norification should include the old value of 
	 the attribute followed by the new value of the attribute for 
	 each attribute reported."
    REFERENCE
	"ITU-T Rec. X.721 (1992) | ISO/IEC 10165-2 : 1992 
	    stateChange NOTIFICATION."
    ::= { tmnNotifications 14 }

timeDomainViolation NOTIFICATION-TYPE
    OBJECTS {
	objectInstance,
	securityAlarmCause, -- SecurityAlarmCause,
	securityAlarmSeverity, -- SecurityAlarmSeverity,
	securityAlarmDetector, -- SecurityAlarmDetector,
	serviceUser, -- ServiceUser,
	serviceProvider -- ServiceProvider,
	-- notificationIdentifier NotificationIdentifier OPTIONAL,
	-- correlatedNotifications [1] CorrelatedNotifications OPTIONAL,
	-- additionalText AdditionalText OPTIONAL,
	-- additionalInformation [2] AdditionalInformation OPTIONAL }
    }
    STATUS current
    DESCRIPTION
	"This notification is used to report that an event has occurred 
	 at an unexpected or prohibited time."
    REFERENCE
	"ITU-T Rec. X.721 (1992) | ISO/IEC 10165-2 : 1992 
	    timeDomainViolation NOTIFICATION."
    ::= { tmnNotifications 15 }

-- This is a general purpose notification taken from X.723.  It relies 
-- on the definition of some Scalars from this module and some textual 
-- conventions from the OPENSS7-TMN-TC module.

communicationsInformation NOTIFICATION-TYPE
    OBJECTS {
	objectInstance,
	informationType
	-- informationData
    }
    STATUS current
    DESCRIPTION
	"This notification may be used to report the occurrence of 
	 events pertaining to the normal operation of a managed object. 
	 These are informational events; important enough to report, but 
	 not requiring any further action by a manager.  Faults and 
	 abnormal conditions (which may require manager action) shall be 
	 reported using the event types defined in CCITT Rec.  X.733 
	 (1992) | ISO/IEC 10164-4:1992.

	 The communicationsInformation notification is modelled on the 
	 TMN notification of the same name.

	 The first paraemter of the communicationInformation 
	 notification is the information type, which is an object 
	 identifier defined with the OBJECT-IDENTITY macro.  The 
	 information type identifies the event.

	 Beacuse its value is defined by an OBJECT-IDENTITY macro, the 
	 DESCRIPTION clause in that macro defining an information type 
	 should clearly identify the purpose of the event notification, 
	 when it is geenrtated, ahd how any information data refines the 
	 information type.  This makes this information available to 
	 managers via the MIB generating the alarms.  When a generic 
	 value is not used, the information type should be defined 
	 within the MIB module that issues them."
    REFERENCE
	"ITU-T Recommendation X.723 (1993) | ISO/IEC 10165-5 : 1993, 
	    communicationInformation"
    ::= { tmnNotifications 16 }

-- =====================================================================
--
-- NOTIFICATION (and ALARM) TYPE (from X.721)
--
-- =====================================================================

smi2Notification OBJECT IDENTIFIER ::=
{ joint-iso-ccitt(2) ms(9) smi(3) part2(2) notification(10) }

attributeValueChangeType OBJECT-IDENTITY
    STATUS current
    DESCRIPTION
	"The event type for the attributeValueChange notification."
    REFERENCE
	"ITU-T Rec. X.721 (1992) | ISO/IEC 10165-2 : 1992 
	    attributeValueChangeType."
    ::= { smi2Notification 1 }

communicationsAlarmType OBJECT-IDENTITY
    STATUS current
    DESCRIPTION
	"The event type for the communicationsAlarm notification.  An 
	 alarm of this type is principally associated with the 
	 procedures or processes required to convey information from one 
	 point to another."
    REFERENCE
	"ITU-T Rec. X.721 (1992) | ISO/IEC 10165-2 : 1992 
	    attributeValueChangeType."
    ::= { smi2Notification 2 }

environmentalAlarmType OBJECT-IDENTITY
    STATUS current
    DESCRIPTION
	"The event type for the environmentalAlarm notification.  An 
	 alarm of this type is principally associated with a condition 
	 relating to an enclosure in which the equipment resides."
    REFERENCE
	"ITU-T Rec. X.721 (1992) | ISO/IEC 10165-2 : 1992 
	    attributeValueChangeType."
    ::= { smi2Notification 3 }

equipmentAlarmType OBJECT-IDENTITY
    STATUS current
    DESCRIPTION
	"The event type for the equipmentAlarm notification.  An alarm 
	 of this type is principally associated with an equipment 
	 fault."
    REFERENCE
	"ITU-T Rec. X.721 (1992) | ISO/IEC 10165-2 : 1992 
	    attributeValueChangeType."
    ::= { smi2Notification 4 }

integrityViolationType OBJECT-IDENTITY
    STATUS current
    DESCRIPTION
	"The event type for the integrityViolation notification."
    REFERENCE
	"ITU-T Rec. X.721 (1992) | ISO/IEC 10165-2 : 1992 
	    attributeValueChangeType."
    ::= { smi2Notification 5 }

objectCreationType OBJECT-IDENTITY
    STATUS current
    DESCRIPTION
	"The event type for the objectCreation notification."
    REFERENCE
	"ITU-T Rec. X.721 (1992) | ISO/IEC 10165-2 : 1992 
	    attributeValueChangeType."
    ::= { smi2Notification 6 }

objectDeletionType OBJECT-IDENTITY
    STATUS current
    DESCRIPTION
	"The event type for the objectDeletion notification."
    REFERENCE
	"ITU-T Rec. X.721 (1992) | ISO/IEC 10165-2 : 1992 
	    attributeValueChangeType."
    ::= { smi2Notification 7 }

operationalViolationType OBJECT-IDENTITY
    STATUS current
    DESCRIPTION
	"The event type for the operationalViolation notification."
    REFERENCE
	"ITU-T Rec. X.721 (1992) | ISO/IEC 10165-2 : 1992 
	    attributeValueChangeType."
    ::= { smi2Notification 8 }

physicalViolationType OBJECT-IDENTITY
    STATUS current
    DESCRIPTION
	"The event type for the physicalViolation notification."
    REFERENCE
	"ITU-T Rec. X.721 (1992) | ISO/IEC 10165-2 : 1992 
	    attributeValueChangeType."
    ::= { smi2Notification 9 }

processingErrorAlarmType OBJECT-IDENTITY
    STATUS current
    DESCRIPTION
	"The event type for the processingErrorAlarm notification.  An 
	 alarm of this type is principally associated with a software or 
	 processing fault."
    REFERENCE
	"ITU-T Rec. X.721 (1992) | ISO/IEC 10165-2 : 1992 
	    attributeValueChangeType."
    ::= { smi2Notification 10 }

qualityofServiceAlarmType OBJECT-IDENTITY
    STATUS current
    DESCRIPTION
	"The event type for the qualityofServiceAlarm notification.  An 
	 alarm of this type is principally associated with a degradation 
	 in the quality of service."
    REFERENCE
	"ITU-T Rec. X.721 (1992) | ISO/IEC 10165-2 : 1992 
	    attributeValueChangeType."
    ::= { smi2Notification 11 }

relationshipChangeType OBJECT-IDENTITY
    STATUS current
    DESCRIPTION
	"The event type for the relationshipChange notification.  This 
	 notification type is used to report the change of one or more 
	 relationship attributes of a managed object, that result 
	 through either the internal operation of the resource or via 
	 management operation.  It is also used to report changes in 
	 object class specific relationship attributes."
    REFERENCE
	"ITU-T Rec. X.721 (1992) | ISO/IEC 10165-2 : 1992 
	     attributeValueChangeType.
	 ITU-T Rec. X.732 (1992) | ISO/IEC 10164-3 : 1993 
	     Section 8.2.1."
    ::= { smi2Notification 12 }

securityServiceOrMechanismViolationType OBJECT-IDENTITY
    STATUS current
    DESCRIPTION
	"The event type for the securityServiceOrMechanismViolation 
	 notification."
    REFERENCE
	"ITU-T Rec. X.721 (1992) | ISO/IEC 10165-2 : 1992 
	    attributeValueChangeType."
    ::= { smi2Notification 13 }

stateChangeType OBJECT-IDENTITY
    STATUS current
    DESCRIPTION
	"The event type for the stateChange notification."
    REFERENCE
	"ITU-T Rec. X.721 (1992) | ISO/IEC 10165-2 : 1992 
	    attributeValueChangeType."
    ::= { smi2Notification 14 }

timeDomainViolationType OBJECT-IDENTITY
    STATUS current
    DESCRIPTION
	"The event type for the timeDomainViolation notification."
    REFERENCE
	"ITU-T Rec. X.721 (1992) | ISO/IEC 10165-2 : 1992 
	    attributeValueChangeType."
    ::= { smi2Notification 15 }

communicationsInformationType OBJECT-IDENTITY
    STATUS current
    DESCRIPTION
	"The event type for the communicationsInformation notification."
    REFERENCE
	"ITU-T Recommendation X.723 (1993) | ISO/IEC 10165-5 : 1993, 
	    communicationInformation."
    ::= { smi2Notification 16 }


-- =====================================================================
--
-- PROBABLE CAUSES (from X.721)
--
-- =====================================================================

arfProbableCause OBJECT IDENTIFIER ::=
{ joint-iso-ccitt(2) ms(9) smi(3) part2(2) standardSpecificExtensions(0) arf(0) }

adapterError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry."
    REFERENCE
	"ITU-T Rec. X.721 (1992) | ISO/IEC 10165-2 : 1992, 
	 adapterError"
    ::= { arfProbableCause 1 }

applicationSubsystemFailure OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A failure in an application subsystem has occured (an 
	 application subsystem may include software to support the 
	 Session, Presentation or Application layers)."
    REFERENCE
	"ITU-T Rec. X.721 (1992) | ISO/IEC 10165-2 : 1992, 
	    applicationSubsystemFailure"
    ::= { arfProbableCause 2 }

bandwidthReduced OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 The available transmission bandwidth has decreased."
    REFERENCE
	"ITU-T Rec. X.721 (1992) | ISO/IEC 10165-2 : 1992, 
	    bandwidthReduced"
    ::= { arfProbableCause 3 }

callEstablishmentError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error occured while attempting to establish a connection."
    REFERENCE
	"ITU-T Rec. X.721 (1992) | ISO/IEC 10165-2 : 1992, 
	    callEstablishmentError"
    ::= { arfProbableCause 4 }

communicationsProtocolError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A communications protocol has been violated."
    REFERENCE
	"ITU-T Rec. X.721 (1992) | ISO/IEC 10165-2 : 1992, 
	    communicationsProtocolError"
    ::= { arfProbableCause 5 }

communicationsSubsystemFailure OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A failure in a subsystem that supports communications over 
	 telecommunications links, there may be implemented via leased 
	 telephone lines, by X.25 networks, token-ring LAN, or 
	 otherwise."
    REFERENCE
	"ITU-T Rec. X.721 (1992) | ISO/IEC 10165-2 : 1992, 
	    communicationsSubsystemFailure"
    ::= { arfProbableCause 6 }

configurationOrCustomizationError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A system or device generation or customization parameter has 
	 been specified incorrectly, or is inconsistent with the actual 
	 configuration."
    REFERENCE
	"ITU-T Rec. X.721 (1992) | ISO/IEC 10165-2 : 1992, 
	    configurationOrCustomizationError"
    ::= { arfProbableCause 7 }

congestion OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A system or network component has reached its capacity or is 
	 approaching it."
    REFERENCE
	"ITU-T Rec. X.721 (1992) | ISO/IEC 10165-2 : 1992, 
	    congestion"
    ::= { arfProbableCause 8 }

corruptData OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error has caused data to be incorrect and thus unreliable."
    REFERENCE
	"ITU-T Rec. X.721 (1992) | ISO/IEC 10165-2 : 1992, 
	    corruptData"
    ::= { arfProbableCause 9 }

cpuCyclesLimitExceeded OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A Central Processing Unit has issued an unacceptable number of 
	 instructions to accomplish a task."
    REFERENCE
	"ITU-T Rec. X.721 (1992) | ISO/IEC 10165-2 : 1992, 
	    cpuCyclesLimitExceeded"
    ::= { arfProbableCause 10 }

dataSetOrModemError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An internal error has occured on a dataset or modem."
    REFERENCE
	"ITU-T Rec. X.721 (1992) | ISO/IEC 10165-2 : 1992, 
	    dataSetOrModemError"
    ::= { arfProbableCause 11 }

degradedSignal OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 The quiality or reliability of transmitted data has decreased."
    REFERENCE
	"ITU-T Rec. X.721 (1992) | ISO/IEC 10165-2 : 1992, 
	    degradedSignal"
    ::= { arfProbableCause 12 }

dTE-DCEInterfaceError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A problem in a DTE-DCE interface, which includes the interface 
	 between the DTE and DCE, any protocol used to communicate 
	 between the DTE and DCE and information provided by the DCE 
	 about the circuit."
    REFERENCE
	"ITU-T Rec. X.721 (1992) | ISO/IEC 10165-2 : 1992, 
	    dTE-DCEInterfaceError"
    ::= { arfProbableCause 13 }

enclosureDoorOpen OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An enclosure door is open."
    REFERENCE
	"ITU-T Rec. X.721 (1992) | ISO/IEC 10165-2 : 1992, 
	    enclosureDoorOpen"
    ::= { arfProbableCause 14 }

equipmentMalfunction OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An internal machine error has occured for which no more 
	 specific probable cause has been identified."
    REFERENCE
	"ITU-T Rec. X.721 (1992) | ISO/IEC 10165-2 : 1992, 
	    equipmentMalfunction"
    ::= { arfProbableCause 15 }

excessiveVibration OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 Vibratory or siesmic limits have been exceeded."
    REFERENCE
	"ITU-T Rec. X.721 (1992) | ISO/IEC 10165-2 : 1992, 
	    excessiveVibration"
    ::= { arfProbableCause 16 }

fileError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 The format of a file (or set of files) is incorrect and thus 
	 cannot be used reliably in processing."
    REFERENCE
	"ITU-T Rec. X.721 (1992) | ISO/IEC 10165-2 : 1992, 
	    fileError"
    ::= { arfProbableCause 17 }

fireDetected OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A fire has been detected."
    REFERENCE
	"ITU-T Rec. X.721 (1992) | ISO/IEC 10165-2 : 1992, 
	    fireDetected"
    ::= { arfProbableCause 18 }

floodDetected OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A flood has been detected."
    REFERENCE
	"ITU-T Rec. X.721 (1992) | ISO/IEC 10165-2 : 1992, 
	    floodDetected"
    ::= { arfProbableCause 19 }

framingError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error in the information that delimits the bit groups within 
	 a continuous stream of bits has occured."
    REFERENCE
	"ITU-T Rec. X.721 (1992) | ISO/IEC 10165-2 : 1992, 
	    framingError"
    ::= { arfProbableCause 20 }

heatingOrVentilationOrCoolingSystemProblem OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A heating, ventilation or cooling system problem has been 
	 detected."
    REFERENCE
	"ITU-T Rec. X.721 (1992) | ISO/IEC 10165-2 : 1992, 
	    heatingOrVentilationCoolingSystemProblem"
    ::= { arfProbableCause 21 }

humidityUnacceptable OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 The humidity is not within acceptable limits."
    REFERENCE
	"ITU-T Rec. X.721 (1992) | ISO/IEC 10165-2 : 1992, 
	    humidityUnacceptable"
    ::= { arfProbableCause 22 }

inputOutputDeviceError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error has occured on the input-output device."
    REFERENCE
	"ITU-T Rec. X.721 (1992) | ISO/IEC 10165-2 : 1992, 
	    inputOutputDeviceError"
    ::= { arfProbableCause 23 }

inputDeviceError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry."
    REFERENCE
	"ITU-T Rec. X.721 (1992) | ISO/IEC 10165-2 : 1992, 
	    adapterError"
    ::= { arfProbableCause 24 }

lANError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error has occured in the input device."
    REFERENCE
	"ITU-T Rec. X.721 (1992) | ISO/IEC 10165-2 : 1992, 
	    inputDeviceError"
    ::= { arfProbableCause 25 }

leakDetected OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A leakage or (non-toxic) fluid or gas has been detected."
    REFERENCE
	"ITU-T Rec. X.721 (1992) | ISO/IEC 10165-2 : 1992, 
	    leakDetected"
    ::= { arfProbableCause 26 }

localNodeTransmissionError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error occured on a communications channel between the local 
	 node and an adjacent node."
    REFERENCE
	"ITU-T Rec. X.721 (1992) | ISO/IEC 10165-2 : 1992, 
	    localNodeTransmissionError"
    ::= { arfProbableCause 27 }

lossOfFrame OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An inability to locate the information that delimits the bit 
	 grouping within a continuous stream of bits has occured."
    REFERENCE
	"ITU-T Rec. X.721 (1992) | ISO/IEC 10165-2 : 1992, 
	    lossOfFrame"
    ::= { arfProbableCause 28 }

lossOfSignal OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error condition in which no data is present on a 
	 communications circuit or channel."
    REFERENCE
	"ITU-T Rec. X.721 (1992) | ISO/IEC 10165-2 : 1992, lossOfSignal"
    ::= { arfProbableCause 29 }

materialSupplyExhausted OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A supply of needed material has been exhausted."
    REFERENCE
	"ITU-T Rec. X.721 (1992) | ISO/IEC 10165-2 : 1992, 
	 materialSupplyExhausted"
    ::= { arfProbableCause 30 }

multiplexerProblem OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error has occured while multiplexing communications 
	 signals."
    REFERENCE
	"ITU-T Rec. X.721 (1992) | ISO/IEC 10165-2 : 1992, 
	 multiplexerProblem"
    ::= { arfProbableCause 31 }

outOfMemory OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 There is no program-addressable storage available."
    REFERENCE
	"ITU-T Rec. X.721 (1992) | ISO/IEC 10165-2 : 1992, outOfMemory"
    ::= { arfProbableCause 32 }

ouputDeviceError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error has occured on the output device."
    REFERENCE
	"ITU-T Rec. X.721 (1992) | ISO/IEC 10165-2 : 1992, 
	 outputDeviceError"
    ::= { arfProbableCause 33 }

performanceDegraded OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 Service agreements or service limits are outside acceptable 
	 limits."
    REFERENCE
	"ITU-T Rec. X.721 (1992) | ISO/IEC 10165-2 : 1992, 
	 performanceDegraded"
    ::= { arfProbableCause 34 }

powerProblem OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 There is a problem with the power supply for one or more 
	 resources."
    REFERENCE
	"ITU-T Rec. X.721 (1992) | ISO/IEC 10165-2 : 1992, powerProblem"
    ::= { arfProbableCause 35 }

pressureUnacceptable OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A fluid or gas pressure is not within acceptable limits."
    REFERENCE
	"ITU-T Rec. X.721 (1992) | ISO/IEC 10165-2 : 1992, 
	 pressureUnacceptable"
    ::= { arfProbableCause 36 }

processorProblem OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An internal machine error has occured on a Central Processing 
	 Unit."
    REFERENCE
	"ITU-T Rec. X.721 (1992) | ISO/IEC 10165-2 : 1992, 
	 processorProblem"
    ::= { arfProbableCause 37 }

pumpFailure OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 Failure of mechanism that transports a fluid by inducing 
	 pressure differentials within the fluid."
    REFERENCE
	"ITU-T Rec. X.721 (1992) | ISO/IEC 10165-2 : 1992, pumpFailure"
    ::= { arfProbableCause 38 }

queueSizeExceeded OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 The number of items to be processed (configurable or not) has 
	 exceeded the maximum allowable."
    REFERENCE
	"ITU-T Rec. X.721 (1992) | ISO/IEC 10165-2 : 1992, 
	 queueSizeExceeded"
    ::= { arfProbableCause 39 }

receiveFailure OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 Receive failure."
    REFERENCE
	"ITU-T Rec. X.721 (1992) | ISO/IEC 10165-2 : 1992, 
	 receiveFailure"
    ::= { arfProbableCause 40 }

receiverFailure OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 Receiver failure."
    REFERENCE
	"ITU-T Rec. X.721 (1992) | ISO/IEC 10165-2 : 1992, 
	 receiverFailure"
    ::= { arfProbableCause 41 }

remoteNodeTransmissionError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An error occured on a communication channel beyond the adjacent 
	 node."
    REFERENCE
	"ITU-T Rec. X.721 (1992) | ISO/IEC 10165-2 : 1992, 
	 remoteNodeTransmissionError"
    ::= { arfProbableCause 42 }

resourceAtOrNearingCapacity OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 The usage of a resource is at or nearing the maximum allowable 
	 capacity."
    REFERENCE
	"ITU-T Rec. X.721 (1992) | ISO/IEC 10165-2 : 1992, 
	 resourceAtOrNearingCapacity"
    ::= { arfProbableCause 43 }

responseTimeExcessive OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 The elapsed time between the end of an inquiry and beginning of 
	 the answer to the inquiry is outside acceptable limits."
    REFERENCE
	"ITU-T Rec. X.721 (1992) | ISO/IEC 10165-2 : 1992, 
	 responseTimeExcessive"
    ::= { arfProbableCause 44 }

retransmissionRateExcessive OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 The number of repeat transmissions is outside of acceptable 
	 limits."
    REFERENCE
	"ITU-T Rec. X.721 (1992) | ISO/IEC 10165-2 : 1992, 
	 retransmissionRateExcessive"
    ::= { arfProbableCause 45 }

softwareError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A software error has occured for which no more specific 
	 probable cause can be identified."
    REFERENCE
	"ITU-T Rec. X.721 (1992) | ISO/IEC 10165-2 : 1992, 
	 softwareError"
    ::= { arfProbableCause 46 }

softwareProgramAbnormallyTerminated OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A software program has abnormally terminated due to some 
	 unrecoverable error condition."
    REFERENCE
	"ITU-T Rec. X.721 (1992) | ISO/IEC 10165-2 : 1992, 
	 softwareProgramAbnormallyTerminated"
    ::= { arfProbableCause 47 }

softwareProgramError OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A software program has abnormally terminated due to some 
	 unrecoverable error condition."
    REFERENCE
	"ITU-T Rec. X.721 (1992) | ISO/IEC 10165-2 : 1992, 
	 softwareProgramError"
    ::= { arfProbableCause 48 }

storageCapacityProblem OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A storage device has very little or no space available to store 
	 additional data."
    REFERENCE
	"ITU-T Rec. X.721 (1992) | ISO/IEC 10165-2 : 1992, 
	 storageCapacityProblem"
    ::= { arfProbableCause 49 }

temperatureUnacceptable OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A temperature is not within acceptable limits."
    REFERENCE
	"ITU-T Rec. X.721 (1992) | ISO/IEC 10165-2 : 1992, 
	 temperatureUnacceptable"
    ::= { arfProbableCause 50 }

thresholdCrossed OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A limit (configurable or not) has been exceeded."
    REFERENCE
	"ITU-T Rec. X.721 (1992) | ISO/IEC 10165-2 : 1992, 
	 thresholdCrossed"
    ::= { arfProbableCause 51 }

timingProblem OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A process that requires timed execution or coordination cannot 
	 complete, or has completed but cannot be considered reliable."
    REFERENCE
	"ITU-T Rec. X.721 (1992) | ISO/IEC 10165-2 : 1992, 
	 timingProblem"
    ::= { arfProbableCause 52 }

toxicLeakDetected OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 A leakage of toxic fluid or gas has been detected."
    REFERENCE
	"ITU-T Rec. X.721 (1992) | ISO/IEC 10165-2 : 1992, 
	 toxicLeaKDetected"
    ::= { arfProbableCause 53 }

transmitFailure OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 Transmit failure."
    REFERENCE
	"ITU-T Rec. X.721 (1992) | ISO/IEC 10165-2 : 1992, 
	 transmitFailure"
    ::= { arfProbableCause 54 }

transmitterFailure OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.

	 Transmitter failure."
    REFERENCE
	"ITU-T Rec. X.721 (1992) | ISO/IEC 10165-2 : 1992, 
	 transmitterFailure"
    ::= { arfProbableCause 55 }

underlyingResourceUnavailable OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 An entity upon which the reporting object depends has become 
	 unavailable."
    REFERENCE
	"ITU-T Rec. X.721 (1992) | ISO/IEC 10165-2 : 1992, 
	 underlyingResourceUnavailable"
    ::= { arfProbableCause 56 }

versionMismatch OBJECT-IDENTITY
    STATUS current
    DESCRIPTION
	"X.721 probable cause value for use in notifications and event 
	 records.  May be used in a communicationsAlarm, 
	 environmentalAlarm, equipmentAlarm, processingErrorAlarm or 
	 qualityofServiceAlarm notification, and may appear in an 
	 AlarmRecordEntry.
	 
	 There is a conflict in the functionality of version of two or 
	 more communicating entites which may affect any processing 
	 involving those entities."
    REFERENCE
	"ITU-T Rec. X.721 (1992) | ISO/IEC 10165-2 : 1992, 
	 versionMismatch"
    ::= { arfProbableCause 57 }

-- =====================================================================

-- ProposedRepairActions values

arfProposedRepairAction OBJECT IDENTIFIER ::= -- { smiOids 3 }
{ joint-iso-ccitt(2) ms(9) smi(3) part2(2) standardSpecificExtensions(0) arfpra(2) }

noActionRequired OBJECT-IDENTITY
    STATUS current
    DESCRIPTION
	"X.721 proposed repair action value for use in notifications and 
	 event records.  May be used in a communicationsAlarm, 
	 environmentalAlarm, equipmentAlarm, processingErrorAlarm or 
	 qualityofServiceAlarm notification, and may appear in 
	 AlarmRecordEntry.
	 
	 Specifies that no repair action is required."
    REFERENCE
	"ITU-T Rec. X.721 (1992) | ISO/IEC 10165-2 : 1992, 
	 noActionRequired"
    ::= { arfProposedRepairAction 1 }

repairActionRequired OBJECT-IDENTITY
    STATUS current
    DESCRIPTION
	"X.721 proposed repair action value for use in notifications and 
	 event records.  May be used in a communicationsAlarm, 
	 environmentalAlarm, equipmentAlarm, processingErrorAlarm or 
	 qualityofServiceAlarm notification, and may appear in 
	 AlarmRecordEntry.
	 
	 Specifies that repair action is required."
    REFERENCE
	"ITU-T Rec. X.721 (1992) | ISO/IEC 10165-2 : 1992, 
	 repairActionRequired"
    ::= { arfProposedRepairAction 2 }

-- =====================================================================
--
-- PROBABLE CAUSES (from M.3100)
--
-- =====================================================================
-- Note that these probable causes are simple local values in M.3100 but 
-- are coded as global values here.  Some names conflict with object 
-- identities of the same name from X.721 and, for those cases, a Gnm 
-- suffix is added to the name.
--

gnmProbableCause OBJECT IDENTIFIER ::=
{ ccitt(0) recommendation(0) m(13) gmn(3100) informationModel(0) standardSpecificExtension(0) probableCauses(1) }

--
-- Probable Causes from M.3100 for use with communicationsAlarm
--

aIS OBJECT-IDENTITY
    STATUS current
    DESCRIPTION
	"Global value of M.3100 probable cause error for use 
	 with communicationsAlarm."
    REFERENCE
	"ITU-T Rec. M.3100 (1992) : aIS"
    ::= { gnmProbableCause 1 }

callSetUpFailure OBJECT-IDENTITY
    STATUS current
    DESCRIPTION
	"Global value of M.3100 probable cause error for use 
	 with communicationsAlarm."
    REFERENCE
	"ITU-T Rec. M.3100 (1992) : callSetUpFailure"
    ::= { gnmProbableCause 2 }

degradedSignalGnm OBJECT-IDENTITY
    STATUS current
    DESCRIPTION
	"Global value of M.3100 probable cause error for use 
	 with communicationsAlarm."
    REFERENCE
	"ITU-T Rec. M.3100 (1992) : degradedSignal"
    ::= { gnmProbableCause 3 }

farEndReceiverFailure OBJECT-IDENTITY
    STATUS current
    DESCRIPTION
	"Global value of M.3100 probable cause error for use 
	 with communicationsAlarm."
    REFERENCE
	"ITU-T Rec. M.3100 (1992) : farEndReceiverFailure"
    ::= { gnmProbableCause 4 }

framingErrorGnm OBJECT-IDENTITY
    STATUS current
    DESCRIPTION
	"Global value of M.3100 probable cause error for use 
	 with communicationsAlarm.  The original name conflicts 
	 with the ITU-T Rec. X.721 probable cause of the same 
	 name."
    REFERENCE
	"ITU-T Rec. M.3100 (1992) : framingError"
    ::= { gnmProbableCause 5 }

lossOfFrameGnm OBJECT-IDENTITY
    STATUS current
    DESCRIPTION
	"Global value of M.3100 probable cause error for use 
	 with communicationsAlarm.  The original name conflicts 
	 with the ITU-T Rec. X.721 probable cause of the same 
	 name."
    REFERENCE
	"ITU-T Rec. M.3100 (1992) : lossOfFrame"
    ::= { gnmProbableCause 6 }

lossOfPointer OBJECT-IDENTITY
    STATUS current
    DESCRIPTION
	"Global value of M.3100 probable cause error for use 
	 with communicationsAlarm."
    REFERENCE
	"ITU-T Rec. M.3100 (1992) : lossOfPointer"
    ::= { gnmProbableCause 7 }

lossOfSignalGnm OBJECT-IDENTITY
    STATUS current
    DESCRIPTION
	"Global value of M.3100 probable cause error for use 
	 with communicationsAlarm.  The original name conflicts 
	 with the ITU-T Rec. X.721 probable cause of the same 
	 name."
    REFERENCE
	"ITU-T Rec. M.3100 (1992) : lossOfSignal"
    ::= { gnmProbableCause 8 }

payloadTypeMismatch OBJECT-IDENTITY
    STATUS current
    DESCRIPTION
	"Global value of M.3100 probable cause error for use 
	 with communicationsAlarm."
    REFERENCE
	"ITU-T Rec. M.3100 (1992) : payloadTypeMismatch"
    ::= { gnmProbableCause 9 }

transmissionError OBJECT-IDENTITY
    STATUS current
    DESCRIPTION
	"Global value of M.3100 probable cause error for use 
	 with communicationsAlarm."
    REFERENCE
	"ITU-T Rec. M.3100 (1992) : transmissionError"
    ::= { gnmProbableCause 10 }

remoteAlarmInterface OBJECT-IDENTITY
    STATUS current
    DESCRIPTION
	"Global value of M.3100 probable cause error for use 
	 with communicationsAlarm."
    REFERENCE
	"ITU-T Rec. M.3100 (1992) : remoteAlarmInterface"
    ::= { gnmProbableCause 11 }

excessiveBER OBJECT-IDENTITY
    STATUS current
    DESCRIPTION
	"Global value of M.3100 probable cause error for use 
	 with communicationsAlarm."
    REFERENCE
	"ITU-T Rec. M.3100 (1992) : excessiveBER"
    ::= { gnmProbableCause 12 }

pathTraceMismatch OBJECT-IDENTITY
    STATUS current
    DESCRIPTION
	"Global value of M.3100 probable cause error for use 
	 with communicationsAlarm."
    REFERENCE
	"ITU-T Rec. M.3100 (1992) : pathTraceMismatch"
    ::= { gnmProbableCause 13 }

unavailable OBJECT-IDENTITY
    STATUS current
    DESCRIPTION
	"Global value of M.3100 probable cause error for use 
	 with communicationsAlarm."
    REFERENCE
	"ITU-T Rec. M.3100 (1992) : unavailable"
    ::= { gnmProbableCause 14 }

signalLabelMismatch OBJECT-IDENTITY
    STATUS current
    DESCRIPTION
	"Global value of M.3100 probable cause error for use 
	 with communicationsAlarm."
    REFERENCE
	"ITU-T Rec. M.3100 (1992) : signalLabelMismatch"
    ::= { gnmProbableCause 15 }

lossOfMultiFrame OBJECT-IDENTITY
    STATUS current
    DESCRIPTION
	"Global value of M.3100 probable cause error for use 
	 with communicationsAlarm."
    REFERENCE
	"ITU-T Rec. M.3100 (1992) : lossOfMultiFrame"
    ::= { gnmProbableCause 16 }

--
-- Values 17-50 are reserved for communications alarm related probable causes
--

--
-- Probable Causes from M.3100 for use with equipmentAlarm
--

backplaneFailure OBJECT-IDENTITY
    STATUS current
    DESCRIPTION
	"Global value of M.3100 probable cause error for use 
	 with equipmentAlarm."
    REFERENCE
	"ITU-T Rec. M.3100 (1992) : backplaneFailure"
    ::= { gnmProbableCause 51 }

dataSetProblem OBJECT-IDENTITY
    STATUS current
    DESCRIPTION
	"Global value of M.3100 probable cause error for use 
	 with equipmentAlarm."
    REFERENCE
	"ITU-T Rec. M.3100 (1992) : dataSetProblem"
    ::= { gnmProbableCause 52 }

equipmentIdentifierDuplication OBJECT-IDENTITY
    STATUS current
    DESCRIPTION
	"Global value of M.3100 probable cause error for use 
	 with equipmentAlarm."
    REFERENCE
	"ITU-T Rec. M.3100 (1992) : 
	 equipmentIdentifierDuplication"
    ::= { gnmProbableCause 53 }

externalIFDeviceProblem OBJECT-IDENTITY
    STATUS current
    DESCRIPTION
	"Global value of M.3100 probable cause error for use 
	 with equipmentAlarm."
    REFERENCE
	"ITU-T Rec. M.3100 (1992) : externalIFDeviceProblem"
    ::= { gnmProbableCause 54 }

lineCardProblem OBJECT-IDENTITY
    STATUS current
    DESCRIPTION
	"Global value of M.3100 probable cause error for use 
	 with equipmentAlarm."
    REFERENCE
	"ITU-T Rec. M.3100 (1992) : lineCardProblem"
    ::= { gnmProbableCause 55 }

multiplexerProblemGnm OBJECT-IDENTITY
    STATUS current
    DESCRIPTION
	"Global value of M.3100 probable cause error for use 
	 with equipmentAlarm.  The original name conflicts with 
	 the ITU-T Rec. X.721 probable cause of the same name."
    REFERENCE
	"ITU-T Rec. M.3100 (1992) : multiplexerProblem"
    ::= { gnmProbableCause 56 }

nEIdentifierDuplication OBJECT-IDENTITY
    STATUS current
    DESCRIPTION
	"Global value of M.3100 probable cause error for use 
	 with equipmentAlarm."
    REFERENCE
	"ITU-T Rec. M.3100 (1992) : nEIdentifierDuplication"
    ::= { gnmProbableCause 57 }

powerProblemGnm OBJECT-IDENTITY
    STATUS current
    DESCRIPTION
	"Global value of M.3100 probable cause error for use 
	 with equipmentAlarm.  The original name conflicts with 
	 the ITU-T Rec. X.721 probable cause of the same name."
    REFERENCE
	"ITU-T Rec. M.3100 (1992) : powerProblem"
    ::= { gnmProbableCause 58 }

processorProblemGnm OBJECT-IDENTITY
    STATUS current
    DESCRIPTION
	"Global value of M.3100 probable cause error for use 
	 with equipmentAlarm.  The original name conflicts with 
	 the ITU-T Rec. X.721 probable cause of the same name."
    REFERENCE
	"ITU-T Rec. M.3100 (1992) : processorProblem"
    ::= { gnmProbableCause 59 }

protectionPathFailure OBJECT-IDENTITY
    STATUS current
    DESCRIPTION
	"Global value of M.3100 probable cause error for use 
	 with equipmentAlarm."
    REFERENCE
	"ITU-T Rec. M.3100 (1992) : protectionPathFailure"
    ::= { gnmProbableCause 60 }

receiverFailureGnm OBJECT-IDENTITY
    STATUS current
    DESCRIPTION
	"Global value of M.3100 probable cause error for use 
	 with equipmentAlarm.  The original name conflicts with 
	 the ITU-T Rec. X.721 probable cause of the same name."
    REFERENCE
	"ITU-T Rec. M.3100 (1992) : receiverFailure"
    ::= { gnmProbableCause 61 }

replaceableUnitMissing OBJECT-IDENTITY
    STATUS current
    DESCRIPTION
	"Global value of M.3100 probable cause error for use 
	 with equipmentAlarm."
    REFERENCE
	"ITU-T Rec. M.3100 (1992) : replaceableUnitMissing"
    ::= { gnmProbableCause 62 }

replaceableUnitTypeMismatch OBJECT-IDENTITY
    STATUS current
    DESCRIPTION
	"Global value of M.3100 probable cause error for use 
	 with equipmentAlarm."
    REFERENCE
	"ITU-T Rec. M.3100 (1992) : replaceableUnitTypeMismatch"
    ::= { gnmProbableCause 63 }

synchronizationSourceMismatch OBJECT-IDENTITY
    STATUS current
    DESCRIPTION
	"Global value of M.3100 probable cause error for use 
	 with equipmentAlarm."
    REFERENCE
	"ITU-T Rec. M.3100 (1992) : 
	 synchronizationSourceMismatch"
    ::= { gnmProbableCause 64 }

terminalProblem OBJECT-IDENTITY
    STATUS current
    DESCRIPTION
	"Global value of M.3100 probable cause error for use 
	 with equipmentAlarm."
    REFERENCE
	"ITU-T Rec. M.3100 (1992) : terminalProblem"
    ::= { gnmProbableCause 65 }

timingProblemGnm OBJECT-IDENTITY
    STATUS current
    DESCRIPTION
	"Global value of M.3100 probable cause error for use 
	 with equipmentAlarm.  The original name conflicts with 
	 the ITU-T Rec. X.721 probable cause of the same name."
    REFERENCE
	"ITU-T Rec. M.3100 (1992) : timingProblem"
    ::= { gnmProbableCause 66 }

transmitterFailureGnm OBJECT-IDENTITY
    STATUS current
    DESCRIPTION
	"Global value of M.3100 probable cause error for use 
	 with equipmentAlarm.  The original name conflicts with 
	 the ITU-T Rec. X.721 probable cause of the same name."
    REFERENCE
	"ITU-T Rec. M.3100 (1992) : transmitterFailure"
    ::= { gnmProbableCause 67 }

trunkCardProblem OBJECT-IDENTITY
    STATUS current
    DESCRIPTION
	"Global value of M.3100 probable cause error for use 
	 with equipmentAlarm."
    REFERENCE
	"ITU-T Rec. M.3100 (1992) : trunkCardProblem"
    ::= { gnmProbableCause 68 }

replaceableUnitProblem OBJECT-IDENTITY
    STATUS current
    DESCRIPTION
	"Global value of M.3100 probable cause error for use 
	 with equipmentAlarm."
    REFERENCE
	"ITU-T Rec. M.3100 (1992) : replaceableUnitProblem"
    ::= { gnmProbableCause 69 }

--
-- Values 70-100 are reserved for equipment alarm related probable causes
--

--
-- Probable Causes from M.3100 for use with environmentalAlarm
--

airCompressorFailure OBJECT-IDENTITY
    STATUS current
    DESCRIPTION
	"Global value of M.3100 probable cause error for use 
	 with environmentalAlarm."
    REFERENCE
	"ITU-T Rec. M.3100 (1992) : airCompressorFailure"
    ::= { gnmProbableCause 101 }

airConditioningFailure OBJECT-IDENTITY
    STATUS current
    DESCRIPTION
	"Global value of M.3100 probable cause error for use 
	 with environmentalAlarm."
    REFERENCE
	"ITU-T Rec. M.3100 (1992) : airConditioningFailure"
    ::= { gnmProbableCause 102 }

airDryerFailure OBJECT-IDENTITY
    STATUS current
    DESCRIPTION
	"Global value of M.3100 probable cause error for use 
	 with environmentalAlarm."
    REFERENCE
	"ITU-T Rec. M.3100 (1992) : airDryerFailure"
    ::= { gnmProbableCause 103 }

batteryDischarging OBJECT-IDENTITY
    STATUS current
    DESCRIPTION
	"Global value of M.3100 probable cause error for use 
	 with environmentalAlarm."
    REFERENCE
	"ITU-T Rec. M.3100 (1992) : batteryDischarging"
    ::= { gnmProbableCause 104 }

batteryFailure OBJECT-IDENTITY
    STATUS current
    DESCRIPTION
	"Global value of M.3100 probable cause error for use 
	 with environmentalAlarm."
    REFERENCE
	"ITU-T Rec. M.3100 (1992) : batteryFailure"
    ::= { gnmProbableCause 105 }

commercialPowerFailure OBJECT-IDENTITY
    STATUS current
    DESCRIPTION
	"Global value of M.3100 probable cause error for use 
	 with environmentalAlarm."
    REFERENCE
	"ITU-T Rec. M.3100 (1992) : commercialPowerFailure"
    ::= { gnmProbableCause 106 }

coolingFanFailure OBJECT-IDENTITY
    STATUS current
    DESCRIPTION
	"Global value of M.3100 probable cause error for use 
	 with environmentalAlarm."
    REFERENCE
	"ITU-T Rec. M.3100 (1992) : coolingFanFailure"
    ::= { gnmProbableCause 107 }

engineFailure OBJECT-IDENTITY
    STATUS current
    DESCRIPTION
	"Global value of M.3100 probable cause error for use 
	 with environmentalAlarm."
    REFERENCE
	"ITU-T Rec. M.3100 (1992) : engineFailure"
    ::= { gnmProbableCause 108 }

fireDetectorFailure OBJECT-IDENTITY
    STATUS current
    DESCRIPTION
	"Global value of M.3100 probable cause error for use 
	 with environmentalAlarm."
    REFERENCE
	"ITU-T Rec. M.3100 (1992) : fireDetectorFailure"
    ::= { gnmProbableCause 109 }

fuseFailure OBJECT-IDENTITY
    STATUS current
    DESCRIPTION
	"Global value of M.3100 probable cause error for use 
	 with environmentalAlarm."
    REFERENCE
	"ITU-T Rec. M.3100 (1992) : fuseFailure"
    ::= { gnmProbableCause 110 }

generatorFailure OBJECT-IDENTITY
    STATUS current
    DESCRIPTION
	"Global value of M.3100 probable cause error for use 
	 with environmentalAlarm."
    REFERENCE
	"ITU-T Rec. M.3100 (1992) : generatorFailure"
    ::= { gnmProbableCause 111 }

lowBatteryThreshold OBJECT-IDENTITY
    STATUS current
    DESCRIPTION
	"Global value of M.3100 probable cause error for use 
	 with environmentalAlarm."
    REFERENCE
	"ITU-T Rec. M.3100 (1992) : lowBatteryThreshold"
    ::= { gnmProbableCause 112 }

pumpFailureGnm OBJECT-IDENTITY
    STATUS current
    DESCRIPTION
	"Global value of M.3100 probable cause error for use 
	 with environmentalAlarm.  The original name conflicts 
	 with the ITU-T Rec. X.721 probable cause of the same 
	 name."
    REFERENCE
	"ITU-T Rec. M.3100 (1992) : pumpFailure"
    ::= { gnmProbableCause 113 }

rectifierFailure OBJECT-IDENTITY
    STATUS current
    DESCRIPTION
	"Global value of M.3100 probable cause error for use 
	 with environmentalAlarm."
    REFERENCE
	"ITU-T Rec. M.3100 (1992) : rectifierFailure"
    ::= { gnmProbableCause 114 }

rectifierHighVoltage OBJECT-IDENTITY
    STATUS current
    DESCRIPTION
	"Global value of M.3100 probable cause error for use 
	 with environmentalAlarm."
    REFERENCE
	"ITU-T Rec. M.3100 (1992) : rectifierHighVoltage"
    ::= { gnmProbableCause 115 }

rectifierLowVoltage OBJECT-IDENTITY
    STATUS current
    DESCRIPTION
	"Global value of M.3100 probable cause error for use 
	 with environmentalAlarm."
    REFERENCE
	"ITU-T Rec. M.3100 (1992) : rectifierLowVoltage"
    ::= { gnmProbableCause 116 }

ventilationsSystemFailure OBJECT-IDENTITY
    STATUS current
    DESCRIPTION
	"Global value of M.3100 probable cause error for use 
	 with environmentalAlarm."
    REFERENCE
	"ITU-T Rec. M.3100 (1992) : ventilationsSystemFailure"
    ::= { gnmProbableCause 117 }

enclosureDoorOpenGnm OBJECT-IDENTITY
    STATUS current
    DESCRIPTION
	"Global value of M.3100 probable cause error for use 
	 with environmentalAlarm.  The original name conflicts 
	 with the ITU-T Rec. X.721 probable cause of the same 
	 name."
    REFERENCE
	"ITU-T Rec. M.3100 (1992) : enclosureDoorOpen"
    ::= { gnmProbableCause 118 }

explosiveGas OBJECT-IDENTITY
    STATUS current
    DESCRIPTION
	"Global value of M.3100 probable cause error for use 
	 with environmentalAlarm."
    REFERENCE
	"ITU-T Rec. M.3100 (1992) : explosiveGas"
    ::= { gnmProbableCause 119 }

fire OBJECT-IDENTITY
    STATUS current
    DESCRIPTION
	"Global value of M.3100 probable cause error for use 
	 with environmentalAlarm."
    REFERENCE
	"ITU-T Rec. M.3100 (1992) : fire"
    ::= { gnmProbableCause 120 }

flood OBJECT-IDENTITY
    STATUS current
    DESCRIPTION
	"Global value of M.3100 probable cause error for use 
	 with environmentalAlarm."
    REFERENCE
	"ITU-T Rec. M.3100 (1992) : flood"
    ::= { gnmProbableCause 121 }

highHumidity OBJECT-IDENTITY
    STATUS current
    DESCRIPTION
	"Global value of M.3100 probable cause error for use 
	 with environmentalAlarm."
    REFERENCE
	"ITU-T Rec. M.3100 (1992) : highHumidity"
    ::= { gnmProbableCause 122 }

highTemperature OBJECT-IDENTITY
    STATUS current
    DESCRIPTION
	"Global value of M.3100 probable cause error for use 
	 with environmentalAlarm."
    REFERENCE
	"ITU-T Rec. M.3100 (1992) : highTemperature"
    ::= { gnmProbableCause 123 }

highWind OBJECT-IDENTITY
    STATUS current
    DESCRIPTION
	"Global value of M.3100 probable cause error for use 
	 with environmentalAlarm."
    REFERENCE
	"ITU-T Rec. M.3100 (1992) : highWind"
    ::= { gnmProbableCause 124 }

iceBuildUp OBJECT-IDENTITY
    STATUS current
    DESCRIPTION
	"Global value of M.3100 probable cause error for use 
	 with environmentalAlarm."
    REFERENCE
	"ITU-T Rec. M.3100 (1992) : iceBuildUp"
    ::= { gnmProbableCause 125 }

intrusionDetectionGnm OBJECT-IDENTITY
    STATUS current
    DESCRIPTION
	"Global value of M.3100 probable cause error for use 
	 with environmentalAlarm.  The original name conflicts 
	 with the ITU-T Rec. X.721 probable cause of the same 
	 name."
    REFERENCE
	"ITU-T Rec. M.3100 (1992) : intrusionDetection"
    ::= { gnmProbableCause 126 }

lowFuel OBJECT-IDENTITY
    STATUS current
    DESCRIPTION
	"Global value of M.3100 probable cause error for use 
	 with environmentalAlarm."
    REFERENCE
	"ITU-T Rec. M.3100 (1992) : lowFuel"
    ::= { gnmProbableCause 127 }

lowHumidity OBJECT-IDENTITY
    STATUS current
    DESCRIPTION
	"Global value of M.3100 probable cause error for use 
	 with environmentalAlarm."
    REFERENCE
	"ITU-T Rec. M.3100 (1992) : lowHumidity"
    ::= { gnmProbableCause 128 }

lowCablePressure OBJECT-IDENTITY
    STATUS current
    DESCRIPTION
	"Global value of M.3100 probable cause error for use 
	 with environmentalAlarm."
    REFERENCE
	"ITU-T Rec. M.3100 (1992) : lowCablePressure"
    ::= { gnmProbableCause 129 }

lowTemperature OBJECT-IDENTITY
    STATUS current
    DESCRIPTION
	"Global value of M.3100 probable cause error for use 
	 with environmentalAlarm."
    REFERENCE
	"ITU-T Rec. M.3100 (1992) : lowTemperature"
    ::= { gnmProbableCause 130 }

lowWater OBJECT-IDENTITY
    STATUS current
    DESCRIPTION
	"Global value of M.3100 probable cause error for use 
	 with environmentalAlarm."
    REFERENCE
	"ITU-T Rec. M.3100 (1992) : lowWater"
    ::= { gnmProbableCause 131 }

smoke OBJECT-IDENTITY
    STATUS current
    DESCRIPTION
	"Global value of M.3100 probable cause error for use 
	 with environmentalAlarm."
    REFERENCE
	"ITU-T Rec. M.3100 (1992) : smoke"
    ::= { gnmProbableCause 132 }

toxicGas OBJECT-IDENTITY
    STATUS current
    DESCRIPTION
	"Global value of M.3100 probable cause error for use 
	 with environmentalAlarm."
    REFERENCE
	"ITU-T Rec. M.3100 (1992) : toxicGas"
    ::= { gnmProbableCause 133 }

--
-- Values 134-150 are reserved for environmental alarm related probable causes
--

--
-- Probable Causes from M.3100 for use with processingErrorAlarm
--

storageCapacityProblemGnm OBJECT-IDENTITY
    STATUS current
    DESCRIPTION
	"Global value of M.3100 probable cause error for use 
	 with processingErrorAlarm.  The original name conflicts 
	 with the ITU-T Rec. X.721 probable cause of the same 
	 name."
    REFERENCE
	"ITU-T Rec. M.3100 (1992) : storageCapacityProblem"
    ::= { gnmProbableCause 151 }

memoryMismatchGnm OBJECT-IDENTITY
    STATUS current
    DESCRIPTION
	"Global value of M.3100 probable cause error for use 
	 with processingErrorAlarm.  The original name conflicts 
	 with the ITU-T Rec. X.721 probable cause of the same 
	 name."
    REFERENCE
	"ITU-T Rec. M.3100 (1992) : memoryMismatch"
    ::= { gnmProbableCause 152 }

corruptDataGnm OBJECT-IDENTITY
    STATUS current
    DESCRIPTION
	"Global value of M.3100 probable cause error for use 
	 with processingErrorAlarm.  The original name conflicts 
	 with the ITU-T Rec. X.721 probable cause of the same 
	 name."
    REFERENCE
	"ITU-T Rec. M.3100 (1992) : corruptData"
    ::= { gnmProbableCause 153 }

outOfCPUCycles OBJECT-IDENTITY
    STATUS current
    DESCRIPTION
	"Global value of M.3100 probable cause error for use 
	 with processingErrorAlarm."
    REFERENCE
	"ITU-T Rec. M.3100 (1992) : outOfCPUCycles"
    ::= { gnmProbableCause 154 }

sfwrEnvironmentProblem OBJECT-IDENTITY
    STATUS current
    DESCRIPTION
	"Global value of M.3100 probable cause error for use 
	 with processingErrorAlarm."
    REFERENCE
	"ITU-T Rec. M.3100 (1992) : sfwrEnvironmentProblem"
    ::= { gnmProbableCause 155 }

sfwrDownloadFailure OBJECT-IDENTITY
    STATUS current
    DESCRIPTION
	"Global value of M.3100 probable cause error for use 
	 with processingErrorAlarm."
    REFERENCE
	"ITU-T Rec. M.3100 (1992) : sfwrDownloadFailure"
    ::= { gnmProbableCause 156 }

-- =====================================================================
--
-- SECURITY ALARM CAUSES (from X.721)
--
-- =====================================================================

arfSecurityAlarmCause OBJECT IDENTIFIER ::=
{ joint-iso-ccitt(2) ms(9) smi(3) part2(2) standardSpecificExtensions(0) sarf(1) }

authenticationFailure OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 authenticationFailure"
    ::= { arfSecurityAlarmCause 1 }

breachOfConfidentiality OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 breachOfConfidentiality"
    ::= { arfSecurityAlarmCause 2 }

cableTamper OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, cableTamper"
    ::= { arfSecurityAlarmCause 3 }

delayedInformation OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 delayedInformation"
    ::= { arfSecurityAlarmCause 4 }

denialOfService OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 denialOfService"
    ::= { arfSecurityAlarmCause 5 }

duplicateInformation OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 duplicateInformation"
    ::= { arfSecurityAlarmCause 6 }

informationMissing OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 informationMissing"
    ::= { arfSecurityAlarmCause 7 }

informationModificationDetected OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 informationModificationDetected"
    ::= { arfSecurityAlarmCause 8 }

informationOutOfSequence OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 informationOutOfSequence"
    ::= { arfSecurityAlarmCause 9 }

intrusionDetection OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 intrusionDetection"
    ::= { arfSecurityAlarmCause 10 }

keyExpired OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, keyExpired"
    ::= { arfSecurityAlarmCause 11 }

nonRepudiationFailure OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 nonRepudiationFailure"
    ::= { arfSecurityAlarmCause 12 }

outOfHoursActivity OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 outOfHoursActivity"
    ::= { arfSecurityAlarmCause 13 }

outOfService OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, outOfService"
    ::= { arfSecurityAlarmCause 14 }

proceduralError OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 proceduralError"
    ::= { arfSecurityAlarmCause 15 }

unauthorizedAccessAttempt OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 unauthorizedAccessAttempt"
    ::= { arfSecurityAlarmCause 16 }

unexpectedInformation OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 unexpectedInformation"
    ::= { arfSecurityAlarmCause 17 }

unspecifiedReason OBJECT-IDENTITY
    STATUS current
    DESCRIPTION
	"X.721 security alarm cause for use in notifications and event 
	 records.  May be used in an integrityViolation, 
	 operationalViolation, physicalViolation, 
	 securityServiceOrMechanismViolation or timeDomainViolation 
	 notification, and may appear in a 
	 SecurityAlarmReportRecordEntry."
    REFERENCE
	"ITU-T Rec. X.721 (1992) | ISO/IEC 10165-2 : 1992, 
	 unspecifiedReason"
    ::= { arfSecurityAlarmCause 18 }


-- =====================================================================
--
-- TABLES
--
-- =====================================================================
--
-- NOTE: TMN has a mechanism for mapping perceived severities.  This 
-- could be accomplished by the manager; however, it is possible for the 
-- manager to create a table of mappings and that is presented here.
--

tmnSeverityMappingTable OBJECT-TYPE
    SYNTAX SEQUENCE OF TmnSeverityMappingEntry
    MAX-ACCESS not-accessible
    STATUS current
    DESCRIPTION
	"This is severity mapping table that can be used to arbitrarily 
	 map the severity of an alarm to another severity.  It is 
	 similar to the TMN capability."
    REFERENCE
	"ITU-T Recommendation X.721 (1992)"
    ::= { tmnSeverityMapping 1 }

tmnSeverityMappingEntry OBJECT-TYPE
    SYNTAX TmnSeverityMappingEntry
    MAX-ACCESS not-accessible
    STATUS current
    DESCRIPTION
	"This is an entry in the severity mapping table.  It is indexed 
	 from a probable cause and also by a perceived severity.  This 
	 permits each probable cause, specific problem and severity 
	 value to be mapped to a new severity value."
    INDEX   {
	    tmnProbableCause,
	    tmnSpecificProblem,
	    tmnPerceivedSeverity
	}
    ::= { tmnSeverityMappingTable 1 }

TmnSeverityMappingEntry ::=
    SEQUENCE {
	tmnProbableCause
	    ProbableCause,
	tmnSpecificProblem
	    SpecificProblems,
	tmnOriginalPerceivedSeverity
	    PerceivedSeverity,
	tmnReplacementPerceivedSeverity
	    PerceivedSeverity,
	tmnSeverityMappingStatus
	    RowStatus
    }

tmnProbableCause OBJECT-TYPE
    SYNTAX ProbableCause
    MAX-ACCESS read-only
    STATUS current
    DESCRIPTION
	"Provides the probable cause which is the primary alarm 
	 type as an index into the mapping table."
    ::= { tmnSeverityMappingEntry 1 }

tmnSpecificProblem OBJECT-TYPE
    SYNTAX SpecificProblem
    MAX-ACCESS read-only
    STATUS current
    DESCRIPTION
	"Provides the sepcific problem (or zeroDotZero for no or 
	 any specific problem) as an index into the mapping 
	 table."
    DEFVAL      { zeroDotZero }
    ::= { tmnSeverityMappingEntry 2 }

tmnOriginalPerceivedSeverity OBJECT-TYPE
    SYNTAX PerceivedSeverity
    MAX-ACCESS read-only
    STATUS current
    DESCRIPTION
	"Provides the original perceived severity as an index 
	 into the mapping table.  The value cleared(5) will be 
	 refused.  The value indeterminate(0) means any severity 
	 if no other value exists."
    DEFVAL      { 0 } -- indeterminate(0)
    ::= { tmnSeverityMappingEntry 3 }

tmnReplacementPerceivedSeverity OBJECT-TYPE
    SYNTAX PerceivedSeverity
    MAX-ACCESS read-create
    STATUS current
    DESCRIPTION
	"Provides the replacement perceived severity for this 
	 entry."
    ::= { tmnSeverityMappingEntry 4 }

tmnSeverityMappingStatus OBJECT-TYPE
    SYNTAX RowStatus
    MAX-ACCESS read-create
    STATUS current
    DESCRIPTION
	"Provides a mechanism for management stations to add and 
	 delete entries from this table in accordance with the 
	 RowStatus textual convention."
    ::= { tmnSeverityMappingEntry 5 }


-- =====================================================================

tmnAlarmSummaryTable OBJECT-TYPE
    SYNTAX SEQUENCE OF TmnAlarmSummaryEntry
    MAX-ACCESS not-accessible
    STATUS current
    DESCRIPTION
	"The alarm summary table provides a summary of 
	 oustanding alarms generated by the agent that have not 
	 yet been cleared."
    ::= { tmnAlarmSummary 1 }

tmnAlarmSummaryEntry OBJECT-TYPE
    SYNTAX TmnAlarmSummaryEntry
    MAX-ACCESS not-accessible
    STATUS current
    DESCRIPTION
	"Provides an alarm summary entry which represents an 
	 alarm generated by an object which remains outstanding.  
	 The entry is indexed by the objectInstance which 
	 identifies the managed object generating the alarm, and 
	 the alarm identifier which is a combination of 
	 ProbableCause and SpecificProblem.  If no specific 
	 problem was specified, the value zeroDotZero is used 
	 for the the specific problem."
    INDEX   {
	    tmnAlarmSummaryPerceivedSeverity,
	    tmnAlarmSummaryTimeStamp,
	    tmnAlarmSummaryAlarmType,
	    tmnAlarmSummaryProbableCause,
	    tmnAlarmSummarySpecificProblem
	}
    ::= { tmnAlarmSummaryTable 1 }

TmnAlarmSummaryEntry ::=
    SEQUENCE {
	tmnAlarmSummaryPerceivedSeverity
	    PerceivedSeverity,
	tmnAlarmSummaryTimeStamp
	    TimeStamp,
	tmnAlarmSummaryAlarmType
	    AlarmType,
	tmnAlarmSummaryProbableCause
	    ProbableCause,
	tmnAlarmSummarySpecificProblem
	    SpecificProblem,
	tmnAlarmSummaryObjectInstance
	    RowPointer
    }

tmnAlarmSummaryPerceivedSeverity OBJECT-TYPE
    SYNTAX PerceivedSeverity
    MAX-ACCESS read-write
    STATUS current
    DESCRIPTION
	"Provides the mapped perceived severity of the alarm 
	 associated with this instance of an alarm in this table 
	 which is outstanding using the PerceivedSeverity 
	 textual convention.

	 Management stations may set this value to a different 
	 severity level to upgrade or downgrade the perceived 
	 severity.  Values set will not survive an agent 
	 reboot."
    REFERENCE
	"OPENSS7-TMN-TC PerceivedSeverity"
    ::= { tmnAlarmSummaryEntry 1 }

tmnAlarmSummaryTimeStamp OBJECT-TYPE
    SYNTAX TimeStamp
    MAX-ACCESS read-only
    STATUS current
    DESCRIPTION
	"Provides a time stamp of the time at which the alarm 
	 was raised following the TimeStamp textual convention."
    ::= { tmnAlarmSummaryEntry 2 }

tmnAlarmSummaryAlarmType OBJECT-TYPE
    SYNTAX AlarmType
    MAX-ACCESS read-only
    STATUS current
    DESCRIPTION
	"Provides an alarm type object identifier, using the 
	 AlarmType textual convention, which is the registration 
	 of one of the alarm norification generated by this 
	 module: communicationsAlarm, environmentalAlarm, 
	 equipmentAlarm, processingErrorAlarm, or 
	 qualityofSerivceAlarm.  Security alarms are not 
	 included in this table."
    ::= { tmnAlarmSummaryEntry 3 }

tmnAlarmSummaryProbableCause OBJECT-TYPE
    SYNTAX ProbableCause
    MAX-ACCESS read-only
    STATUS current
    DESCRIPTION
	"Provides the probable cause for this instance of an 
	 alarm in this table which is outstanding using the 
	 ProbableCause textual convention."
    REFERENCE
	"OPENSS7-TMN-TC ProbableCause"
    ::= { tmnAlarmSummaryEntry 4 }

tmnAlarmSummarySpecificProblem OBJECT-TYPE
    SYNTAX SpecificProblem
    MAX-ACCESS read-only
    STATUS current
    DESCRIPTION
	"Provides the specific problem associated with the 
	 probable cause for this instance of an alarm in this 
	 table which is outstanding using the SpecificProblem 
	 textual convention.  If no specific problem was 
	 associated with the probable cause for this alarm 
	 instance, the value of this column is zeroDotZero."
    REFERENCE
	"OPENSS7-TMN-TC SpecificProblem"
    ::= { tmnAlarmSummaryEntry 5 }

tmnAlarmSummaryObjectInstance OBJECT-TYPE
    SYNTAX RowPointer
    MAX-ACCESS read-only
    STATUS current
    DESCRIPTION
	"Provides the object instance that generated an alarm in 
	 this table which is outstanding using the RowPointer 
	 textual convention.  Note that if the agent deletes 
	 this row from the corresponding table, the agent alarm 
	 must remove the alarm from this table as well."
    ::= { tmnAlarmSummaryEntry 6 }

--
--  Scalars for alarm summary.
--

tmnAlarmOutstanding OBJECT-TYPE
    SYNTAX RowPointer
    MAX-ACCESS read-only
    STATUS current
    DESCRIPTION
	"Provides a pointer to the oldest outstanding highest 
	 severity alarm in the alarm summary table using the 
	 RowPointer textual convention, or zeroDotZero if there 
	 is no oustanding alarm."
    ::= { tmnScalars 1 }

tmpAlarmOutstandingCritical OBJECT-TYPE
    SYNTAX RowPointer
    MAX-ACCESS read-only
    STATUS current
    DESCRIPTION
	"Provides a pointer to the oldest outstanding critical 
	 alarm in the alarm summary table using the RowPointer 
	 textual convention, or zeroDotZero if there is no 
	 oustanding critical alarm."
    ::= { tmnScalars 2 }

tmpAlarmOutstandingMajor OBJECT-TYPE
    SYNTAX RowPointer
    MAX-ACCESS read-only
    STATUS current
    DESCRIPTION
	"Provides a pointer to the oldest outstanding major 
	 alarm in the alarm summary table using the RowPointer 
	 textual convention, or zeroDotZero if there is no 
	 oustanding major alarm."
    ::= { tmnScalars 3 }

tmpAlarmOutstandingMinor OBJECT-TYPE
    SYNTAX RowPointer
    MAX-ACCESS read-only
    STATUS current
    DESCRIPTION
	"Provides a pointer to the oldest outstanding minor 
	 alarm in the alarm summary table using the RowPointer 
	 textual convention, or zeroDotZero if there is no 
	 oustanding minor alarm."
    ::= { tmnScalars 4 }

-- =====================================================================

--
-- From ITU-T Rec. X.733 (1992)/Cor.2 (1999)
--
-- cleared: The Cleared severity level indicates the clearing of one or 
-- more previously reported alarms.  The alarms to be cleared are 
-- indicated by the managed object, Event type, Probable cause, Specific 
-- problems (if present) and Correlated notifications parameters as 
-- follows:
--
-- a) If the Correlated notifications and Specific problem parameters 
--    are not present or empty, all previous alarms with the same 
--    managed object, Probable cause and Event type parameters are 
--    cleared irresepctive of whether a Notification identifier or 
--    Specific problem parameter was present in the alarms to be cleared 
--    (i.e. can clear alarms without looking at Notification identifier 
--    or Specific problem parameters).
--
-- b) If the Specific problems parameter is present and not empty, and 
--    the Correlated notifications is not present or empty, then only 
--    previous alarms that have an exact match on managed object, 
--    Probable cause, Event type, and have a matching set or subset of 
--    Specific problems will be cleared.
--
-- c) If the Correlated notifications parameter is present and not 
--    empty, those alarms listed in this parameter are cleared 
--    irrespective of the value for the managed object, Probable cause, 
--    Event type and Specific problems parameters.  In addition, all 
--    alarms which match managed object are also cleared as specified in 
--    b) above, or as in a), ignoring the presence of the Correlated 
--    notifications.
--


-- =====================================================================
-- 
-- Managed objects from ITU-T Rec. Q.821
-- 
-- =====================================================================

AlarmStatusList ::= TEXTUAL-CONVENTION
    STATUS current
    DESCRIPTION
	"Specifies an alarm status list.  This is a set-valued 
	 attribute."
    REFERENCE
	"ITU-T Recommendation M.3100 ASN.1 AlarmStatus."
    SYNTAX BITS {
	    cleared(0),
	    activeReportable-Indeterminate(1),
	    activeReportable-Warning(2),
	    activeReportable-Minor(3),
	    activeReportable-Major(4),
	    activeReportable-Critical(5),
	    activePending(6)
	}


currentAlarmSummaryControlTable OBJECT-TYPE
    SYNTAX SEQUENCE OF CurrentAlarmSummaryControlEntry
    MAX-ACCESS not-accessible
    STATUS current
    DESCRIPTION
	""
    REFERENCE
	"ITU-T Rec. Q.821 (2000) currentAlarmSummaryControl."
    ::= { tmnAlarmSummaryControl 1 }


currentAlarmSummaryControlEntry OBJECT-TYPE
    SYNTAX CurrentAlarmSummaryControlEntry
    MAX-ACCESS not-accessible
    STATUS current
    DESCRIPTION
	""
    REFERENCE
	"ITU-T Rec. Q.821 (2000) currentAlarmSummaryControl."
    INDEX {
	    currentAlarmSummaryControlId -- index
	}
    ::= { currentAlarmSummaryControlTable 1 }

CurrentAlarmSummaryControlEntry ::=
    SEQUENCE {
	currentAlarmSummaryControlId
	    SimpleNameType,
	alarmStatusList
	    AlarmStatusList,
	objectList
	    ObjectList,
	perceivedSeverityList
	    PerceivedSeverityList,
	probableCauseList
	    OCTET STRING,
	currentAlarmSummaryStorageType
	    StorageType,
	currentAlarmSummaryRowStatus
	    RowStatus
    }

currentAlarmSummaryControlId OBJECT-TYPE
    SYNTAX SimpleNameType
    MAX-ACCESS not-accessible
    STATUS current
    DESCRIPTION
	""
    REFERENCE
	""
    ::= { currentAlarmSummaryControlEntry 1 }

alarmStatusList OBJECT-TYPE
    SYNTAX AlarmStatusList
    MAX-ACCESS read-create
    STATUS current
    DESCRIPTION
	""
    REFERENCE
	""
    ::= { currentAlarmSummaryControlEntry 2 }

objectList OBJECT-TYPE
    SYNTAX ObjectList
    MAX-ACCESS read-create
    STATUS current
    DESCRIPTION
	""
    REFERENCE
	""
    ::= { currentAlarmSummaryControlEntry 3 }

perceivedSeverityList OBJECT-TYPE
    SYNTAX PerceivedSeverityList
    MAX-ACCESS read-create
    STATUS current
    DESCRIPTION
	""
    REFERENCE
	""
    ::= { currentAlarmSummaryControlEntry 4 }

probableCauseList OBJECT-TYPE
    SYNTAX OCTET STRING
    MAX-ACCESS read-create
    STATUS current
    DESCRIPTION
	""
    REFERENCE
	""
    ::= { currentAlarmSummaryControlEntry 5 }

currentAlarmSummaryStorageType OBJECT-TYPE
    SYNTAX StorageType
    MAX-ACCESS read-create
    STATUS current
    DESCRIPTION
	""
    REFERENCE
	""
    ::= { currentAlarmSummaryControlEntry 6 }

currentAlarmSummaryRowStatus OBJECT-TYPE
    SYNTAX RowStatus
    MAX-ACCESS read-create
    STATUS current
    DESCRIPTION
	""
    REFERENCE
	""
    ::= { currentAlarmSummaryControlEntry 7 }

-- =====================================================================

managementOperationsScheduleTable OBJECT-TYPE
    SYNTAX		SEQUENCE OF ManagementOperationsScheduleEntry
    MAX-ACCESS	not-accessible
    STATUS		current
    DESCRIPTION
	""
    REFERENCE
	"ITU-T Rec. Q.821 (2000) managementOperationsSchedule."
    ::= { managementOperationsSchedule 1 }

managementOperationsScheduleEntry OBJECT-TYPE
    SYNTAX		ManagementOperationsScheduleEntry
    MAX-ACCESS	not-accessible
    STATUS		current
    DESCRIPTION
	""
    REFERENCE
	"ITU-T Rec. Q.821 (2000) managementOperationsSchedule."
    INDEX	{
		mosScheduleId -- index
	}
    ::= { managementOperationsScheduleTable 1 }

ManagementOperationsScheduleEntry ::=
    SEQUENCE {
	mosAdministrativeState
	    AdministrativeState,
	-- mosAffectedObjectClass
	mosAffectedObjectInstance
	    RowPointer,
	mosBeginTime
	    TimeStamp,
	mosDestinationAddress
	    ,
	mosEndTime
	    TimeStamp,
	mosInterval
	    TimeInterval,
	mosScheduleId
	    SimpleNameType,
	mosStorageType
	    StorageType,
	mosRowStatus
	    RowStatus
    }

-- =====================================================================

enhancedCurrentAlarmSummaryControlTable OBJECT-TYPE
    SYNTAX SEQUENCE OF EnhancedCurrentAlarmSummaryControlEntry
    MAX-ACCESS not-accessible
    STATUS current
    DESCRIPTION
	""
    REFERENCE
	"ITU-T Rec. Q.821 (2000) 
	 enhancedCurrentAlarmSummaryControl."
    ::= { enhancedCurrentAlarmSummaryControl 1 }

enhancedCurrentAlarmSummaryControlEntry OBJECT-TYPE
    SYNTAX EnhancedCurrentAlarmSummaryControlEntry
    MAX-ACCESS not-accessible
    STATUS current
    DESCRIPTION
	""
    REFERENCE
	"ITU-T Rec. Q.821 (2000) 
	 enhancedCurrentAlarmSummaryControl."
    INDEX	{
	    enhancedCurrentAlarmSummaryControlId
	}
    ::= { enhancedCurrentAlarmSummaryControlTable 1 }

EnhancedCurrentAlarmSummaryControlEntry ::=
    SEQUENCE {
	enhancedCurrentAlarmSummaryControlId
	    SimpleNameType,
	-- action alarmSynchronization
	-- logRecordIdActionParameter
	-- correlatedRecordNameActionParameter
	-- invalidBaseManagedObjectErrorParameter
	-- invalidObjectInstanceErrorParameter
	-- suspectObjectListActionParameter
	-- cancelledAlarmSynchronizationParameter
	ecasStorageType
	    StorageType,
	ecasRowStatus
	    RowStatus
    }

-- =====================================================================
-- =====================================================================
--
-- Managed objects from ITU-T Rec. X.721
--
-- =====================================================================

discriminatorTable OBJECT-TYPE
    SYNTAX SEQUENCE OF Discriminator
    MAX-ACCESS not-accessible
    STATUS current
    DESCRIPTION
	""
    REFERENCE
	"ITU-T Rec. X.721 | ISO/IEC 10165-2"
    ::= { discriminator 1 }

discriminatorEntry OBJECT-TYPE
    SYNTAX Discriminator
    MAX-ACCESS not-accessible
    STATUS current
    DESCRIPTION
	""
    REFERENCE
	"ITU-T Rec. X.721 | ISO/IEC 10165-2"
    INDEX   {
	    discriminatorId -- index
	}
    ::= { discriminatorTable 1 }

-- NOTIFICATIONS
-- stateChange,
-- attributeValueChange,
-- objectCreation,
-- objectDeletion;;;

Discriminator ::=
    SEQUENCE {
	discriminatorId
	    SimpleNameType,
	discriminatorConstruct
	    OCTET STRING,  -- way to complex for now
	discriminatorAdministrativeState
	    AdministrativeState,
	discriminatorOperationalState
	    OperationalState,
	-- availabilityStatusPackage PRESENT IF "any of the 
	-- scheduling packages, (duration, weekly scheduling, 
	-- external) are present", 
	discriminatorAvailabilityStatus
	    AvailabilityStatus, -- but only offDuty component
	discriminatorStorageType
	    StorageType,
	discriminatorRowStatus
	    RowStatus
    }

-- discriminatorTable side-table
-- duration PRESENT IF "the discriminator function is scheduled to start 
-- at a specified time and stop at either a specified time or function 
-- continuously",

discriminatorDurationTable OBJECT-TYPE
    SYNTAX SEQUENCE OF DiscriminatorDurationEntry
    MAX-ACCESS not-accessible
    STATUS current
    DESCRIPTION
	""
    REFERENCE
	"ITU-T Rec. X.721 | ISO/IEC 10165-2"
    ::= { discriminatorDuration 1 }

discriminatorDurationEntry OBJECT-TYPE
    SYNTAX DiscriminatorDurationEntry
    MAX-ACCESS not-accessible
    STATUS current
    DESCRIPTION
	""
    REFERENCE
	"ITU-T Rec. X.721 | ISO/IEC 10165-2"
    INDEX {
	    discriminatorId -- shared index
	}
    ::= { discriminatorDurationTable 1 }

DiscriminatorDurationEntry ::=
    SEQUENCE {
	discriminatorDurationStartTime
	    ExtUTCTime,
	discriminatorDurationStopTime
	    ExtUTCTime,
	discriminatorDurationStorageType
	    StorageType,
	discriminatorDurationRowStatus
	    RowStatus
    }

-- discriminatorTable side-table
-- dailyScheduling PRESENT IF "both the weekly scheduling package and 
-- external scheduler packages are not present in an instance and daily 
-- scheduling is supported by that instance",

discriminatorDailySchedulingTable OBJECT-TYPE
    SYNTAX SEQUENCE OF DiscriminatorDailySchedulingEntry
    MAX-ACCESS not-accessible
    STATUS current
    DESCRIPTION
	""
    REFERENCE
	"ITU-T Rec. X.721 | ISO/IEC 10165-2"
    ::= { discriminatorDailySchedule 1 }

discriminatorDailySchedulingEntry OBJECT-TYPE
    SYNTAX DiscriminatorDailySchedulingEntry
    MAX-ACCESS not-accessible
    STATUS current
    DESCRIPTION
	""
    REFERENCE
	"ITU-T Rec. X.721 | ISO/IEC 10165-2"
    INDEX {
	    discriminatorId, -- shared index
	    discriminatorIntervalStart, -- index
	    discriminatorIntervalEnd -- index
	}
    ::= { discriminatorDailyScheduleTable 1 }

DiscriminatorDailySchedulingEntry ::=
    SEQUENCE {
	discriminatorIntervalStart
	    Time24,
	discriminatorIntervalEnd
	    Time24,
	discriminatorDailySchedulingStorageType
	    StorageType,
	discriminatorDailySchedulingRowStatus
	    RowStatus
    }

-- discriminatorTable side-table
-- weeklyScheduling PRESENT IF "both the daily scheduling package and 
-- external scheduler packages are not present in an instance and weekly 
-- scheduling is supported by that instance",

discriminatorWeeklySchedulingTable OBJECT-TYPE
    SYNTAX SEQUENCE OF DiscriminatorWeeklySchedulingEntry
    MAX-ACCESS not-accessible
    STATUS current
    DESCRIPTION
	""
    REFERENCE
	"ITU-T Rec. X.721 | ISO/IEC 10165-2"
    ::= { discriminatorWeeklyScheduling 1 }

discriminatorWeeklySchedulingEntry OBJECT-TYPE
    SYNTAX DiscriminatorWeeklySchedulingEntry
    MAX-ACCESS not-accessible
    STATUS current
    DESCRIPTION
	""
    REFERENCE
	"ITU-T Rec. X.721 | ISO/IEC 10165-2"
    INDEX {
	    discriminatorId -- shared index
	    discriminatorIntervalStart, -- shared index
	    discriminatorIntervalEnd -- shared index
	}
    ::= { discriminatorWeeklySchedulingTable 1 }

DiscriminatorWeeklySchedulingEntry ::=
    SEQUENCE {
	discriminatorWeekMask
	    BITS,
	discriminatorWeeklySchedulingStorageType
	    StorageType,
	discriminatorWeeklySchedulingRowStatus
	    RowStatus
    }

-- discriminatorTable side-table
-- externalScheduler PRESENT IF "both the daily scheduling package and 
-- weekly scheduling packages are not present in an instance and 
-- external scheduling is supported by that instance";

discriminatorExternalSchedulerTable OBJECT-TYPE
    SYNTAX SEQUENCE OF DiscriminatorExternalSchedulerEntry
    MAX-ACCESS not-accessible
    STATUS current
    DESCRIPTION
	""
    REFERENCE
	"ITU-T Rec. X.721 | ISO/IEC 10165-2"
    ::= { discriminatorExternalScheduler 1 }

discriminatorExternalSchedulerEntry OBJECT-TYPE
    SYNTAX DiscriminatorExternalSchedulerEntry
    MAX-ACCESS not-accessible
    STATUS current
    DESCRIPTION
	""
    REFERENCE
	"ITU-T Rec. X.721 | ISO/IEC 10165-2"
    INDEX {
	    discriminatorId -- shared index
	}
    ::= { discriminatorExternalSchedulerTable 1 }

DiscriminatorExternalSchedulerEntry ::=
    SEQUENCE {
	discriminatorExternalSchedulerName
	    RowPointer,
	discriminatorExternalSchedulerStorageType
	    StorageType,
	discriminatorExternalSchedulerRowStatus
	    RowStatus
    }

-- =====================================================================

eventForwardingDiscriminatorTable OBJECT-TYPE
    SYNTAX SEQUENCE OF EventForwardingDiscriminator
    MAX-ACCESS not-accessible
    STATUS current
    DESCRIPTION
	""
    REFERENCE
	"ITU-T Rec. X.721 | ISO/IEC 10165-2"
    ::= { eventForwardingDiscriminator 1 }

eventForwardingDiscriminatorEntry OBJECT-TYPE
    SYNTAX EventForwardingDiscriminator
    MAX-ACCESS not-accessible
    STATUS current
    DESCRIPTION
	""
    REFERENCE
	"ITU-T Rec. X.721 | ISO/IEC 10165-2"
    INDEX {
	    discriminatorId -- derived from discriminator
	}
    ::= { eventForwardingDiscriminatorTable 1 }

EventForwardingDiscriminator ::=
    SEQUENCE {
	-- eventForwardingDiscriminatorDestination
	--  ,
	-- backUpDestinationListPackage PACKAGE
	eventForwardingDiscriminatorActiveDestination
	    OCTET STRING,
	-- eventForwardingDiscriminatorBackUpDestinationList
	--  ,
	eventForwardingDiscriminatorConfirmedMode
	    TruthValue,
	eventForwardingDiscriminatorStorageType
	    StorageType,
	eventForwardingDiscriminatorRowStatus
	    RowStatus
    }

-- side-table to expand destination lists

efdDestinationTable OBJECT-TYPE
    SYNTAX SEQUENCE OF EfdDestinationEntry
    MAX-ACCESS not-accessible
    STATUS current
    DESCRIPTION
	""
    REFERENCE
	"ITU-T Rec. X.721 | ISO/IEC 10165-2"
    ::= { efdDestination 1 }

efdDestinationEntry OBJECT-TYPE
    SYNTAX EfdDestinationEntry
    MAX-ACCESS not-accessible
    STATUS current
    DESCRIPTION
	""
    REFERENCE
	"ITU-T Rec. X.721 | ISO/IEC 10165-2"
    ::= { efdDestinationTable 1 }

EfdDestinationEntry ::=
    SEQUENCE {
	efdDestination
	    OCTET STRING,
	efdDestinationType
	    INTEGER,
	efdDestinationStorageType
	    StorageType,
	efdDestinationRowStatus
	    RowStatus
    }

-- =====================================================================

logTable OBJECT-TYPE
    SYNTAX SEQUENCE OF Log
    MAX-ACCESS not-accessible
    STATUS current
    DESCRIPTION
	""
    REFERENCE
	"ITU-T Rec. X.721 | ISO/IEC 10165-2"
    ::= { log 1 }

logEntry OBJECT-TYPE
    SYNTAX Log
    MAX-ACCESS not-accessible
    STATUS current
    DESCRIPTION
	"Each entry represents a log that is used to store 
	 incoming event reports and local system notifications.  
	 Additional details are defined in ITU-T Rec. X.735 | 
	 ISO/IEC 10164-6."
    REFERENCE
	"ITU-T Rec. X.721 | ISO/IEC 10165-2"
    INDEX {
	logId -- index
    }
    ::= { logTable 1 }

Log ::=
    SEQUENCE {
	logId
	    SimpleNameType,
	logDiscriminatorConstruct
	    OCTET STRING,
	logAdministrativeState
	    AdministrativeState,
	logOperationalState
	    OperationalState,
	logAvailabilityStatus
	    AvailabilityStatus,
	logFullAction
	    INTEGER, -- { wrap(0), halt(1) }
	-- finiteLogSizePackage PACKAGE
	maxLogSize
	    INTEGER, -- size in octets or unlimited(0)
	currentLogSize
	    INTEGER,
	numberOfRecords
	    INTEGER,
	-- logAlarmPackage PACKAGE
	capacityAlarmThreshold
	    OCTET STRING, -- SET OF INTEGER(0..100)
	logAvailabilityStatus
	    AvailabilityStatus,
	logStorageType
	    StorageType,
	logRowStatus
	    RowStatus
    }

-- NOTIFICATIONS
-- objectCreation,
-- objectDeletion,
-- attributeValueChange,
-- stateChange,
-- processingErrorAlarm

-- duration package

logDurationTable OBJECT-TYPE
    SYNTAX SEQUENCE OF LogDurationEntry
    MAX-ACCESS not-accessible
    STATUS current
    DESCRIPTION
	""
    REFERENCE
	""
    ::= { logDuration 1 }

logDurationEntry OBJECT-TYPE
    SYNTAX LogDurationEntry
    MAX-ACCESS not-accessible
    STATUS current
    DESCRIPTION
	""
    REFERENCE
	""
    INDEX {
	logId -- shared index
    }
    ::= { logDurationTable 1 }

LogDurationEntry ::=
    SEQUENCE {
	logDurationStartTime
	    ExtUTCTime,
	logDurationStopTime
	    ExtUTCTime,
	logDurationStorageType
	    StorageType,
	logDurationRowStatus
	    RowStatus
    }

-- dailySchedulingPackage

logDailySchedulingTable OBJECT-TYPE
    SYNTAX SEQUENCE OF LogDailySchedulingEntry
    MAX-ACCESS not-accessible
    STATUS current
    DESCRIPTION
	""
    REFERENCE
	""
    ::= { logDailyScheduling 1 }

logDailySchedulingEntry OBJECT-TYPE
    SYNTAX LogDailySchedulingEntry
    MAX-ACCESS not-accessible
    STATUS current
    DESCRIPTION
	""
    REFERENCE
	""
    INDEX {
	logId, -- shared index
	logIntervalStart, -- index
	logIntervalEnd -- index
    }
    ::= { logDailySchedulingTable 1 }

LogDailySchedulingEntry ::=
    SEQUENCE {
	logIntervalStart
	    Time24,
	logIntervalEnd
	    Time24,
	logDailySchedulingStorageType
	    StorageType,
	logDailySchedulingRowStatus
	    RowStatus
    }

-- weeklySchedulingPackage

logWeeklySchedulingTable OBJECT-TYPE
    SYNTAX SEQUENCE OF LogWeeklySchedulingEntry
    MAX-ACCESS not-accessible
    STATUS current
    DESCRIPTION
	""
    REFERENCE
	""
    ::= { logWeeklyScheduling 1 }

logWeeklySchedulingEntry OBJECT-TYPE
    SYNTAX LogWeeklySchedulingEntry
    MAX-ACCESS not-accessible
    STATUS current
    DESCRIPTION
	""
    REFERENCE
	""
    INDEX {
	logId, -- shared index
	logIntervalStart, -- shared index
	logIntervalEnd -- shared index
    }
    ::= { logWeeklySchedulingTable 1 }

LogWeeklySchedulingEntry ::=
    SEQUENCE {
	logWeekMask
	    BITS,
	logWeeklySchedulingStorageType
	    StorageType,
	logWeeklySchedulingRowStatus
	    RowStatus
    }

-- externalSchedulerPackage

logExternalSchedulerTable OBJECT-TYPE
    SYNTAX SEQUENCE OF LogExternalSchedulerEntry
    MAX-ACCESS not-accessible
    STATUS current
    DESCRIPTION
	""
    REFERENCE
	""
    ::= { logExternalScheduler 1 }

logExternalSchedulerEntry OBJECT-TYPE
    SYNTAX LogExternalSchedulerEntry
    MAX-ACCESS not-accessible
    STATUS current
    DESCRIPTION
	""
    REFERENCE
	""
    INDEX {
	logId -- shared index
    }
    ::= { logExternalSchedulerTable 1 }

LogExternalSchedulerEntry ::=
    SEQUENCE {
	logExternalSchedulerName
	    RowPointer,
	logExternalSchedulerStorageType
	    StorageType,
	logExternalSchedulerRowStatus
	    RowStatus
    }

-- =====================================================================

logRecordTable OBJECT-TYPE
    SYNTAX SEQUENCE OF LogRecord
    MAX-ACCESS not-accessible
    STATUS current
    DESCRIPTION
	""
    REFERENCE
	"ITU-T Rec. X.721 | ISO/IEC 10165-2"
    ::= { logRecord 1 }

logRecordEntry OBJECT-TYPE
    SYNTAX LogRecord
    MAX-ACCESS not-accessible
    STATUS current
    DESCRIPTION
	""
    REFERENCE
	"ITU-T Rec. X.721 | ISO/IEC 10165-2"
    INDEX {
	logId, -- shared index
	logRecordId -- index
    }
    ::= { logRecordTable 1 }

LogRecord ::=
    SEQUENCE {
    }

-- =====================================================================

eventLogRecordTable OBJECT-TYPE
    SYNTAX SEQUENCE OF EventLogRecord
    MAX-ACCESS not-accessible
    STATUS current
    DESCRIPTION
	""
    REFERENCE
	"ITU-T Rec. X.721 | ISO/IEC 10165-2"
    ::= { eventLogRecord 1 }

eventLogRecordEntry OBJECT-TYPE
    SYNTAX EventLogRecord
    MAX-ACCESS not-accessible
    STATUS current
    DESCRIPTION
	""
    REFERENCE
	"ITU-T Rec. X.721 | ISO/IEC 10165-2"
    INDEX {
	logId, -- shared index
	logRecordId -- shared index
    }
    ::= { eventLogRecordTable 1 }

EventLogRecord ::=
    SEQUENCE {
    }

-- =====================================================================

alarmRecordTable OBJECT-TYPE
    SYNTAX SEQUENCE OF AlarmRecord
    MAX-ACCESS not-accessible
    STATUS current
    DESCRIPTION
	""
    REFERENCE
	"ITU-T Rec. X.721 | ISO/IEC 10165-2"
    ::= { alarmRecord 1 }

alarmRecordEntry OBJECT-TYPE
    SYNTAX AlarmRecord
    MAX-ACCESS not-accessible
    STATUS current
    DESCRIPTION
	""
    REFERENCE
	"ITU-T Rec. X.721 | ISO/IEC 10165-2"
    INDEX {
	logId, -- shared index
	logRecordId -- shared index
    }
    ::= { alarmRecordTable 1 }

AlarmRecord ::=
    SEQUENCE {
    }

-- =====================================================================

attributeValueChangeRecordTable OBJECT-TYPE
    SYNTAX SEQUENCE OF AttributeValueChangeRecord
    MAX-ACCESS not-accessible
    STATUS current
    DESCRIPTION
	""
    REFERENCE
	"ITU-T Rec. X.721 | ISO/IEC 10165-2"
    ::= { attributeValueChangeRecord 1 }

attributeValueChangeRecordEntry OBJECT-TYPE
    SYNTAX AttributeValueChangeRecord
    MAX-ACCESS not-accessible
    STATUS current
    DESCRIPTION
	""
    REFERENCE
	"ITU-T Rec. X.721 | ISO/IEC 10165-2"
    INDEX {
	logId, -- shared index
	logRecordId -- shared index
    }
    ::= { attributeValueChangeRecordTable 1 }

AttributeValueChangeRecord ::=
    SEQUENCE {
    }

-- =====================================================================

objectCreationRecordTable OBJECT-TYPE
    SYNTAX SEQUENCE OF ObjectCreationRecord
    MAX-ACCESS not-accessible
    STATUS current
    DESCRIPTION
	""
    REFERENCE
	"ITU-T Rec. X.721 | ISO/IEC 10165-2"
    ::= { objectCreationRecord 1 }

objectCreationRecordEntry OBJECT-TYPE
    SYNTAX ObjectCreationRecord
    MAX-ACCESS not-accessible
    STATUS current
    DESCRIPTION
	""
    REFERENCE
	"ITU-T Rec. X.721 | ISO/IEC 10165-2"
    INDEX {
	logId, -- shared index
    logRecordId -- shared index
    }
    ::= { objectCreationRecordTable 1 }

ObjectCreationRecord ::=
    SEQUENCE {
    }

-- =====================================================================

objectDeletionRecordTable OBJECT-TYPE
    SYNTAX SEQUENCE OF ObjectDeletionRecord
    MAX-ACCESS not-accessible
    STATUS current
    DESCRIPTION
	""
    REFERENCE
	"ITU-T Rec. X.721 | ISO/IEC 10165-2"
    ::= { objectDeletionRecord 1 }

objectDeletionRecordEntry OBJECT-TYPE
    SYNTAX ObjectDeletionRecord
    MAX-ACCESS not-accessible
    STATUS current
    DESCRIPTION
	""
    REFERENCE
	"ITU-T Rec. X.721 | ISO/IEC 10165-2"
    INDEX {
	logId, -- shared index
	logRecordId -- shared index
    }
    ::= { objectDeletionRecordTable 1 }

ObjectDeletionRecord ::=
    SEQUENCE {
    }

-- =====================================================================

relationshipChangeRecordTable OBJECT-TYPE
    SYNTAX SEQUENCE OF RelationshipChangeRecord
    MAX-ACCESS not-accessible
    STATUS current
    DESCRIPTION
	""
    REFERENCE
	"ITU-T Rec. X.721 | ISO/IEC 10165-2"
    ::= { relationshipChangeRecord 1 }

relationshipChangeRecordEntry OBJECT-TYPE
    SYNTAX RelationshipChangeRecord
    MAX-ACCESS not-accessible
    STATUS current
    DESCRIPTION
	""
    REFERENCE
	"ITU-T Rec. X.721 | ISO/IEC 10165-2"
    INDEX {
	logId, -- shared index
	logRecordId -- shared index
    }
    ::= { relationshipChangeRecordTable 1 }

RelationshipChangeRecord ::=
    SEQUENCE {
    }

-- =====================================================================

securityAlarmReportRecordTable OBJECT-TYPE
    SYNTAX SEQUENCE OF SecurityAlarmReportRecord
    MAX-ACCESS not-accessible
    STATUS current
    DESCRIPTION
	""
    REFERENCE
	"ITU-T Rec. X.721 | ISO/IEC 10165-2"
    ::= { securityAlarmReportRecord 1 }

securityAlarmReportRecordEntry OBJECT-TYPE
    SYNTAX SecurityAlarmReportRecord
    MAX-ACCESS not-accessible
    STATUS current
    DESCRIPTION
	""
    REFERENCE
	"ITU-T Rec. X.721 | ISO/IEC 10165-2"
    INDEX {
	logId, -- shared index
	logRecordId -- shared index
    }
    ::= { securityAlarmReportRecordTable 1 }

SecurityAlarmReportRecord ::=
    SEQUENCE {
    }

-- =====================================================================

stateChangeRecordTable OBJECT-TYPE
    SYNTAX SEQUENCE OF StateChangeRecord
    MAX-ACCESS not-accessible
    STATUS current
    DESCRIPTION
	""
    REFERENCE
	"ITU-T Rec. X.721 | ISO/IEC 10165-2"
    ::= { stateChangeRecord 1 }

stateChangeRecordEntry OBJECT-TYPE
    SYNTAX StateChangeRecord
    MAX-ACCESS not-accessible
    STATUS current
    DESCRIPTION
	""
    REFERENCE
	"ITU-T Rec. X.721 | ISO/IEC 10165-2"
    INDEX   {
	logId, -- shared index
	logRecordId -- shared index
    }
    ::= { stateChangeRecordTable 1 }

StateChangeRecord ::=
    SEQUENCE {
    }

-- =====================================================================

systemTable OBJECT-TYPE
    SYNTAX SEQUENCE OF System
    MAX-ACCESS not-accessible
    STATUS current
    DESCRIPTION
	""
    REFERENCE
	"ITU-T Rec. X.721 | ISO/IEC 10165-2"
    ::= { system 1 }

systemEntry OBJECT-TYPE
    SYNTAX System
    MAX-ACCESS not-accessible
    STATUS current
    DESCRIPTION
	""
    REFERENCE
	"ITU-T Rec. X.721 | ISO/IEC 10165-2"
    ::= { systemTable 1 }

System ::=
    SEQUENCE {
    }

-- =====================================================================

-- =====================================================================

-- =====================================================================

-- =====================================================================

-- =====================================================================

-- =====================================================================

END

-- vim: ft=mib comments=\f\:\",\b\:\-\-,\:\-\-,\f\b\:- fo+=tcqlornw tw=72 nocin nosi sts=4 sw=4
