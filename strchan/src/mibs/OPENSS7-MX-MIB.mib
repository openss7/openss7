-- vim: ft=mib comments=\f\:\",\b\:\-\-,\:\-\-,\f\b\:- fo+=tcqlornw tw=72 nocin nosi sts=4 sw=4
-- =============================================================================
-- 
-- @(#) $RCSfile: OPENSS7-MX-MIB.mib,v $ $Name: OpenSS7-0_9_2 $($Revision: 0.9.2.14 $) $Date: 2009-01-16 20:45:03 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-16 20:45:03 $ by $Author: brian $
--
-- -----------------------------------------------------------------------------
--
-- $Log: OPENSS7-MX-MIB.mib,v $
-- Revision 0.9.2.14  2009-01-16 20:45:03  brian
-- - updating mibs and agents
--
-- Revision 0.9.2.13  2009-01-14 14:30:09  brian
-- - working up agents
--
-- Revision 0.9.2.12  2009-01-14 10:13:34  brian
-- - fix errors
--
-- Revision 0.9.2.11  2009-01-14 09:08:46  brian
-- - mib updates
--
-- Revision 0.9.2.10  2009-01-12 12:09:48  brian
-- - mib updates
--
-- Revision 0.9.2.9  2009-01-11 18:42:58  brian
-- - updated mibs
--
-- Revision 0.9.2.8  2009-01-10 17:46:47  brian
-- - updated agents and mibs
--
-- Revision 0.9.2.7  2009-01-03 10:51:12  brian
-- - updated agent
--
-- Revision 0.9.2.6  2008-12-27 15:35:03  brian
-- - correct default values
--
-- Revision 0.9.2.5  2008-12-20 12:48:40  brian
-- - added manpages and mibs
--
-- Revision 0.9.2.4  2008-12-02 06:51:28  brian
-- - document CHI
--
-- Revision 0.9.2.3  2008/01/14 19:47:06  brian
-- - updated and corrected mibs
--
-- Revision 0.9.2.2  2008/01/03 12:46:02  brian
-- - updates for new mib2c
--
-- Revision 0.9.2.1  2008/01/01 13:59:39  brian
-- - added new mibs
--
-- =============================================================================

OPENSS7-MX-MIB DEFINITIONS ::= BEGIN

IMPORTS
    MODULE-IDENTITY, OBJECT-IDENTITY, OBJECT-TYPE, Counter32, Integer32, 
    Unsigned32
	FROM SNMPv2-SMI
    TEXTUAL-CONVENTION, AutonomousType, DateAndTime, DisplayString, 
    RowPointer, RowStatus, StorageType, TimeInterval, TimeStamp, 
    TruthValue
	FROM SNMPv2-TC
    MODULE-COMPLIANCE, OBJECT-GROUP
	FROM SNMPv2-CONF
    SnmpAdminString
	FROM SNMP-FRAMEWORK-MIB
    PerfCurrentCount, PerfIntervalCount, PerfTotalCount
	FROM PerfHist-TC-MIB
    HCPerfValidIntervals, HCPerfInvalidIntervals, HCPerfTimeElapsed,
    HCPerfIntervalThreshold, HCPerfCurrentCount, HCPerfIntervalCount,
    HCPerfTotalCount
	FROM HC-PerfHist-TC-MIB
    StreamsModuleName
	FROM OPENSS7-STREAMS-MIB
    CommonLanguageName
	FROM OPENSS7-TC
    AdministrativeState, AlarmStatus, AvailabilityStatus, ControlStatus, 
    OperationalState, ProceduralStatus, SimpleNameType, StandbyStatus, 
    UnknownStatus, UsageState
	FROM OPENSS7-SMI-MIB
    openss7Modules
	FROM OPENSS7-SMI;

mxMIB MODULE-IDENTITY
    LAST-UPDATED	"200901141143Z"
    ORGANIZATION
	"The OpenSS7 Project"
    CONTACT-INFO
	"Brian Bidulock
	 OpenSS7 Corporation
	 1469 Jefferys Crescent
	 Edmonton AB  T6L 6T1
	 CANADA
	 Tel: +1 780 490 1141
	 Fax: +1 780 490 1241
	 Mob: +1 780 953 0557
	 E-Mail: bidulock@openss7.org"
    DESCRIPTION	
	"MIB Module for the MX multiplexing driver.  In the OpenSS7 
	 system the MX multiplexing driver is a TDM switching module."
    REVISION	"200901141143Z"
    DESCRIPTION
	"Added driver table to the MIB."
    REVISION	"200801011353Z"
    DESCRIPTION	
	"First release of this module."
    ::= { openss7Modules 11 }

-- ====================================================================
-- TEXUTAL CONVENTIONS
-- ====================================================================

SpanIdentity ::= TEXTUAL-CONVENTION
    DISPLAY-HINT "1d:"
    STATUS	current
    DESCRIPTION	
	"Provides a specification of a span identifier amoungst all of 
	 the spans available on all cards in the system.  The octet 
	 string is coded as follows: the first two octets is the module 
	 identity number of the device driver, most significant octet 
	 first, the third octet is the card number; and the fourth octet 
	 is the span number on the card."
    SYNTAX	OCTET STRING (SIZE(0 | 4))

SpanNumber ::= TEXTUAL-CONVENTION
    DISPLAY-HINT "d-0"
    STATUS	current
    DESCRIPTION	
	"Provides a specification of a span relative to a span group.  
	 This is a small ordinal number from 1 to 32.  The number zero 
	 (0) indicates no span or an entire span group. The values 1..3 
	 are used for E2; 1..4 for T1; 
	 1..21 for E3; and 1..28 for T3."
    SYNTAX	Unsigned32 (0..32)

ChannelNumber ::= TEXTUAL-CONVENTION
    DISPLAY-HINT "d-0"
    STATUS	current
    DESCRIPTION	
	"Provides a specification of a channel relative to a span.  This 
	 is a small ordinal number from 1 to 24 for T1 spans and 1 to 31 
	 for E1 spans.  The number is the same as the time slot number 
	 for the span.  The number zero (0) indicates no chanel or an 
	 entire span."
    SYNTAX	Unsigned32 (0..31)

ChannelSet ::= TEXTUAL-CONVENTION
    STATUS	current
    DESCRIPTION	
	"Provides a specificiation of a set of channels within a span.  
	 This is bit mask of the channels included in the set (channels 
	 1 through 24 for T1 and 1 through 31 for E1)."
    SYNTAX	BITS {
	ch1(0), ch2(1), ch3(2), ch4(3), ch5(4), ch6(5), ch7(6), ch8(7), 
	ch9(8), ch10(9), ch11(10), ch12(11), ch13(12), ch14(13), 
	ch15(14), ch16(15), ch17(16), ch18(17), ch19(18), ch20(19), 
	ch21(20), ch22(21), ch23(22), ch24(23), ch25(24), ch26(25), 
	ch27(26), ch28(27), ch29(28), ch30(29), ch31(30) }

PhysicalPointOfAppearance ::= TEXTUAL-CONVENTION
    STATUS	current
    DESCRIPTION	
	"Provides a specification of a physical point of appearance 
	 (e.g. card and port) that corresponds to a trace termination 
	 point of a network arc (network interface).  The PPA is coded 
	 as two octets, where the first octet is the most significant 8 
	 bits of the PPA and the second octet is the least significant 8 
	 bits of the PPA."
    SYNTAX	OCTET STRING (SIZE(2))

mxNotifications OBJECT IDENTIFIER
    ::= { mxMIB 0 }

mxObjects OBJECT IDENTIFIER
    ::= { mxMIB 1 }

-- ====================================================================
-- TABLES
-- ====================================================================

mxTables OBJECT IDENTIFIER
    ::= { mxObjects 1 }

mxSync OBJECT IDENTIFIER
    ::= { mxTables 1 }

mxSyncTable OBJECT-TYPE
    SYNTAX	SEQUENCE OF MxSyncEntry
    MAX-ACCESS	not-accessible
    STATUS	current
    DESCRIPTION	
	"The synchronization table is a table of synchronization groups.  
	 Equipped cards that are configured for automatic synchronzation 
	 are assigned to a synchronization group."
    ::= { mxSync 1 }

mxSyncEntry OBJECT-TYPE
    SYNTAX	MxSyncEntry
    MAX-ACCESS	not-accessible
    STATUS	current
    DESCRIPTION	
	"Each entry in the synchronization table represents a 
	 synchronization source to be used for automatic synchronization 
	 within each group in the order of the index.  Rows may be 
	 created and deleted explicitly by management stations.  Rows 
	 may be deleted implicitly as a part of system operation when a 
	 card is disassociated with a synchroniation group."
    INDEX	{
	mxSyncGroup,
	mxSyncIndex
    }
    ::= { mxSyncTable 1 }

MxSyncEntry ::= SEQUENCE {
    mxSyncGroup					Unsigned32,
    mxSyncIndex					Unsigned32,
    mxSyncSpanId				SpanIdentity,
    mxSyncRowStatus				RowStatus
}

mxSyncGroup OBJECT-TYPE
    SYNTAX	Unsigned32 (1..16)
    MAX-ACCESS	not-accessible
    STATUS	current
    DESCRIPTION	
	"Specifies the group number of the entry.  A synchronization 
	 group is a group of cards which share a common timing bus.  
	 Membership in the group is the cards which have an 
	 synchronization group value equal to this index and a 
	 synchronization source setting of syncAuto(6)."
    ::= { mxSyncEntry 1 }

mxSyncIndex OBJECT-TYPE
    SYNTAX	Unsigned32 (1..8)
    MAX-ACCESS	not-accessible
    STATUS	current
    DESCRIPTION	
	"Specifies the index of the entry and the priority at which the 
	 entry will be used for synchronization of the card.  Index 
	 value 1 is the highest priority and index value 8 is the lowest 
	 priority."
    ::= { mxSyncEntry 2 }

mxSyncSpanId OBJECT-TYPE
    SYNTAX	SpanIdentity
    MAX-ACCESS	read-create
    STATUS	current
    DESCRIPTION	
	"Specifies the card and span to be used as a card 
	 synchronization source at the priority of the corresponding 
	 index.  Cards 1..16 and spans 1..4 can be specified in 
	 accordance with the SpanIdentity textual convention.  However, 
	 the card number specified must belong to the same 
	 synchronization group as the indexed group.  That is, the card 
	 must have its synchronization group set to the index of this 
	 entry, and the card synchronization source must be set to 
	 syncAuto(6)."
    ::= { mxSyncEntry 3 }

mxSyncRowStatus OBJECT-TYPE
    SYNTAX	RowStatus
    MAX-ACCESS	read-create
    STATUS	current
    DESCRIPTION	
	"Provides a mechanism whereby management stations may create or 
	 delete rows in this table.
	 
	 Rows may be created or deleted explicitly by management 
	 stations or implicitly as a part of system oepration.  When a 
	 card is removed from a synchronization group (by having its 
	 sychronization group number changed or having its 
	 synchronization source set to other than syncAuto(6)), the 
	 system may automatically delete rows from this table."
    REFERENCE	
	"STD 58, SNMPv2-TC RowStatus."
    ::= { mxSyncEntry 4 }


mxDriv OBJECT IDENTIFIER
    ::= { mxTables 2 }

mxDrivTable OBJECT-TYPE
    SYNTAX	SEQUENCE OF MxDrivEntry
    MAX-ACCESS	not-accessible
    STATUS	current
    DESCRIPTION	
	"The driver table is a table of device drivers.  Each driver 
	 that provides support for hardware cards is represented in this 
	 table."
    ::= { mxDriv 1 }

mxDrivEntry OBJECT-TYPE
    SYNTAX	MxDrivEntry
    MAX-ACCESS	not-accessible
    STATUS	current
    DESCRIPTION	
	"Each entry in the driver table represents a software device 
	 driver that supports objects in this MIB.  Rows in this table 
	 are generated automatically by the agent.  Additional rows may 
	 be added (but not removed) by a management station."
    INDEX	{
	mxDrivName
    }
    ::= { mxDrivTable 1 }

MxDrivEntry ::= SEQUENCE {
    mxDrivName					StreamsModuleName,
    mxDrivIdnum					Unsigned32,
    mxDrivMajor					Unsigned32,
    mxDrivDescription				SnmpAdminString,
    mxDrivRevision				SnmpAdminString,
    mxDrivCopyright				SnmpAdminString,
    mxDrivSupportedDevice			SnmpAdminString,
    mxDrivContact				SnmpAdminString,
    mxDrivLicense				INTEGER,
    mxDrivDate					DateAndTime,
    mxDrivRowStatus				RowStatus
}

mxDrivName OBJECT-TYPE
    SYNTAX	StreamsModuleName
    MAX-ACCESS	not-accessible
    STATUS	current
    DESCRIPTION	
	"Provides the STREAMS driver name associated with the device 
	 driver.  This is equivalent to the strModName entry in the 
	 OPENSS7-STREAMS-MIB.  This driver name also describes the path 
	 to the device driver for the agent to use in accessing the 
	 driver (e.g. /dev/streams/mxDrivName/0)."
    ::= { mxDrivEntry 1 }

mxDrivIdnum OBJECT-TYPE
    SYNTAX	Unsigned32 (0..16383)
    MAX-ACCESS	read-only
    STATUS	current
    DESCRIPTION	
	"Provides the STREAMS module identification number associated 
	 with the device driver.  This is equivalent to the strModIdnum  
	 entry in the OPENSS7-STREAMS-MIB."
    ::= { mxDrivEntry 2 }

mxDrivMajor OBJECT-TYPE
    SYNTAX	Unsigned32 (0..16383)
    MAX-ACCESS	read-only
    STATUS	current
    DESCRIPTION	
	"Provides the STREAMS driver major device number associated with 
	 the device driver.  This is equivalent to the strModMajor entry 
	 in the OPENSS7-STREAMS-MIB."
    ::= { mxDrivEntry 3 }

mxDrivDescription OBJECT-TYPE
    SYNTAX	SnmpAdminString
    MAX-ACCESS	read-only
    STATUS	current
    DESCRIPTION	
	"Provides a brief one line description of the device driver."
    ::= { mxDrivEntry 4 }

mxDrivRevision OBJECT-TYPE
    SYNTAX	SnmpAdminString
    MAX-ACCESS	read-only
    STATUS	current
    DESCRIPTION	
	"Provides a brief one line description of the device driver 
	 version and revision."
    ::= { mxDrivEntry 5 }

mxDrivCopyright OBJECT-TYPE
    SYNTAX	SnmpAdminString
    MAX-ACCESS	read-only
    STATUS	current
    DESCRIPTION	
	"Provides a brief one line copyright statement."
    ::= { mxDrivEntry 6 }

mxDrivSupportedDevice OBJECT-TYPE
    SYNTAX	SnmpAdminString
    MAX-ACCESS	read-only
    STATUS	current
    DESCRIPTION
	"Provides a brief one line text description of the supported 
	 devices.  This is the MODULE_SUPPORTED_DEVICE() field 
	 associated with the kernel module."
    ::= { mxDrivEntry 7 }

mxDrivContact OBJECT-TYPE
    SYNTAX	SnmpAdminString
    MAX-ACCESS	read-only
    STATUS	current
    DESCRIPTION	
	"Provides the contact information (e.g. email address) of the 
	 author or other contact for the device driver.  This is the 
	 MODULE_AUTHOR() field associated with the kernel module."
    ::= { mxDrivEntry 8 }

mxDrivLicense OBJECT-TYPE
    SYNTAX	INTEGER {
	proprietary(0), gpl(1), gplV2(2), gplPlus(3), dualBsdGpl(4), 
	dualMitGpl(5), dualMplGpl(6) }
    MAX-ACCESS	read-only
    STATUS	current
    DESCRIPTION	
	"Provides the Linux kernel license applicable to the kernel 
	 module representing the device driver.  This object is 
	 single-valued and can assume one of the following values:
	 
	 - proprietary(0), non-free products;
	 - gpl(1), GNU Public License v2 or later;
	 - gplV2(2), GNU Public License v2;
	 - gplPlus(3), GNU Public License v2 rights and more (e.g. LGPL);
	 - dualBsdGpl(4), GNU Public License v2 or BSD license choice;
	 - dualMitGpl(4), GNU Public License v2 or MIT license choice;
	 - dualMplGpl(4), GNU Public License v2 or MPL license choice.
	 
	 This is the MODULE_LICENSE() field associated with the kernel 
	 module."
    ::= { mxDrivEntry 9 }

mxDrivDate OBJECT-TYPE
    SYNTAX	DateAndTime
    MAX-ACCESS	read-only
    STATUS	current
    DESCRIPTION	
	"Provides the date of the device driver."
    ::= { mxDrivEntry 10 }

mxDrivRowStatus OBJECT-TYPE
    SYNTAX	RowStatus
    MAX-ACCESS	read-create
    STATUS	current
    DESCRIPTION	
	"Provides a mechanism whereby management stations may create or 
	 delete rows in this table.  Rows added by management stations 
	 persist across an agent reboot.  Management stations must 
	 provide a valid value for the mxDrivName field that corresponds 
	 to a device driver in the managed system.  The agent will 
	 populate other fields accordingly.  Invalid, unsupported or 
	 non-existent device drivers will cause the row creation request 
	 to be rejected with an inconsistent name.  Requests to destroy 
	 rows in this table that are referenced in other tables will be 
	 likewise refused."
    ::= { mxDrivEntry 11 }


mxCard OBJECT IDENTIFIER
    ::= { mxTables 3 }

mxCardNextIndex OBJECT-TYPE
    SYNTAX	Unsigned32
    MAX-ACCESS	read-only
    STATUS	current
    DESCRIPTION	
	"Provides the next available index into the mxCardTable for 
	 use by management stations when adding rows to the table."
    REFERENCE	
	"STD 58"
    ::= { mxCard 1 }

mxCardTable OBJECT-TYPE
    SYNTAX	SEQUENCE OF MxCardEntry
    MAX-ACCESS	not-accessible
    STATUS	current
    DESCRIPTION	
	"Provides the table which indexes each card in the managed 
	 element.  The Card Table provides an entry for each of the 
	 equipped cards in the system."
    ::= { mxCard 2 }

mxCardEntry OBJECT-TYPE
    SYNTAX	MxCardEntry
    MAX-ACCESS	not-accessible
    STATUS	current
    DESCRIPTION	
	"Provides an entry in the card table.  Each entry in the table 
	 indexes a card in the managed element.  Cards are not intended 
	 on being added to or removed from this table by management 
	 stations.  Physical insertion and removal of cards is required 
	 and as these cards do not support PCI hotplug, the system needs 
	 to be rebooted in which case the cards will appear in this 
	 table on reboot.  Therefore there is no NextIndex scalar or 
	 RowStatus column for this table.
	
	 Rows are neither created nor deleted explicity by mangement 
	 stations but are present inherently as a part of system 
	 operation.  Each entry in the table corresponds to an existing 
	 and installed card."
    INDEX	{
	mxDrivName,	-- shared index
	mxCardIndex
    }
    ::= { mxCardTable 1 }

MxCardEntry ::= SEQUENCE {
    mxCardIndex					Unsigned32,
    mxCardType					AutonomousType,
    mxCardIdentifier				INTEGER,
    mxCardRevision				DisplayString,
    mxCardChipType				AutonomousType,
    mxCardChipRevision				DisplayString,
    mxCardPciBus				Unsigned32,
    mxCardPciSlot				Unsigned32,
    mxCardPciIrq				Unsigned32,
    mxCardSpanType				INTEGER,
    mxCardMode					BITS,
    mxCardSyncMaster				INTEGER,
    mxCardSyncSource				INTEGER,
    mxCardSyncGroup				Unsigned32,
    mxCardAdministrativeState			AdministrativeState,
    mxCardOperationalState			OperationalState,
    mxCardUsageState				UsageState,
    mxCardAlarmStatus				AlarmStatus,
    mxCardProceduralStatus			ProceduralStatus,
    mxCardAvailabilityStatus			AvailabilityStatus,
    mxCardControlStatus				ControlStatus,
    mxCardUnknownStatus				UnknownStatus,
    mxCardStandbyStatus				StandbyStatus,
    mxCardSyncSpanId				SpanIdentity,
    mxCardSyncTransitions			Counter32,
    mxCardName					CommonLanguageName,
    mxCardStatus				RowStatus
}

mxCardIndex OBJECT-TYPE
    SYNTAX	Unsigned32 (1..16)
    MAX-ACCESS	not-accessible -- index
    STATUS	current
    DESCRIPTION	
	"Provides an index for the card in the managed element.  This is 
	 the ordinal value of the card number and is used as a handle to 
	 refer to this card.  This is a small ordinal number beginning 
	 with a 1 and enumerating as many as 16 cards."
    ::= { mxCardEntry 1 }

mxCardType OBJECT-TYPE
    SYNTAX	AutonomousType
    MAX-ACCESS	read-only
    STATUS	current
    DESCRIPTION	
	"Indicates the card type for the entry using an AutonomousType.  
	 Following are some examples (some of these example card types 
	 are obsolete):
	 
	 - zeroDotZero,
	 - mxCardTypePLX9030,
	 - mxCardTypePLXDevelopmentBoard,
	 - mxCardTypeX400P,
	 - mxCardTypeE400P,
	 - mxCardTypeT400P,
	 - mxCardTypeX400P-SS7,
	 - mxCardTypeE400P-SS7,
	 - mxCardTypeT400P-SS7,
	 - mxCardTypeV400PE,
	 - mxCardTypeV400PT,
	 - mxCardTypeV401PE,
	 - mxCardTypeV401PT,
	"
    ::= { mxCardEntry 2 }

mxCardIdentifier OBJECT-TYPE
    SYNTAX	INTEGER (SIZE(2))
    MAX-ACCESS	read-only
    STATUS	current
    DESCRIPTION	
	"This is a 2 octet card identifier that is written to the card 
	 to identify it regardless of the slot position."
    ::= { mxCardEntry 3 }

mxCardRevision OBJECT-TYPE
    SYNTAX	DisplayString (SIZE(1))
    MAX-ACCESS	read-only
    STATUS	current
    DESCRIPTION	
	"Indicates a single character revision (e.g. Rev. A) indicating 
	 the board revision number.  It is typically a single character 
	 beginning an A and working up.  That is, the first revision of 
	 a board is Rev. A, the second revision, Rev. B, an so on."
    ::= { mxCardEntry 4 }

mxCardChipType OBJECT-TYPE
    SYNTAX	AutonomousType
    MAX-ACCESS	read-only
    STATUS	current
    DESCRIPTION	
	"Indicates the type of framer chip found in the device using an 
	 autonomous type.  An example of values for Dallas framer chips 
	 follow:
	 
	 - zeroDotZero, indicates that the equipment is either absent, 
	   not configured or failed.
	 
	 - mxChipTypeDS2152, the DS2152 T1 chip.
	 - mxChipTypeDS21352, the DS21352 T1 chip.
	 - mxChipTypeDS21552, the DS21552 T1 chip.
	 
	 - mxChipTypeDS2154, the DS2154 E1 chip.
	 - mxChipTypeDS21354, the DS21354 E1 chip.
	 - mxChipTypeDS21554, the DS21554 E1 chip.
	 
	 - mxChipTypeDS2155, the DS2155 E1/T1/J1 chip.
	 - mxChipTypeDS2156, the DS2156 E1/T1/J1 chip.
	 
	 The DS2152, DS21352, DS21552 are T1-only chips; the DS2154, 
	 DS21354, DS21554 are E1-only chips; the DS2155 and DS2156 are 
	 E1/T1/J1 chips."
    ::= { mxCardEntry 5 }

mxCardChipRevision OBJECT-TYPE
    SYNTAX	DisplayString (SIZE(1))
    MAX-ACCESS	read-only
    STATUS	current
    DESCRIPTION	
	"Indicates a single character revision (e.g. Rev. A) indicate 
	 the chipset revision number.  It is typically a single 
	 character beginning at A and working up.  That is, the first 
	 revision of a chipset is Rev. A, the second revision, Rev. B, 
	 and so on."
    ::= { mxCardEntry 6 }

mxCardPciBus OBJECT-TYPE
    SYNTAX	Unsigned32 (0..16)
    MAX-ACCESS	read-only
    STATUS	current
    DESCRIPTION	
	"Indicates the PCI bus number for the PCI bus on which the card 
	 is located.  The value zero (0) means that the card is not on a 
	 bus (i.e. the card is unequiped)."
    ::= { mxCardEntry 7 }

mxCardPciSlot OBJECT-TYPE
    SYNTAX	Unsigned32 (0..16)
    MAX-ACCESS	read-only
    STATUS	current
    DESCRIPTION	
	"Indicates the PCI bus slot number in which the card is located.  
	 The value zero (0) means that the card is not in a slot (i.e. 
	 the card is unequipped)."
    ::= { mxCardEntry 8 }

mxCardPciIrq OBJECT-TYPE
    SYNTAX	Unsigned32 (0..1024)
    MAX-ACCESS	read-only
    STATUS	current
    DESCRIPTION	
	"Indicates the PCI IRQ that is assigned to the card.  The value 
	 zero (0) means that no IRQ is currently assigned (i.e. the card 
	 is unequipped or is not configured at the system level)."
    ::= { mxCardEntry 9 }

mxCardSpanType OBJECT-TYPE
    SYNTAX	INTEGER {
	none(1), t1(2), e1(3), j1(4) }
    MAX-ACCESS	read-create
    STATUS	current
    DESCRIPTION	
	"Specifies or indicates the span type for the indexed card.  
	 Some cards and chipsets support mutliple span types, in which 
	 case, this column sets the default span type.  Some cards and 
	 chipsets only support a single span type, in which case, this 
	 column is read-only and provides the span type for all spans on 
	 the card.  The value can be:
	 
	 - none(1), unknown or unspecified.
	 
	 - t1(2), the default is T1 operation.
	 
	 - e1(3), the default is E1 operation.
	 
	 - j1(4), the default is J1 operation.
	 
	 The value none(1) can be read but not written.  When read, the 
	 value none(1) indicates that the equipment is either absent, 
	 not configured or failed.
	 
	 Note that not all values are applicable to all card types and 
	 chipsets.  Also, not all cards or chipsets will allow all 
	 values to be set."
    ::= { mxCardEntry 10 }

mxCardMode OBJECT-TYPE
    SYNTAX	BITS { remoteLoopback(0), localLoopback(1) }
    MAX-ACCESS	read-create
    STATUS	current
    DESCRIPTION	
	"Specifies the loopback mode for the entire card.  The value may 
	 contain:
	 
	 - remoteLoopback(0), RSER is looped back on TSER for all spans; 
	   that is, all received bits are looped back to the transmit 
	   between the elastic store and the system bus.  This is 
	   equivalent to a per-span payload loopback, but is performed 
	   through the elastic store and on a card basis.
	  
	 - localLoopback(1), RxBuf is driven by TxBuf; that is, all 
	   transmitted data bits are passed to the corresponding receive 
	   data bits between the elastic store and the system bus.
	  
	 These modes are only useful for specialized testing and the 
	 card must have a control status of subjectToTest(0) or 
	 reservedForTest(2) before either of these values may be added 
	 to the set."
    ::= { mxCardEntry 11 }

mxCardSyncMaster OBJECT-TYPE
    SYNTAX	INTEGER { slave(0), master(1) }
    MAX-ACCESS	read-create
    STATUS	current
    DESCRIPTION	
	"Specifies whether the card is a slave or a master on the 
	 external timing bus.  The value can be one of:
	 
	 - slave(0), the external timing bus may be used as a 
	   synchronization source for the card by setting the card 
	   synchronization source to syncExtern(5).  Spans that use the 
	   external timing source should have their span clocking set to 
	   slave(6).
	 
	 - master(1), the card drives the external timing bus and the 
	   synchronization source may not also be set to syncExtern(5)."
    ::= { mxCardEntry 12 }

mxCardSyncSource OBJECT-TYPE
    SYNTAX	INTEGER {
	syncSelf(0), sync1(1), sync2(2), sync3(3), sync4(4), 
	syncExtern(5), syncAuto(6) }
    MAX-ACCESS	read-create
    STATUS	current
    DESCRIPTION	
	"Specifies the synchronization source for the entire card (the 
	 synchronization applied to the TCLK pin on all spans).  The 
	 synchronization source may be one of:
	 
	 - syncSelf(0), the internal clock will be used as a 
	   synchronization source for the card.
	 
	 - sync1(1), sync2(2), sync3(3) or sync4(4), the corresponding 
	   span RCLK output will be used as the TCLK input for all spans 
	   on the card.
	 
	 - syncExtern(5), the TCLK input for all spans will be taken 
	   from the external timing bus.
	 
	 - syncAuto(6), the driver will use the spans specified in the 
	   mxSyncTable side-table for the card as synchronization 
	   sources.
	 
	 Note that the card synchronization source only affects spans 
	 that are set for internal(2) or slave(6) span clocking."
    ::= { mxCardEntry 13 }

mxCardSyncGroup OBJECT-TYPE
    SYNTAX	Unsigned32 (1..16)
    MAX-ACCESS	read-create
    STATUS	current
    DESCRIPTION	
	"Specifies the synchronization group to which this card belongs.  
	 This value is only significant when the synchronization source 
	 is set to syncAuto(6).  A synchronization group is a group of 
	 cards, including the current card in the set, that are 
	 connected together with a timing cable and therefore share the 
	 same timing bus.  The order of cards and spans that will be 
	 used for timing are specified against the synchronization group 
	 that has an group index of the same value as this column."
    ::= { mxCardEntry 14 }

mxCardAdministrativeState OBJECT-TYPE
    SYNTAX	AdministrativeState
    MAX-ACCESS	read-create
    STATUS	current
    DESCRIPTION	
	"Provides the administrative state of the card following the 
	 AdministrativeState textual convention of the OPENSS7-SMI-MIB 
	 module in accordance with the administrativeState attribute of 
	 ITU-T Rec. X.721 | ISO/IEC 10165-2.  The administrative state 
	 can have one of the following values:
	 
	 - locked(0), the card is administratively prohibited from 
	   providing service to users: no user will be permitted to 
	   access a channel on the card.
	 
	 - unlocked(1), the card is administratively permitted to 
	   provide service to users: users will be permitted to access 
	   channels on the card.
	 
	 - shuttingDown(2), the card will continue to provider service 
	   to existing users but will reject new users.  Once there are 
	   no more users of the card, the card will move to the 
	   locked(1) state: no new users will be permitted to access 
	   channels on the card, however, existing users will be allowed 
	   to continue using channels until they are released by the 
	   user."
    REFERENCE	
	"OPENSS7-SMI-MIB, ITU-T Rec. X.721 | ISO/IEC 10165-2, 
	     administrativeState."
    DEFVAL	{ locked }
    ::= { mxCardEntry 15 }

mxCardOperationalState OBJECT-TYPE
    SYNTAX	OperationalState
    MAX-ACCESS	read-only
    STATUS	current
    DESCRIPTION	
	"Provides the operational state of the card following the 
	 OperationalState textual convention of the OPENSS7-SMI-MIB 
	 module in accordance with the operationalState attribute of 
	 ITU-T Rec. X.721 | ISO/IEC 10165-2.  The operational state can 
	 have one of the following values:
	 
	 - disabled(0), the card is inoperable and unable to provide 
	   service to users;
	 
	 - enabled(1), it is partially or fully operable and available 
	   for use."
    REFERENCE	
	"OPENSS7-SMI-MIB, ITU-T Rec. X.721 | ISO/IEC 10165-2, 
	     operationalState."
    DEFVAL	{ disabled }
    ::= { mxCardEntry 16 }

mxCardUsageState OBJECT-TYPE
    SYNTAX	UsageState
    MAX-ACCESS	read-only
    STATUS	current
    DESCRIPTION	
	"Provides the usage state of the card following the UsageState 
	 textual convention of the OPENSS7-SMI-MIB module in accordance 
	 with the usageState attribute of ITU-T Rec. X.721 | ISO/IEC 
	 10165-2.
	 
	 The usage state can be one of the following:
	 
	 - idle(0), the card is not curently in use; no channels are in 
	   use.
	 
	 - active(1), the card is in use and has sufficient operating 
	   capacity to provide for additional users simultaneously (i.e. 
	   some channel in some span is idle(0)); some channels are in 
	   use.
	 
	 - busy(2), the card is in use and has no spare capacity (i.e.  
	   all spanse are busy(2)): all spans and channels are in use."
    REFERENCE	
	"OPENSS7-SMI-MIB, ITU-T Rec. X.721 | ISO/IEC 10165-2, 
	     usageState."
    DEFVAL	{ idle }
    ::= { mxCardEntry 17 }

mxCardAlarmStatus OBJECT-TYPE
    SYNTAX	AlarmStatus
    MAX-ACCESS	read-create
    STATUS	current
    DESCRIPTION	
	"Provides the alarm status for the card following the 
	 AlarmStatus textual convention of the OPENSS7-SMI-MIB module in 
	 accordance with the alarmStatus attribute of ITU-T Rec. X.721 | 
	 ISO/IEC 10165-2.  The alarm status is set-valued and may 
	 contain:
	 
	 - underRepair(0), the card is marked as under repair either 
	   locally or by a management station; the card is currently 
	   being repaired, the operational state is disabled(0).
	 
	 - critical(1), one or more critical faults were detected for 
	   which alarms are oustanding; does not occur.
	 
	 - major(2), one or more major faults were detected for which 
	   alarms are oustanding; does not occur.
	 
	 - minor(3), one or more minor faults were detected for which 
	   alarms are outstanding; indicates that one or more minor 
	   alarms indicating a faults have been detected in the 
	   resource, and have not yet been cleared, the operational 
	   status is enabled(1).
	 
	 - alarmOutstanding(4), one more more alarms are outstanding; 
	   indicates that one or more alarms have been detected in the 
	   resource, and have not yet been cleared, the condition of 
	   which may be disabling.  When alarmOutstanding(4) is set, and 
	   the operational state is enabled(1), other status and state 
	   attributes provide additional information, particularly the 
	   carrier alarm related columns.
	 
	 The alarm status for the card is not directly associated with 
	 the alarm status of the spans provided by the card.  Alarm 
	 notifications associated with the card occur when 
	 synchronization is lost the span currently used as a 
	 synchronization source and the card is searching for another 
	 synchronization source."
    REFERENCE	
	"OPENSS7-SMI-MIB, ITU-T Rec. X.721 | ISO/IEC 10165-2, 
	     alarmStatus."
    DEFVAL	{ '00000'B }
    ::= { mxCardEntry 18 }

mxCardProceduralStatus OBJECT-TYPE
    SYNTAX	ProceduralStatus
    MAX-ACCESS	read-only
    STATUS	current
    DESCRIPTION	
	"Provides the procedural status of the card following the 
	 ProceduralStatus textual convention of the OPENSS7-SMI-MIB 
	 module in accordance with the proceduralStatus attribute of 
	 ITU-T Rec. X.721 | ISO/IEC 10165-2.  The procedural status is 
	 set-valued and may contain the following:
	 
	 - initializationRequired(0), the card requires initialization 
	   by the management station before it can perform normal 
	   functions and this procedure has not been initiated.  The 
	   operational state is disabled; a driver has not been loaded 
	   against this card or the card has not been configured for 
	   operation; the operational state is disabled(0).
	 
	 - notInitialized(1), the card requires initialization before it 
	   can perform its normal functions and this procedure has not 
	   been initiated.  The card initializes itself autonomously; 
	   the operational state is disabled; a driver has been loaded 
	   against the card and the card has been configured for 
	   operation; however, spans still require configuration before 
	   the channels on the card are usable; the operational state is 
	   disabled(1).
	 
	 - initializing(2), the card requires initialization before it 
	   can perform its normal functions and this procedure has been 
	   initiated but is not yet complete; when present, the 
	   initialization requried condition is absent; the operational 
	   state is disabled; spans are being initialized; the 
	   operational state is enabled(1).
	 
	 - reporting(3), the card is reporting the results of a 
	   procedure; this condition is not applicable;
	 
	 - terminating(4), the card is in a termination phase; if the 
	   resource does not initialize itself autonomously, the 
	   initialization required condition is also present and 
	   operational state is disabled; the resource is in a 
	   termination phase and the driver is being unloaded; the 
	   operational state is disabled(0).
	"
    REFERENCE	
	"OPENSS7-SMI-MIB, ITU-T Rec. X.721 | ISO/IEC 10165-2, 
	     proceduralStatus."
    DEFVAL	{ '00000'B }
    ::= { mxCardEntry 19 }

mxCardAvailabilityStatus OBJECT-TYPE
    SYNTAX	AvailabilityStatus
    MAX-ACCESS	read-only
    STATUS	current
    DESCRIPTION	
	"Provides the availability status of the card following the 
	 AvailabilityStatus textual convention of the OPENSS7-SMI-MIB 
	 module in accordance with the availabilityStatus attribute of 
	 ITU-T Rec. X.721 | ISO/IEC 10165-2.  The availability status is 
	 set-valued and may contain the following:
	 
	 - inTest(0), the card is undergoing a test procedure.  The 
	   administrative state is locked(0) and the operational state 
	   is disabled(1).  This condition exists while the card is 
	   powering up or is being reset.  Not applicable.  The card is 
	   not tested as a whole.
	 
	 - failed(1), the card has an internal fault that prevents it 
	   from operating.  The operational state is disabled.  Some 
	   cards fail when firmware cannot be loaded, or the card cannot 
	   be configured for operation, or some aspect of the hardware 
	   is incompatible with a driver.  The operational state is 
	   disabled.  An alarm will have been generated.
	 
	 - powerOff(2), the card requires power to be applied and is not 
	   powered on.  For example, power managements may have removed 
	   power from the device.  Not applicable.  Some cards do not 
	   support power management.
	 
	 - offLine(3), the card requires a routing operation to be 
	   performed to place it online an make it available for use.  
	   The operation may be manual or automatic, or both.  The 
	   operational state is disabled.  When the card is configured 
	   for use but the transmitters and receivers have been powered 
	   down, the card is considered offline.
	 
	 - offDuty(4), the card has been made inactve by an internal 
	   control process in accordance with a predetermined time 
	   schedule.  Under normal conditions, the control process can 
	   be expected to reactivate the card at some scheduled time.
	 
	 - dependency(5), the card cannot operate because some other 
	   resource on which it depends is unavailable.  Some cards have 
	   the dependency that spans and channels must at least be 
	   partially configured before they are available for use.  This 
	   value is reflected until at least one span and one channel 
	   are configured.
	 
	 - degraded(6), the card is operating with degraded performance.  
	   This is the case when the card is searching for a new 
	   synchronization source and a yellow or red alarm condition 
	   has occurred on the current synchronization source.  Some 
	   cards are degraded when thier spans or circuits are degraded.
	 
	 - notInstalled(7), the card is not present in the system or is 
	   incomplete.  The card does not exist in the system, or the 
	   card exists in the system but is not loaded with a driver.  
	   The operational state is diabled(0).
	 
	 - logFull(8), not used.  Not applicable."
    REFERENCE	
	"OPENSS7-SMI-MIB, ITU-T Rec. X.721 | ISO/IEC 10165-2, 
	     availabilityStatus."
    DEFVAL	{ '000000000'B }
    ::= { mxCardEntry 20 }

mxCardControlStatus OBJECT-TYPE
    SYNTAX	ControlStatus
    MAX-ACCESS	read-create
    STATUS	current
    DESCRIPTION	
	"Provides the control status of the card following the 
	 ControlStatus textual convention of the OPENSS7-SMI-MIB module 
	 and in accordance with the controlStatus attribute of ITU-T 
	 Rec. X.721 | ISO/IEC 10165-2.  The control status is set-valued 
	 and may contain:
	 
	 - subjectToTest(0), the card is available to normal users but 
	   tests may be conducted on it simultaneously at unpredicatble 
	   times, which may cause it to exhibit unusual characteristics 
	   to users.  Not applicable.
	 
	 - partOfServicesLocked(1), when present, a manager has 
	   administratively locked some part of the card.  The card may 
	   exhibit this value when the card is unlocked(1), but one or 
	   more of its spans or channels is locked(1).
	 
	 - reservedForTest(2), when present, the card is undergoing a 
	   test procedures and is unavailable to users.  Not applicable.
	 
	 - suspended(3), when present, service has been administratively 
	   suspended to users.  Not applicable."
    REFERENCE	
	"OPENSS7-SMI-MIB, ITU-T Rec. X.721 | ISO/IEC 10165-2, 
	     controlStatus."
    DEFVAL	{ '0000'B }
    ::= { mxCardEntry 21 }

mxCardUnknownStatus OBJECT-TYPE
    SYNTAX	UnknownStatus
    MAX-ACCESS	read-only
    STATUS	current
    DESCRIPTION	
	"Provides the unknown status of the card following the 
	 UnknownStatus textual convention of the OPENSS7-SMI-MIB module 
	 in accordance with the unknownStatus attribute of ITU-T Rec.  
	 X.721 | ISO/IEC 10165-2.  It indicates whether the values of 
	 other state and status objects for this row are known or not.
	
	 - false(0), the status of the objects is not unknown.
	 - true(1), the status of the objects is unknown.
	"
    REFERENCE	
	"OPENSS7-SMI-MIB, ITU-T Rec. X.721 | ISO/IEC 10165-2, 
	     unknownStatus."
    DEFVAL	{ false }
    ::= { mxCardEntry 22 }

mxCardStandbyStatus OBJECT-TYPE
    SYNTAX	StandbyStatus
    MAX-ACCESS	read-only
    STATUS	current
    DESCRIPTION	
	"Provides the standby status of the card according to the 
	 StandbyStatus textual convention.  This status returns a 
	 standby status when the card has been configured in the system 
	 to act as a backup unit for another card providing service to 
	 the same span.  This is performed by placing the receivers into 
	 high impedance mode, and powering down the transmitters.
	 
	 - hotStandby(0), The receivers are in high impedance mode and 
	   are monitoring the T1/E1/J1 spans, however, the transmitters 
	   are open-circuited.  In this case, the card is syncrhonized 
	   to the incoming frames and ready to be brought into service 
	   by merely powering up the transmitters.
	 
	 - coldStandby(1), Both the receives and the transmitters are 
	   open-circuited, or are connected to a separate facility via a 
	   DACCS or other cross-connect system which will be connected 
	   when a changeover occurs.
	 
	 - providingService(2), Both the receivers and transmitters are 
	   connects and powered up.  The spans on the card are passing 
	   data to and from the wire.
	 
	 There are a number of backup arrangements possible with this 
	 card, however, have an entire card act as a backup for another 
	 entire card is the only way that line synchronization can be 
	 made the same for both cards."
    REFERENCE	
	"OPENSS7-SMI-MIB, ITU-T Rec. X.721 | ISO/IEC 10165-2, 
	     standbyStatus."
    DEFVAL	{ providingService }
    ::= { mxCardEntry 23 }

mxCardSyncSpanId OBJECT-TYPE
    SYNTAX	SpanIdentity
    MAX-ACCESS	read-only
    STATUS	current
    DESCRIPTION	
	"Indicates which card and span is being used as the current 
	 synchronization source for the indexed card.  When the 
	 synchronization source is set to syncSelf(0) or syncExtern(5), 
	 this value will be the null octet string.  When the 
	 synchronization source is set to sync1(1), sync2(2), sync3(3) 
	 or sync4(4), the value will always ben the same as the 
	 identifier of span 1, 2, 3 or 4, respectively, for the indexed 
	 card.  When the synchronization source is set to syncAuto(6), 
	 the value reflectes the identifier of the span currently 
	 providing the synchronization source, or the null octet string 
	 if no span is providing the synchroniation source."
    ::= { mxCardEntry 24 }

mxCardSyncTransitions OBJECT-TYPE
    SYNTAX	Counter32
    MAX-ACCESS	read-only
    STATUS	current
    DESCRIPTION	
	"Indicates the number of times since the last discontinuity that 
	 the synchronization span has transitioned."
    ::= { mxCardEntry 25 }

mxCardName OBJECT-TYPE
    SYNTAX	CommonLanguageName
    MAX-ACCESS	read-only
    STATUS	current
    DESCRIPTION	
	"Provides the name of the card using COMMON LANGUAGE procedures 
	 and the CommonLanguageName textual convention."
    REFERENCE	
	"OPENSS7-TC"
    ::= { mxCardEntry 26 }

mxCardStatus OBJECT-TYPE
    SYNTAX	RowStatus
    MAX-ACCESS	read-only
    STATUS	current
    DESCRIPTION	
	"Provides management stations with the ability to add and delete 
	 rows from the mxCardTable.  All written columns in all rows 
	 are persistent across agent reboot.  Management stations may 
	 add to this table but may not add to the subordinate tables.  
	 Entries in subordinate tables are established automatically by 
	 the agent when a row is created in this table.
	 
	 The primary purpose for allowing management stations to add to 
	 this table is to permit management station to configure cards 
	 that have not yet been installed in the system.
	 
	 Rows cannot be deleted that correspond to physical cards."
    ::= { mxCardEntry 27 }


mxSpan OBJECT IDENTIFIER
    ::= { mxTables 4 }

mxSpanTable OBJECT-TYPE
    SYNTAX	SEQUENCE OF MxSpanEntry
    MAX-ACCESS	not-accessible
    STATUS	current
    DESCRIPTION	
	"The Span Table provides an entry for each of the equipped spans 
	 in the system."
    ::= { mxSpan 1 }

mxSpanEntry OBJECT-TYPE
    SYNTAX	MxSpanEntry
    MAX-ACCESS	not-accessible
    STATUS	current
    DESCRIPTION	
	"Rows are neither created nor deleted explicitly by management 
	 stations but are present inherently as a part of system 
	 operation.  Each entry in the table corresponds to a equipped 
	 and installed span."
    INDEX	{
	mxDrivName,	-- shared index
	mxCardIndex,	-- shared index
	mxSpanIndex
    }
    ::= { mxSpanTable 1 }

MxSpanEntry ::= SEQUENCE {
    mxSpanIndex					Unsigned32,
    mxSpanName					CommonLanguageName,
    mxSpanDevice				RowPointer,
    mxSpanEquipmentId				PhysicalPointOfAppearance,
    mxSpanType					INTEGER,
    mxSpanNumber				SpanNumber,
    mxSpanRate					INTEGER,
    mxSpanMode					BITS,
    mxSpanCrc					INTEGER,
    mxSpanClocking				INTEGER,
    mxSpanPriority				Unsigned32,
    mxSpanCoding				INTEGER,
    mxSpanFraming				INTEGER,
    mxSpanLineImpedance				INTEGER,
    mxSpanLineMode				INTEGER,
    mxSpanLineLength				INTEGER,
    mxSpanLineAttenuation			INTEGER,
    mxSpanLineGain				INTEGER,
    mxSpanLineDelay				Unsigned32,
    mxSpanTxLevel				INTEGER,
    mxSpanRxLevel				INTEGER,
    mxSpanAlarmSettleTime			TimeInterval,
    mxSpanLineCodeTime				TimeInterval,
    mxSpanPrimary				Unsigned32,
    mxSpanDataLink				BITS,
    mxSpanLineCode				INTEGER,
    mxSpanAlarmSeverityMappingProfile		RowPointer,
    mxSpanAdministrativeState			AdministrativeState,
    mxSpanOperationalState			OperationalState,
    mxSpanUsageState				UsageState,
    mxSpanAlarmStatus				AlarmStatus,
    mxSpanProceduralStatus			ProceduralStatus,
    mxSpanAvailabilityStatus			AvailabilityStatus,
    mxSpanControlStatus				ControlStatus,
    mxSpanStandbyStatus				StandbyStatus,
    mxSpanUnknownStatus				UnknownStatus,
    mxSpanSap					RowPointer,
    mxSpanLoopbackStatus			BITS,
    mxSpanLineStatus				BITS,
    mxSpanAlarms				BITS,
    mxSpanEvents				BITS,
    mxSpanReceiveLevel				Unsigned32,
    mxSpanReceiveThreshold			Unsigned32,
    mxSpanRowStatus				RowStatus
}

mxSpanIndex OBJECT-TYPE
    SYNTAX	Unsigned32
    MAX-ACCESS	not-accessible
    STATUS	current
    DESCRIPTION	
	"Provides and index by card of the span.  This is a small 
	 integer from (0..32), where 1 through 32 indicates spans 1 
	 through 32 on the card, and the special index 0 indicates 
	 defaults or settings for the entire card.  Active rows 
	 corresponding to spans can only be added to this table by the 
	 agent.  Management stations can add notinservice rows and 
	 control or configure the span by accessing the read-create 
	 columns for each span entry."
    ::= { mxSpanEntry 1 }

mxSpanName OBJECT-TYPE
    SYNTAX	CommonLanguageName
    MAX-ACCESS	read-create
    STATUS	current
    DESCRIPTION	
	"Provides an optional administrative COMMON LANGUAGE NAME for 
	 the span using the CommonLanguageName textual convention of the 
	 OPENSS7-TC module and in accordance with Telcordia procedures.  
	 This name, when provided, must uniquely identify a row in this 
	 table.  Management station creation requests with names that 
	 have already been assigned to an existing row will be refused 
	 as having an inconsistent value."
    DEFVAL	{ '' }
    ::= { mxSpanEntry 2 }

mxSpanDevice OBJECT-TYPE
    SYNTAX	RowPointer
    MAX-ACCESS	read-create
    STATUS	current
    DESCRIPTION	
	"Specifies a row in a table that models the device or driver 
	 that provides the span.  In some implementations this may model 
	 a pseudo-device driver rather than a hardware device 
	 (equipment) or real device driver.  This identifier must be 
	 specified on row creation (by agent or management station) and 
	 must be a valid device identifier.  For example, for the x400p 
	 driver modelled by the OPENSS7-X400P-MX-MIB, this is a 
	 RowPointer to the x400pCardEntry in the x400pCardTable that 
	 corresponds to the hardware card that provides the span."
    DEFVAL	{ { zeroDotZero } }
    ::= { mxSpanEntry 3 }

mxSpanEquipmentId OBJECT-TYPE
    SYNTAX	PhysicalPointOfAppearance
    MAX-ACCESS	read-create
    STATUS	current
    DESCRIPTION	
	"Provides the equipment identifier that identifies the span 
	 within the device, driver or system.  This equipment identifier 
	 must be specified on row creation and must be a valid equipment 
	 identifier."
    ::= { mxSpanEntry 4 }

mxSpanType OBJECT-TYPE
    SYNTAX	INTEGER {
	none(0), t1(1), e1(2), j1(3), e2(4), e3(5), t3(6) }
    MAX-ACCESS	read-create
    STATUS	current
    DESCRIPTION	
	"Provides the group interface type for the span and the span 
	 type.  This object is single-valued and can have one of the 
	 following values:
	 
	 - none(0), unknown or unspecified (this value cannot be set); 
	   the interface is capable of being placed in any of the modes 
	   and has not yet been configured for one of them;
	 
	 - t1(1), the span is a T1 or DSX1 span;
	 
	 - e1(2), the span is an E1 span;
	 
	 - j1(3), the span is a J1 or DSX1 span;
	 
	 - e2(4), the span is an E1 span in an E2 facility;
	 
	 - e3(5), the span is an E1 span in an E3 facility;
	 
	 - t3(6), the span is a T1 span in a T3 facility.
	 
	 The value none(0) can be read but not written.  When read, the 
	 value none(0) indicates that the equipment is either absent, 
	 not configured, or failed.
	 
	 For some implementations this might be a read-only field.  The 
	 default value if unspecified on row creation is implementation 
	 specific."
    DEFVAL	{ none }
    ::= { mxSpanEntry 5 }

mxSpanNumber OBJECT-TYPE
    SYNTAX	SpanNumber
    MAX-ACCESS	read-create
    STATUS	current
    DESCRIPTION	
	"Specifies the span number within an E2, E3 or T3 facility.  For 
	 simple span types this value is zero.  The agent may supply a 
	 default based on the mxSpanEquipmentId, or may require that 
	 this value be set upon creation."
    ::= { mxSpanEntry 6 }

mxSpanRate OBJECT-TYPE
    SYNTAX	INTEGER (0|1544|2048)
    UNITS	"kilobits per second"
    MAX-ACCESS	read-only
    STATUS	current
    DESCRIPTION	
	"Provides the span unframed syncrhonous bit rate in kilobits per 
	 second.  This is either the T1/J1 rate (1544 kbps) when 
	 configured for T1 or J1, or the E1 rate (2048) when for E1.  
	 Returns zero (0) when the hardware has not yet been configured 
	 for any interface type."
    DEFVAL	{ 0 }
    ::= { mxSpanEntry 7 }

mxSpanMode OBJECT-TYPE
    SYNTAX	BITS {
	local(0), remote(1), framer(2), payload(3) }
    MAX-ACCESS	read-create
    STATUS	current
    DESCRIPTION	
	"Specifies the loopback to apply.  This object may include the 
	 following values:
	 
	 - local(0), payload bits for tranmission from the host 
	   interface are looped back on receive payload bits (data may 
	   be transmitted as normal but the received payload is 
	   discarded);
	 
	 - remote(1), the received serial bit stream is looped back 
	   after the line interface unit to the transmitted serial bit 
	   stream (transmit data from the host is ignored, but received 
	   data may be delivered to the host);
	 
	 - framer(2), the transmitted serial bit stream is looped back 
	   at the framer to the receive serial bit stream (unframed all 
	   ones is transmittted to the line interface and received 
	   information is ignored);
	 
	 - payload(3), the received payload bits are looped back to the 
	   tranmit payload bits at the framer (transmitted data from the 
	   host is ignored, but received data may be delivered to the 
	   host).
	 
	 Only one of framer(2) or payload(3) may be present.  Only one 
	 of local(0) and remote(1) may be present.  local(0) and 
	 framer(2) are only useful for specialized testing.  The span 
	 must have a control status of subjectToTest(0) or 
	 reservedForTest(2) before any values may be added to the set by 
	 a management station.
	 
	 These values represent the loopback condition that has been set 
	 by a management station or locallly as a part of system 
	 operations.  The current loppback condition is reported in the 
	 mxSpanLoopbackStatus object.
	 
	 To request or remote a loopback at the far end, use the 
	 mxSpanLineCode object."
    DEFVAL	{ '0000'B }
    ::= { mxSpanEntry 8 }

mxSpanCrc OBJECT-TYPE
    SYNTAX	INTEGER {
	none(0), crc4(1), crc5(2), crc6(3), crc6j(4) }
    MAX-ACCESS	read-create
    STATUS	current
    DESCRIPTION	
	"Provides the cyclic redundancy check code calculation that is 
	 performed on the framing and the policy for the span.  This 
	 object is single-valued and can assume one of the following 
	 values:
	 
	 - none(0), the span has not yet been configured for a CRC 
	   calculation and the hardware has not yet been enabled;
	 
	 - crc4(1), the span is configured for CRC4 calculation (E1); 
	   CRC4 is used for MF alignment in addition to CRC5 for errored 
	   frames on E1 spans;
	 
	 - crc5(2), the span is configured for CRC5 calculation (E1); 
	   CRC4 is not used for MF alignment, only CRC5 is used for 
	   errored frames on E1 spans (default for E1);
	 
	 - crc6(3), the span is configured for CRC6 calculation (T1); 
	   CRC6 is used on T1 spans;
	 
	 - crc6j(4), the span is configured for CRC6J calculation (J1); 
	   CRC6J is used on J1 spans.
	 
	 Not all values are valid for all span types.  The agent may 
	 refuse settings that conflict with the span type.  It may be 
	 necessary for the span to be in a disabled operational state, 
	 in a locked administrative state, or not in service via the row 
	 status, for the agent to permit changing this value.  The value 
	 may be changed autonomously by the agent when the interface 
	 type is changed.
	 
	 The value none(0) can be read but not written.  When read, the 
	 value none(0) indicates that the equipment is either absent, 
	 not configured, or failed."
    DEFVAL	{ none }
    ::= { mxSpanEntry 9 }

mxSpanClocking OBJECT-TYPE
    SYNTAX	INTEGER {
	none(0), loop(1), local(2), internal(3), external(4), 
	adaptive(5) }
    MAX-ACCESS	read-create
    STATUS	current
    DESCRIPTION	
	"Provides the clock source for the span.  This object is 
	 single-valued and can assume one of the following values:
	 
	 - none(0), the default clocking for the span, or the span has 
	   not yet been configured for clocking, the value is unknown or 
	   unspecified (the span might not be operational while this 
	   value is present);
	 
	 - loop(1), loop clocking: the clock is recovered from the 
	   receive line (e.g. using digital PLL) and used to drive the 
	   transmit clock for the span;
	 
	 - local(2), the timing source is internal to the device (e.g. 
	   provided by a crystal oscillator);
	 
	 - internal(3), internal clocking: the span receives its 
	   clocking from an internal source (i.e. whatever is defined 
	   for the device);
	 
	 - external(4), external clocking: the span receives its 
	   clocking from an external source (e.g. an external timing bus 
	   or timing input);
	 
	 - adaptive(5), clocking is adpated to the DSU side system or 
	   serial bus;
	 
	 Not all values are applicable to all card types.  Not all chip 
	 sets are capable of setting all values.  The agent will refuse 
	 any value that is not possible given the hardware or is 
	 inconsistent with the span type.
	 
	 The value none(0) can be read but not written.  When read, the 
	 value none(0) indicates that the equipment is either absent, 
	 not configured, or failed."
    ::= { mxSpanEntry 10 }

mxSpanPriority OBJECT-TYPE
    SYNTAX	Unsigned32
    MAX-ACCESS	read-create
    STATUS	current
    DESCRIPTION	
	"Specifies or indicates the priority of this span as a timing 
	 source.  When zero(0), this span will not be used as a timing 
	 source.  When non-zero, the recovered receive clock of this 
	 span will be used as the timing source with the priority 
	 given."
    ::= { mxSpanEntry 11 }

mxSpanCoding OBJECT-TYPE
    SYNTAX	INTEGER {
	none(0), ami(1), b6zs(2), b8zs(3), hdb3(4), jbzs(5), zbtsi(6) }
    MAX-ACCESS	read-create
    STATUS	current
    DESCRIPTION	
	"Provides the span line coding for the PCM signal.  This object 
	 is single-valued and can assume one of the following values:
	 
	 - none(0), the value is unknown or unspecified (the span might 
	   not be operational while this value is present);
	 
	 - ami(1), Alternate Mark Inversion (AMI), applicable to all 
	   span types;
	 
	 - b6zs(2), Bipolar with 6 Zero Substitution (B6ZS), applicable 
	   to DS3 span types, not used;
	 
	 - b8zs(3), Bipolar with 8 Zero Substitution (B8ZS), applicable 
	   to, and the default for, T1 and J1 spans;
	 
	 - hdb3(4), High-Density Bipolar 3 (HDB3), applicable to, and 
	   the default for, E1 spans;
	 
	 - jbzs(5), Jammed Bit Zero Suppression (JBZS), applicable to T1 
	   clear channel and E1 CCS spans;
	 
	 - zbtsi(6), Zero Byte Time Slot Interchange (ZBTSI), not used.
	 
	 Not all values are applicable to all span types.  Not all chip 
	 sets are capable of setting all values.  The agent will refuse 
	 any value that is not possible given the hardware or is 
	 inconsistent with the span type.
	 
	 The value none(0) can be read but not written.  When read, the 
	 value none(0), indicates that the equipment is either absent, 
	 not configured, or failed."
    ::= { mxSpanEntry 12 }

mxSpanFraming OBJECT-TYPE
    SYNTAX	INTEGER {
	none(0), ccs(1), cas(2), sf(3), d4(4), esf(5) }
    MAX-ACCESS	read-create
    STATUS	current
    DESCRIPTION	
	"Provides the framing for the span.  This object is 
	 single-valued and can assume one of the following values:
	 
	 - none(0), the framing is unknown or unspecified;
	 
	 - ccs(1), common channel signalling framing for E1 spans (CCS 
	   signalling on TS16 without CAS MF); setting this value causes 
	   the CRC setting to default to crc5(2);
	 
	 - cas(2), channel associated signalling framing for E1 spans 
	   (CAS signalling on TS16 with CAS MF); setting this value 
	   causes the CRC setting to default to crc4(1);
	 
	 - sf(3), super-frame (SF) framing for T1 spans;
	 
	 - d4(4), D4 framing for T1 spans;
	 
	 - esf(5), extended super-frame framing for T1 or J1 spans.
	 
	 Not all values are applicable to all span types.  Not all chip 
	 sets are capable of setting all values.  The agent will refuse 
	 any value that is not possible given the hardware or is 
	 inconsistent with the span type.
	 
	 The value none(0) can be read but not written.  When read, the 
	 value none(0) indicates that the equipment is either absent, 
	 not configured, or failed."
    ::= { mxSpanEntry 13 }

mxSpanLineImpedance OBJECT-TYPE
    SYNTAX	INTEGER {
	none(0), unbalanced75ohm(1), balanced100ohm(2), 
	balanced120ohm(3) }
    MAX-ACCESS	read-create
    STATUS	current
    DESCRIPTION	
	"Specifies and indicates the line impedance of the span.  The 
	 object can have one of the following values:
	 
	 - none(0), unknown or unspecified;
	 
	 - unbalanced75ohm(1), unbalanced 75 Ohms, for E1 spans;
	 
	 - balanced100ohm(2), balanced 100 Ohms, for T1 or J1 spans;
	 
	 - balanced120ohm(3), balanced 120 Ohms, for E1 spans.
	 
	 The value none(0) can be read but not written.  When read, the 
	 value none(0) indicates that the equipment is either absent, 
	 not configured, or failed."
    ::= { mxSpanEntry 14 }

mxSpanLineMode OBJECT-TYPE
    SYNTAX	INTEGER {
	none(0), dsu(1), csu(2), monitor(3) }
    MAX-ACCESS	read-create
    STATUS	current
    DESCRIPTION	
	"Provides the span line mode.  The object can have one of the 
	 following values:
	 
	 - none(0), unknown or unspecified;
	 
	 - dsu(1), data service unit (DSU) application (short-haul E1 
	   and limited long-haul, DSX, T1/J1 spans);
	 
	 - csu(2), channel service unit (CSU) application (long-haul 
	   E1 or T1/J1 span);
	 
	 - monitor(3), high-impedance line monitoring of the span.
	 
	 The value none(0) can be read but not written.  When read, the 
	 value none(0) indicates that the equipment is either absent, 
	 not configured, or failed."
    DEFVAL	{ none }
    ::= { mxSpanEntry 15 }

mxSpanLineLength OBJECT-TYPE
    SYNTAX	INTEGER {
	none(0), dsx133ft(1), dsx266ft(2), dsx399ft(3), dsx533ft(4), 
	dsx666ft(5) }
    MAX-ACCESS	read-create
    STATUS	current
    DESCRIPTION	
	"Provides the line length for T1 DSX operation.  The object can 
	 have one of the following values:
	 
	 - none(0), unknown, unspecified or not applicable;
	 
	 - dsx133ft(1), DSX-1 0 to 133 feet;
	 
	 - dsx266ft(2), DSX-1 133 to 266 feet;
	 
	 - dsx399ft(3), DSX-1 266 to 399 feet;
	 
	 - dsx533ft(4), DSX-1 399 to 533 feet;
	 
	 - dsx666ft(5), DSX-1 533 to 666 feet.
	 
	 The value none(0) can be read but not written.  When read, the 
	 value none(0) indicates that the span is either absent, not 
	 configured or failed.
	 
	 The value is only significant when mxSpanLineMode is set to 
	 dsu(1) for T1 spans."
    DEFVAL	{ dsx133ft }
    ::= { mxSpanEntry 16 }

mxSpanLineAttenuation OBJECT-TYPE
    SYNTAX	INTEGER {
	none(0), csu0dB(1), csu8dB(2), csu15dB(3), csu23db(4) }
    MAX-ACCESS	read-create
    STATUS	current
    DESCRIPTION	
	"Provides the line attenuation for T1 CSU operation.  The object 
	 can have one of the following values:
	 
	 - none(0), unknown, unspecified or not applicable;
	 
	 - csu0dB(1), CSU 0 dB;
	 
	 - csu8dB(2), CSU -7.5 dB;
	 
	 - csu15dB(3), CSU -15 dB;
	 
	 - csu23db(4), CSU -22.5 dB.
	 
	 The value none(0) can be read but not written.  When read, the 
	 value none(0) indicates that the span is either absent, not 
	 configured, or failed.
	 
	 The value is only significant when mxSpanLineMode is set to 
	 csu(2) for T1 spans."
    DEFVAL	{ none }
    ::= { mxSpanEntry 17 }

mxSpanLineGain OBJECT-TYPE
    SYNTAX	INTEGER {
	none(0), mon0dB(1), mon12dB(2), mon20dB(3), mon26dB(4), 
	mon30dB(5), mon32dB(6) }
    MAX-ACCESS	read-create
    STATUS	current
    DESCRIPTION	
	"Specifies and indicates the line gain for monitoring operation.  
	 The object can have one of the following values:
	 
	 - none(0), unknown, unspecified or not applicable;
	 
	 - mon0dB(1), 0 dB linear monitoring gain;
	 
	 - mon12dB(2), 12 dB linear monitoring gain;
	 
	 - mon20dB(3), 20 dB linear monitoring gain;
	 
	 - mon26dB(4), 26 dB linear monitoring gain;
	 
	 - mon30dB(5), 30 dB linear monitoring gain;
	 
	 - mon32dB(6), 32 dB linear monitoring gain.
	 
	 The value none(0) can be read but not written.  When read, the 
	 value none(0) indicates that the span is either absent, not 
	 configured, or failed.
	 
	 The value is only significant when mxSpanLineMode is set to 
	 monitor(3)."
    DEFVAL	{ none }
    ::= { mxSpanEntry 18 }

mxSpanLineDelay OBJECT-TYPE
    SYNTAX	Unsigned32
    UNITS	"microseconds"
    MAX-ACCESS	read-create
    STATUS	current
    DESCRIPTION	
	"Specifies and indicates the line delay in microseconds.  This 
	 can be measured and by maangement stations for the use of users 
	 of the span or channel within the span.
	 
	 When the value is zero (0) it indicates that the loop delay is 
	 unknown."
    DEFVAL	{ 0 }
    ::= { mxSpanEntry 19 }

mxSpanTxLevel OBJECT-TYPE
    SYNTAX	INTEGER {
	open(0), off(1), on(2) }
    MAX-ACCESS	read-create
    STATUS	current
    DESCRIPTION	
	"Specifies whether the transmitters for the span are enabled or 
	 disabled.
	 
	 - open(0), the transmitters are open-circuited.
	 
	 - off(1), the transmitters are disabled.
	 
	 - on(2), the transmitters are enabled.

	 Disabling transmitters is often performed in monitoring modes.  
	 Also, when a span wired as a backup for another span, the 
	 receivers are high-impeadance but the transmitters are directly 
	 connected.  Disabling the transmitters places the span in hot 
	 standby and the span becomes active when the transmitters are 
	 enabled.
	 
	 All chip sets are capable of disabling the transmitters."
    DEFVAL	{ open }
    ::= { mxSpanEntry 20 }

mxSpanRxLevel OBJECT-TYPE
    SYNTAX	INTEGER {
	open(0), off(1), on(2) }
    MAX-ACCESS	read-create
    STATUS	current
    DESCRIPTION	
	"Specifies whether the receivers for the span are enabled or 
	 disabled.
	 
	 - open(1), the receiver is open-circuited.
	 
	 - off(1), the receiver is disabled.
	 
	 - on(2), the receiver is enabled.
	 
	 Disabling of receives does not serve much purpose except to 
	 avoid alarms on spans that are not being used.
	 
	 All chip sets are capable of disabling the receivers."
    DEFVAL	{ open }
    ::= { mxSpanEntry 21 }

mxSpanAlarmSettleTime OBJECT-TYPE
    SYNTAX	TimeInterval
    UNITS	"centiseconds"
    MAX-ACCESS	read-create
    STATUS	current
    DESCRIPTION	
	"After local alarm conditions clear, the driver will continue to 
	 transmit a yellow alarm (T1/J1) or RAI (E1) to the remote 
	 terminal until the local alarm conditions have remained clear 
	 for this period of time.  The default is 5 seconds (500 
	 centiseconds).  This column may be read-only for some systems."
    DEFVAL	{ 500 } -- 5 seconds
    ::= { mxSpanEntry 22 }

mxSpanLineCodeTime OBJECT-TYPE
    SYNTAX	TimeInterval
    UNITS	"centiseconds"
    MAX-ACCESS	read-create
    STATUS	current
    DESCRIPTION	
	"The period of time for which to transmit or expect to receive a 
	 loop-up, loop-down, or spare code.  This value is only 
	 significant for T1 or J1 operation.  The default value is 5 
	 seconds (500 centiseconds).  This column may be read-only for 
	 some systems."
    DEFVAL	{ 500 } -- 5 seconds
    ::= { mxSpanEntry 23 }

mxSpanPrimary OBJECT-TYPE
    SYNTAX	Unsigned32
    MAX-ACCESS	read-create
    STATUS	current
    DESCRIPTION	
	"Provides the primary span index of the span in the system to 
	 which this span is acting as a backup.  When the span is not 
	 acting as a backup (it is a primary span, the default), the 
	 index is set to the null string, an invalid span index. Only 
	 one span in the system may act as a backup to any other span in 
	 the system.  The span index specified must be a primary span 
	 (that is, the primay span must not be backing up another span 
	 and its corrresponding value in this column must be the null 
	 string.
	 
	 The state of the backup span is indicated by the standby status 
	 of the span.  Only the primary span index can be referenced 
	 directly by a service access point."
    ::= { mxSpanEntry 24 }

mxSpanDataLink OBJECT-TYPE
    SYNTAX	BITS {
	ansiT1403(0), aTT54016(1), other(2) }
    MAX-ACCESS	read-create
    STATUS	current
    DESCRIPTION	
	"Provides for the use of a facility data link.  This set may 
	 contain:
	 
	 - ansiT1403(0), present when the ANSI T1.403 protocol issued on 
	   the FDL;
	 
	 - aTT54016(1), present when the AT&T TR54016 protocol is used 
	   on the FDL;
	 
	 - other(2), present when another protocol is used.
	  
	 When the set is empty, no FDL is used."
    ::= { mxSpanEntry 25 }

mxSpanLineCode OBJECT-TYPE
    SYNTAX	INTEGER {
	noCode(1), lineCode(2), payloadCode(3), resetCode(4), 
	testCode(5), unframedAllOnes(6), unframedOneAndZero(7) }
    MAX-ACCESS	read-create
    STATUS	current
    DESCRIPTION	
	"Specifies the line code being tranmitted.  The object can have 
	 values:
	 
	 - noCode(1), no code is being tranmitted: normal or loopback 
	   data is being transmitted if the transmitters are enabled;
	 
	 - lineCode(2), the loop-up line code is being transmitted;
	 
	 - payloadCode(3), the loop-up payload code is being 
	   transmitted;
	 
	 - resetCode(4), the loop-down code is being transmitted;
	 
	 - testCode(5), a BERT code or test pattern is being 
	   transmitted;
	 
	 - unframedAllOnes(6), unframed all ones pattern ('11111111'B), 
	   'out of service indication', is being transmitted;
	 
	 - unframedOneAndZero(7), unframed alternating one and zero 
	   pattern ('10101010'B), 'customer disconnect indication 
	   signal', is being transmitted.
	 
	 The linkCode(2), payloadCode(3) and resetCode(4) settings will 
	 only persist for 5 seconds.  Other settings will persist until 
	 reset."
    DEFVAL	{ noCode }
    ::= { mxSpanEntry 26 }

mxSpanAlarmSeverityMappingProfile OBJECT-TYPE
    SYNTAX	RowPointer
    MAX-ACCESS	read-create
    STATUS	current
    DESCRIPTION	
	"Provides the name of an alarm severity mapping profile to be 
	 used when generating alarm notifications.  When this is the 
	 null string, or when a mapping does not exist, the default 
	 values will be used."
    DEFVAL	{ { zeroDotZero } }
    ::= { mxSpanEntry 27 }

mxSpanAdministrativeState OBJECT-TYPE
    SYNTAX	AdministrativeState
    MAX-ACCESS	read-create
    STATUS	current
    DESCRIPTION	
	"Provides the administrative state of the span following the 
	 AdministrativeState textual convention of the OPENSS7-SMI-MIB 
	 module in accordance with ITU-T Rec. X.721 | ISO/IEC 10165-2.
	 
	 - locked(0), the span is administratively prohibited from 
	   providing service; no user may use the span;
	 
	 - unlocked(1), the span is administratively permitted to 
	   provide service; users may use the span;
	 
	 - shuttingDown(2), the span will be locked(0) once all of its 
	   circuits are no longer in use; existing users can complete 
	   using the span before it is shut down, but no new users may 
	   use the span.
	   
	 The administrative state will transition from shuttingDown(2) 
	 to locked(0)."
    REFERENCE	
	"OPENSS7-SMI-MIB, ITU-T Rec. X.721 | ISO/IEC 10165-2, 
	     administrativeState."
    DEFVAL	{ locked }
    ::= { mxSpanEntry 28 }

mxSpanOperationalState OBJECT-TYPE
    SYNTAX	OperationalState
    MAX-ACCESS	read-only
    STATUS	current
    DESCRIPTION	
	"Provides the operational state of the span following the 
	 OperationalState textual convention of the OPENSS7-SMI-MIB 
	 module in accordance with ITU-T Rec. X.721 | ISO/IEC 10165-2.
	 
	 The operational state is single-valued and may assume one of 
	 the following values:
	 
	 - disabled(0), the span is (and all its circuits are) 
	   inoperable and unable to provide service to users;
	 
	 - enabled(1), the span is partially or fully operable and 
	   available for, or in, use (some or all of its circuits are 
	   operable)."
    REFERENCE	
	"OPENSS7-SMI-MIB, ITU-T Rec. X.721 | ISO/IEC 10165-2, 
	     operationalState."
    ::= { mxSpanEntry 29 }

mxSpanUsageState OBJECT-TYPE
    SYNTAX	UsageState
    MAX-ACCESS	read-only
    STATUS	current
    DESCRIPTION	
	"Provides the usage state of the circuit following the 
	 UsageState textual convention of the OPENSS7-SMI-MIB in 
	 accordance with ITU-T Rec. X.721 | ISO/IEC 10165-2.  The usage 
	 state is single-valued and may assume one of the following 
	 values:
	 
	 - idle(0), neither the span (nor its circuits) are currently in 
	   use; no data is being transferred in the span or its 
	   circuits;
	 
	 - active(1), the span is in use and has sufficient operating 
	   capacity to provide for additional users simultanteously 
	   (e.g. some channels are available);
	 
	 - busy(2), the span is in use and has no spare capacity (i.e. 
	   all channels are in use).
	 
	 If the driver does not support the independent use of channels, 
	 only the values idle(0) and busy(2) are returned."
    REFERENCE	
	"OPENSS7-SMI-MIB, ITU-T Rec. X.721 | ISO/IEC 10165-2, 
	     usageState."
    ::= { mxSpanEntry 30 }

mxSpanAlarmStatus OBJECT-TYPE
    SYNTAX	AlarmStatus
    MAX-ACCESS	read-create
    STATUS	current
    DESCRIPTION	
	"Provides the alarm status of the span following the AlarmStatus 
	 textual convention of the OPENSS7-SMI-MIB module in accordance 
	 with ITU-T Rec. X.721 | ISO/IEC 10165-2.  This object is 
	 set-valued and can contain zero or more of the following 
	 values:
	 
	 - underRepair(0), the span is under repair;
	 
	 - critical(1), a critical alarm is outstanding: one or more 
	   critical alarms indicating a fault have been detected and 
	   have not been cleared.
	 
	 - major(2), a major alarm is outstanding: one or more major 
	   alarms indicating a fault have been detected and have not 
	   been cleared.
	 
	 - minor(3), a minor alarm is outstanding: one or more minor 
	   alarms indicating a fault have beem detected and have not 
	   been cleared.
	 
	 - alarmOutstanding(4), an alarm is outstanding: one or more 
	   alarms have been detected, the condition of which may or may 
	   not be disabling.
	 
	 The presence or absence of an alarm state condition does not 
	 affect the generation of future fault related notifications.  
	 Only underRepair(0) may be added to the set by management 
	 stations.  The remaining alarm statuses can only be removed 
	 from the set by management stations and has the effect of a 
	 manual clearing action, particularly for those alarm conditions 
	 that do not have clearing events."
    REFERENCE	
	"OPENSS7-SMI-MIB, ITU-T Rec. X.721 | ISO/IEC 10165-2, 
	     alarmStatus."
    DEFVAL	{ '00000'B }
    ::= { mxSpanEntry 31 }

mxSpanProceduralStatus OBJECT-TYPE
    SYNTAX	ProceduralStatus
    MAX-ACCESS	read-only
    STATUS	current
    DESCRIPTION	
	"Provides the procedural status of the span following the 
	 ProceduralStatus textual convention of the OPENSS7-SMI-MIB 
	 module in accordance with the proceduralStatus attribute of 
	 ITU-T Rec. X.721 | ISO/IEC 10165-2.  The procedural status is 
	 set-valued and can contain zero or more of the following 
	 values:
	 
	 - initializationRequired(0), the span requires initialization 
	   by the management station before it can perform normal 
	   functions and this procedure has not been initiated.  The 
	   operational state is disabled.
	 
	 - notInitialized(1), the span requires initialization before it 
	   can perform its normal functions and this procedure has not 
	   been initiated.  The span initializes itself autonomously.  
	   The operational state is disabled.
	 
	 - initializing(2), the span requires initialization before it 
	   can perform its normal functions and this procedure has been 
	   initiated but is not yet complete.  When this condition is 
	   present, the initialization requried condition is absent.  
	   The operational state is disabled.
	 
	 - reporting(3), the span is reporting the results of a 
	   procedure.  This condition is applicable to test procedures.
	 
	 - terminating(4), the span is in a termination phase.  If the 
	   resource does not initialize itself autonomously, the 
	   initialization required condition is also present and 
	   operational state is disabled."
    REFERENCE	
	"OPENSS7-SMI-MIB, ITU-T Rec. X.721 | ISO/IEC 10165-2, 
	     proceduralStatus."
    ::= { mxSpanEntry 32 }

mxSpanAvailabilityStatus OBJECT-TYPE
    SYNTAX	AvailabilityStatus
    MAX-ACCESS	read-only
    STATUS	current
    DESCRIPTION	
	"Provides the availability status of the span following the 
	 AvailabilityStatus textual convention of the OPENSS7-SMI-MIB 
	 module in accordance with the availabilityStatus attribute of 
	 ITU-T Rec. X.721 | ISO/IEC 10165-2.  The availability status is 
	 set-valued and can contain zero or more of the following 
	 values:
	 
	 - inTest(0), the span is undergoing a test procedure.  If the 
	   administrative state is locked or shutting down then normal 
	   users are precluded from using the resource and the control 
	   status attribute has the value reservedForTest(2).  Tests 
	   that do not exclude additional uses can be present in any 
	   operational or administrative state but the 
	   reservedForTest(2) condition should not be present.  This 
	   condition is present when the span is in one of the loopback 
	   or test modes.
	 
	 - failed(1), the span has an internal fault that prevents it 
	   from operating (e.g. blue alarm).  The operational state is 
	   disabled.
	 
	 - powerOff(2), the resource requires power to be applied and is 
	   not powered on.  For example, a fuse or other protection 
	   devices is known to have removed power or a low voltage 
	   condition has been detected.  The operational state is 
	   disabled.
	 
	 - offLine(3), the resource requires a routine operation to be 
	   performed to place it online and make it available for use.  
	   The operation may be manual or automatic, or both.  The 
	   operational state is disabled.
	 
	 - offDuty(4), the resource has been made inactive by an 
	   internal control process in accordance with a predetermined 
	   time schedule.  Under normal conditions the control process 
	   can be expected to reactivate the resource at some scheduled 
	   time.  The operational state is enabled or disabled.
	 
	 - dependency(5), the resource cannot operate because of some 
	   other resource on which it depends is unavailable (e.g. the 
	   card is not operational).  The operational state is disabled.
	 
	 - degraded(6), the service available from the resource is 
	   degraded in some respect, such as in speed or operating 
	   capacity.  However, the resource remains available for 
	   service, either because some services are satisfactory or 
	   because degraded service is preferrable to no service at all.  
	   This is the cause for yellow and red alarm conditions on the 
	   carrier.  The operational state is enabled.
	 
	 - notInstalled(7), the resource represented is not present, or 
	   is incomplete.  For example, a card is missing or a span is 
	   not provided by a card.
	 
	 - logFull(8), indicate a log full condition.  This is not 
	   applicable to spans."
    REFERENCE	
	"OPENSS7-SMI-MIB, ITU-T Rec. X.721 | ISO/IEC 10165-2, 
	     availabilityStatus."
    ::= { mxSpanEntry 33 }

mxSpanControlStatus OBJECT-TYPE
    SYNTAX	ControlStatus
    MAX-ACCESS	read-create
    STATUS	current
    DESCRIPTION	
	"Provides the control status of the span following the 
	 ControlStatus textual convention of the OPENSS7-SMI-MIB module 
	 in accordance with the controlStatus attribute of ITU-T Rec. 
	 X.721 | ISO/IEC 10165-2.  The controls status is single-valued 
	 and can assume one of the following values:
	 
	 - subjectToTest(0), the span is available for use but may be 
	   subject to test at unpredictable times and may cause it to 
	   exhibit unusual characteristics to users; the adminitrative 
	   state is unlocked(1).
	 
	 - partOfServicesLocked(1), although the administrative is 
	   unlocked(1), some part of the service is locked (such as 
	   specific channels).
	 
	 - reservedForTest(2), the span is unavailable to normal users 
	   because it is undergoing a test procedure; the administrative 
	   state is locked(0).
	 
	 - suspended(3), service has been administratively suspsended to 
	   users of the resource and does not resume performing services 
	   until the suspended condition is revoked; the administrative 
	   state is unlocked(1)."
    REFERENCE	
	"OPENSS7-SMI-MIB, ITU-T Rec. X.721 | ISO/IEC 10165-2, 
	     controlStatus."
    ::= { mxSpanEntry 34 }

mxSpanStandbyStatus OBJECT-TYPE
    SYNTAX	StandbyStatus
    MAX-ACCESS	read-create
    STATUS	current
    DESCRIPTION	
	"Provides the standby status of the span following the 
	 StandbyStatus textual convention of the OPENSS7-SMI-MIB module 
	 in accordance with the standbyStatus attribute of ITU-T Rec. 
	 X.721 | ISO/IEC 10165-2.  The standby status is single-valued 
	 and may assume one of the following values:
	 
	 - hotStandby(0), the card is synchronizing with the receive 
	   stream but is not providing service (i.e. the transmitters 
	   are off or open-circuited).  Writing this value for a backup 
	   span results in the span assuming a hot standby role.
	 
	 - coldStandby(1), the card has both receiver and transmitters 
	   off.  Writing this value for a backup span results in the 
	   span assuming a cold standby role.
	 
	 - providingService(2), the card responsible for providing 
	   service as a back-up, or is a primary or solitary resource.  
	   This value cannot be written.
	 
	 This value cannot be written for primary or solitary spans.  
	 For backup spans, any value may be written, but the value read 
	 reflects the current state of the backup span.
	 
	 The value will transition from the hotStandby(0) or 
	 coldStandby(1) value to the providingService(2) value should 
	 the primary span to which this span is a backup experiences a 
	 disabling fault condition or is otherwise disabled by a 
	 management station.
	 
	 There are normally two ways that a span can be wired as a 
	 standby: either the receivers are in high-impedance mode and 
	 are tapped onto the same receive line as the primary and the 
	 transmitters are turned off; or the span is on a drop-down 
	 arrangement (through a DCCS) but is receiving OOS signal (blue 
	 alarm)."
    REFERENCE	
	"OPENSS7-SMI-MIB, ITU-T Rec. X.721 | ISO/IEC 10165-2, 
	     standbyStatus."
    DEFVAL	{ providingService }
    ::= { mxSpanEntry 35 }

mxSpanUnknownStatus OBJECT-TYPE
    SYNTAX	UnknownStatus
    MAX-ACCESS	read-only
    STATUS	current
    DESCRIPTION	
	"Provides the unknown status of the span following the 
	 UnknownStatus textual convention of the OPENSS7-SMI-MIB module 
	 in accordance with the unknownStatus attribute of ITU-T Rec. 
	 X.721 | ISO/IEC 10165-2.  It indicates whether the other status 
	 attributes are known or not.
	 
	 - false(0), the status is known and other status attributes are 
	   valid; the value of the other TMN state and status textual 
	   conventions may not reflect the actual state of the span.

	 - true(1), the status is unknown and other status attributes 
	   may be invalid; the value of the other TMN state and status 
	   textual conventions reflects the actual state of the span."
    REFERENCE	
	"OPENSS7-SMI-MIB, ITU-T Rec. X.721 | ISO/IEC 10165-2, 
	     unknownStatus."
    ::= { mxSpanEntry 36 }

mxSpanSap OBJECT-TYPE
    SYNTAX	RowPointer
    MAX-ACCESS	read-only
    STATUS	current
    DESCRIPTION	
	"Indicates the name of the service access point that represents 
	 the user of the entire span.   When the value is the null 
	 string, it indicates that there is no user of the entire span."
    ::= { mxSpanEntry 37 }

mxSpanLoopbackStatus OBJECT-TYPE
    SYNTAX	BITS {
	nearEndInward(0), nearEndLine(1), nearEndFramer(2), 
	nearEndPayload(3), farEndLine(4), farEndPayload(5) }
    MAX-ACCESS	read-only
    STATUS	current
    DESCRIPTION	
	"Provides the current (versus the desired) loopback status of 
	 the span.  This object may contain the following values:
	 
	 - nearEndInward(0), payload bits for transmission overwrite the 
	   receive payload bits;
	 
	 - nearEndLine(1), the received serial bit stream is copied to 
	   the transmit serial bit stream;
	 
	 - nearEndFramer(2), the transmit serial bit stream is copied to 
	   the receive serial bit stream;
	 
	 - nearEndPayload(3), the received payload bits overwrite the 
	   transmit payload bits;
	 
	 - farEndLine(4), the far end is in line loopback;
	 
	 - farEndPayload(5), the far end is in payload loopback.
	 
	 When the object contains no values, the loopback status is 
	 either unknown or no loopback is present.  The two conditions 
	 can be distinguished using the mxSpanUnknownStatus object in 
	 the same row."
    ::= { mxSpanEntry 38 }

mxSpanLineStatus OBJECT-TYPE
    SYNTAX	BITS {
	none(0), rcvFarEndLOF(1), xmtFarEndLOF(2), rcvAIS(3), xmtAIS(4), 
	lossOfFrame(5), lossOfSignal(6), loopbackState(7), t16AIS(8), 
	rcvFarEndLOMF(9), xmtFarEndLOMF(10), rcvTestCode(11), 
	otherFailure(12), uavailSigState(13), netEquipOOS(14), 
	rcvPayloadAIS(15), perfThreshold(16) }
    MAX-ACCESS	read-only
    STATUS	current
    DESCRIPTION	
	"Provides the line status for the span.  This object is 
	 set-valued and can contain the following values:
	 
	 - none(0), only present when no other status is present;
	 
	 - rcvFarEndLOF(1), receiving a far end loss of frame indication 
	   (receiving yellow alarm/RAI);
	 
	 - xmtFarEndLOF(2), transmitting a far end loss of frame 
	   indication (transmitting yellow alarm/RAI);
	 
	 - rcvAIS(3), receiving an AIS indication (receiving blue 
	   alarm/AIS);
	 
	 - xmtAIS(4), transmitting an AIS indication (transmitting blue 
	   alarm/AIS);
	 
	 - lossOfFrame(5), experiencing a receive loss of frame 
	   condition;
	 
	 - lossOfSignal(6), experiencing a receive loss of signal 
	   condition;
	 
	 - loopbackState(7), in a loopback state;
	 
	 - t16AIS(8), receiving an AIS indication in TS16;
	 
	 - rcvFarEndLOMF(9), receiving a far end loss of multiframe 
	   indication (receiving E-bits);
	 
	 - xmtFarEndLOMF(10), transmitting a far end loss of multiframe 
	   indication (transmitting E-bits);
	 
	 - rcvTestCode(11), receiving a test code;
	 
	 - otherFailure(12), other failure (e.g. transitter open 
	   circuit, transmitter short circuit);
	 
	 - uavailSigState(13), in an unavailable signalling state;
	 
	 - netEquipOOS(14), associated network equipment is out of 
	   service;
	 
	 - rcvPayloadAIS(15), receiving a payload AIS;
	 
	 - perfThreshold(16), performance threshold exceeded."
    DEFVAL	{ '00000000000000000'B }
    ::= { mxSpanEntry 39 }

mxSpanAlarms OBJECT-TYPE
    SYNTAX	BITS {
	yellow(0), red(1), blue(2), recovery(3) }
    MAX-ACCESS	read-only
    STATUS	current
    DESCRIPTION	
	"Indicates the current span alarms.  The may contain:
	 
	 - yellow(0), a yellow alarm (T1/J1) or RAI (E1) condition 
	   exists, present while a received yellow alarm or RAI 
	   condition perists;
	 
	 - red(1), a red alarm condition exists, present while a receive 
	   loss of sync or receive carrier loss condition persists;
	 
	 - blue(2), a blue alarm (T1/J1) or AIS (E1) condition exists, 
	   present while a received unframed all-ones condition 
	   persists;
	 
	 - recovery(3), after a read or blue/AIS alarm condition has 
	   cleared, the driver waits for an alarm recovery period 
	   (mxSpanAlarmSettleTime) before clearing the sending of yellow 
	   alarm (T1/J1) or RAI condition (E1), present after the red or 
	   blue/AIS alarms clear while waiting for the alarm recovery 
	   period."
    DEFVAL	{ '0000'B }
    ::= { mxSpanEntry 40 }

mxSpanEvents OBJECT-TYPE
    SYNTAX	BITS {
	rlos(0), frcl(1), rual(2), ryel(3), rra(4), rdma(5), v52lnk(6), 
	lorc(7), lotc(8), lup(9), ldn(10), lspare(11), tocd(12), 
	tcle(13) }
    MAX-ACCESS	read-only
    STATUS	current
    DESCRIPTION	
	"Indicates the current span detected events.  This may contain 
	 the following:
	 
	 - rlos(0), receiver loss of synchronization, present while the 
	   framer is not synchronized to the receive data stream;
	 
	 - frcl(1), framer receive carrier loss, present when a frame 
	   (or second) of consecutive zeros has been detected;
	 
	 - rua1(2), receive unframed all ones, T1 blue alarm, E1 AIS, 
	   present when an unframed all one's code is received;
	 
	 - ryel(3), receive yellow alarm condition, T1 yellow alarm, 
	   present when a yellow alarm is received;
	 
	 - rra(4), receive remote alarm condition, E1 only, present when 
	   a remote alarm is received.
	 
	 - rdma(5), receive distant multiframe alarm condition, E1 only, 
	   present when bit 6 of time slot 16 in frame 
	   0 has been set for two consecutive mutliframes.
	 
	 - v52lnk(6), V5.2 link detected condition, E1 only, present on 
	   detection of a V5.2 link identification signal (G.965).
	 
	 - lorc(7), loss of receive clock condition, present when the 
	   receive clock has not transitioned for one channel time.
	 
	 - lotc(8), loss of transmit clock condition, present when the 
	   TCLK pin has not transitioned for one channel time.
	 
	 - lup(9), loop-up code detected condition, T1 only, present 
	   when the loop-up code is being received.
	 
	 - ldn(10), loop-down code detected condition, T1 only, present 
	   when the loop-down code is being received.
	 
	 - lspare(11), spare code detected condition, T1 only, present 
	   when the spare code is being received.
	 
	 - tocd(12), transmit open circuit detected, present when an 
	   open circuit on the transmit leads is detected.
	 
	 - tcle(13), transmit current limite exceeded, present when the 
	   50mA short circuit current limiter is in effect.
	 
	 Note that some of these conditions are only applicable to T1 
	 operation and some are only applicable to E1 operation.  Not 
	 all devices will report all conditions.  Some conditions may 
	 also cause alarm conditions and notifications."
    DEFVAL	{ '0000000000000'B }
    ::= { mxSpanEntry 41 }

mxSpanReceiveLevel OBJECT-TYPE
    SYNTAX	Unsigned32 (0..600)
    UNITS	"negative tenths of a decibel"
    MAX-ACCESS	read-only
    STATUS	current
    DESCRIPTION	
	"Indicates the receive level in increments of -0.1 dB.  
	 The level indicated is only within the range detected 
	 by the device."
    ::= { mxSpanEntry 42 }

mxSpanReceiveThreshold OBJECT-TYPE
    SYNTAX	Unsigned32 (0..600)
    UNITS	"negative tenths of a decibel"
    MAX-ACCESS	read-create
    STATUS	current
    DESCRIPTION	
	"Specifies or indicates the lowest receive level threshold in 
	 increments of -0.1 dB.  The level indicated by the 
	 mxSpanReceiveLevel is only within the range from 0 to this 
	 value.  When this value returns zero (0), the device is 
	 incapable of providing the receive level."
    ::= { mxSpanEntry 43 }

mxSpanRowStatus OBJECT-TYPE
    SYNTAX	RowStatus
    MAX-ACCESS	read-create
    STATUS	current
    DESCRIPTION	
	"Provides a mechanism whereby management stations may create or 
	 destroy rows in this table.
	 
	 The primary purpose is to permit management stations to 
	 configure cards that have not yet been installed.  Installed 
	 cards will have their rows populated automatically by the 
	 agent.  Management stations may not delete rows that correspond 
	 to installed equipment.  Management stations may not activate 
	 rows that do not correspond to installed equipment."
    ::= { mxSpanEntry 44 }


mxBert OBJECT IDENTIFIER
    ::= { mxTables 5 }

mxBertTable OBJECT-TYPE
    SYNTAX	SEQUENCE OF MxBertEntry
    MAX-ACCESS	not-accessible
    STATUS	current
    DESCRIPTION	
	"The MX BERT table provides a mechanism whereby BERT teseting 
	 can be performed on a span by span basis."
    ::= { mxBert 1 }

mxBertEntry OBJECT-TYPE
    SYNTAX	MxBertEntry
    MAX-ACCESS	not-accessible
    STATUS	current
    DESCRIPTION	
	"Each entry in the table provides an interface to BERT testing 
	 for the span.  Entries exist in this table as a part of system 
	 configuration.  A span whose device hardware or driver does not 
	 support any BERT testing will not have a corresponding entry in 
	 this table."
    INDEX	{
	mxDrivName,	-- shared index
	mxCardIndex,	-- shared index
	mxSpanIndex	-- shared index
    }
    ::= { mxBertTable 1 }

MxBertEntry ::= SEQUENCE {
    mxBertMode					INTEGER,
    mxBertSelect				INTEGER,
    mxBertPattern				OCTET STRING,
    mxBertOperationalState			OperationalState,
    mxBertProceduralStatus			ProceduralStatus,
    mxBertBitCount				Counter32,
    mxBertErrorCount				Counter32
}

mxBertMode OBJECT-TYPE
    SYNTAX	INTEGER {
	none(0), span(1), channel(2), fbit(3) }
    MAX-ACCESS	read-write
    STATUS	current
    DESCRIPTION	
	"Specifies the BERT testing for the span on span types and span 
	 equipment that supports the selected BERT testing.  This object 
	 can have one of the following values:
	 
	 - none(0), no testing will be performed;
	 
	 - span(1), BERT testing will be peformed on the entire span;
	 
	 - channel(2), BERT testing will be performed on the channels 
	   that have been marked for test;
	 
	 - fbit(3), testing will be performed using the F-bit.
	 
	 The value fbit(3) can only be set for T1 or J1 mode spans with 
	 supporting span equipment.  To set span(1), because it disrupts 
	 the entire span, the span must be idle.  To set channel(2), 
	 because it disrupts the selected channels, selected channels 
	 must be idle.
	 
	 Not all values are supported by all spans, and not all values 
	 are supported by all span equipment."
    DEFVAL	{ none }
    ::= { mxBertEntry 1 }

mxBertSelect OBJECT-TYPE
    SYNTAX	INTEGER {
	none(0), pre2E7minus1(1), pre2E9minus1(2), pre2E11minus1(3), 
	pre2E15minus1(4), qrss(5), daly(6), repeating(7), alternating(8) 
	}
    MAX-ACCESS	read-write
    STATUS	current
    DESCRIPTION	
	"Specifies the BERT test pattern selected.  The value can be one 
	 of:
	 
	 - none(0), the test pattern selected is unknown or unspecified;
	 
	 - pre2E7minus1(1), a pseudorandom 127-bit pattern;
	 
	 - pre2E9minus1(2), a pseudorandom 511-bit pattern.
	 
	 - pre2E11minus1(3), a pseudorandom 2047-bit pattern;
	 
	 - pre2E15minus1(4), a pesudorandom 16383-bit pattern;
	 
	 - qrss(5), a pseudorandom QRSS 1048575-bit pattern;
	 
	 - daly(6), a 55-octet (440-bit) daly (ATIS T1.TR25) pattern;
	 
	 - repeating(7), a repeating bit pattern between one and 
	   32 bits long;
	 
	 - alternating(8), an alternating word pattern with 1 to 255 
	   repetitions of one 16-bit word followed by the same number of 
	   repetitions of a second 16-bit word.
	 
	 Not all values are supported by all span types and not all 
	 values are supported by all span equipment."
    DEFVAL	{ none }
    ::= { mxBertEntry 2 }

mxBertPattern OBJECT-TYPE
    SYNTAX	OCTET STRING (SIZE(0..33))
    MAX-ACCESS	read-write
    STATUS	current
    DESCRIPTION	
	"Specifies the BERT pattern to use when the BERT test pattern 
	 selected is repeating(7) or alternating(8).  
	 
	 When the BERT test pattern selected is repeating(7), the first 
	 octet provides the bit length of the pattern (1..32) and the 
	 remaining octets provide the bit pattern itself beginning with 
	 the first bit of the first octet.  The first octet will be 
	 treated modulo 32, with zero (0) mapping to 32, should the 
	 value be outside the valid range (1..32).  For example, the 
	 value 129 will be treated as the length 1.  Bits specified 
	 beyond the number of bits indicated by the bit length are 
	 ignored.
	 
	 When the BERT test pattern selected is alternating(8), the 
	 first octet provides the number of times to repeat each word 
	 (1..255), the second and third octets provides the first word 
	 to alternate, and the fourth and fifth octets provides the 
	 second word to alternate.
	 
	 Note that this value is of no significance when the BERT 
	 pattern selected is other than repeating(7) or alternating(8)."
    DEFVAL	{ '10FFFFFFFF'X }
    ::= { mxBertEntry 3 }

mxBertOperationalState OBJECT-TYPE
    SYNTAX	OperationalState
    MAX-ACCESS	read-only
    STATUS	current
    DESCRIPTION	
	"Specifies the operational state of the test following the 
	 OperationalState textual convention of the OPENSS7-TMN-TC 
	 module in accordance with the operationalState attribute of 
	 ITU-T Rec. X.721 | ISO/IEC 10165-2.
	 
	 The operational state is one of:
	 
	 - disabled(0), the test is unable to provide service to users;
	 
	 - enabled(1), it is partially or fully operable and available 
	   for use."
    REFERENCE	
	"OPENSS7-TMN-TC, ITU-T Rec. X.721 | ISO/IEC 10165-2 
	 operationalState."
    ::= { mxBertEntry 4 }

mxBertProceduralStatus OBJECT-TYPE
    SYNTAX	ProceduralStatus
    MAX-ACCESS	read-only
    STATUS	current
    DESCRIPTION	
	"Indicates the procedure status of BERT testing following the 
	 ProceduralStatus textual convention of the OPENSS7-TMN-TC 
	 module in accordance with the proceduralStatus attribute of 
	 ITU-T Rec. X.721 | ISO/IEC 10165-2.
	 
	 The procedural status is set-valued and may contain the 
	 following:
	 
	 - initializationRequired(0), the test requires initialization 
	   by the management station before it can perform test 
	   functions and this procedure has not been initiated.  The 
	   operational state of the test is disabled.
	 
	 - notInitialized(1), the test requires initialization before it 
	   can perform its test functions and this procedure has not 
	   been initiated.  The test initializes itself autonomously.  
	   The operational state of the test is disabled.
	 
	 - initializing(2), the test requires initialization before it 
	   can perform its test functions and this procedure has been 
	   initiated but is not yet complete.  When this condition is 
	   present, the initialization required condition is absent.  
	   The operational state of the test is disabled.
	 
	 - reporting(3), the test is reporting the results of a 
	   procedure.  The results counts are valid while this value is 
	   present.
	 
	 - terminating(4), the test is in a termination phase.  If the 
	   test does not initialize itself autonomously, the 
	   initialization required condition is also present and 
	   operational state of the test is disabled."
    REFERENCE	
	"OPENSS7-TMN-TC, ITU-T Rec. X.721 | ISO/IEC 10165-2 
	 proceduralStatus."
    ::= { mxBertEntry 5 }

mxBertBitCount OBJECT-TYPE
    SYNTAX	Counter32
    MAX-ACCESS	read-only
    STATUS	current
    DESCRIPTION	
	"Indicates the count of the number of bits tested.  At a 
	 minimum, this counter will wrap every 30 minutes.  This counter 
	 only increments while the BERT receiver is synchronized on the 
	 test pattern."
    ::= { mxBertEntry 6 }

mxBertErrorCount OBJECT-TYPE
    SYNTAX	Counter32
    MAX-ACCESS	read-only
    STATUS	current
    DESCRIPTION	
	"Indicates the count of the number of bits in error.  At a 
	 minimum, this counter will wrap every 30 minutes.  This counter 
	 only increments while the BERT receiver is synchronized on the 
	 test pattern."
    ::= { mxBertEntry 7 }

mxChan OBJECT IDENTIFIER
    ::= { mxTables 6 }

mxChanTable OBJECT-TYPE
    SYNTAX	SEQUENCE OF MxChanEntry
    MAX-ACCESS	not-accessible
    STATUS	current
    DESCRIPTION	
	"The channel table provides an entry for each of the channels 
	 for each card and span in the system."
    ::= { mxChan 1 }

mxChanEntry OBJECT-TYPE
    SYNTAX	MxChanEntry
    MAX-ACCESS	not-accessible
    STATUS	current
    DESCRIPTION	
	"For T1 spans, there can be 24 channels numbered 1 through 24.  
	 For E1 spans there can be 31 channels numbered 1 through 31.  
	 Channels are neither created nor deleted by managemention 
	 stations but exist inherently as a part of system operation.
	 
	 Rows are neither created nor deleted explicitly by management 
	 stations but are present inherently as a part of system 
	 operation.  Each entry in the table corresponds to a channel of 
	 an equipped span."
    INDEX	{
	mxDrivName,	-- shared index
	mxCardIndex,	-- shared index
	mxSpanIndex,	-- shared index
	mxChanIndex
    }
    ::= { mxChanTable 1 }

MxChanEntry ::= SEQUENCE {
    mxChanIndex					Unsigned32,
    mxChanType					INTEGER,
    mxChanFormat				INTEGER,
    mxChanRate					INTEGER,
    mxChanMode					BITS,
    mxChanSap					RowPointer,
    mxChanAdministrativeState			AdministrativeState,
    mxChanOperationalState			OperationalState,
    mxChanUsageState				UsageState,
    mxChanAvailabilityStatus			AvailabilityStatus,
    mxChanControlStatus				ControlStatus,
    mxChanProceduralStatus			ProceduralStatus,
    mxChanAlarmStatus				AlarmStatus,
    mxChanStandbyStatus				StandbyStatus
}

mxChanIndex OBJECT-TYPE
    SYNTAX	Unsigned32 (1..31)
    MAX-ACCESS	not-accessible
    STATUS	current
    DESCRIPTION	
	"Provides a time slot index for the channel.  For T1 and J1 
	 spans, the time slots 1..24 index the corresponding  time slot 
	 in the span.  For E1 spans, the time slot indices 1..31 index 
	 the corresponding time slot in the  span.
	 
	 For E1 operation, TS0 is unusable and does not appear in this 
	 table.  For E1 CAS operation, TS16 is not available to users 
	 for payload but continues to appear in this table.
	 
	 Special semantics channel 0 refers to the characteristics of 
	 all the other channels statistically multiplexed together into 
	 a single virtual channel.  However, this used is deprecated.
	 
	 Management stations do not add or delete rows from this table, 
	 only agents, and then only at boot time."
    ::= { mxChanEntry 1 }

mxChanType OBJECT-TYPE
    SYNTAX	INTEGER {
	none(0), cas(1), ccs(2) }
    MAX-ACCESS	read-write
    STATUS	current
    DESCRIPTION	
	"Specifies whether the channel has channel associated signalling 
	 or common channel signalling.  For T1 or J1 spans, channel 
	 associated signalling implies 56kbps DS0A operation within the 
	 channel; otherwise, 64kbps DS0 operation within the channel is 
	 indicated.  The default is ccs(1).  For E1 CAS operation, 
	 channel 17 (timeslot 16) is unavailable for use."
    DEFVAL	{ ccs }
    ::= { mxChanEntry 2 }

mxChanFormat OBJECT-TYPE
    SYNTAX	INTEGER {
	none(1), ds0a(2), ds0(3), t1(4), j1(5), e1(6) }
    MAX-ACCESS	read-write
    STATUS	current
    DESCRIPTION	
	"
	 - none(1), no specific channel type;
	 - ds0a(2), the channel is a DS0-A channel;
	 - ds0(3), the channel is a DS0 channel;
	 - t1(4), the channel is a full T1 span;
	 - j1(5), the channel is a full J1 span;
	 - e1(6), the channel is a full E1 span.
	"
    ::= { mxChanEntry 3 }

mxChanRate OBJECT-TYPE
    SYNTAX	INTEGER {
	variable(0), kbits56(56), kbits64(64), kbits1536(1536), kbits1984(1984) }
    UNITS	"kilobits per second"
    MAX-ACCESS	read-write
    STATUS	current
    DESCRIPTION	
	"Indicates the bit rate of the channel.  Channels 1..24 for T1 
	 and J1 can be 56 or 64 kbps.  Channels 1..31 for E1 are 64 kbps 
	 but can be artificially placed into 56 kbps mode.  The default 
	 is 64kbps for E1 and T1 ccs(3) channels; 56kbps for T1 cas(2) 
	 channels.
	 
	 - variable(0), the channel bit rate is variable;
	 
	 - kbits56(56000), the channel bit rate is 56 kbits per second;
	 
	 - kbits64(64000), the channel bit rate is 65 kbits per second;
	 
	 - kbits1536(1536000), the channel bit rate is 1536 kbits per 
	   second;
	 
	 - kbits1984(1984000), the channel bit rate is 1984 kbits per 
	   second.
	"
    ::= { mxChanEntry 4 }

mxChanMode OBJECT-TYPE
    SYNTAX	BITS {
	remoteLoopback(0), localLoopback(1), test(2), loopbackEcho(3) }
    MAX-ACCESS	read-write
    STATUS	current
    DESCRIPTION	
	"Provides the channel mode.  This object is set-valued and may 
	 contain zero or more of the following values:
	 
	 - remoteLoopback(0), the channel is in remote loopback mode; 
	   the receive data in the channel is looped back to replace the 
	   transmit data for the channel.  This may either be 
	   accomplished within the host or using the per-channel 
	   loopback capability of the chip sets.
	 
	 - localLoopback(1), the channel is in local loopback mode; the 
	   transmit data for the channel is looped back to replace the 
	   receive data for the channel.  This may is accomplished 
	   within the host.
	 
	 - test(2), the channel is marked for BERT testing.  When BERT 
	   testing for the span is enabled on a channel basis, this 
	   channel will be included in the channels upon which the BERT 
	   test pattern is transmitted.
	 
	 - loopbackEcho(3), the channel is in local loopback and echo 
	   mode;
	 
	 Because these tests are disruptive, no value can be added to 
	 this set unless the channel has a control status of 
	 subjectToTest(0) or reservedForTest(2)."
    ::= { mxChanEntry 5 }

mxChanSap OBJECT-TYPE
    SYNTAX	RowPointer
    MAX-ACCESS	read-only
    STATUS	current
    DESCRIPTION	
	"Indicates the name of the service access point that represents 
	 the user of the channel.  When the value is the null string, it 
	 indicates that there is no user of the channel."
    ::= { mxChanEntry 6 }

mxChanAdministrativeState OBJECT-TYPE
    SYNTAX	AdministrativeState
    MAX-ACCESS	read-write
    STATUS	current
    DESCRIPTION	
	"Provides the administrative state of the channel following the 
	 AdministrativeState textual convention of the OPENSS7-SMI-MIB 
	 module in accordance with the administrativeState attribute of 
	 ITU-T Rec. X.721 | ISO/IEC 10165-2.  The state can be one of 
	 the following:
	 
	 - locked(0), the channel is administratively prohibited from 
	   providing service to users;
	 
	 - unlocked(1), the channel is administratively permitted to 
	   provide service to users;
	 
	 - shuttingDown(2), the channel is shutting down and will move 
	   to the locked state once is it idle: the channel will 
	   continue to provide service to existing users but will reject 
	   new users: once there are no more users of the channel, the 
	   channel will move to the locked state.
	 
	 The administrative state can be changed to shuttingDown(2) or 
	 locked(0) by a management station (either NMS or EMS)."
    REFERENCE	
	"OPENSS7-SMI-MIB, ITU-T Rec. X.721 | ISO/IEC 10165-2, 
	     administrativeState."
    DEFVAL	{ locked }
    ::= { mxChanEntry 7 }

mxChanOperationalState OBJECT-TYPE
    SYNTAX	OperationalState
    MAX-ACCESS	read-only
    STATUS	current
    DESCRIPTION	
	"Provides the operational state of the channel following the 
	 OperationalState textual convention of the OPENSS7-SMI-MIB and 
	 ITU-T Rec. X.721 | ISO/IEC 10165-2.  The state can be one of 
	 the following:
	 
	 - disabled(0), the channel is not operational;
	 - enabled(1), the channel is operational.
	 
	 The operational state of the channel is changed only by the 
	 managed system."
    REFERENCE	
	"OPENSS7-SMI-MIB, ITU-T Rec. X.721 | ISO/IEC 10165-2, 
	 operationalState."
    DEFVAL	{ 0 } -- disabled
    ::= { mxChanEntry 8 }

mxChanUsageState OBJECT-TYPE
    SYNTAX	UsageState
    MAX-ACCESS	read-only
    STATUS	current
    DESCRIPTION	
	"Provides the usage state of the channel following the 
	 UsageState textual convention of the OPENSS7-SMI-MIB module in 
	 accordances with the usageState attribute of  ITU-T Rec. X.721 
	 | ISO/IEC 10165-2.  The state can be one of the following:
	 
	 - idle(0), the channel is not currently in use;
	 
	 - active(1), the channel is in use and has sufficient operating 
	   capacity to provide for additional users simultaneously (e.g. 
	   a half-channel is used);
	 
	 - busy(2), the channel is in use and has no spare capacity 
	   (i.e. the full channel is in use).
	  
	 If partial channels are not supported, only the values idle(0) 
	 and busy(2) are returned.
	 
	 The usage state of the channel is changed only by the managed 
	 system."
    REFERENCE	
	"OPENSS7-SMI-MIB, ITU-T Rec. X.721 | ISO/IEC 10165-2, 
	     usageState."
    ::= { mxChanEntry 9 }

mxChanAvailabilityStatus OBJECT-TYPE
    SYNTAX	AvailabilityStatus
    MAX-ACCESS	read-only
    STATUS	current
    DESCRIPTION	
	"Provides the availability status of the channel following the 
	 AvailabilityStatus textual convention of the OPENSS7-SMI-MIB 
	 module in accordance with the availabilityStatus attribute of 
	 ITU-T Rec. X.721 | ISO/IEC 10165-2.  The availability status is 
	 set-valued and may contain the following values:
	 
	 - inTest(0), the channel is undergoing a test procedure.  The 
	   administrative state is locked(0) and the operational state 
	   is disabled(1).  This condition exists while the span is in 
	   test in a manner diruptive to the channel, or when the 
	   channel is in loopback or test mode.
	 
	 - failed(1), the channel has an internal fault that prevents it 
	   from operating.  The operational state is disabled.  This 
	   value is present when the same value is present in the span 
	   availability status.
	 
	 - powerOff(2), the channel requires power to be applied and is 
	   not powered on.  For example, power managements may have 
	   removed power from the device.  This value is present when 
	   the same value is present in the span availability status.
	 
	 - offLine(3), the channel requires a routing operation to be 
	   performed to place it online and make it available for use.  
	   The operation may be manual or automatic, or both.  The 
	   operational state is disabled.  This value is present when 
	   the same value is present in the span availability status.
	 
	 - offDuty(4), the channel has been made inactive by an internal 
	   control process in accordance with a predetermined time 
	   schedule.  Under normal conditions, the control process can 
	   be expected to reactivate the channel at some scheduled time.
	 
	 - dependency(5), the channel cannot operate because some other 
	   resource on which it depends is unavailable (e.g. the span).
	 
	 - degraded(6), the channel is operating with degraded 
	   performance.  This value is present when the same value is 
	   present in the span availability status.
	 
	 - notInstalled(7), the channel is not present in the system or 
	   is incomplete.
	 
	 - logFull(8), not used.
	 
	 The availabiltiy status of the channel is changed only by the 
	 managed system."
    REFERENCE	
	"OPENSS7-SMI-MIB, ITU-T Rec. X.721 | ISO/IEC 10165-2, 
	     availabilityStatus."
    ::= { mxChanEntry 10 }

mxChanControlStatus OBJECT-TYPE
    SYNTAX	ControlStatus
    MAX-ACCESS	read-write
    STATUS	current
    DESCRIPTION	
	"Provides the control status of the channel following the 
	 ControlStatus textual convention of the OPENSS7-SMI-MIB module 
	 in accordance with the controlStatus attribute of ITU-T Rec. 
	 X.721 | ISO/IEC 10165-2.  The control status is set-valued and 
	 read-write and may contain the following values:
	 
	 - subjectToTest(0), the channel is available to normal users, 
	   but tests may be conducted on it simultaneously at 
	   unpredictable times, which may cause it to exhibit unusual 
	   characteristics to users;
	 
	 - partOfServicesLocked(1), when present, a manager has 
	   administratively locked some part of the channel;
	 
	 - reservedForTest(2), the channel has been made 
	   administratively unavailable to normal users because it is 
	   undergoing a test procedure (e.g. BERT testing): the 
	   administrative state is locked;
	 
	 - suspended(3), service by the channel is suspended but the 
	   administrative state is unlocked: the resource may remember 
	   the user of the resource; for channels this has the effect of 
	   temporarily disconnecting the channel.
	 
	 On of the primary uses of the control status is to permit 
	 management stations to mark channels as subject to test or 
	 reserved for test so that when a BERT test is activated on the 
	 span, the channels marked for test are included in the BERT 
	 test."
    REFERENCE	
	"OPENSS7-SMI-MIB, ITU-T Rec. X.721 | ISO/IEC 10165-2, 
	     controlStatus."
    ::= { mxChanEntry 11 }

mxChanProceduralStatus OBJECT-TYPE
    SYNTAX	ProceduralStatus
    MAX-ACCESS	read-only
    STATUS	current
    DESCRIPTION	
	"Provides the procedural status of the channel following the 
	 ProceduralStatus textual convention of the OPENSS7-SMI-MIB and 
	 ITU-T Rec. X.721 | ISO/IEC 10165-2.  The status can contain 
	 zero or more of the following:
	 
	 - initializationRequired(0),
	 - notInitialized(1),
	 - initializing(2),
	 - reporting(3),
	 - terminating(4),
	 
	 The procedural status of the channel is changed only by the 
	 managed system."
    REFERENCE	
	"OPENSS7-SMI-MIB, ITU-T Rec. X.721 | ISO/IEC 10165-2, 
	     proceduralStatus."
    ::= { mxChanEntry 12 }

mxChanAlarmStatus OBJECT-TYPE
    SYNTAX	AlarmStatus
    MAX-ACCESS	read-write
    STATUS	current
    DESCRIPTION	
	"Provides the alarm state of the channel following the 
	 AlarmStatus textual convention of the OPENSS7-SMI-MIB and ITU-T 
	 Rec. X.721 | ISO/IEC 10165-2.  The status can contain zero or 
	 more of the following:
	 
	 - underRepair(0), the channel is under repair;
	 - critical(1), a critical alarm is oustanding;
	 - major(2), a major alarm is outstanding;
	 - minor(3), a minor alarm is outstanding;
	 - alarmOutstanding(4), an alarm is outstanding.
	 
	 Management stations can set underRepair(0) or clear an alarm."
    REFERENCE	
	"OPENSS7-SMI-MIB, ITU-T Rec. X.721 | ISO/IEC 10165-2, 
	     alarmStatus."
    ::= { mxChanEntry 13 }

mxChanStandbyStatus OBJECT-TYPE
    SYNTAX	StandbyStatus
    MAX-ACCESS	read-only
    STATUS	current
    DESCRIPTION	
	"
	 - hotStandby(0),
	 - coldStandby(1),
	 - providingService(2),
	"
    REFERENCE	
	"OPENSS7-SMI-MIB, ITU-T Rec. X.721 | ISO/IEC 10165-2, 
	     standbyStatus."
    DEFVAL	{ providingService }
    ::= { mxChanEntry 14 }

mxXcon OBJECT IDENTIFIER
    ::= { mxTables 7 }

mxXconTable OBJECT-TYPE
    SYNTAX	SEQUENCE OF MxXconEntry
    MAX-ACCESS	not-accessible
    STATUS	current
    DESCRIPTION	
	"The cross-connect table provides a 1-1 and 0-0 cross connect 
	 capability."
    ::= { mxXcon 1 }

mxXconEntry OBJECT-TYPE
    SYNTAX	MxXconEntry
    MAX-ACCESS	not-accessible
    STATUS	current
    DESCRIPTION	
	"Each entry in the cross-connect table describes either a 1-1 
	 cross-connect or a 0-0 cross-connect.  When the channel indices 
	 are both zero, the entry describes a 1-1 cross-connect; when 
	 both non-zero, a 0-0 cross-connect.  When the both span and 
	 both channel indices are the same, the entry describes either a 
	 1-1 loopback or a 0-0 loopback.
	 
	 Entries in the table can be created and deleted by management 
	 stations.  Entries may also be created or delete autonomously 
	 as a part of system operation.  Management stations may only 
	 create and delete entries that correspond to permanent or 
	 semi-permanent connections.  As a part of system operation, 
	 permanent, semi-permanent, or switched connections may be 
	 created or deleted autonomously.
	 
	 Entries created or deleted by management stations typically 
	 survive an agent and system reboot, however, the storage type 
	 can be used to alter this behaviour."
    INDEX	{
	mxDrivName,	-- shared index
	mxCardIndex,	-- shared index
	mxSpanIndex,	-- shared index
	mxChanIndex	-- shared index
    }
    ::= { mxXconTable 1 }

MxXconEntry ::= SEQUENCE {
    mxXconCardIndex				Unsigned32,
    mxXconSpanIndex				Unsigned32,
    mxXconChanIndex				Unsigned32,
    mxXconType					INTEGER,
    mxXconStorageType				StorageType,
    mxXconRowStatus				RowStatus
}

mxXconCardIndex OBJECT-TYPE
    SYNTAX	Unsigned32
    MAX-ACCESS	read-create
    STATUS	current
    DESCRIPTION	
	"Provides the index of the card to which the cross-connected 
	 span belongs."
    ::= { mxXconEntry 1 }

mxXconSpanIndex OBJECT-TYPE
    SYNTAX	Unsigned32
    MAX-ACCESS	read-create
    STATUS	current
    DESCRIPTION	
	"Provides the index of the span which is cross-connected to the 
	 indexed span."
    ::= { mxXconEntry 2 }

mxXconChanIndex OBJECT-TYPE
    SYNTAX	Unsigned32 (0..31)
    MAX-ACCESS	read-create
    STATUS	current
    DESCRIPTION	
	"Provides the channel number of the channel to which the indexed 
	 span and channel is cross-connected."
    ::= { mxXconEntry 3 }

mxXconType OBJECT-TYPE
    SYNTAX	INTEGER {
	switched(1), semiPermanent(2), permanent(3) }
    MAX-ACCESS	read-create
    STATUS	current
    DESCRIPTION	
	"Specifies and indicates the type of connection.  The value may 
	 be one of:
	 
	 - switched(1), connection is a switch connection;
	 
	 - semiPermanent(2), connection is a semi-permanent connection;
	 
	 - permanent(3), connection is a permanent connection.
	 
	 Switched connections cannot be created by management stations 
	 (but the agent may support management station deletion of 
	 switch connections).  Management stations may create and delete 
	 semi-permanent and permanent connections."
    DEFVAL	{ permanent }
    ::= { mxXconEntry 4 }

mxXconStorageType OBJECT-TYPE
    SYNTAX	StorageType
    MAX-ACCESS	read-create
    STATUS	current
    DESCRIPTION	
	"Provides the memory realization of a conceptual row.  Possible 
	 values are:
	 
	 - volatile(2), the row is lost upon reboot, applicable to 
	   switched, semi-permanent and permanent connections;
	  
	 - nonVolatile(3), the row is not lost upon reboot, applicable 
	   to semi-permanent and permanent connections."
    DEFVAL	{ nonVolatile }
    ::= { mxXconEntry 5 }

mxXconRowStatus OBJECT-TYPE
    SYNTAX	RowStatus
    MAX-ACCESS	read-create
    STATUS	current
    DESCRIPTION	
	"Provides a mechanism whereby management stations can explicitly 
	 create and delete rows in this table.  Management stations 
	 cannot explicitly create a switched connection type but may 
	 explicitly delete all connection types.  Rows may be created or 
	 deleted implicitly as a part of system operations.  Rows cannot 
	 be created that would form a connection to a span and channel 
	 which is already engaged in another connection, the other 
	 connection must first be deleted.  Rows may not be taken out of 
	 service."
    ::= { mxXconEntry 6 }


-- ====================================================================
-- SCALARS
-- ====================================================================

mxScalars OBJECT IDENTIFIER
    ::= { mxObjects 2 }

mxDiscontinuityTime OBJECT-TYPE
    SYNTAX	TimeStamp
    MAX-ACCESS	read-only
    STATUS	current
    DESCRIPTION	
	"Provides the uptime of the last discontinuity."
    ::= { mxScalars 1 }


mxNotifs OBJECT IDENTIFIER
    ::= { mxObjects 3 }

mxOids OBJECT IDENTIFIER
    ::= { mxObjects 4 }

-- ====================================================================
-- CARD TYPES
-- ====================================================================
--
-- Cards can largely be identifier by their PCI information in Chip 
-- numbers, but theses are some autonomous types that permit the MIB to 
-- be extended without changing it when a new card comes along.
--

mxCardTypes OBJECT IDENTIFIER
    ::= { mxOids 1 }

mxCardTypePLX9030 OBJECT-IDENTITY
    STATUS	current
    DESCRIPTION	
	"This the the PLX 90303 board resulting from finding '9030'X in 
	 the PCI id.  This is a card that has not has the correct PCI Id 
	 burnt into it."
    ::= { mxCardTypes 1 }

mxCardTypePLXDevelopmentBoard OBJECT-IDENTITY
    STATUS	current
    DESCRIPTION	
	"This is a PLX development board as identified by the PCI Id 
	 '3001'X."
    ::= { mxCardTypes 2 }

mxCardTypeX400P OBJECT-IDENTITY
    STATUS	current
    DESCRIPTION	
	"This is an old Digium X400P card as identified by its PCI Id 
	 'D00D'X.  The next position below this arc identifies whether 
	 it is a T1 card or an E1 card.  If there is nothing below this 
	 arc, the card supports both E1 and T1 modes.  These cards were 
	 discontinued when Digium decided to force upgrade everyone to a 
	 TE410 card."
    ::= { mxCardTypes 3 }

mxCardTypeE400P OBJECT-IDENTITY
    STATUS	current
    DESCRIPTION	
	"This is an old Digium E400P card as identifier by its PCI Id 
	 'D00D'X.  The card reports a DS2154, DS21354, DS21554 Dallas 
	 chip indicating that this is an E1 card.  This card does not 
	 support a T1 mode. It also does not support some of the 
	 snazzier features.  These cards were discontinued when Digium 
	 decided to force upgrade everyone to a TE410 card."
    ::= { mxCardTypeX400P 1 }

mxCardTypeT400P OBJECT-IDENTITY
    STATUS	current
    DESCRIPTION	
	"This is the old Digium T400P card as identified by its PCI Id 
	 'D00D'X.  The card reporets a DS2152, DS21352, DS21552 Dallas 
	 chip indicating that this ia a T1 card.  This card does not 
	 support an E1 mode. It also does not support some of the 
	 snazzier features.  These cards were discontinued when Digium 
	 decided to force upgrade everyone to a TE410 card."
    ::= { mxCardTypeX400P 2 }

mxCardTypeX400P-SS7 OBJECT-IDENTITY
    STATUS	current
    DESCRIPTION	
	"This is an old OpenSS7 X400P-SS7 card as identified by its PCI 
	 Id '0557'X. The next position below this arc identifies whether 
	 this is a T1 card or an E1 card.  If there is nothing below 
	 this arc, the card supports both E1 and T1.  These cards were 
	 discontinued when Digium decided to force upgrade everyone to a 
	 TE410 card."
    ::= { mxCardTypes 4 }

mxCardTypeE400P-SS7 OBJECT-IDENTITY
    STATUS	current
    DESCRIPTION	
	"This is an old OpenSS7 E400P-SS7 card as identified by its PCI 
	 Id '0557'X.  These are electically equivalent to the E400P 
	 card.  The card reports a DS2154, DS21354 or DS21554 Dallas 
	 chip indicating that this is an E1 card.  This card does not 
	 support a T1 mode.  It also does not support some othe snazzier 
	 features.  These cards were discontinued when Digium decided to 
	 force upgrade everyone to a TE410 card."
    ::= { mxCardTypeX400P-SS7 1 }

mxCardTypeT400P-SS7 OBJECT-IDENTITY
    STATUS	current
    DESCRIPTION	
	"This is an old OpenSS7 T400P-SS7 card as identified by its PCI 
	 Id '0557'X.  These are electically equivalent to the T400P 
	 card.  The card reports a DS2152, DS21352 or DS21552 Dallas 
	 chip indicating that this is a T1 card.  This card does not 
	 support an E1 mode.  It also does not support some othe 
	 snazzier features.  These cards were discontinued when Digium 
	 decided to force upgrade everyone to a TE410 card."
    ::= { mxCardTypeX400P-SS7 2 }

mxCardTypeV400P OBJECT-IDENTITY
    STATUS	current
    DESCRIPTION	
	"This is a old Varion V400P card as identified by its PCI id 
	 '4000'X.  The next position below this arc identifies whether 
	 this is a T1 card or an E1 card.  If there is nothing below 
	 this arc, the card supports both E1 and T1.  These cards were 
	 discontinued by Varion due to excessive lead content compared 
	 to newer European standards."
    ::= { mxCardTypes 5 }

mxCardTypeV400PE OBJECT-IDENTITY
    STATUS	current
    DESCRIPTION	
	"This is an old Varion V400PE card as identified by its PCI id 
	 '4000'X.  These cards sometimes have a E1 only chip and 
	 sometimes have a chip that does both E1 and T1.  Some of the 
	 E1/T1 chips can be configured for J1.  These cards are treated 
	 as E1 only.  These cards were discontinued by Varion due to 
	 excessive lead content compared to newer European standards."
    ::= { mxCardTypeV400P 1 }

mxCardTypeV400PT OBJECT-IDENTITY
    STATUS	current
    DESCRIPTION	
	"This is an old Varion V400PT card as identified by its PCI id 
	 '4000'X.  These cards sometimes have a T1 only chip and 
	 sometimes have a chip that does both E1 and T1.  Some of the 
	 E1/T1 chips can be configured for J1.  These cards are treated 
	 as T1 only.  These cards were discontinued by Varion due to 
	 excessive lead content compared to newer European standards."
    ::= { mxCardTypeV400P 2 }

mxCardTypeV401PE OBJECT-IDENTITY
    STATUS	current
    DESCRIPTION	
	"This is a current Varion V401PE card as identified by its PCI 
	 id 'D33D'X.  Unfortunately, even though it reports itself as an 
	 E1 card, most of these cards are electrically identical to the 
	 T1 card, just reporting a different PCI Id.  The chips support 
	 E1/T1/J1 and can be configured for any mode of operation, 
	 typically on a card by card basis and sometimes on a span by 
	 span basis."
    ::= { mxCardTypes 6 }

mxCardTypeV401PT OBJECT-IDENTITY
    STATUS	current
    DESCRIPTION	
	"This is a current Varion V401PT card as identified by its PCI 
	 id 'D44D'X.  Unfortunately, even though it reports itself as a 
	 T1 card, most of these cards are electrically identical to the 
	 E1 card, just reporting a different PCI Id.  The chips support 
	 E1/T1/J1 and can be configured for any mode of operation, 
	 typically on a card by card basis and sometimes on a span by 
	 span basis."
    ::= { mxCardTypes 7 }

-- ====================================================================
-- CHIP TYPES
-- ====================================================================

mxChipTypes OBJECT IDENTIFIER
    ::= { mxOids 2 }

mxChipTypeDS2152 OBJECT-IDENTITY
    STATUS	current
    DESCRIPTION	
	"The Dallas DS2152 T1 framer chip."
    ::= { mxChipTypes 1 }

mxChipTypeDS21352 OBJECT-IDENTITY
    STATUS	current
    DESCRIPTION	
	"The Dallas DS21352 Quad T1 framer chip."
    ::= { mxChipTypes 2 }

mxChipTypeDS21552 OBJECT-IDENTITY
    STATUS	current
    DESCRIPTION	
	"The Dallas DS21552 Quad T1 framer chip."
    ::= { mxChipTypes 3 }

mxChipTypeDS2154 OBJECT-IDENTITY
    STATUS	current
    DESCRIPTION	
	"The Dallas DS2154 E1 framer chip."
    ::= { mxChipTypes 4 }

mxChipTypeDS21354 OBJECT-IDENTITY
    STATUS	current
    DESCRIPTION	
	"The Dallas DS21354 Quad T1 framer chip."
    ::= { mxChipTypes 5 }

mxChipTypeDS21554 OBJECT-IDENTITY
    STATUS	current
    DESCRIPTION	
	"The Dallas DS21554 Quad T1 framer chip."
    ::= { mxChipTypes 6 }

mxChipTypeDS2155 OBJECT-IDENTITY
    STATUS	current
    DESCRIPTION	
	"The Dallas DS2155 E1/T1/J1 framer chip."
    ::= { mxChipTypes 7 }

mxChipTypeDS2156 OBJECT-IDENTITY
    STATUS	current
    DESCRIPTION	
	"The Dallas DS2156 E1/T1/J1 framer chip."
    ::= { mxChipTypes 8 }


mxStats OBJECT IDENTIFIER
    ::= { mxObjects 5 }

mxNearEndStats OBJECT IDENTIFIER
    ::= { mxStats 1 }

mxNearEndCurrent OBJECT IDENTIFIER
    ::= { mxNearEndStats 1 }

mxNearEndCurrentTable OBJECT-TYPE
    SYNTAX	SEQUENCE OF MxNearEndCurrentEntry
    MAX-ACCESS	not-accessible
    STATUS	current
    DESCRIPTION	
	"Provides a table of near end current statistic."
    ::= { mxNearEndCurrent 1 }

mxNearEndCurrentEntry OBJECT-TYPE
    SYNTAX	MxNearEndCurrentEntry
    MAX-ACCESS	not-accessible
    STATUS	current
    DESCRIPTION	
	"Each entry in this table provides the current accumulation of 
	 near end performance statistics for a given span.  Spans that 
	 do not support the far end reporting of performance 
	 measurements will not have an associated entry in this table."
    INDEX	{
	mxDrivName,	-- shared index
	mxCardIndex,	-- shared index
	mxSpanIndex	-- shared index
    }
    ::= { mxNearEndCurrentTable 1 }

MxNearEndCurrentEntry ::= SEQUENCE {
    mxNearEndCurrentTimeElapsed			HCPerfTimeElapsed,
    mxNearEndCurrentESs				PerfCurrentCount,
    mxNearEndCurrentSESs			PerfCurrentCount,
    mxNearEndCurrentSEFSs			PerfCurrentCount,
    mxNearEndCurrentUASs			PerfCurrentCount,
    mxNearEndCurrentCSSs			PerfCurrentCount,
    mxNearEndCurrentPCVs			PerfCurrentCount,
    mxNearEndCurrentLESs			PerfCurrentCount,
    mxNearEndCurrentBESs			PerfCurrentCount,
    mxNearEndCurrentDMs				PerfCurrentCount,
    mxNearEndCurrentLCVs			PerfCurrentCount
}

mxNearEndCurrentTimeElapsed OBJECT-TYPE
    SYNTAX	HCPerfTimeElapsed
    UNITS	"seconds"
    MAX-ACCESS	read-only
    STATUS	current
    DESCRIPTION	
	"The number of seconds that have elapsed in the current 
	 measurement period."
    ::= { mxNearEndCurrentEntry 1 }

mxNearEndCurrentESs OBJECT-TYPE
    SYNTAX	PerfCurrentCount
    UNITS	"seconds"
    MAX-ACCESS	read-only
    STATUS	current
    DESCRIPTION	
	"The number of Errored Seconds (ESs) in the current interval.  
	 An Errored Second has one or more Path Code Violations, one or 
	 more Out of Frame defects, one or more Controlled Slip events, 
	 or a detected Alarm Indication Signal (AIS) defect."
    ::= { mxNearEndCurrentEntry 2 }

mxNearEndCurrentSESs OBJECT-TYPE
    SYNTAX	PerfCurrentCount
    UNITS	"seconds"
    MAX-ACCESS	read-only
    STATUS	current
    DESCRIPTION	
	"The number of Severely Errored Seconds (SESs) in the current 
	 interval.  A Severely Errored Second ...."
    ::= { mxNearEndCurrentEntry 3 }

mxNearEndCurrentSEFSs OBJECT-TYPE
    SYNTAX	PerfCurrentCount
    UNITS	"seconds"
    MAX-ACCESS	read-only
    STATUS	current
    DESCRIPTION	
	"The number of Severely Errored Framing Seconds (SEFSs) in the 
	 current interval.  A Severely Errored Frame Second has one or 
	 more Out of Frame defects or a detected AIS defect."
    ::= { mxNearEndCurrentEntry 4 }

mxNearEndCurrentUASs OBJECT-TYPE
    SYNTAX	PerfCurrentCount
    UNITS	"seconds"
    MAX-ACCESS	read-only
    STATUS	current
    DESCRIPTION	
	"The number of Unavailable Seconds (UASs) in the current 
	 interval."
    ::= { mxNearEndCurrentEntry 5 }

mxNearEndCurrentCSSs OBJECT-TYPE
    SYNTAX	PerfCurrentCount
    UNITS	"seconds"
    MAX-ACCESS	read-only
    STATUS	current
    DESCRIPTION	
	"The number of Controlled Slip Seconds (CSSs) in the current 
	 interval."
    ::= { mxNearEndCurrentEntry 6 }

mxNearEndCurrentPCVs OBJECT-TYPE
    SYNTAX	PerfCurrentCount
    UNITS	"violations"
    MAX-ACCESS	read-only
    STATUS	current
    DESCRIPTION	
	"The number of Path Coding Violations (PCVs) in the current 
	 interval.  A Path Coding Violation is a frame syncrhonization 
	 bit error in the D4 and E1 no-CRC4 formats, or a CRC or frame 
	 syncrhonization bit error in the ESF and E1 CRC4 formats."
    ::= { mxNearEndCurrentEntry 7 }

mxNearEndCurrentLESs OBJECT-TYPE
    SYNTAX	PerfCurrentCount
    UNITS	"seconds"
    MAX-ACCESS	read-only
    STATUS	current
    DESCRIPTION	
	"The number of Line Errored Seconds (LESs) in the current 
	 interval.  A Line Errored Second is a second in which one or 
	 more Line Code Violation error events are detected."
    ::= { mxNearEndCurrentEntry 8 }

mxNearEndCurrentBESs OBJECT-TYPE
    SYNTAX	PerfCurrentCount
    UNITS	"seconds"
    MAX-ACCESS	read-only
    STATUS	current
    DESCRIPTION	
	"The number of Bursty Errored Seconds (BESs) in the current 
	 interval.  A Bursty Errored Second has 2 to 319 Path Coding 
	 Violation error events, no Severely Errored Frame defects, and 
	 no detected incoming AIS defects."
    ::= { mxNearEndCurrentEntry 9 }

mxNearEndCurrentDMs OBJECT-TYPE
    SYNTAX	PerfCurrentCount
    UNITS	"minutes"
    MAX-ACCESS	read-only
    STATUS	current
    DESCRIPTION	
	"The number of Degraded Minutes (DMs) in the current interval."
    ::= { mxNearEndCurrentEntry 10 }

mxNearEndCurrentLCVs OBJECT-TYPE
    SYNTAX	PerfCurrentCount
    UNITS	"violations"
    MAX-ACCESS	read-only
    STATUS	current
    DESCRIPTION	
	"The number of Line Coding Violations (LCVs) in the current 
	 interval.  An LCV is the occurence of a Bipolar Violation (BPV) 
	 or Excessive Zeroes (EXZ) error event."
    ::= { mxNearEndCurrentEntry 11 }


mxNearEndInterval OBJECT IDENTIFIER
    ::= { mxNearEndStats 2 }

mxNearEndIntervalTable OBJECT-TYPE
    SYNTAX	SEQUENCE OF MxNearEndIntervalEntry
    MAX-ACCESS	not-accessible
    STATUS	current
    DESCRIPTION	
	"Provides a table of near end performance interval measurements 
	 for a given span.  Entries exist the previous 96 intervals 
	 associated with each span."
    ::= { mxNearEndInterval 1 }

mxNearEndIntervalEntry OBJECT-TYPE
    SYNTAX	MxNearEndIntervalEntry
    MAX-ACCESS	not-accessible
    STATUS	current
    DESCRIPTION	
	"Each entry in the table provides the interval measurements for 
	 one of 96 intervals associated with each span.  If the 
	 associated span does not support the reporting of near end 
	 performance measurements, there may be no intervals in this 
	 table for the associated span; or the intervals may have the 
	 mxNearEndIntervalValidData column set to false(2)."
    INDEX	{
	mxDrivName,	-- shared index
	mxCardIndex,	-- shared index
	mxSpanIndex,	-- shared index
	mxNearEndIntervalIndex
    }
    ::= { mxNearEndIntervalTable 1 }

MxNearEndIntervalEntry ::= SEQUENCE {
    mxNearEndIntervalIndex			Unsigned32,
    mxNearEndIntervalESs			PerfIntervalCount,
    mxNearEndIntervalSESs			PerfIntervalCount,
    mxNearEndIntervalSEFSs			PerfIntervalCount,
    mxNearEndIntervalUASs			PerfIntervalCount,
    mxNearEndIntervalCSSs			PerfIntervalCount,
    mxNearEndIntervalPCVs			PerfIntervalCount,
    mxNearEndIntervalLESs			PerfIntervalCount,
    mxNearEndIntervalBESs			PerfIntervalCount,
    mxNearEndIntervalDMs			PerfIntervalCount,
    mxNearEndIntervalLCVs			PerfIntervalCount,
    mxNearEndIntervalValidData			TruthValue
}

mxNearEndIntervalIndex OBJECT-TYPE
    SYNTAX	Unsigned32 (1..96)
    MAX-ACCESS	not-accessible
    STATUS	current
    DESCRIPTION	
	"Provides an index into the interval table.  Each interval 
	 represents 15 minute increments in the past with the lowest 
	 index value being most recent."
    ::= { mxNearEndIntervalEntry 1 }

mxNearEndIntervalESs OBJECT-TYPE
    SYNTAX	PerfIntervalCount
    UNITS	"seconds"
    MAX-ACCESS	read-only
    STATUS	current
    DESCRIPTION	
	"The number of Errored Seconds (ESs) in the indexed interval."
    ::= { mxNearEndIntervalEntry 2 }

mxNearEndIntervalSESs OBJECT-TYPE
    SYNTAX	PerfIntervalCount
    UNITS	"seconds"
    MAX-ACCESS	read-only
    STATUS	current
    DESCRIPTION	
	"The number of Severely Errored Seconds (SESs) in the indexed 
	 interval."
    ::= { mxNearEndIntervalEntry 3 }

mxNearEndIntervalSEFSs OBJECT-TYPE
    SYNTAX	PerfIntervalCount
    UNITS	"seconds"
    MAX-ACCESS	read-only
    STATUS	current
    DESCRIPTION	
	"The number of Severely Errored Framing Seconds (SEFSs) in the 
	 indexed interval."
    ::= { mxNearEndIntervalEntry 4 }

mxNearEndIntervalUASs OBJECT-TYPE
    SYNTAX	PerfIntervalCount
    UNITS	"seconds"
    MAX-ACCESS	read-only
    STATUS	current
    DESCRIPTION	
	"The number of Unavailable Seconds (UASs) in the indexed 
	 interval."
    ::= { mxNearEndIntervalEntry 5 }

mxNearEndIntervalCSSs OBJECT-TYPE
    SYNTAX	PerfIntervalCount
    UNITS	"seconds"
    MAX-ACCESS	read-only
    STATUS	current
    DESCRIPTION	
	"The number of Controlled Slip Seconds (CSSs) in the indexed 
	 interval."
    ::= { mxNearEndIntervalEntry 6 }

mxNearEndIntervalPCVs OBJECT-TYPE
    SYNTAX	PerfIntervalCount
    UNITS	"violations"
    MAX-ACCESS	read-only
    STATUS	current
    DESCRIPTION	
	"The number of Path Coding Violations (PCVs) in the indexed 
	 interval."
    ::= { mxNearEndIntervalEntry 7 }

mxNearEndIntervalLESs OBJECT-TYPE
    SYNTAX	PerfIntervalCount
    UNITS	"seconds"
    MAX-ACCESS	read-only
    STATUS	current
    DESCRIPTION	
	"The number of Line Errored Seconds (LESs) in the indexed 
	 interval."
    ::= { mxNearEndIntervalEntry 8 }

mxNearEndIntervalBESs OBJECT-TYPE
    SYNTAX	PerfIntervalCount
    UNITS	"seconds"
    MAX-ACCESS	read-only
    STATUS	current
    DESCRIPTION	
	"The number of Bursty Errored Seconds (BESs) in the indexed 
	 interval."
    ::= { mxNearEndIntervalEntry 9 }

mxNearEndIntervalDMs OBJECT-TYPE
    SYNTAX	PerfIntervalCount
    UNITS	"minutes"
    MAX-ACCESS	read-only
    STATUS	current
    DESCRIPTION	
	"The number of Degraded Minutes (DMs) in the indexed interval."
    ::= { mxNearEndIntervalEntry 10 }

mxNearEndIntervalLCVs OBJECT-TYPE
    SYNTAX	PerfIntervalCount
    UNITS	"violations"
    MAX-ACCESS	read-only
    STATUS	current
    DESCRIPTION	
	"The number of Line Coding Violations (LCVs) in the indexed 
	 interval."
    ::= { mxNearEndIntervalEntry 11 }

mxNearEndIntervalValidData OBJECT-TYPE
    SYNTAX	TruthValue
    MAX-ACCESS	read-only
    STATUS	current
    DESCRIPTION	
	"Indicates whether the performance interval counts are valid for 
	 the indexed interval."
    ::= { mxNearEndIntervalEntry 12 }


mxNearEndTotal OBJECT IDENTIFIER
    ::= { mxNearEndStats 3 }

mxNearEndTotalTable OBJECT-TYPE
    SYNTAX	SEQUENCE OF MxNearEndTotalEntry
    MAX-ACCESS	not-accessible
    STATUS	current
    DESCRIPTION	
	"Provides a table of near end performance measurement totals."
    ::= { mxNearEndTotal 1 }

mxNearEndTotalEntry OBJECT-TYPE
    SYNTAX	MxNearEndTotalEntry
    MAX-ACCESS	not-accessible
    STATUS	current
    DESCRIPTION	
	"Each entry in the table provides near end performance 
	 statistics for a given span.  Spans whose drivers or equipment 
	 does not support the reporting of near end performance 
	 measurements will not have an entry in this table, or may have 
	 an entry where the mxNearEndTotalValidIntervals is zero (0)."
    INDEX	{
	mxDrivName,	-- shared index
	mxCardIndex,	-- shared index
	mxSpanIndex	-- shared index
    }
    ::= { mxNearEndTotalTable 1 }

MxNearEndTotalEntry ::= SEQUENCE {
    mxNearEndTotalValidIntervals		HCPerfValidIntervals,
    mxNearEndTotalInvalidIntervals		HCPerfInvalidIntervals,
    mxNearEndTotalESs				PerfTotalCount,
    mxNearEndTotalSESs				PerfTotalCount,
    mxNearEndTotalSEFSs				PerfTotalCount,
    mxNearEndTotalUASs				PerfTotalCount,
    mxNearEndTotalCSSs				PerfTotalCount,
    mxNearEndTotalPCVs				PerfTotalCount,
    mxNearEndTotalLESs				PerfTotalCount,
    mxNearEndTotalBESs				PerfTotalCount,
    mxNearEndTotalDMs				PerfTotalCount,
    mxNearEndTotalLCVs				PerfTotalCount
}

mxNearEndTotalValidIntervals OBJECT-TYPE
    SYNTAX	HCPerfValidIntervals
    MAX-ACCESS	read-only
    STATUS	current
    DESCRIPTION	
	"The number of intervals for which data was collected."
    ::= { mxNearEndTotalEntry 1 }

mxNearEndTotalInvalidIntervals OBJECT-TYPE
    SYNTAX	HCPerfInvalidIntervals
    MAX-ACCESS	read-only
    STATUS	current
    DESCRIPTION	
	"The number of intervals in the range from 0 to 
	 mxNearEndTotalValidIntervals for which data is invalid 
	 (missing)."
    ::= { mxNearEndTotalEntry 2 }

mxNearEndTotalESs OBJECT-TYPE
    SYNTAX	PerfTotalCount
    UNITS	"seconds"
    MAX-ACCESS	read-only
    STATUS	current
    DESCRIPTION	
	"The total number of Errored Seconds (ESs) in all available 
	 intervals over the last 24-hour period."
    ::= { mxNearEndTotalEntry 3 }

mxNearEndTotalSESs OBJECT-TYPE
    SYNTAX	PerfTotalCount
    UNITS	"seconds"
    MAX-ACCESS	read-only
    STATUS	current
    DESCRIPTION	
	"The total number of Severly Errored Seconds (SESs) in all 
	 available intervals over the last 24-hour period."
    ::= { mxNearEndTotalEntry 4 }

mxNearEndTotalSEFSs OBJECT-TYPE
    SYNTAX	PerfTotalCount
    UNITS	"seconds"
    MAX-ACCESS	read-only
    STATUS	current
    DESCRIPTION	
	"The total number of Severely Errored Framing Seconds (SEFSs) in 
	 all available intervals over the last 24-hour period."
    ::= { mxNearEndTotalEntry 5 }

mxNearEndTotalUASs OBJECT-TYPE
    SYNTAX	PerfTotalCount
    UNITS	"seconds"
    MAX-ACCESS	read-only
    STATUS	current
    DESCRIPTION	
	"The total number of Unavailable Seconds (UASs) in all available 
	 intervals over the last 24-hour period."
    ::= { mxNearEndTotalEntry 6 }

mxNearEndTotalCSSs OBJECT-TYPE
    SYNTAX	PerfTotalCount
    UNITS	"seconds"
    MAX-ACCESS	read-only
    STATUS	current
    DESCRIPTION	
	"The total number of Controlled Slip Seconds (CSSs) in all 
	 available intervals over the last 24-hour period."
    ::= { mxNearEndTotalEntry 7 }

mxNearEndTotalPCVs OBJECT-TYPE
    SYNTAX	PerfTotalCount
    UNITS	"violations"
    MAX-ACCESS	read-only
    STATUS	current
    DESCRIPTION	
	"The total number of Path Coding Violations (PCVs) in all 
	 available intervals over the last 24-hour period."
    ::= { mxNearEndTotalEntry 8 }

mxNearEndTotalLESs OBJECT-TYPE
    SYNTAX	PerfTotalCount
    UNITS	"seconds"
    MAX-ACCESS	read-only
    STATUS	current
    DESCRIPTION	
	"The total number of Line Errored Seconds (LESs) in all 
	 available intervals over the last 24-hour period."
    ::= { mxNearEndTotalEntry 9 }

mxNearEndTotalBESs OBJECT-TYPE
    SYNTAX	PerfTotalCount
    UNITS	"seconds"
    MAX-ACCESS	read-only
    STATUS	current
    DESCRIPTION	
	"The total number of Bursty Errored Seconds (BESs) in all 
	 available intervals over the last 24-hour period."
    ::= { mxNearEndTotalEntry 10 }

mxNearEndTotalDMs OBJECT-TYPE
    SYNTAX	PerfTotalCount
    UNITS	"minutes"
    MAX-ACCESS	read-only
    STATUS	current
    DESCRIPTION	
	"The total number of Degraded Minutes (DMs) in all available 
	 intervals over the last 24-hour period."
    ::= { mxNearEndTotalEntry 11 }

mxNearEndTotalLCVs OBJECT-TYPE
    SYNTAX	PerfTotalCount
    UNITS	"violations"
    MAX-ACCESS	read-only
    STATUS	current
    DESCRIPTION	
	"The total number of Line Coding Violations (LCVs) in all 
	 available intervals over the last 24-hour period."
    ::= { mxNearEndTotalEntry 12 }


mxFarEndStats OBJECT IDENTIFIER
    ::= { mxStats 2 }

mxFarEndCurrent OBJECT IDENTIFIER
    ::= { mxFarEndStats 1 }

mxFarEndCurrentTable OBJECT-TYPE
    SYNTAX	SEQUENCE OF MxFarEndCurrentEntry
    MAX-ACCESS	not-accessible
    STATUS	current
    DESCRIPTION	
	"Provides a table of far end current statistic."
    ::= { mxFarEndCurrent 1 }

mxFarEndCurrentEntry OBJECT-TYPE
    SYNTAX	MxFarEndCurrentEntry
    MAX-ACCESS	not-accessible
    STATUS	current
    DESCRIPTION	
	"Each entry in this table provides the current accumulation of 
	 far end performance statistics for a given span.  Spans that do 
	 not support the far end reporting of performance measurements 
	 will not have an associated entry in this table."
    INDEX	{
	mxDrivName,	-- shared index
	mxCardIndex,	-- shared index
	mxSpanIndex	-- shared index
    }
    ::= { mxFarEndCurrentTable 1 }

MxFarEndCurrentEntry ::= SEQUENCE {
    mxFarEndCurrentTimeElapsed			HCPerfTimeElapsed,
    mxFarEndCurrentESs				PerfCurrentCount,
    mxFarEndCurrentSESs				PerfCurrentCount,
    mxFarEndCurrentSEFSs			PerfCurrentCount,
    mxFarEndCurrentUASs				PerfCurrentCount,
    mxFarEndCurrentCSSs				PerfCurrentCount,
    mxFarEndCurrentPCVs				PerfCurrentCount,
    mxFarEndCurrentLESs				PerfCurrentCount,
    mxFarEndCurrentBESs				PerfCurrentCount,
    mxFarEndCurrentDMs				PerfCurrentCount
}

mxFarEndCurrentTimeElapsed OBJECT-TYPE
    SYNTAX	HCPerfTimeElapsed
    UNITS	"seconds"
    MAX-ACCESS	read-only
    STATUS	current
    DESCRIPTION	
	"The number of seconds that have elapsed in the current 
	 measurement period."
    ::= { mxFarEndCurrentEntry 1 }

mxFarEndCurrentESs OBJECT-TYPE
    SYNTAX	PerfCurrentCount
    UNITS	"seconds"
    MAX-ACCESS	read-only
    STATUS	current
    DESCRIPTION	
	"The number of Errored Seconds (ESs) in the current interval."
    ::= { mxFarEndCurrentEntry 2 }

mxFarEndCurrentSESs OBJECT-TYPE
    SYNTAX	PerfCurrentCount
    UNITS	"seconds"
    MAX-ACCESS	read-only
    STATUS	current
    DESCRIPTION	
	"The number of Severely Errored Seconds (SESs) in the current 
	 interval."
    ::= { mxFarEndCurrentEntry 3 }

mxFarEndCurrentSEFSs OBJECT-TYPE
    SYNTAX	PerfCurrentCount
    UNITS	"seconds"
    MAX-ACCESS	read-only
    STATUS	current
    DESCRIPTION	
	"The number of Severely Errored Framing Seconds (SEFSs) in the 
	 current interval."
    ::= { mxFarEndCurrentEntry 4 }

mxFarEndCurrentUASs OBJECT-TYPE
    SYNTAX	PerfCurrentCount
    UNITS	"seconds"
    MAX-ACCESS	read-only
    STATUS	current
    DESCRIPTION	
	"The number of Unavailable Seconds (UASs) in the current 
	 interval."
    ::= { mxFarEndCurrentEntry 5 }

mxFarEndCurrentCSSs OBJECT-TYPE
    SYNTAX	PerfCurrentCount
    UNITS	"seconds"
    MAX-ACCESS	read-only
    STATUS	current
    DESCRIPTION	
	"The number of Controlled Slip Seconds (CSSs) in the current 
	 interval."
    ::= { mxFarEndCurrentEntry 6 }

mxFarEndCurrentPCVs OBJECT-TYPE
    SYNTAX	PerfCurrentCount
    UNITS	"violations"
    MAX-ACCESS	read-only
    STATUS	current
    DESCRIPTION	
	"The number of Path Coding Violations (PCVs) in the current 
	 interval."
    ::= { mxFarEndCurrentEntry 7 }

mxFarEndCurrentLESs OBJECT-TYPE
    SYNTAX	PerfCurrentCount
    UNITS	"seconds"
    MAX-ACCESS	read-only
    STATUS	current
    DESCRIPTION	
	"The number of Line Errored Seconds (LESs) in the current 
	 interval."
    ::= { mxFarEndCurrentEntry 8 }

mxFarEndCurrentBESs OBJECT-TYPE
    SYNTAX	PerfCurrentCount
    UNITS	"seconds"
    MAX-ACCESS	read-only
    STATUS	current
    DESCRIPTION	
	"The number of Bursty Errored Seconds (BESs) in the current 
	 interval."
    ::= { mxFarEndCurrentEntry 9 }

mxFarEndCurrentDMs OBJECT-TYPE
    SYNTAX	PerfCurrentCount
    UNITS	"minutes"
    MAX-ACCESS	read-only
    STATUS	current
    DESCRIPTION	
	"The number of Degraded Minutes (DMs) in the current interval."
    ::= { mxFarEndCurrentEntry 10 }


mxFarEndInterval OBJECT IDENTIFIER
    ::= { mxFarEndStats 2 }

mxFarEndIntervalTable OBJECT-TYPE
    SYNTAX	SEQUENCE OF MxFarEndIntervalEntry
    MAX-ACCESS	not-accessible
    STATUS	current
    DESCRIPTION	
	"Provides a table of far end performance interval measurements 
	 for a given span.  Entries exist the previous 96 intervals 
	 associated with each span."
    ::= { mxFarEndInterval 1 }

mxFarEndIntervalEntry OBJECT-TYPE
    SYNTAX	MxFarEndIntervalEntry
    MAX-ACCESS	not-accessible
    STATUS	current
    DESCRIPTION	
	"Each entry in the table provides the interval measurements for 
	 one of 96 intervals associated with each span.  If the 
	 associated span does not support the reporting of far end 
	 performance measurements, there may be no intervals in this 
	 table for the associated span; or the intervals may have the 
	 mxFarEndIntervalValidData column set to false(2)."
    INDEX	{
	mxDrivName,	-- shared index
	mxCardIndex,	-- shared index
	mxSpanIndex,	-- shared index
	mxFarEndIntervalIndex
    }
    ::= { mxFarEndIntervalTable 1 }

MxFarEndIntervalEntry ::= SEQUENCE {
    mxFarEndIntervalIndex			Unsigned32,
    mxFarEndIntervalESs				PerfIntervalCount,
    mxFarEndIntervalSESs			PerfIntervalCount,
    mxFarEndIntervalSEFSs			PerfIntervalCount,
    mxFarEndIntervalUASs			PerfIntervalCount,
    mxFarEndIntervalCSSs			PerfIntervalCount,
    mxFarEndIntervalPCVs			PerfIntervalCount,
    mxFarEndIntervalLESs			PerfIntervalCount,
    mxFarEndIntervalBESs			PerfIntervalCount,
    mxFarEndIntervalDMs				PerfIntervalCount,
    mxFarEndIntervalValidData			TruthValue
}

mxFarEndIntervalIndex OBJECT-TYPE
    SYNTAX	Unsigned32 (1..96)
    MAX-ACCESS	not-accessible
    STATUS	current
    DESCRIPTION	
	"Provides an index in increments of 15 minute intervals with the 
	 lowest index value being the most recent interval."
    ::= { mxFarEndIntervalEntry 1 }

mxFarEndIntervalESs OBJECT-TYPE
    SYNTAX	PerfIntervalCount
    UNITS	"seconds"
    MAX-ACCESS	read-only
    STATUS	current
    DESCRIPTION	
	"The number of Errored Seconds (ESs) in the indexed interval."
    ::= { mxFarEndIntervalEntry 2 }

mxFarEndIntervalSESs OBJECT-TYPE
    SYNTAX	PerfIntervalCount
    UNITS	"seconds"
    MAX-ACCESS	read-only
    STATUS	current
    DESCRIPTION	
	"The number of Severely Errored Seconds (SESs) in the indexed 
	 interval."
    ::= { mxFarEndIntervalEntry 3 }

mxFarEndIntervalSEFSs OBJECT-TYPE
    SYNTAX	PerfIntervalCount
    UNITS	"seconds"
    MAX-ACCESS	read-only
    STATUS	current
    DESCRIPTION	
	"The number of Severely Errored Framing Seconds (SEFSs) in the 
	 indexed interval."
    ::= { mxFarEndIntervalEntry 4 }

mxFarEndIntervalUASs OBJECT-TYPE
    SYNTAX	PerfIntervalCount
    UNITS	"seconds"
    MAX-ACCESS	read-only
    STATUS	current
    DESCRIPTION	
	"The number of Unavailable Seconds (UASs) in the indexed 
	 interval."
    ::= { mxFarEndIntervalEntry 5 }

mxFarEndIntervalCSSs OBJECT-TYPE
    SYNTAX	PerfIntervalCount
    UNITS	"seconds"
    MAX-ACCESS	read-only
    STATUS	current
    DESCRIPTION	
	"The number of Controlled Slip Seconds (CSSs) in the indexed 
	 interval."
    ::= { mxFarEndIntervalEntry 6 }

mxFarEndIntervalPCVs OBJECT-TYPE
    SYNTAX	PerfIntervalCount
    UNITS	"violations"
    MAX-ACCESS	read-only
    STATUS	current
    DESCRIPTION	
	"The number of Path Coding Violations (PCVs) in the indexed 
	 interval."
    ::= { mxFarEndIntervalEntry 7 }

mxFarEndIntervalLESs OBJECT-TYPE
    SYNTAX	PerfIntervalCount
    UNITS	"seconds"
    MAX-ACCESS	read-only
    STATUS	current
    DESCRIPTION	
	"The number of Line Errored Seconds (LESs) in the indexed 
	 interval."
    ::= { mxFarEndIntervalEntry 8 }

mxFarEndIntervalBESs OBJECT-TYPE
    SYNTAX	PerfIntervalCount
    UNITS	"seconds"
    MAX-ACCESS	read-only
    STATUS	current
    DESCRIPTION	
	"The number of Bursty Errored Seconds (BESs) in the indexed 
	 interval."
    ::= { mxFarEndIntervalEntry 9 }

mxFarEndIntervalDMs OBJECT-TYPE
    SYNTAX	PerfIntervalCount
    UNITS	"minutes"
    MAX-ACCESS	read-only
    STATUS	current
    DESCRIPTION	
	"The number of Degraded Minutes (DMs) in the indexed interval."
    ::= { mxFarEndIntervalEntry 10 }

mxFarEndIntervalValidData OBJECT-TYPE
    SYNTAX	TruthValue
    MAX-ACCESS	read-only
    STATUS	current
    DESCRIPTION	
	"Indicates whether the performance interval counts are valid for 
	 the indexed interval."
    ::= { mxFarEndIntervalEntry 11 }


mxFarEndTotal OBJECT IDENTIFIER
    ::= { mxFarEndStats 3 }

mxFarEndTotalTable OBJECT-TYPE
    SYNTAX	SEQUENCE OF MxFarEndTotalEntry
    MAX-ACCESS	not-accessible
    STATUS	current
    DESCRIPTION	
	"Provides a table of far end performance statistic totals."
    ::= { mxFarEndTotal 1 }

mxFarEndTotalEntry OBJECT-TYPE
    SYNTAX	MxFarEndTotalEntry
    MAX-ACCESS	not-accessible
    STATUS	current
    DESCRIPTION	
	"Each entry in the table provides far end performance statistics 
	 for a given span.  Spans whose drivers or equipment does not 
	 support the reporting of far end performance measurements will 
	 not have an entry in this  table, or may have an entry where 
	 the mxFarEndTotalValidIntervals is zero (0)."
    INDEX	{
	mxDrivName,	-- shared index
	mxCardIndex,	-- shared index
	mxSpanIndex	-- shared index
    }
    ::= { mxFarEndTotalTable 1 }

MxFarEndTotalEntry ::= SEQUENCE {
    mxFarEndTotalValidIntervals			HCPerfValidIntervals,
    mxFarEndTotalInvalidIntervals		HCPerfInvalidIntervals,
    mxFarEndTotalESs				PerfTotalCount,
    mxFarEndTotalSESs				PerfTotalCount,
    mxFarEndTotalSEFSs				PerfTotalCount,
    mxFarEndTotalUASs				PerfTotalCount,
    mxFarEndTotalCSSs				PerfTotalCount,
    mxFarEndTotalPCVs				PerfTotalCount,
    mxFarEndTotalLESs				PerfTotalCount,
    mxFarEndTotalBESs				PerfTotalCount,
    mxFarEndTotalDMs				PerfTotalCount
}

mxFarEndTotalValidIntervals OBJECT-TYPE
    SYNTAX	HCPerfValidIntervals
    MAX-ACCESS	read-only
    STATUS	current
    DESCRIPTION	
	"The number of intervals for which data was collected."
    ::= { mxFarEndTotalEntry 1 }

mxFarEndTotalInvalidIntervals OBJECT-TYPE
    SYNTAX	HCPerfInvalidIntervals
    MAX-ACCESS	read-only
    STATUS	current
    DESCRIPTION	
	"The number of intervals in the range from 0 to 
	 mxFarEndTotalValidIntervals for which data is invalid 
	 (missing)."
    ::= { mxFarEndTotalEntry 2 }

mxFarEndTotalESs OBJECT-TYPE
    SYNTAX	PerfTotalCount
    UNITS	"seconds"
    MAX-ACCESS	read-only
    STATUS	current
    DESCRIPTION	
	"The total number of Errored Seconds (ESs) in all available 
	 intervals over the last 24-hour period."
    ::= { mxFarEndTotalEntry 3 }

mxFarEndTotalSESs OBJECT-TYPE
    SYNTAX	PerfTotalCount
    UNITS	"seconds"
    MAX-ACCESS	read-only
    STATUS	current
    DESCRIPTION	
	"The total number of Severly Errored Seconds (SESs) in all 
	 available intervals over the last 24-hour period."
    ::= { mxFarEndTotalEntry 4 }

mxFarEndTotalSEFSs OBJECT-TYPE
    SYNTAX	PerfTotalCount
    UNITS	"seconds"
    MAX-ACCESS	read-only
    STATUS	current
    DESCRIPTION	
	"The total number of Severely Errored Framing Seconds (SEFSs) in 
	 all available intervals over the last 24-hour period."
    ::= { mxFarEndTotalEntry 5 }

mxFarEndTotalUASs OBJECT-TYPE
    SYNTAX	PerfTotalCount
    UNITS	"seconds"
    MAX-ACCESS	read-only
    STATUS	current
    DESCRIPTION	
	"The total number of Unavailable Seconds (UASs) in all available 
	 intervals over the last 24-hour period."
    ::= { mxFarEndTotalEntry 6 }

mxFarEndTotalCSSs OBJECT-TYPE
    SYNTAX	PerfTotalCount
    UNITS	"seconds"
    MAX-ACCESS	read-only
    STATUS	current
    DESCRIPTION	
	"The total number of Controlled Slip Seconds (CSSs) in all 
	 available intervals over the last 24-hour period."
    ::= { mxFarEndTotalEntry 7 }

mxFarEndTotalPCVs OBJECT-TYPE
    SYNTAX	PerfTotalCount
    UNITS	"violations"
    MAX-ACCESS	read-only
    STATUS	current
    DESCRIPTION	
	"The total number of Path Coding Violations (PCVs) in all 
	 available intervals over the last 24-hour period."
    ::= { mxFarEndTotalEntry 8 }

mxFarEndTotalLESs OBJECT-TYPE
    SYNTAX	PerfTotalCount
    UNITS	"seconds"
    MAX-ACCESS	read-only
    STATUS	current
    DESCRIPTION	
	"The total number of Line Errored Seconds (LESs) in all 
	 available intervals over the last 24-hour period."
    ::= { mxFarEndTotalEntry 9 }

mxFarEndTotalBESs OBJECT-TYPE
    SYNTAX	PerfTotalCount
    UNITS	"seconds"
    MAX-ACCESS	read-only
    STATUS	current
    DESCRIPTION	
	"The total number of Bursty Errored Seconds (BESs) in all 
	 available intervals over the last 24-hour period."
    ::= { mxFarEndTotalEntry 10 }

mxFarEndTotalDMs OBJECT-TYPE
    SYNTAX	PerfTotalCount
    UNITS	"minutes"
    MAX-ACCESS	read-only
    STATUS	current
    DESCRIPTION	
	"The total number of Degraded Minutes (DMs) in all available 
	 intervals over the last 24-hour period."
    ::= { mxFarEndTotalEntry 11 }

mxConformance OBJECT IDENTIFIER
    ::= { mxMIB 2 }

mxGroups OBJECT IDENTIFIER
    ::= { mxConformance 1 }

mxSyncMandatoryGroup OBJECT-GROUP
    OBJECTS	{
	mxSyncSpanId, mxSyncRowStatus }
    STATUS	current
    DESCRIPTION	
	"A collection of objects identifying the span."
    ::= { mxGroups 1 }

mxCardIdGroup OBJECT-GROUP
    OBJECTS	{
	mxCardType, mxCardIdentifier, mxCardRevision }
    STATUS	current
    DESCRIPTION	
	"A collection of objects identifying the span type."
    ::= { mxGroups 2 }

mxChipGroup OBJECT-GROUP
    OBJECTS	{
	mxCardChipType, mxCardChipRevision }
    STATUS	current
    DESCRIPTION	
	"A collection of objects identifying the chip type."
    ::= { mxGroups 3 }

mxPciGroup OBJECT-GROUP
    OBJECTS	{
	mxCardPciBus, mxCardPciSlot, mxCardPciIrq }
    STATUS	current
    DESCRIPTION	
	"A collectin of objects identifying the bus location."
    ::= { mxGroups 4 }

mxCardGroup OBJECT-GROUP
    OBJECTS	{
	mxCardSpanType, mxCardMode, mxCardSyncMaster, 
	mxCardSyncSource, mxCardSyncGroup, 
	mxCardAdministrativeState, mxCardOperationalState, 
	mxCardUsageState, mxCardAlarmStatus, 
	mxCardProceduralStatus, mxCardAvailabilityStatus, 
	mxCardControlStatus, mxCardUnknownStatus, 
	mxCardSyncSpanId, mxCardSyncTransitions }
    STATUS	current
    DESCRIPTION	
	"A collection of objects identifying the card state."
    ::= { mxGroups 5 }

mxSpanGroup OBJECT-GROUP
    OBJECTS	{
	mxSpanDevice, mxSpanEquipmentId, mxSpanType, mxSpanNumber, 
	mxSpanRate, mxSpanMode, mxSpanCrc, mxSpanClocking, 
	mxSpanPriority, mxSpanCoding, mxSpanFraming, 
	mxSpanLineImpedance, mxSpanLineMode, mxSpanLineLength, 
	mxSpanLineAttenuation, mxSpanLineGain, mxSpanLineDelay, 
	mxSpanTxLevel, mxSpanRxLevel, mxSpanAlarmSettleTime, 
	mxSpanLineCodeTime, mxSpanPrimary, mxSpanDataLink, 
	mxSpanLineCode, mxSpanAlarmSeverityMappingProfile, 
	mxSpanAdministrativeState, mxSpanOperationalState, 
	mxSpanUsageState, mxSpanAlarmStatus, mxSpanProceduralStatus, 
	mxSpanAvailabilityStatus, mxSpanControlStatus, 
	mxSpanStandbyStatus, mxSpanUnknownStatus, mxSpanSap, 
	mxSpanLoopbackStatus, mxSpanLineStatus, mxSpanAlarms, 
	mxSpanEvents, mxSpanReceiveLevel, mxSpanReceiveThreshold, 
	mxSpanRowStatus }
    STATUS	current
    DESCRIPTION	
	"A collection of objects implementing the span group."
    ::= { mxGroups 6 }

mxChanGroup OBJECT-GROUP
    OBJECTS	{
	mxChanType, mxChanFormat, mxChanRate, mxChanMode, mxChanAdministrativeState, 
	mxChanUsageState, mxChanAvailabilityStatus, mxChanControlStatus, 
	mxChanSap }
    STATUS	current
    DESCRIPTION	
	"A collection of objects implementing the channel group."
    ::= { mxGroups 7 }

mxXconGroup OBJECT-GROUP
    OBJECTS	{
	mxXconSpanIndex, mxXconChanIndex, mxXconType, mxXconStorageType, 
	mxXconRowStatus }
    STATUS	current
    DESCRIPTION	
	"A collection of objects implementing the cross-connect group."
    ::= { mxGroups 8 }

mxBertGroup OBJECT-GROUP
    OBJECTS	{
	mxBertMode, mxBertSelect, mxBertPattern, mxBertOperationalState, 
	mxBertProceduralStatus, mxBertBitCount, mxBertErrorCount }
    STATUS	current
    DESCRIPTION	
	"A collection of objects implementing the bit error rate testing 
	 group."
    ::= { mxGroups 9 }

mxScalarGroup OBJECT-GROUP
    OBJECTS	{ mxDiscontinuityTime }
    STATUS	current
    DESCRIPTION	
	"A collection of scalars."
    ::= { mxGroups 10 }

mxNearEndCurrentGroup OBJECT-GROUP
    OBJECTS	{
	mxNearEndCurrentTimeElapsed, mxNearEndCurrentESs, 
	mxNearEndCurrentSESs, mxNearEndCurrentSEFSs, 
	mxNearEndCurrentUASs, mxNearEndCurrentCSSs, 
	mxNearEndCurrentPCVs, mxNearEndCurrentLESs, 
	mxNearEndCurrentBESs, mxNearEndCurrentDMs, mxNearEndCurrentLCVs 
	}
    STATUS	current
    DESCRIPTION	
	"A collection of objects implementing the near end current 
	 group."
    ::= { mxGroups 11 }

mxNearEndIntervalGroup OBJECT-GROUP
    OBJECTS	{
	mxNearEndIntervalESs, mxNearEndIntervalSESs, 
	mxNearEndIntervalSEFSs, mxNearEndIntervalUASs, 
	mxNearEndIntervalCSSs, mxNearEndIntervalPCVs, 
	mxNearEndIntervalLESs, mxNearEndIntervalBESs, 
	mxNearEndIntervalDMs, mxNearEndIntervalLCVs, 
	mxNearEndIntervalValidData }
    STATUS	current
    DESCRIPTION	
	"A collection of objects implementing the near end interval 
	 group."
    ::= { mxGroups 12 }

mxNearEndTotalGroup OBJECT-GROUP
    OBJECTS	{
	mxNearEndTotalValidIntervals, mxNearEndTotalInvalidIntervals, 
	mxNearEndTotalESs, mxNearEndTotalSESs, mxNearEndTotalSEFSs, 
	mxNearEndTotalUASs, mxNearEndTotalCSSs, mxNearEndTotalPCVs, 
	mxNearEndTotalLESs, mxNearEndTotalBESs, mxNearEndTotalDMs, 
	mxNearEndTotalLCVs }
    STATUS	current
    DESCRIPTION	
	"A collection of objects implementing the near end total group."
    ::= { mxGroups 13 }

mxFarEndCurrentGroup OBJECT-GROUP
    OBJECTS	{
	mxFarEndCurrentTimeElapsed, mxFarEndCurrentESs, 
	mxFarEndCurrentSESs, mxFarEndCurrentSEFSs, mxFarEndCurrentUASs, 
	mxFarEndCurrentCSSs, mxFarEndCurrentPCVs, mxFarEndCurrentLESs, 
	mxFarEndCurrentBESs, mxFarEndCurrentDMs }
    STATUS	current
    DESCRIPTION	
	"A collection of objects implementing the far end current 
	 group."
    ::= { mxGroups 14 }

mxFarEndIntervalGroup OBJECT-GROUP
    OBJECTS	{
	mxFarEndIntervalESs, mxFarEndIntervalSESs, 
	mxFarEndIntervalSEFSs, mxFarEndIntervalUASs, 
	mxFarEndIntervalCSSs, mxFarEndIntervalPCVs, 
	mxFarEndIntervalLESs, mxFarEndIntervalBESs, mxFarEndIntervalDMs, 
	mxFarEndIntervalValidData }
    STATUS	current
    DESCRIPTION	
	"A collection of objects implementing the far end interval 
	 group."
    ::= { mxGroups 15 }

mxFarEndTotalGroup OBJECT-GROUP
    OBJECTS	{
	mxFarEndTotalValidIntervals, mxFarEndTotalInvalidIntervals, 
	mxFarEndTotalESs, mxFarEndTotalSESs, mxFarEndTotalSEFSs, 
	mxFarEndTotalUASs, mxFarEndTotalCSSs, mxFarEndTotalPCVs, 
	mxFarEndTotalLESs, mxFarEndTotalBESs, mxFarEndTotalDMs }
    STATUS	current
    DESCRIPTION	
	"A collection of objects implementing the far end total group."
    ::= { mxGroups 16 }

mxCompliances OBJECT IDENTIFIER
    ::= { mxConformance 2 }

mxBasicCompliance MODULE-COMPLIANCE
    STATUS	current
    DESCRIPTION	
	"A compliance profile providing basic operation."

    MODULE	-- this module

    MANDATORY-GROUPS	{
	mxScalarGroup, mxSpanGroup, mxChanGroup, mxCardIdGroup, 
	mxChipGroup }

    GROUP	mxPciGroup
    DESCRIPTION	
	"Optional group providing PCI bus information.  Not all 
	 implementations are expected to have PCI busses."

    GROUP	mxXconGroup
    DESCRIPTION	
	"Optional group providing cross-connection indication and 
	 control."

    GROUP	mxBertGroup
    DESCRIPTION	
	"Optional group providing bit error rate testing."
    OBJECT	mxBertSelect
    MIN-ACCESS	read-only
    DESCRIPTION	
	"Some implementations might not permit BERT test selection from 
	 a management station."
    OBJECT	mxBertPattern
    MIN-ACCESS	read-only
    DESCRIPTION	
	"Some implementations might not permit BERT test pattern 
	 selection from a management station."

    GROUP	mxNearEndCurrentGroup
    DESCRIPTION	
	"Optional group providing near end current statistics."

    GROUP	mxNearEndIntervalGroup
    DESCRIPTION	
	"Optional group providing near end interval statistics."

    GROUP	mxNearEndTotalGroup
    DESCRIPTION	
	"Optional group providing near end total statistics."

    GROUP	mxFarEndCurrentGroup
    DESCRIPTION	
	"Optional group providing far end current statistics."

    GROUP	mxFarEndIntervalGroup
    DESCRIPTION	
	"Optional group providing far end interval statistics."

    GROUP	mxFarEndTotalGroup
    DESCRIPTION	
	"Optional group providing far end total statistics."

    ::= { mxCompliances 1 }

mxEnhancedCompliance MODULE-COMPLIANCE
    STATUS	current
    DESCRIPTION	
	"A compliance profile providing enhanced operation."

    MODULE	-- this module

    MANDATORY-GROUPS	{
	mxScalarGroup, mxSpanGroup, mxChanGroup, mxXconGroup, 
	mxNearEndCurrentGroup, mxFarEndCurrentGroup }

    GROUP	mxBertGroup
    DESCRIPTION	
	"Optional group providing bit error rate testing."

    GROUP	mxNearEndIntervalGroup
    DESCRIPTION	
	"Optional group providing near end interval statistics."

    GROUP	mxNearEndTotalGroup
    DESCRIPTION	
	"Optional group providing near end interval totals."

    GROUP	mxFarEndIntervalGroup
    DESCRIPTION	
	"Optional group providing far end interval statistics."

    GROUP	mxFarEndTotalGroup
    DESCRIPTION	
	"Optional group providing far end total statistics."

    ::= { mxCompliances 2 }

END -- end of module OPENSS7-MX-MIB.

-- vim: ft=mib comments=\f\:\",\b\:\-\-,\:\-\-,\f\b\:- fo+=tcqlornw tw=72 nocin nosi sts=4 sw=4
