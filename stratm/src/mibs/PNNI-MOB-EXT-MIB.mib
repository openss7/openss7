-- vim: ft=mib comments=\f\:\",\b\:\-\-,\:\-\-,\f\b\:- fo+=tcqlornw tw=72 nocin nosi sts=4 sw=4
-- =============================================================================
-- 
-- @(#) $RCSfile: PNNI-MOB-EXT-MIB.mib,v $ $Name: OpenSS7-0_9_2 $($Revision: 0.9.2.1 $) $Date: 2008-12-20 12:34:16 $
--
-- -----------------------------------------------------------------------------
--
-- Copyright (c) 2001-2008  OpenSS7 Corporation <http://www.openss7.com/>
-- Copyright (c) 1997-2000  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2008-12-20 12:34:16 $ by $Author: brian $
--
-- -----------------------------------------------------------------------------
--
-- $Log: PNNI-MOB-EXT-MIB.mib,v $
-- Revision 0.9.2.1  2008-12-20 12:34:16  brian
-- - added mib files
--
-- =============================================================================

PNNI-MOB-EXT-MIB DEFINITIONS ::= BEGIN
        IMPORTS                MODULE-IDENTITY, OBJECT-TYPE,
                Counter32, Integer32, enterprises                        FROM SNMPv2-SMI
                TEXTUAL-CONVENTION,
                TimeStamp, TruthValue
                        FROM SNMPv2-TC
                InterfaceIndex
                        FROM IF-MIB
                PnniNodeId, PnniAtmAddr, PnniPeerGroupId,
                pnniNodeIndex, PnniNodeIndex, PnniLevel,
                pnniNodeEntry, pnniIfEntry
                        FROM PNNI-MIB
                MODULE-COMPLIANCE, OBJECT-GROUP
                        FROM SNMPv2-CONF;

pnniMobExtMIB MODULE-IDENTITY
        LAST-UPDATED    "9902120000Z"
        ORGANIZATION    "The ATM Forum"
        CONTACT-INFO
            "The ATM Forum
             2570 West El Camino Real, Suite 304
             Mountain View, CA 94040-1313 USA
             Phone: +1 415-949-6700
             Fax:   +1 415-949-6705
             info@atmforum.com"
        DESCRIPTION
            "The MIB module for managing the ATM Forum extensions of 
             PNNI routing for mobile networks."
       REVISION "9902120000Z"
       DESCRIPTION
          "Initial version of the MIB module for managing PNNI routing
           extensions for the support of mobile networks."
        ::= { atmfPnni 2 }

-- The object identifier subtree for the ATM Forum mobility extensions PNNI MIBs

atmForum        OBJECT IDENTIFIER ::= { enterprises 353 }
atmForumNetworkManagement       OBJECT IDENTIFIER ::= { atmForum 5 }
atmfPnni        OBJECT IDENTIFIER ::= { atmForumNetworkManagement 4 }

pnniMobExtMIBObjects OBJECT IDENTIFIER ::= { pnniMobExtMIB 1 }

    PnniOnhlIndex ::= TEXTUAL-CONVENTION
        STATUS        current
        DESCRIPTION
            "An index that identifies an outside nodal hierarchy list
             in the managed mobile system.

             The distinguished value zero indicates the null instance 
             or no instance."
        SYNTAX        Integer32 (0..65535)

-- This MIB is divided in two main groups of objects :
--
--    Objects needed for the management of a mobile switching system
--    Objects needed for the management of an access point switching system
--
-- The pnniMobExtBaseGroup contains objects for the general management 
-- of the mobility extensions.
-- 

-- The pnniMobileSwitchGroup contains objects needed for the management of
-- a mobile switching system.
-- Content : - Table of mobility enabled PNNI interfaces 
--           - Mobile logical group node
--           - Table of outside nodal hierarchy list
--           - Table of decision process information per node
--           - Table of input onhl per node
--
-- The pnniAccessPointGroup contains objects needed for the management of
-- an access point switching system.
-- Content : - Table of partial NHL filter for PNNI interfaces
--

--
-- Group: pnniMobExtBaseGroup
-- 
pnniMobExtBaseGroup OBJECT IDENTIFIER ::= { pnniMobExtMIBObjects 1 }

pnniMobExtVersion OBJECT-TYPE
        SYNTAX        INTEGER {unsupported (1), version1point0 (2)}
        MAX-ACCESS    read-only
        STATUS        current
        DESCRIPTION
            "The version of the PNNI Addendum for mobility extensions 
            that the software in this switching system is capable of 
            executing."
        REFERENCE
            "ATM Forum PNNI Addendum for mobility extensions section 2.1"
        ::= { pnniMobExtBaseGroup 1 }


--
-- Mobile Switch Group: pnniMobileSwitchGroup
-- 

pnniMobileSwitchGroup OBJECT IDENTIFIER ::= { pnniMobExtMIBObjects 2 }

-- Mobility enabled interface table

pnniMSMobileIfTable OBJECT-TYPE
        SYNTAX        SEQUENCE OF PnniMSMobileIfEntry
        MAX-ACCESS    not-accessible
        STATUS        current
        DESCRIPTION
            "Contains the attributes necessary to configure PNNI interfaces on 
             a mobile switching system"
        REFERENCE
            "ATM Forum PNNI Addendum for mobility extensions section 1.1"
        ::= { pnniMobileSwitchGroup 1 }

pnniMSMobileIfEntry OBJECT-TYPE
        SYNTAX        PnniMSMobileIfEntry
        MAX-ACCESS    not-accessible
        STATUS        current
        DESCRIPTION
            "Contains the attributes necessary to configure PNNI interfaces 
             on a mobile switching system "
        REFERENCE
            "ATM Forum PNNI Addendum for mobility extensions section 1.1"
        AUGMENTS { pnniIfEntry }
        ::= { pnniMSMobileIfTable 1 }

PnniMSMobileIfEntry ::=
        SEQUENCE {
                  pnniIfMobilityEnabled     TruthValue
                 }

pnniIfMobilityEnabled OBJECT-TYPE
        SYNTAX        TruthValue
        MAX-ACCESS    read-write
        STATUS        current
        DESCRIPTION
            "Indicates whether this interface is configured as a PNNI mobility 
             enabled interface or not. When the interface is configured as 
             mobility enabled, the mobile switch considers the nodal hierarchy
             list received from this interface as a candidate for the decision
             process."
        REFERENCE
            "ATM Forum PNNI Addendum for mobility extensions section 1.1"
        DEFVAL { false } 
        ::= { pnniMSMobileIfEntry 1 }

-- Mobile logical group node 

pnniMSMobileLgnGroup OBJECT IDENTIFIER ::= { pnniMobileSwitchGroup 2 }

pnniMobileLgnIndex OBJECT-TYPE
        SYNTAX        PnniNodeIndex
        MAX-ACCESS    read-write
        STATUS        current
        DESCRIPTION
            "Indicates the node index of the mobile logical group
             node on this switching system. The mobile logical
             group node can be either active, or yet to become operational.
             This attribute contains always the index to an entry in
             the pnniNodeTable.

             The distinguished value zero indicates the null instance or 
             no instance in the pnniMobileLgnIndex. It indicates that no
             mobile logical group node has been configured on this
             switching system.

             The mobile logical node cannot be the lowest level node in the 
             switching system.

             This object must reference the highest configured node (i.e.
             the highest level node that can become operational). 

             If the node has a value of 'up' for its pnniOperStatus, the 
             pnniPeerGroupId and pnniNodeLevel have relevant values,
             that must be considered as READ-ONLY. 

             If the node has a value of 'down' for its pnniOperStatus, the 
             values of pnniPeerGroupId and pnniNodeLevel are not relevant."
        REFERENCE
            "ATM Forum PNNI Addendum for mobility extensions section 2.2"
        ::= { pnniMSMobileLgnGroup 1 }

pnniMobileLgnMinLevel OBJECT-TYPE
        SYNTAX        PnniLevel
        MAX-ACCESS    read-only
        STATUS        current
        DESCRIPTION
            "This value indicates the lowest level at which the
             mobile logical group node can join a host peer group.

             This value is read-only to reflect that it is dependent
             on the configuration of the local nodes in this switching 
             system. The value is equal to the value of the level
             indicator of the child node of this mobile logical
             group node minus 1."
        REFERENCE
            "ATM Forum PNNI Addendum for mobility extensions section 2.2"
        ::= { pnniMSMobileLgnGroup 2 }

pnniMobileLgnMaxLevel OBJECT-TYPE
        SYNTAX        PnniLevel
        MAX-ACCESS    read-write
        STATUS        current
        DESCRIPTION
            "This value indicates the highest level at which the
             mobile logical group node is allowed to join a host
             peer group.

             If the value of this attribute is larger (i.e. the 
             level is lower) than the value of pnniMobileLgnMinLevel, 
             the mobile logical group node is not able to join any 
             host peer group."
        REFERENCE
            "ATM Forum PNNI Addendum for mobility extensions section 2.2"
        ::= { pnniMSMobileLgnGroup 3 }

-- Mobile switch : outside nodal hierarchy list table

pnniMSOnhlTable OBJECT-TYPE
        SYNTAX        SEQUENCE OF PnniMSOnhlEntry
        MAX-ACCESS    not-accessible
        STATUS        current
        DESCRIPTION
            "A table of the outside nodal hierarchy lists present 
             in this switching system."
        REFERENCE
            "ATM Forum PNNI Addendum for mobility extensions section 2.2"
        ::= { pnniMobileSwitchGroup 3 }

pnniMSOnhlEntry OBJECT-TYPE
        SYNTAX        PnniMSOnhlEntry
        MAX-ACCESS    not-accessible
        STATUS        current
        DESCRIPTION
            "An entry in this table that contains attributes 
             describing one level of an outside nodal hierarchy list"
        REFERENCE
            "ATM Forum PNNI Addendum for mobility extensions section 2.2"
        INDEX { pnniOnhlIndex, pnniOnhlLevel } 
        ::= { pnniMSOnhlTable 1 }

PnniMSOnhlEntry ::=
        SEQUENCE {
                  pnniOnhlIndex                  PnniOnhlIndex,
                  pnniOnhlLevel                  PnniLevel,
                  pnniOnhlPeerGroupId            PnniPeerGroupId,
                  pnniOnhlNodeId                 PnniNodeId,
                  pnniOnhlAtmAddr                PnniAtmAddr
                 }

pnniOnhlIndex OBJECT-TYPE
        SYNTAX        PnniOnhlIndex
        MAX-ACCESS    not-accessible
        STATUS        current
        DESCRIPTION
            "A value assigned to an outside nodal hierarchy list 
             in this switching system that uniquely identifies it 
             in the MIB."
        ::= { pnniMSOnhlEntry 1 }

pnniOnhlLevel OBJECT-TYPE
        SYNTAX        PnniLevel
        MAX-ACCESS    not-accessible
        STATUS        current
        DESCRIPTION
            "A level included in this outside nodal hierarchy list."
        ::= { pnniMSOnhlEntry 2 }

pnniOnhlPeerGroupId OBJECT-TYPE
        SYNTAX        PnniPeerGroupId
        MAX-ACCESS    read-only
        STATUS        current
        DESCRIPTION
            "The peer group id advertised by another switching system
             at this level of its nodal hierarchy list."
        REFERENCE
            "ATM Forum PNNI Addendum for mobility extensions section 3.2"
        ::= { pnniMSOnhlEntry 3 }

pnniOnhlNodeId OBJECT-TYPE
        SYNTAX        PnniNodeId
        MAX-ACCESS    read-only
        STATUS        current
        DESCRIPTION
            "The node id advertised by another switching system
             at this level of its nodal hierarchy list."
        REFERENCE
            "ATM Forum PNNI Addendum for mobility extensions section 3.2"
        ::= { pnniMSOnhlEntry 4 }

pnniOnhlAtmAddr OBJECT-TYPE
        SYNTAX        PnniAtmAddr
        MAX-ACCESS    read-only
        STATUS        current
        DESCRIPTION
            "The atm address advertised by another switching system
             at this level of its nodal hierarchy list."
        REFERENCE
            "ATM Forum PNNI Addendum for mobility extensions section 3.2"
        ::= { pnniMSOnhlEntry 5 }

-- mobile switch : node table

pnniMSNodeTable OBJECT-TYPE
        SYNTAX        SEQUENCE OF PnniMSNodeEntry
        MAX-ACCESS    not-accessible
        STATUS        current
        DESCRIPTION
            "The pnniMSNodeTable collects attributes that affect 
             the decision process executed by each node local to
             this switching system.

             This table is an augmentation of the pnniNodeTable."
        REFERENCE
            "ATM Forum PNNI Addendum for mobility extensions section 2"
        ::= { pnniMobileSwitchGroup 4 }

pnniMSNodeEntry OBJECT-TYPE
        SYNTAX        PnniMSNodeEntry
        MAX-ACCESS    not-accessible
        STATUS        current
        DESCRIPTION
            "An entry in the table, containing information about 
             the decision process associated to the logical node
             in this switching system"
        REFERENCE
            "ATM Forum PNNI Addendum for mobility extensions section 2"
        AUGMENTS { pnniNodeEntry }
        ::= { pnniMSNodeTable 1 }

PnniMSNodeEntry ::=
        SEQUENCE {
               pnniOutputOnhlIndex               PnniOnhlIndex,
               pnniOutputOnhlTimeStamp           TimeStamp,
               pnniDecisionProcessTimeStamp      TimeStamp,
               pnniDecisionProcessCount          Counter32
                 }

pnniOutputOnhlIndex OBJECT-TYPE
        SYNTAX        PnniOnhlIndex
        MAX-ACCESS    read-only
        STATUS        current
        DESCRIPTION
            "Indicates the local index in the pnniMSOnhlTable of 
             the outside nodal hierarchy list resulting from the 
             last decision process.

             If the decision process has never run, or if no
             outside nodal hierarchy list was chosen, this
             attribute is set to the null value (0)"
        REFERENCE
            "ATM Forum PNNI Addendum for mobility extensions section 2.2"
        ::= { pnniMSNodeEntry 1 }

pnniOutputOnhlTimeStamp OBJECT-TYPE
        SYNTAX        TimeStamp
        MAX-ACCESS    read-only
        STATUS        current
        DESCRIPTION
            "Indicates the time at which the current outside 
             nodal hierarchy list resulting from the decision
             process was selected as output onhl.

             This time is not reset each time that the
             pnniDecisionProcessTimeStamp is reset. The condition
             for a reset is that the outside nodal hierarchy list 
             resulting from the decision process is different from
             the previous one."
        REFERENCE
            "ATM Forum PNNI Addendum for mobility extensions section 2.2"
        ::= { pnniMSNodeEntry 2 }

pnniDecisionProcessTimeStamp OBJECT-TYPE
        SYNTAX        TimeStamp
        MAX-ACCESS    read-only
        STATUS        current
        DESCRIPTION
            "Indicates the last time that the decision process
             was executed by this node."
        REFERENCE
            "ATM Forum PNNI Addendum for mobility extensions section 2.2"
        ::= { pnniMSNodeEntry 3 }

pnniDecisionProcessCount OBJECT-TYPE
        SYNTAX        Counter32
        MAX-ACCESS    read-only
        STATUS        current
        DESCRIPTION
            "The number of times that the decision process has
             been executed by this node."
        REFERENCE
            "ATM Forum PNNI Addendum for mobility extensions section 2.2"
        ::= { pnniMSNodeEntry 4 }

-- mobile switch : input outside nodal hierarchy list table

pnniMSInputOnhlTable OBJECT-TYPE
        SYNTAX        SEQUENCE OF PnniMSInputOnhlEntry
        MAX-ACCESS    not-accessible
        STATUS        current
        DESCRIPTION
            "The pnniMSInputOnhlTable collects attributes
             on a per node basis for each outside nodal hierarchy list 
             that is an input to the decision process."
         REFERENCE
            "ATM Forum PNNI Addendum for mobility extensions section 2.2"
        ::= { pnniMobileSwitchGroup 5 }

pnniMSInputOnhlEntry OBJECT-TYPE
        SYNTAX        PnniMSInputOnhlEntry
        MAX-ACCESS    not-accessible
        STATUS        current
        DESCRIPTION
            "An entry to the table containing attributes 
             about an outside nodal hierarchy list which
             belongs to the input pool of a decision process.

             Only outside nodal hierarchy lists that are valid
             candidates for the decision process are part of the
             input pool."
        REFERENCE
            "ATM Forum PNNI Addendum for mobility extensions section 2.2"
        INDEX { pnniNodeIndex, pnniOnhlIndex } 
        ::= { pnniMSInputOnhlTable 1 }

PnniMSInputOnhlEntry ::=
        SEQUENCE {
                  pnniInputOnhlTimeStamp         TimeStamp,
                  pnniInputOnhlSourceType        INTEGER,
                  pnniInputOnhlNodeIdSource      PnniNodeId,
                  pnniInputOnhlMobileIfSource    InterfaceIndex,
                  pnniInputOnhlNodeIndexSource   PnniNodeIndex
                 }

pnniInputOnhlTimeStamp OBJECT-TYPE
        SYNTAX        TimeStamp
        MAX-ACCESS    read-only
        STATUS        current
        DESCRIPTION
            "Indicates the time at which the outside nodal hierarchy
             list was inserted into the input pool of this nodal decision
             process."
        REFERENCE
            "ATM Forum PNNI Addendum for mobility extensions section 2.2"
        ::= { pnniMSInputOnhlEntry 1 }

pnniInputOnhlSourceType OBJECT-TYPE
        SYNTAX        INTEGER { undefined(0), 
                                mobileInterface(1), 
                                nodalInformationGroup(2),
                                localNode(3)
                               }
        MAX-ACCESS    read-only
        STATUS        current
        DESCRIPTION
            "The type of the source that originated the outside nodal 
             hierarchy list.

             If the outside nodal hierarchy list is a copy of a nodal
             hierarchy list received from a mobile interface,
             this attribute contains the value 'mobileInterface'.

             If the outside nodal hierarchy list was extracted from a 
             nodal information group of an external node (i.e. not on
             this switching system), this attribute contains the 
             value 'nodalInformationGroup'.

             If the outside nodal hierarchy list is passed from a child
             node (i.e on the same switching system), this attribute
             contains the value 'localNode'."
        REFERENCE
            "ATM Forum PNNI Addendum for mobility extensions section 2.2"
        ::= { pnniMSInputOnhlEntry 2 }

pnniInputOnhlNodeIdSource OBJECT-TYPE
        SYNTAX        PnniNodeId
        MAX-ACCESS    read-only
        STATUS        current
        DESCRIPTION
            "The node id of the node which was the source of this outside
             nodal hierarchy list.

             If pnniInputOnhlSourceType has a value of 'mobileInterface',
             this attribute contains the node id of the border node that
             advertised the nodal hierarchy list.

             If pnniInputOnhlSourceType has a value of 'nodalInformationGroup' ,
             this attribute contains the node id of the node that generated 
             the nodal information group.

             If pnniInputOnhlSourceType has a value of 'localNode',
             inside of the switching system, this attribute contains the 
             node id of the local node.

             If pnniInputOnhlSourceType has none of the above mentioned values, 
             this attribute has a value of 0."
        REFERENCE
            "ATM Forum PNNI Addendum for mobility extensions section 2.2"
        ::= { pnniMSInputOnhlEntry 3 }

pnniInputOnhlMobileIfSource OBJECT-TYPE
        SYNTAX        InterfaceIndex
        MAX-ACCESS    read-only
        STATUS        current
        DESCRIPTION
            "If pnniInputOnhlSourceType has the value of 'mobileInterface',
             this attributes contains the index in the pnniIfTable of
             the mobile interface from which the outside nodal hierarchy
             list was generated.

             For all other values of pnniInputOnhlSourceType, this attribute 
             has a value of 0."
        REFERENCE
            "ATM Forum PNNI Addendum for mobility extensions section 2.2"
        ::= { pnniMSInputOnhlEntry 4 }

pnniInputOnhlNodeIndexSource OBJECT-TYPE
        SYNTAX        PnniNodeIndex
        MAX-ACCESS    read-only
        STATUS        current
        DESCRIPTION
            "If pnniInputOnhlSourceType has the value of 'localNode',
             this attribute contains the index in the pnniNodeTable of
             the child node that selected this outside nodal hierarchy 
             list as the output nodal hierarchy list.

             For all other values of pnniInputOnhlSourceType, this attribute 
             has a value of 0."
        REFERENCE
            "ATM Forum PNNI Addendum for mobility extensions section 2.2"
        ::= { pnniMSInputOnhlEntry 5 }

--
-- Access Point Group: pnniAccessPointGroup
-- 

pnniAccessPointGroup OBJECT IDENTIFIER ::= { pnniMobExtMIBObjects 3 }

-- access point : NHL filters for PNNI interfaces

pnniAPMobileIfTable OBJECT-TYPE
        SYNTAX        SEQUENCE OF PnniAPMobileIfEntry
        MAX-ACCESS    not-accessible
        STATUS        current
        DESCRIPTION
             "Contains the attributes necessary to configure PNNI interfaces 
             on an access point switching system "
        REFERENCE
            "ATM Forum PNNI Addendum for mobility extensions section 2.2.2."
        ::= { pnniAccessPointGroup 1 }

pnniAPMobileIfEntry OBJECT-TYPE
        SYNTAX        PnniAPMobileIfEntry
        MAX-ACCESS    not-accessible
        STATUS        current
        DESCRIPTION
            " Contains the attributes necessary to configure PNNI interfaces 
             on an access point switching system "
        REFERENCE
            "ATM Forum PNNI Addendum for mobility extensions section 2.2.2"
        AUGMENTS { pnniIfEntry }
        ::= { pnniAPMobileIfTable 1 }

PnniAPMobileIfEntry ::=
        SEQUENCE {
                  pnniAPMobileIfNhlLevelFilter      PnniLevel
                 }

pnniAPMobileIfNhlLevelFilter OBJECT-TYPE
        SYNTAX        PnniLevel
        MAX-ACCESS    read-write
        STATUS        current
        DESCRIPTION
            "This attribute is used to apply a mask on the nodal hierarchy 
             list advertised in HELLO protocol on this specific 
             interface.

             The value of this attribute specifies the highest level 
             of the PNNI hierarchy advertised in the nodal hierarchy list.
             In other words, any entry of the nodal hierarchy list that 
             has a value for the level smaller than the value of this 
             attribute is not advertised.

             A value of zero indicates that no filter is applied"
        REFERENCE
            "ATM Forum PNNI Addendum for mobility extensions section 2.2.2"
        DEFVAL { 0 } 
        ::= { pnniAPMobileIfEntry 1 }


-- conformance information

pnniMobExtMIBConformance
                   OBJECT IDENTIFIER ::= { pnniMobExtMIB 2 }
pnniMobExtMIBCompliances
                   OBJECT IDENTIFIER ::= { pnniMobExtMIBConformance 1 }
pnniMobExtMIBGroups
                   OBJECT IDENTIFIER ::= { pnniMobExtMIBConformance 2 }


-- compliance statements

pnniMobExtMIBCompliance MODULE-COMPLIANCE
        STATUS        current
        DESCRIPTION
            "The compliance statement for entities which implement
             the PNNI mobility extensions MIB.

             Groups of the PNNI mobility extensions objects required
             for using these extensions are identified by the suffix MinGroup.

             Groups of PNNI mobile extensions objects required for management 
             of a mobile switch are identified by the suffix MSGroup.

             Groups of optional PNNI mobility extensions objects for 
             the management of an  access point switch are identified 
             by the suffix APOptionalGroup."

        MODULE  -- this module
            MANDATORY-GROUPS { 
                               pnniMobExtMinGroup
                              }

        ::= { pnniMobExtMIBCompliances 1 }

-- units of conformance

pnniMobExtMinGroup OBJECT-GROUP
        OBJECTS { 
                  pnniMobExtVersion

                  }
        STATUS current
        DESCRIPTION
            "A collection of mobility extensions objects required
             for using the extensions in a switching system."
        ::= { pnniMobExtMIBGroups 1 }

pnniIfMSGroup OBJECT-GROUP
        OBJECTS {
                   pnniIfMobilityEnabled
                 }
        STATUS current
        DESCRIPTION
            "A collection of per interface, mobility related PNNI mobility 
             extensions objects required for the management of mobile switch."
        ::= { pnniMobExtMIBGroups 2 }

pnniMobileLgnMSGroup OBJECT-GROUP
        OBJECTS {
                   pnniMobileLgnIndex,
                   pnniMobileLgnMinLevel,
                   pnniMobileLgnMaxLevel
                 }
        STATUS current
        DESCRIPTION
            "A collection of mobile LGN related PNNI mobility 
             extensions objects required for the management of 
             mobile switch."
        ::= { pnniMobExtMIBGroups 3 }

pnniOnhlMSGroup OBJECT-GROUP
        OBJECTS {
                   pnniOnhlNodeId,
                   pnniOnhlAtmAddr,
                   pnniOnhlPeerGroupId
                  }
        STATUS current
        DESCRIPTION
            "A collection of onhl related PNNI mobility extensions objects 
             required for the management of a mobile switch."
        ::= { pnniMobExtMIBGroups 4 }

pnniNodeMSGroup OBJECT-GROUP
        OBJECTS {
                  pnniOutputOnhlIndex,
                  pnniOutputOnhlTimeStamp,
                  pnniDecisionProcessTimeStamp,
                  pnniDecisionProcessCount
                 }
        STATUS current
        DESCRIPTION
            "A collection of per node decision process related PNNI 
             mobility extensions objects required for management of 
             a mobile switch."
        ::= { pnniMobExtMIBGroups 5 }

pnniInputOnhlMSGroup OBJECT-GROUP
        OBJECTS {
                  pnniInputOnhlTimeStamp,
                  pnniInputOnhlSourceType,
                  pnniInputOnhlNodeIdSource,
                  pnniInputOnhlMobileIfSource,
                  pnniInputOnhlNodeIndexSource
                  }
        STATUS current
        DESCRIPTION
            "A collection of per node input onhl related PNNI 
             mobility extensions objects required for the 
             management of a mobile switch."
        ::= { pnniMobExtMIBGroups 6 }



pnniMobileIfAPOptionalGroup OBJECT-GROUP
        OBJECTS {
                  pnniAPMobileIfNhlLevelFilter
                  }
        STATUS current
        DESCRIPTION
            "A collection of optional, per PNNI interface, NHL 
             filters related PNNI mobility extensions objects 
             for management of an access point switching system."
        ::= { pnniMobExtMIBGroups 7 }

END

-- vim: ft=mib comments=\f\:\",\b\:\-\-,\:\-\-,\f\b\:- fo+=tcqlornw tw=72 nocin nosi sts=4 sw=4
