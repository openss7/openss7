-- vim: ft=mib comments=\f\:\",\b\:\-\-,\:\-\-,\f\b\:- fo+=tcqlornw tw=72 nocin nosi sts=4 sw=4
-- =============================================================================
-- 
-- @(#) $RCSfile: ATM-FORUM-AUTO-CONFIG.mib,v $ $Name: OpenSS7-0_9_2 $($Revision: 0.9.2.1 $) $Date: 2008-12-20 12:34:15 $
--
-- -----------------------------------------------------------------------------
--
-- Copyright (c) 2001-2008  OpenSS7 Corporation <http://www.openss7.com/>
-- Copyright (c) 1997-2000  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2008-12-20 12:34:15 $ by $Author: brian $
--
-- -----------------------------------------------------------------------------
--
-- $Log: ATM-FORUM-AUTO-CONFIG.mib,v $
-- Revision 0.9.2.1  2008-12-20 12:34:15  brian
-- - added mib files
--
-- =============================================================================

ATM-FORUM-AUTO-CONFIG DEFINITIONS ::= BEGIN
------------------------------------------------------------------
-- ATM Forum ILMI Extension for Auto Configuration
--
-- This definition contains the following tables
--        ATM Service Type Table
--        ATM Service Connection Information Table
--        AAL1 Profile Table
--        AAL3/4 Profile Table
--        AAL 5 Profile Table
------------------------------------------------------------------
IMPORTS
     DisplayString                        FROM SNMPv2-TC
     atmForum, atmForumUni                FROM ATM-FORUM-TC-MIB;


atmfAutoConfigGroup   OBJECT IDENTIFIER ::= { atmForumUni 12 }



------------------------------------------------------------------
-- ATM Forum ILMI Extension for Auto Configuration
-- ATM Service Type
------------------------------------------------------------------

atmfAtmServiceTypeTable OBJECT-TYPE
     SYNTAX    SEQUENCE OF    AtmfAtmServiceTypeEntry
     MAX-ACCESS     not-accessible
     STATUS    current
     DESCRIPTION
          "The ATM Forum ILMI Auto Configuration Extension ATM 
          Service Type Information. " 
     ::= { atmfAutoConfigGroup 1 }

atmfAtmServiceTypeEntry OBJECT-TYPE
     SYNTAX    AtmfAtmServiceTypeEntry
     MAX-ACCESS     not-accessible
     STATUS    current
     DESCRIPTION
          "An entry in the service type table describes the reference 
          information about a service that may be associated with 
          individual ATM connections for the purpose of auto-
          configuration.  This information describe the name and sub-
          name of the service, the client layer protocol using the ATM 
          service, the TM 4.0 service category, and the TM 4.0 
          conformance definition."
INDEX          { atmfAtmServiceTypeIndex }
     ::= { atmfAtmServiceTypeTable 1 }

AtmfAtmServiceTypeEntry ::= SEQUENCE {
     atmfAtmServiceTypeIndex            INTEGER,
     atmfAtmServiceProviderName         DisplayString,
     atmfAtmServiceName                 DisplayString,
     atmfAtmServiceSubName              DisplayString,
     atmfAtmServiceClient               DisplayString,
     atmfAtmServiceTMCategory           INTEGER,
     atmfAtmServiceTMConformanceDef     INTEGER
}

atmfAtmServiceTypeIndex OBJECT-TYPE
     SYNTAX    INTEGER (1..2147483647)
     MAX-ACCESS     read-only
     STATUS         current
     DESCRIPTION
          "A number between which identifies the entry in the Service 
          Type Table. "
     ::= { atmfAtmServiceTypeEntry 1 }

atmfAtmServiceProviderName OBJECT-TYPE
     SYNTAX    DisplayString
     MAX-ACCESS     read-only
     STATUS         current
     DESCRIPTION
          "This string identifies the name of the service provider for 
          the service described in this profile. The value of this 
          attribute should not set to NULL."
     ::= { atmfAtmServiceTypeEntry 2 }

atmfAtmServiceName OBJECT-TYPE
     SYNTAX    DisplayString
     MAX-ACCESS     read-only
     STATUS         current
     DESCRIPTION
          "This string identifies the name of the service described in 
          this profile.  The value of this attribute should not be set 
          to NULL.  "
     ::= { atmfAtmServiceTypeEntry 3 }

atmfAtmServiceSubName OBJECT-TYPE
     SYNTAX    DisplayString
     MAX-ACCESS     read-only
     STATUS         current
     DESCRIPTION
          "This string identifies the sub-name of the service described 
          in this profile.  A Service may have zero or more sub-names, 
          each with its own service type profile. "
     ::= { atmfAtmServiceTypeEntry 4 }


atmfAtmServiceClient OBJECT-TYPE
     SYNTAX    DisplayString
     MAX-ACCESS     read-only
     STATUS         current
     DESCRIPTION
          "This string identifies the client protocol of the service 
          described in this profile.  A Service (sub-service) may have 
          zero or more described client, each with its own service type 
          profile. "
     ::= { atmfAtmServiceTypeEntry 5 }

atmfAtmServiceTMCategory OBJECT-TYPE
     SYNTAX    INTEGER {
                     other  (1),
                     cbr    (2),
                     rtVbr  (3),
                     nrtVbr (4),
                     abr    (5),
                     ubr    (6),
                     gfr    (7)
                       }
     MAX-ACCESS     read-only
     STATUS         current
     DESCRIPTION
          "The TM 4.0 Service category used for this service type.  
          Indicates CBR, rt-VBR, nrt-VBR, ABR, UBR, (or GFR) "
     ::= { atmfAtmServiceTypeEntry 6 }

atmfAtmServiceTMConformanceDef OBJECT-TYPE
     SYNTAX    INTEGER {
                     none (0),
                     other(1),
                     cbr1 (2),
                     vbr1 (3),
                     vbr2 (4),
                     vbr3 (5),
                     ubr1 (6),
                     ubr2 (7),
                     abr  (8),
                     gfr1  (9),
                     gfr2 (10)
                       }
     MAX-ACCESS     read-only
     STATUS         current
     DESCRIPTION
          "The TM 4.1 conformance definition used for this service type. 
           Indicates CBR.1, VBR.1, VBR.2, VBR.3, UBR.1, UBR.2, ABR, 
           GFR.1, or GFR.2. "
     ::= { atmfAtmServiceTypeEntry 7 }



------------------------------------------------------------------
-- ATM Forum ILMI Extension for Auto Configuration
-- ATM Service Connection Information
------------------------------------------------------------------

atmfAtmServiceConnInfoTable OBJECT-TYPE
     SYNTAX    SEQUENCE OF    AtmfAtmServiceConnInfoEntry
     MAX-ACCESS     not-accessible
     STATUS    current
     DESCRIPTION
          "The ATM Forum ILMI Auto Configuration Extension ATM 
          Service Connection Information. " 
     ::= { atmfAutoConfigGroup 2 }

atmfAtmServiceConnInfoEntry OBJECT-TYPE
     SYNTAX    AtmfAtmServiceConnInfoEntry
     MAX-ACCESS     not-accessible
     STATUS    current
     DESCRIPTION
          "An entry in the service connection information table 
          describes the ATM connection that provides a service across 
          an ATM interface.  The connection is identified by port and 
          VPI/VCI value.  Information about the connection includes the 
          connection type (VP or VC, SVC or PVC), and the association of 
          the connection with a service type.  Specific connection 
          information, such as traffic descriptors, should be accessed 
          in the atmfVpc and atmfVcc tables defined in ILMI. "
INDEX          { atmfAtmServicePortIndex, atmfAtmServiceVpi,  
                 atmfAtmServiceVci }
     ::= { atmfAtmServiceConnInfoTable 1 }

AtmfAtmServiceConnInfoEntry ::= SEQUENCE {
     atmfAtmServicePortIndex            INTEGER,
     atmfAtmServiceVpi                  INTEGER,
     atmfAtmServiceVci                  INTEGER,
     atmfAtmServiceSignalId             INTEGER,
     atmfAtmServiceConnServiceIndex     INTEGER,
     atmfAtmServiceConnName             DisplayString,
     atmfAtmServiceConnAALType          INTEGER,
     atmfAtmServiceConnAALIndex         INTEGER
}

atmfAtmServicePortIndex OBJECT-TYPE
     SYNTAX    INTEGER (0..2147483647)
     MAX-ACCESS     read-only
     STATUS         current
     DESCRIPTION
          "The value of 0 (zero)has the special meaning of identifying 
          the ATM Interface over which this ILMI message was received. "
     ::= { atmfAtmServiceConnInfoEntry 1 }

atmfAtmServiceVpi OBJECT-TYPE
     SYNTAX    INTEGER (0..255)
     MAX-ACCESS     read-only
     STATUS         current
     DESCRIPTION
          "The VPI value of the ATM service connection at the local ATM 
          interface. "
     ::= { atmfAtmServiceConnInfoEntry 2 }

atmfAtmServiceVci OBJECT-TYPE
     SYNTAX    INTEGER (0..65535)
     MAX-ACCESS     read-only
     STATUS         current
     DESCRIPTION
          "The VCI value of the ATM service connection at the local ATM 
          interface. If the atmfAtmServiceSignalId indicates that the 
          connection is a VP connection, the value of this attribute         
          shall be set to 0 (zero) and any meaning of this attribute 
          ignored."
     ::= { atmfAtmServiceConnInfoEntry 3 }

atmfAtmServiceSignalID OBJECT-TYPE
     SYNTAX    INTEGER {
                    vcCI(0),
                    vpCI(1)
                         }
     MAX-ACCESS     read-only
     STATUS    current
     DESCRIPTION
          "This attribute represents the characteristic
          information of the layer network domain. It may be set to
          either VC characteristic information (vcCI) or VP 
          characteristic information (vpCI)."
     ::= { atmfAtmServiceConnInfoEntry 4 }



atmfAtmServiceConnServiceIndex OBJECT-TYPE
     SYNTAX    INTEGER
     MAX-ACCESS     read-only
     STATUS         current
     DESCRIPTION
          "The value of this object identifies the row in the 
          atmfAtmServiceTypeTable. This entry represents the 
          association between an ATM service connection and an ATM 
          service type profile that describes it. "
     ::= { atmfAtmServiceConnInfoEntry 5 }

atmfAtmServiceConnName OBJECT-TYPE
     SYNTAX    DisplayString
     MAX-ACCESS     read-only
     STATUS         current
     DESCRIPTION
          "This string identifies the name of the service connection.
           The value of this attribute may be set to NULL.  "
     ::= { atmfAtmServiceConnInfoEntry 6 }

atmfAtmServiceConnAALType OBJECT-TYPE
     SYNTAX    INTEGER {
                     none  (0),
                     aal1  (1),
                     aal34 (2),
                     aal5  (3),
                     other (4),
                     unknown (5),
                     aal2  (6)
                        }
     MAX-ACCESS     read-only
     STATUS         current
     DESCRIPTION
          "Describes the AAL Type of the ATM service connection.  A 
          value of none indicates that no AAL is used.  The AAL types 
          include AAL1, AAL 3/4, and AAL 5.  The value other may be a 
          user-defined AAL type.  The unknown type indicates that the 
          AAL type cannot be determined. "
     ::= { atmfAtmServiceConnInfoEntry 7 }


atmfAtmServiceConnAALIndex OBJECT-TYPE
     SYNTAX    INTEGER
     MAX-ACCESS     read-only
     STATUS         current
     DESCRIPTION
          "The value of this object identifies the row in the 
          atmfAAL1ProfileTable for AAL 1 connection, the 
          atmfAAL34ProfileTable for AAL3/4 connection, and the 
          atmfAAL5ProfileTable for AAL 5 connections. This entry 
          represents the association between an ATM service connection 
          and an ATM Adaptation Layer profile that describes it. "
     ::= { atmfAtmServiceConnInfoEntry 8 }



------------------------------------------------------------------
-- ATM Forum ILMI Extension for Auto Configuration
-- ATM AAL1 Profile
------------------------------------------------------------------

atmfAAL1ProfileTable OBJECT-TYPE
     SYNTAX    SEQUENCE OF    AtmfAAL1ProfileEntry
     MAX-ACCESS     not-accessible
     STATUS    current
     DESCRIPTION
          "The ATM Forum ILMI Auto Configuration Extension AAL1 
          Profile Information. " 
     ::= { atmfAutoConfigGroup 3 }

atmfAAL1ProfileEntry OBJECT-TYPE
     SYNTAX    AtmfAAL1ProfileEntry
     MAX-ACCESS     not-accessible
     STATUS    current
     DESCRIPTION
          "An entry in the AAL1 Profile table provides data that 
          describes the AAL1 processing function. "
INDEX          { atmfAAL1ProfileIndex }
     ::= { atmfAAL1ProfileTable 1 }

AtmfAAL1ProfileEntry ::= SEQUENCE {
     atmfAAL1ProfileIndex               INTEGER,
     atmfAAL1Subtype                    INTEGER,
     atmfAAL1CBRRate                    INTEGER,
     atmfAAL1ClkRecoveryType            INTEGER,
     atmfAAL1FEC                        INTEGER,
     atmfAAL1SDT                        INTEGER,
     atmfAAL1PartiallyFilledCells       INTEGER,
     atmfAAL1CellLossIntegrPeriod       INTEGER
}

atmfAAL1ProfileIndex OBJECT-TYPE
     SYNTAX    INTEGER (1..2147483647)
     MAX-ACCESS     read-only
     STATUS         current
     DESCRIPTION
          "A number between which identifies the entry in the AAL1 
          Profile Table. "
     ::= { atmfAAL1ProfileEntry 1 }

atmfAAL1Subtype OBJECT-TYPE
     SYNTAX    INTEGER {
                    null (0),
                    voiceBand (1),
                    circuitEmulationSynchronous (2),
                    circuitEmulationAsynchronous (3),
                    highQualityAuto (4),
                    video (5)
                         }
     MAX-ACCESS     read-only
     STATUS    current
     DESCRIPTION
          "This attribute describes AAL type 1 subtype used by the CBR 
          service application (e.g.  64 KBPS voice band signal 
          transport, circuit transport). "
     ::= { atmfAAL1ProfileEntry 2 }

atmfAAL1CBRRate OBJECT-TYPE
     SYNTAX    INTEGER 
     MAX-ACCESS     read-only
     STATUS    current
     DESCRIPTION
          "This attribute describes the rate of the CBR service 
          supported by the AAL."
     ::= { atmfAAL1ProfileEntry 3 }


atmfAAL1ClkRecoveryType OBJECT-TYPE
     SYNTAX    INTEGER {
                     synchronous (0),
                     srts(1),
                     adaptive (2)
                       }
     MAX-ACCESS     read-only
     STATUS         current
     DESCRIPTION
          "This attribute indicates whether the clock recovery type is 
          synchronous, asynchronous-SRTS(Synchronous Residual Time Stamp), 
          or asynchronous-Adaptive Clock Recovery. "
     ::= { atmfAAL1ProfileEntry 4 }

atmfAAL1FEC OBJECT-TYPE
     SYNTAX    INTEGER {
                     noFEC (0),
                     lossSensitiveSignalFEC (1),
                     delaySensitiveSignalFEC (2)
                        }
     MAX-ACCESS     read-only
     STATUS         current
     DESCRIPTION
          "This attribute indicates the FEC method: no FEC, FEC for 
          Loss Sensitive Signal Transport, or FEC for Delay Sensitive 
          Signal Transport. "
     ::= { atmfAAL1ProfileEntry 5 }

atmfAAL1SDT OBJECT-TYPE
     SYNTAX    INTEGER {
                     false (0),
                     true(1)
                        }
     MAX-ACCESS     read-only
     STATUS         current
     DESCRIPTION
          "This attribute indicates whether Structured Data Transfer 
          (SDT) has been configured at the AAL.  A value of TRUE means 
          SDT has been selected.  This attribute value can be set to 
          TRUE only when the Forward Error Correction Type attribute 
          equals noFEC. "
     ::= { atmfAAL1ProfileEntry 6 }

atmfAAL1PartiallyFilledCells OBJECT-TYPE
     SYNTAX    INTEGER 
     MAX-ACCESS     read-only
     STATUS    current
     DESCRIPTION
          "This attribute identifies the number of leading octets in 
          use."
     ::= { atmfAAL1ProfileEntry 7 }

atmfAAL1CellLossIntegrPeriod OBJECT-TYPE
     SYNTAX    INTEGER 
     MAX-ACCESS     read-only
     STATUS    current
     DESCRIPTION
          "This attribute represents the time in milliseconds for the 
          cell loss integration period.  If cells are lost for this 
          period of time, the Interworking VCC Termination Point entity 
          will generate a cell starvation alarm."
     ::= { atmfAAL1ProfileEntry 8 }


------------------------------------------------------------------
-- ATM Forum ILMI Extension for Auto Configuration
-- ATM AAL3/4 Profile
------------------------------------------------------------------

atmfAAL34ProfileTable OBJECT-TYPE
     SYNTAX    SEQUENCE OF    AtmfAAL34ProfileEntry
     MAX-ACCESS     not-accessible
     STATUS    current
     DESCRIPTION
          "The ATM Forum ILMI Auto Configuration Extension AAL3/4 
          Profile Information. " 
     ::= { atmfAutoConfigGroup 4 }

atmfAAL34ProfileEntry OBJECT-TYPE
     SYNTAX    AtmfAAL34ProfileEntry
     MAX-ACCESS     not-accessible
     STATUS    current
     DESCRIPTION
          "An entry in the AAL34 Profile table provides data that 
          describes the AAL3/4 processing function. "
INDEX          { atmfAAL34ProfileIndex }
     ::= { atmfAAL34ProfileTable 1 }

AtmfAAL34ProfileEntry ::= SEQUENCE {
     atmfAAL34ProfileIndex                INTEGER,
     atmfAAL34MaxCpcsSduSizeForward       INTEGER,
     atmfAAL34MaxCpcsSduSizeBackward      INTEGER,
     atmfAAL34MIDRangeLow                 INTEGER,
     atmfAAL34MIDRangeHigh                INTEGER,
     atmfAAL34AALMode                     INTEGER,
     atmfAAL34SscsType                    INTEGER
}

atmfAAL34ProfileIndex OBJECT-TYPE
     SYNTAX    INTEGER (1..2147483647)
     MAX-ACCESS     read-only
     STATUS         current
     DESCRIPTION
          "A number between which identifies the entry in the AAL3/4 
          Profile Table. "
     ::= { atmfAAL34ProfileEntry 1 }

atmfAAL34MaxCpcsSduSizeForward OBJECT-TYPE
     SYNTAX    INTEGER (1..65535)
     MAX-ACCESS     read-only
     STATUS    current
     DESCRIPTION
          "This attribute represents the maximum CPCS_PDU size that will 
          be transmitted over the connection in both the incoming 
          (forward) direction of transmission. "
     ::= { atmfAAL34ProfileEntry 2 }

atmfAAL34MaxCpcsSduSizeBackward OBJECT-TYPE
     SYNTAX    INTEGER (1..65535)
     MAX-ACCESS     read-only
     STATUS    current
     DESCRIPTION
          "This attribute represents the maximum CPCS_PDU size that will 
          be transmitted over the connection in both the outgoing 
          (backward) direction of transmission. "
     ::= { atmfAAL34ProfileEntry 3 }

atmfAAL34MIDRangeLow OBJECT-TYPE
     SYNTAX    INTEGER (1..66536)
     MAX-ACCESS     read-only
     STATUS    current
     DESCRIPTION
          "This attribute represents the low value of MID supported at 
          the AAL for the supporting VCC."
     ::= { atmfAAL34ProfileEntry 4 }

atmfAAL34MIDRangeHigh OBJECT-TYPE
     SYNTAX    INTEGER (1..66536)
     MAX-ACCESS     read-only
     STATUS    current
     DESCRIPTION
          "This attribute represents the high value of MID supported at 
          the AAL for the supporting VCC."
     ::= { atmfAAL34ProfileEntry 5 }

atmfAAL34AALMode OBJECT-TYPE
     SYNTAX    INTEGER {
                     messageAssured (0),
                     messageUnassured (1),
                     streamingAssured (2),
                     streamingUnassured (3)
                       }
     MAX-ACCESS     read-only
     STATUS         current
     DESCRIPTION
          "This attribute indicates whether the AAL for the supporting 
          VCC is operating in message mode or streaming mode, assured or 
          unassured. "
     ::= { atmfAAL34ProfileEntry 6 }

atmfAAL34SscsType OBJECT-TYPE
     SYNTAX    INTEGER {
                     null (0),
                     dataAssured (1),
                     dataNonAssured (2),
                     frameRelay (3)
                        }
     MAX-ACCESS     read-only
     STATUS         current
     DESCRIPTION
          "This attribute identifies the SSCS type for the AAL.  Valid 
          values are NULL, Data SSCS based on SSCOP (assured operation), 
          Data SSCS based on SSCOP (non-assured operation), or Frame 
          Relay SSCS "
     ::= { atmfAAL34ProfileEntry 7 }


------------------------------------------------------------------
-- ATM Forum ILMI Extension for Auto Configuration
-- ATM AAL5 Profile
------------------------------------------------------------------

atmfAAL5ProfileTable OBJECT-TYPE
     SYNTAX    SEQUENCE OF    AtmfAAL5ProfileEntry
     MAX-ACCESS     not-accessible
     STATUS    current
     DESCRIPTION
          "The ATM Forum ILMI Auto Configuration Extension AAL5 
          Profile Information. " 
     ::= { atmfAutoConfigGroup 5 }

atmfAAL5ProfileEntry OBJECT-TYPE
     SYNTAX    AtmfAAL5ProfileEntry
     MAX-ACCESS     not-accessible
     STATUS    current
     DESCRIPTION
          "An entry in the AAL5 Profile table provides data that 
          describes the AAL5 processing function. "
INDEX          { atmfAAL5ProfileIndex }
     ::= { atmfAAL5ProfileTable 1 }

AtmfAAL5ProfileEntry ::= SEQUENCE {
     atmfAAL5ProfileIndex                INTEGER,
     atmfAAL5MaxCpcsSduSizeForward       INTEGER,
     atmfAAL5MaxCpcsSduSizeBackward      INTEGER,
     atmfAAL5AALMode                     INTEGER,
     atmfAAL5SscsType                    INTEGER
}

atmfAAL5ProfileIndex OBJECT-TYPE
     SYNTAX    INTEGER (1..2147483647)
     MAX-ACCESS     read-only
     STATUS         current
     DESCRIPTION
          "A number between which identifies the entry in the AAL5 
          Profile Table. "
     ::= { atmfAAL5ProfileEntry 1 }

atmfAAL5MaxCpcsSduSizeForward OBJECT-TYPE
     SYNTAX    INTEGER (1..65535)
     MAX-ACCESS     read-only
     STATUS    current
     DESCRIPTION
          "This attribute represents the maximum CPCS_PDU size that will 
          be transmitted over the connection in both the incoming 
          (forward) direction of transmission. "
     ::= { atmfAAL5ProfileEntry 2 }

atmfAAL5MaxCpcsSduSizeBackward OBJECT-TYPE
     SYNTAX    INTEGER (1..65535)
     MAX-ACCESS     read-only
     STATUS    current
     DESCRIPTION
          "This attribute represents the maximum CPCS_PDU size that will 
          be transmitted over the connection in both the outgoing 
          (backward) direction of transmission. "
     ::= { atmfAAL5ProfileEntry 3 }

atmfAAL5AALMode OBJECT-TYPE
     SYNTAX    INTEGER {
                     messageAssured (0),
                     messageUnassured (1),
                     streamingAssured (2),
                     streamingUnassured (3)
                       }
     MAX-ACCESS     read-only
     STATUS         current
     DESCRIPTION
          "This attribute indicates whether the AAL for the supporting 
          VCC is operating in message mode or streaming mode, assured or 
          unassured. "
     ::= { atmfAAL5ProfileEntry 4 }

atmfAAL5SscsType OBJECT-TYPE
     SYNTAX    INTEGER {
                     null (0),
                     dataAssured (1),
                     dataNonAssured (2),
                     frameRelay (3)
                        }
     MAX-ACCESS     read-only
     STATUS         current
     DESCRIPTION
          "This attribute identifies the SSCS type for the AAL.  Valid 
          values are NULL, Data SSCS based on SSCOP (assured operation), 
          Data SSCS based on SSCOP (non-assured operation), or Frame 
          Relay SSCS "
     ::= { atmfAAL5ProfileEntry 5 }


END

-- vim: ft=mib comments=\f\:\",\b\:\-\-,\:\-\-,\f\b\:- fo+=tcqlornw tw=72 nocin nosi sts=4 sw=4
