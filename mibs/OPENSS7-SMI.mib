-- vim: ft=mib comments=\f\:\",\b\:\-\-,\:\-\-,\f\b\:- fo+=tcqlornw tw=72 nocin nosi sts=4 sw=4
-- =============================================================================
-- 
-- @(#) $RCSfile: OPENSS7-SMI.mib,v $ $Name:  $($Revision: 0.9.2.17 $) $Date: 2009-01-21 06:16:29 $
--
-- -----------------------------------------------------------------------------
--
-- Copyright (c) 2008-2009  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2009-01-21 06:16:29 $ by $Author: brian $
--
-- -----------------------------------------------------------------------------
--
-- $Log: OPENSS7-SMI.mib,v $
-- Revision 0.9.2.17  2009-01-21 06:16:29  brian
-- - updated mibs
--
-- Revision 0.9.2.16  2009-01-11 11:46:38  brian
-- - updates
--
-- Revision 0.9.2.15  2009-01-10 17:18:43  brian
-- - updated headers
--
-- Revision 0.9.2.14  2009-01-10 17:14:33  brian
-- - correction
--
-- Revision 0.9.2.13  2009-01-10 17:09:27  brian
-- - updated agents
--
-- Revision 0.9.2.12  2008-12-14 10:32:47  brian
-- - add specification arcs
--
-- Revision 0.9.2.11  2008-12-12 05:07:48  brian
-- - added Q.752 arc
--
-- Revision 0.9.2.10  2008-04-29 07:11:22  brian
-- - updating headers for release
--
-- Revision 0.9.2.8  2008-04-28 12:54:08  brian
-- - update file headers for release
--
-- Revision 0.9.2.7  2008-04-28 09:43:07  brian
-- - update headers for release
--
-- Revision 0.9.2.6  2008-01-24 17:40:57  brian
-- - updated mibs
--
-- Revision 0.9.2.5  2008/01/14 16:55:12  brian
-- - updated mibs
--
-- Revision 0.9.2.4  2008/01/14 13:01:07  brian
-- - updated mibs
--
-- Revision 0.9.2.3  2008/01/10 19:55:43  brian
-- - updating mibs
--
-- Revision 0.9.2.2  2007/12/15 20:19:14  brian
-- - updates
--
-- =============================================================================

OPENSS7-SMI DEFINITIONS ::= BEGIN

IMPORTS
    MODULE-IDENTITY, OBJECT-IDENTITY, enterprises
        FROM SNMPv2-SMI;

openss7 MODULE-IDENTITY
    LAST-UPDATED "200812092224Z"
    ORGANIZATION 
        "OpenSS7 Corporation"
    CONTACT-INFO 
        "Brian Bidulock
         OpenSS7 Corporation
         1469 Jefferys Crescent
         Edmonton, Alberta T6L 6T1
         CANADA
         Tel: +1 780 490 1141
         Fax: +1 780 490 1241
         Mob: +1 780 953 0557
         E-Mail: bidulock@openss7.org"
    DESCRIPTION 
        "Top level OpenSS7 MIB Module."
    REVISION	"200812092224Z"
    DESCRIPTION
	"Added arc for Q.752 based MIBs."
    REVISION    "200709250000Z"
    DESCRIPTION 
        "First revision of this MIB."
    ::= { enterprises 29591 } -- 29591 assigned by IANA

-- Uppermost arcs of the OpenSS7 tree.

-- openss7MIBs OBJECT-IDENTITY
--     STATUS current
--     DESCRIPTION
--  "This is the arc under which OpenSS7 MIBS are defined."
--     ::= { openss7 1 }

openss7Modules OBJECT-IDENTITY
    STATUS      current
    DESCRIPTION 
        "This is the arc under which individual MIB modules are 
         registered."
    ::= { openss7 1 }

openss7Capabilities OBJECT-IDENTITY
    STATUS      current
    DESCRIPTION 
        "This is the arc under which OpenSS7 agent capabilities are 
         registered."
    ::= { openss7 2 }

openss7Ms OBJECT-IDENTITY
    STATUS      current
    DESCRIPTION 
        "Management Systems."
    ::= { openss7 9 }

openss7MsFunction OBJECT-IDENTITY
    STATUS      current
    DESCRIPTION 
        "Management Systems Function."
    ::= { openss7Ms 2 }

openss7MsSmi OBJECT-IDENTITY
    STATUS      current
    DESCRIPTION 
        "Management Systems System Management Information."
    ::= { openss7Ms 3 }

openss7M OBJECT-IDENTITY
    STATUS      current
    DESCRIPTION 
        "ITU-T M-Series Specs."
    ::= { openss7 13 }

openss7Q OBJECT-IDENTITY
    STATUS      current
    DESCRIPTION 
        "ITU-T Q-Series Specs."
    ::= { openss7 17 }

openss7X OBJECT-IDENTITY
    STATUS      current
    DESCRIPTION 
        "ITU-T X-Series Specs."
    ::= { openss7 24 }

openss7Q700 OBJECT-IDENTITY
    STATUS	current
    DESCRIPTION
	"ITU-T Q.700 and ANSI T1.111.0 Specs."
    ::= { openss7Q 700 }

openss7Q701 OBJECT-IDENTITY
    STATUS	current
    DESCRIPTION
	"ITU-T Q.701 and ANSI T1.111.1 Specs."
    ::= { openss7Q 701 }

openss7Q702 OBJECT-IDENTITY
    STATUS	current
    DESCRIPTION
	"ITU-T Q.702 and ANSI T1.111.2 Specs."
    ::= { openss7Q 702 }

openss7Q703 OBJECT-IDENTITY
    STATUS	current
    DESCRIPTION
	"ITU-T Q.703 and ANSI T1.111.3 Specs."
    ::= { openss7Q 703 }

openss7Q704 OBJECT-IDENTITY
    STATUS	current
    DESCRIPTION
	"ITU-T Q.704 and ANSI T1.111.4 Specs."
    ::= { openss7Q 704 }

openss7Q711 OBJECT-IDENTITY
    STATUS	current
    DESCRIPTION
	"ITU-T Q.711 and ANSI T1.112 Specs."
    ::= { openss7Q 711 }

openss7Q751 OBJECT-IDENTITY
    STATUS	current
    DESCRIPTION
	"ITU-T Q.751 and ANSI T1.116 Specs."
    ::= { openss7Q 751 }

openss7Q7511 OBJECT-IDENTITY
    STATUS	current
    DESCRIPTION
	"ITU-T Q.751.1 and ANSI T1.116.1 Specs."
    ::= { openss7Q751 1 }

openss7Q752 OBJECT-IDENTITY
    STATUS	current
    DESCRIPTION
	"ITU-T Q.752 and ANSI T1.116 Specs."
    ::= { openss7Q 752 }

openss7Q771 OBJECT-IDENTITY
    STATUS	current
    DESCRIPTION
	"ITU-T Q.771 and ANSI T1.114 Specs."
    ::= { openss7Q 771 }

openss7Q825 OBJECT-IDENTITY
    STATUS      current
    DESCRIPTION 
        "ITU-T Q.825 Specs."
    ::= { openss7Q 825 }

END -- end of module OPENSS7-SMI.

-- vim: ft=mib comments=\f\:\",\b\:\-\-,\:\-\-,\f\b\:- fo+=tcqlornw tw=72 nocin nosi sts=4 sw=4
