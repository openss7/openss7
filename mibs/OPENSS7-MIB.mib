-- vim: ft=mib comments=\f\:\",\b\:\-\-,\:\-\-,\f\b\:- fo+=tcqlornw tw=72 nocin nosi sts=8
-- =============================================================================
-- 
-- @(#) $RCSfile: OPENSS7-MIB.mib,v $ $Name:  $($Revision: 0.9.2.4 $) $Date: 2008/01/10 19:55:42 $
--
-- -----------------------------------------------------------------------------
--
-- Copyright (c) 2001-2008  OpenSS7 Corporation <http://www.openss7.com/>
-- Copyright (c) 1997-2000  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- -----------------------------------------------------------------------------
--
-- Last Modified $Date: 2008/01/10 19:55:42 $ by $Author: brian $
--
-- -----------------------------------------------------------------------------
--
-- $Log: OPENSS7-MIB.mib,v $
-- Revision 0.9.2.4  2008/01/10 19:55:42  brian
-- - updating mibs
--
-- Revision 0.9.2.3  2008/01/01 13:59:39  brian
-- - added new mibs
--
-- Revision 0.9.2.2  2007/12/15 20:19:13  brian
-- - updates
--
-- Revision 0.9.2.1  2007/09/29 14:31:39  brian
-- - added new mib files
--
-- =============================================================================

OPENSS7-MIB DEFINITIONS ::= BEGIN

IMPORTS
	MODULE-IDENTITY, OBJECT-IDENTITY, enterprises
		FROM SNMPv2-SMI;

openss7 MODULE-IDENTITY
	LAST-UPDATED
		"200801011352Z"
	ORGANIZATION
		"OpenSS7 Corporation"
	CONTACT-INFO
		"Brian Bidulock
		 OpenSS7 Corporation
		 1469 Jefferys Crescent
		 Edmonton, Alberta  T6L 6T1
		 CANADA
		 Tel: +1 780 490 1141
		 Fax: +1 780 490 1241
		 Mob: +1 780 953 0557
		 E-Mail: bidulock@openss7.org"
	DESCRIPTION
		"MIB Module for SIGTRAN M2UA ASP management."
	::= { enterprises 29591 } -- assigned by IANA

--
-- Uppermost arcs of the OpenSS7 tree.
--

-- OpenSS7MIBs OBJECT-IDENTITY
-- 	STATUS current
-- 	DESCRIPTION
-- 		"This is the arc under which OpenSS7 MIBS are defined."
-- 	::= { openss7 1 }

OpenSS7Modules OBJECT-IDENTITY
	STATUS current
	DESCRIPTION
		"This is the arc under which individual MIB modules are 
		 registered."
	::= { openss7 1 }

--
--  FIXME: document mib assigned values, at least as comments
--

OpenSS7Capabilities OBJECT-IDENTITY
	STATUS current
	DESCRIPTION
		"This is the arg under which OpenSS7 agent capabilities 
		 are registered."
	::= { openss7 2 }


-- vim: ft=mib comments=\f\:\",\b\:\-\-,\:\-\-,\f\b\:- fo+=tcqlornw tw=72 nocin nosi sts=8
