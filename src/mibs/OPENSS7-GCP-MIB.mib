-- vim: ft=mib comments=\f\b\:\"ITU\-T,\f\b\:ITU\-T,\f\:\",\b\:\-\-,\:\-\-,\f\b\:\-,\f\b\:\· fo+=tcqlornw12 tw=64 ai nocin nosi sts=4 sw=4 et
-- =============================================================================
-- 
-- @(#) src/mibs/OPENSS7-GCP-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-GCP-MIB DEFINITIONS ::= BEGIN

IMPORTS
    InetAddress, InetAddressType
        FROM INET-ADDRESS-MIB
    NetworkPointCode
        FROM OPENSS7-MTP-MIB
    PortRange
        FROM OPENSS7-RTPSW-MIB
    openss7Modules
        FROM OPENSS7-SMI
    AdministrativeState, AlarmStatus, AvailabilityStatus, 
    OperationalState, ProceduralStatus, SimpleNameType, StandbyStatus, 
    UsageState, attributeValueChangeNotificationPackage, 
    communicationsAlarmPackage, createDeleteNotificationsPackage, 
    tmnObjectInstance, tmnPerceivedSeverity, tmnProbableCause
        FROM OPENSS7-SMI-MIB
    ActionOrResult, CommonLanguageName
        FROM OPENSS7-TC
    ProtectionStatus, ProtectionUnits
        FROM OPENSS7-TMN-SMI
    SnmpAdminString
        FROM SNMP-FRAMEWORK-MIB
    MODULE-COMPLIANCE, NOTIFICATION-GROUP, OBJECT-GROUP
        FROM SNMPv2-CONF
    Gauge32, MODULE-IDENTITY, NOTIFICATION-TYPE, 
    OBJECT-IDENTITY, OBJECT-TYPE, Unsigned32, zeroDotZero
        FROM SNMPv2-SMI
    AutonomousType, RowPointer, RowStatus, TEXTUAL-CONVENTION, 
    TimeInterval, TruthValue
        FROM SNMPv2-TC
    TransportAddress, TransportAddressType
        FROM TRANSPORT-ADDRESS-MIB;

gcpMIB MODULE-IDENTITY
    LAST-UPDATED "201112101120Z"
    ORGANIZATION 
        "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         E-mail: bidulock@openss7.org"
    DESCRIPTION 
        "
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201112101120Z"
    DESCRIPTION 
        "Corrections an smilint workup."
    REVISION    "201107130452Z"
    DESCRIPTION 
        "Initial version of this mib."
    ::= { openss7Modules 600 }


MegacoIdentSelection ::= TEXTUAL-CONVENTION
    STATUS      current
    DESCRIPTION 
        "Provides a selection of the form of the label that 
         a MEGACO entity uses in send messages, or is expected 
         to use in received messages.  The options are:
         
         - ipAddress(1), the MEGACO entity will identify itself 
           by its IPv4 or IPv6 address and transport port;
           
         - domainName(2), the MEGACO entity will identify itself 
           by its domain name;
           
         - deviceName(3), the MEGACO entity will identify itself 
           by its device path;
           
         - mtpAddress(4), the MEGACO entity will identify itself 
           by its MTP Point Code.
           
         This selection is specific to ITU-T Recommendation 
         H.248.1 (MEGACO) operation only."
    REFERENCE   
        "ITU-T Recommendation H.248.1 (09/2005), Annex A, Mid 
               CHOICE."
    SYNTAX      INTEGER { ipAddress(1), domainName(2), deviceName(3), 
                    mtpAddress(4) }

MegacoEncoding ::= TEXTUAL-CONVENTION
    STATUS      current
    DESCRIPTION 
        "Provides a selection of the message encoding that 
         MEGACO entities use.  An object using this textual 
         convention in its syntax clause is single-valued and 
         can assume one of the following values:
         
         - unspecified(0), the encoding is not specified by the 
           managed system and must be determined by means other 
           than provisioning (e.g, well-known port number or 
           negotiation).
           
         - binary(1), the binary encoding, such as that 
           specified by ITU-T Recommendation H.248.1 (09/2005) 
           Annex A and Annex C is to be used.
           
         - text(2), the text encoding, such as that specified by 
           ITU-T Recommendation H.248.1 (09/2005) Annex B and 
           Annex C is to be used.
           
         A changed in the value of an object using this textual 
         convention in its syntax clause will not necessarily be 
         effective until the communications facility is cycled."
    REFERENCE   
        "ITU-T Recommendation H.248.1 (09/2005), Annex A, B."
    SYNTAX      INTEGER { unspecified(0), binary(1), text(2) }

MegacoAuthenticatedAccess ::= TEXTUAL-CONVENTION
    STATUS      current
    DESCRIPTION 
        "Provides a set of the authenticated access methods that 
         will be used or accepted in H.248/MEGACO communications 
         between MG and MGC.  Objects using this textual 
         convention in they SYNTAX clause are set-valued and can 
         contain zero or more of the following methods:
         
         - none(0), association is permitted or attempted 
           without authentication;
           
         - interim(1), the interim (IPv4) approach of ITU-T 
           Recommendation H.248.1 (09/2005) Clause 10.2 is 
           permitted or attempted;
           
         - tls(2), transport layer security is permitted or 
           attempted;
           
         - ah(3), IPv6 authentication header is permitted or 
           attempted;
           
         - esp(4), IPv6 encapsulated security payload is 
           permitted or attempted.
           
         When a value is included in the set, it specifies that 
         the corresponding authentication method is permitted or 
         attempted."
    REFERENCE   
        "ITU-T Recommendation H.248.1 (09/2005), Clause 10."
    SYNTAX      BITS { none(0), interim(1), tls(2), ah(3), esp(4) }

MegacoAuthentication ::= TEXTUAL-CONVENTION
    STATUS      current
    DESCRIPTION 
        "Provides a selection of the authenticated access 
         methods that may be used in H.248/MEGACO communications 
         between MG and MGC.  Objects using this textual 
         convention in they SYNTAX clause are single-valued and 
         can assume one of the following values:
         
         - none(0), no authentication is in effect;
           
         - interim(1), the interim (IPv4) approach of ITU-T 
           Recommendation H.248.1 (09/2005) Clause 10.2 is in 
           effect;
           
         - tls(2), transport layer security is in effect;
           
         - ah(3), IPv6 authentication header is in effect;
           
         - esp(4), IPv6 encapsulated security payload is in 
           effect.
           
         When the association is not operational, this value 
         will alway read the value of the last successful 
         association, or none(0) when no association was ever 
         formed."
    SYNTAX      INTEGER { none(0), interim(1), tls(2), ah(3), esp(4) }

MegacoTerminationId ::= TEXTUAL-CONVENTION
    STATUS      current
    DESCRIPTION 
        "..."
    SYNTAX      OCTET STRING (SIZE(0..32))

MegacoTerminationPath ::= TEXTUAL-CONVENTION
    STATUS      current
    DESCRIPTION 
        "..."
    SYNTAX      OCTET STRING (SIZE(0..32))

gcpNotifications OBJECT IDENTIFIER
    ::= { gcpMIB 0 }

gcpNotifs OBJECT IDENTIFIER
    ::= { gcpMIB 1 }

gcpOldProtectionStatus OBJECT-TYPE
    SYNTAX      ProtectionStatus
    MAX-ACCESS  accessible-for-notify
    STATUS      current
    DESCRIPTION 
        "Provides the old protection status for 
         gcpProtectionSwitchReport notifications."
    ::= { gcpNotifs 1 }

gcpOldRequestSource OBJECT-TYPE
    SYNTAX      INTEGER { local(0), remote(1) }
    MAX-ACCESS  accessible-for-notify
    STATUS      current
    DESCRIPTION 
        "Provides the request source of the old protection status."
    ::= { gcpNotifs 2 }

gcpOldSwitchStatus OBJECT-TYPE
    SYNTAX      INTEGER { pending(0), completed(1), operateFailed(2) }
    MAX-ACCESS  accessible-for-notify
    STATUS      current
    DESCRIPTION 
        "Provides the switch status of the old protection status."
    ::= { gcpNotifs 3 }

gcpOldSwitchDirection OBJECT-TYPE
    SYNTAX      INTEGER { from(1), to(2) }
    MAX-ACCESS  accessible-for-notify
    STATUS      current
    DESCRIPTION 
        "Provides the switch direction of the old protection status."
    ::= { gcpNotifs 4 }

gcpOldRelatedUnit OBJECT-TYPE
    SYNTAX      Unsigned32 (1..255)
    MAX-ACCESS  accessible-for-notify
    STATUS      current
    DESCRIPTION 
        "Provides the related unit of the old protection status."
    ::= { gcpNotifs 5 }

gcpOldAutoSwitchReason OBJECT-TYPE
    SYNTAX      INTEGER { waitToRestore(0), signalDegrade(1), 
                    signalFail(2) }
    MAX-ACCESS  accessible-for-notify
    STATUS      current
    DESCRIPTION 
        "Provides the auto-switch reason for the old protection status."
    ::= { gcpNotifs 6 }

gcpNewProtectionStatus OBJECT-TYPE
    SYNTAX      ProtectionStatus
    MAX-ACCESS  accessible-for-notify
    STATUS      current
    DESCRIPTION 
        "Provides the new protection status for 
         gcpProtectionSwitchReport notifications."
    ::= { gcpNotifs 7 }

gcpNewRequestSource OBJECT-TYPE
    SYNTAX      INTEGER { local(0), remote(1) }
    MAX-ACCESS  accessible-for-notify
    STATUS      current
    DESCRIPTION 
        "Provides the request source of the new protection status."
    ::= { gcpNotifs 8 }

gcpNewSwitchStatus OBJECT-TYPE
    SYNTAX      INTEGER { pending(0), completed(1), operateFailed(2) }
    MAX-ACCESS  accessible-for-notify
    STATUS      current
    DESCRIPTION 
        "Provides the switch status of the new protection status."
    ::= { gcpNotifs 9 }

gcpNewSwitchDirection OBJECT-TYPE
    SYNTAX      INTEGER { from(1), to(2) }
    MAX-ACCESS  accessible-for-notify
    STATUS      current
    DESCRIPTION 
        "Provides the switch direction of the new protection status."
    ::= { gcpNotifs 10 }

gcpNewRelatedUnit OBJECT-TYPE
    SYNTAX      Unsigned32 (1..255)
    MAX-ACCESS  accessible-for-notify
    STATUS      current
    DESCRIPTION 
        "Provides the related unit of the new protection status."
    ::= { gcpNotifs 11 }

gcpNewAutoSwitchReason OBJECT-TYPE
    SYNTAX      INTEGER { waitToRestore(0), signalDegrade(1), 
                    signalFail(2) }
    MAX-ACCESS  accessible-for-notify
    STATUS      current
    DESCRIPTION 
        "Provides the auto-switch reason for the new protection status."
    ::= { gcpNotifs 12 }

gcpScalars OBJECT IDENTIFIER
    ::= { gcpMIB 2 }

gcpDefaults OBJECT IDENTIFIER
    ::= { gcpScalars 1 }

gcpMgcoDefaults OBJECT IDENTIFIER
    ::= { gcpDefaults 1 }

gcpDefaultMgcoIdent OBJECT-TYPE
    SYNTAX      MegacoIdentSelection
    MAX-ACCESS  read-write
    STATUS      current
    DESCRIPTION 
        "Specifies the default default value that will be used in tables 
         where MEGACO identity selection is made.  The options are:
         
         - ipAddress(1), identified by IP address;
         - domainName(2), identified by domain name;
         - deviceName(3), identified by device path;
         - mtpAddress(4), identified by MTP Point Code.
         
         The default default value is ipAddress(1): identify by IP 
         address and port number.  The default default value is only 
         applicable when never set by any management station.  When set, 
         the scalar value must persist across system reboots."
    DEFVAL      { ipAddress }
    ::= { gcpMgcoDefaults 1 }

gcpDefaultMgcoExecutionTime OBJECT-TYPE
    SYNTAX      TimeInterval
    MAX-ACCESS  read-write
    STATUS      current
    DESCRIPTION 
        "Specifies the default interval within which the MG or MGC should 
         expect a response from the other to any transaction (exclusive 
         of network delay)."
    REFERENCE
        "ITU-T Recommendation H.248.1 (09/2005), E.2.1.3 and E.2.1.4."
    DEFVAL      { 400 } -- provisional
    ::= { gcpMgcoDefaults 2 }

gcpDefaultMgcoProvRespTimer OBJECT-TYPE
    SYNTAX      TimeInterval
    MAX-ACCESS  read-write
    STATUS      current
    DESCRIPTION 
        "Specifies the default time within which the MG or MGC should 
         expect a Pending response from the other if a transaction cannot 
         be completed sooner."
    REFERENCE
        "ITU-T Recommendation H.248.1 (09/2005), E.2.1.5 and E.2.1.6."
    DEFVAL      { 400 } -- provisional
    ::= { gcpMgcoDefaults 3 }

gcpDefaultMgcpPendingLimit OBJECT-TYPE
    SYNTAX      Unsigned32
    MAX-ACCESS  read-write
    STATUS      current
    DESCRIPTION 
        "Specifies the default maximum number of transaction pending 
         messages that can be received for a given transaction.  Once 
         this limit is exceeded, the entity should issue a transaction 
         reply with Error 506 (Number of TransactionPendings Exceeded); 
         otherwise, the entity can assume the transaction to be in error."
    REFERENCE   
        "ITU-T Recommendation H.248.1 (09/2005), E.2.1.7 and E.2.1.8."
    DEFVAL      { 5 } -- provisional
    ::= { gcpMgcoDefaults 4 }

gcpDefaultMgcoLongTimer OBJECT-TYPE
    SYNTAX      TimeInterval
    MAX-ACCESS  read-write
    STATUS      current
    DESCRIPTION 
        "Specifies the default long timer.
         
         The default default value is only applicable when never 
         set by any management station.  When set, the scalar 
         value must persist across system reboots."
    ::= { gcpMgcoDefaults 5 }

gcpDefaultMgcoRtoInit OBJECT-TYPE
    SYNTAX      TimeInterval
    MAX-ACCESS  read-write
    STATUS      current
    DESCRIPTION 
        "Specifies the default initial retransmission timeout.  
         The default default values is 100: 1 second.
         
         The default default value is only applicable when never 
         set by any management station.  When set, the scalar 
         value must persist across system reboots."
    REFERENCE   
        "ITU-T Recommendation H.248.1 (09/2005), Annex D.1.3, Computing 
               retransmission timers."
    DEFVAL      { 100 }
    ::= { gcpMgcoDefaults 6 }

gcpDefaultMgcoRtoMin OBJECT-TYPE
    SYNTAX      TimeInterval
    MAX-ACCESS  read-write
    STATUS      current
    DESCRIPTION 
        "Specifies the minimum retransmission timeout.  The 
         default default value is 1: 10 milliseconds.
         
         The default default value is only applicable when never 
         set by any management station.  When set, the scalar 
         value must persist across system reboots."
    REFERENCE   
        "ITU-T Recommendation H.248.1 (09/2005), Annex D.1.3, Computing 
               retransmission timers."
    ::= { gcpMgcoDefaults 7 }

gcpDefaultMgcoRtoMax OBJECT-TYPE
    SYNTAX      TimeInterval
    MAX-ACCESS  read-write
    STATUS      current
    DESCRIPTION 
        "Specifies the maximum retansmission timeout.  The 
         default default value is 400: 4 seconds.
         
         The default default value is only applicable when never 
         set by any management station.  When set, the scalar 
         value must persist across system reboots."
    REFERENCE   
        "ITU-T Recommendation H.248.1 (09/2005), Annex D.1.3, Computing 
               retransmission timers."
    DEFVAL      { 400 }
    ::= { gcpMgcoDefaults 8 }

gcpUdpDefaults OBJECT IDENTIFIER
    ::= { gcpDefaults 2 }

gcpDefaultUdpChecksum OBJECT-TYPE
    SYNTAX      TruthValue
    MAX-ACCESS  read-write
    STATUS      current
    DESCRIPTION 
        "This scalar defines, for GCP, by default whether UDP checksums 
         are used.  Application of UDP checksums increases the 
         computational load on both the sending and receiving systems 
         and does not provide any additional coverage on clean links.
         
         The default default value is false(2): do no calculate 
         checksums.  The default default value is only applicable when 
         never set by any management station.  When set, the scalar 
         value must persist across system reboots."
    ::= { gcpUdpDefaults 1 }

gcpTcpDefaults OBJECT IDENTIFIER
    ::= { gcpDefaults 3 }

gcpDefaultTcpNoDelay OBJECT-TYPE
    SYNTAX      TruthValue
    MAX-ACCESS  read-write
    STATUS      current
    DESCRIPTION 
        "This scalar defined, for GCP, by default whether the Nagle 
         algorithm should be applied to TCP connections.  The Nagle 
         algorithm increases the size of the packets placed on the 
         network at the expense of delaying the transmission of some 
         data during congestion episodes.  When set to true(1), the 
         Nagle algorithm is suppressed; otherwise, set to false(2), the 
         Nagle algorithm is in effect.
         
         The default default is false(2): use the Nagle algorithm.  The 
         default default value is only applicable when never set by any 
         management station.  When set, the scalar value must persist 
         across system reboots."
    REFERENCE   
        "RFC 793, RFC 1122, XNS 5.2"
    DEFVAL      { false }
    ::= { gcpTcpDefaults 1 }

gcpDefaultTcpMaxseg OBJECT-TYPE
    SYNTAX      Unsigned32 (536..65536)
    UNITS       "octets"
    MAX-ACCESS  read-write
    STATUS      current
    DESCRIPTION 
        "This scalar defines, for GCP, the default maximum TCP segment 
         size for outgoing packets.  Values greater than the path MTU 
         are ignored and have no effect.  The value determines the 
         maximum size (in octets) above which TCP will fragment larger 
         segments into smaller ones, and beneath which TCP will combine 
         smaller segments into a larger one.  Normally this value is the 
         path MTU value minus the size of the current IP and TCP 
         headers.  When set to a lower value, the lower value will be 
         used.
         
         The default default allows the prevailing MTU to be controlling 
         (65536 octets).  The default default value is only applicable 
         when never set by any management station.  When set, the scalar 
         value must persist across system reboots."
    REFERENCE   
        "RFC 793, RFC 1122, XNS 5.2"
    DEFVAL      { 65536 }
    ::= { gcpTcpDefaults 2 }

gcpDefaultTcpKeepAlive OBJECT-TYPE
    SYNTAX      TruthValue
    MAX-ACCESS  read-write
    STATUS      current
    DESCRIPTION 
        "This scalar defines, for GCP, by default whether keep-alive 
         messages used to probe destination transport addresses for RTT 
         calculation and activity will be send periodically.
         
         Enabling keep-alive increases the protocol's responsiveness in 
         detection of failure and redirection of traffic away from 
         failed paths and interfaces.  However, TCP connections are far 
         less robust on noisy or congested links with keep-alive 
         enabled.  This scalar should normally be left at its default 
         value.
         
         The default default value is the value recommended by RFC 793, 
         which is false(2): do not send keep-alive probes.  The default 
         default value is only applicable when never set by any 
         management station.  When set, the scalar value must persist 
         across system reboots."
    REFERENCE   
        "RFC 793, RFC 1122, XNS 5.2"
    DEFVAL      { false }
    ::= { gcpTcpDefaults 3 }

gcpDefaultTcpKeepIdle OBJECT-TYPE
    SYNTAX      TimeInterval
    UNITS       "centiseconds"
    MAX-ACCESS  read-write
    STATUS      current
    DESCRIPTION 
        "Defines, for GCP, by default the period of time that the 
         connection must remain idle before a keep-alive probe are 
         initiated.  No minimum is signified by the value zero (0).
         
         The default default is 7200 seconds: (2 hours).  The default 
         default is only applicable when never set by any management 
         station.  When set, the scalar value must persist across system 
         reboots."
    REFERENCE   
        "RFC 793, RFC 1122, XNS 5.2"
    DEFVAL      { 72000 }
    ::= { gcpTcpDefaults 4 }

gcpDefaultTcpKeepAliveItvl OBJECT-TYPE
    SYNTAX      TimeInterval
    UNITS       "centiseconds"
    MAX-ACCESS  read-write
    STATUS      current
    DESCRIPTION 
        "Specifies, for GCP, the default interval between keep-alive 
         probes on idle connections.
         
         When keep-alive is enabled (see gcpDefaultTcpKeepAlive), this 
         value determines the rate at which keep-alive probes are sent 
         before a response is received or the connection is deemed dead.
         
         The default default is the minimum period of time recommended 
         by RFC 1122: 120 seconds (2 minutes).  Note that Linux uses 75 
         seconds (1.25 minutes). The default default value is only 
         applicable when never set by any management station.  When set, 
         the scalar value must persist across system reboots."
    REFERENCE   
        "RFC 793, RFC 1122"
    DEFVAL      { 1200 }
    ::= { gcpTcpDefaults 5 }

gcpDefaultTcpKeepCount OBJECT-TYPE
    SYNTAX      Unsigned32
    MAX-ACCESS  read-write
    STATUS      current
    DESCRIPTION 
        "Specifies, for GCP, the default maximum number of keep-alive 
         probes that will be sent without a response before the 
         connection is deemed failed.
         
         The default default is 9 attempts.  The default default value 
         is only applicable when never set by any management station.  
         When set, the scalar value must persist across system reboots."
    REFERENCE   
        "RFC 793, RFC 1122"
    DEFVAL      { 9 }
    ::= { gcpTcpDefaults 6 }

gcpDefaultTcpSynRetrans OBJECT-TYPE
    SYNTAX      Unsigned32 (0..255)
    MAX-ACCESS  read-write
    STATUS      current
    DESCRIPTION 
        "Specifies the maximum number of times that a SYN will be 
         retransmitted when attempting to establish a TCP connection.  
         Valid values are zero or greater.
         
         The default default value is 5, which corresponds to 180 
         seconds.  The default default value is only applicable when 
         never set by any management station.  Once set, the scalar 
         value must persist across system reboots."
    REFERENCE   
        "RFC 793, RFC 1122"
    DEFVAL      { 5 }
    ::= { gcpTcpDefaults 7 }

gcpDefaultTcpWindowClamp OBJECT-TYPE
    SYNTAX      Unsigned32 (536..65536)
    MAX-ACCESS  read-write
    STATUS      current
    DESCRIPTION 
        "Specifies the maximum receive window that will be advertised.
         
         The default default value is 65636: defeating the window clamp.  
         The default default value is only applicable when never set by 
         any management station.  Once set, the scalar value must 
         persist across system reboots."
    REFERENCE   
        "RFC 793, RFC 1122, XNS 5.2"
    DEFVAL      { 65536 }
    ::= { gcpTcpDefaults 8 }

gcpSctpDefaults OBJECT IDENTIFIER
    ::= { gcpDefaults 4 }

gcpDefaultSctpNoDelay OBJECT-TYPE
    SYNTAX      TruthValue
    MAX-ACCESS  read-write
    STATUS      current
    DESCRIPTION 
        "This scalar defines, for GCP, by default whether the Nagle 
         algorithm should be applied to SCTP associations.  The Nagle 
         algorithm increases the size of the packets placed on the 
         network at the expense of delaying the transmission of some 
         data during congestion episodes.  When set to true(1), the 
         Nagle algorithm is suppressed; otherwise, set to false(2), the 
         Nagle algorithm is in effect.
         
         The default default is true(1): send packets without delay.  
         The default default value is only applicable when never set by 
         any management station.  When set, the scalar value must 
         persist across system reboots."
    REFERENCE   
        "RFC 4960"
    DEFVAL      { true }
    ::= { gcpSctpDefaults 1 }

gcpDefaultSctpMaxseg OBJECT-TYPE
    SYNTAX      Unsigned32 (536..65536)
    UNITS       "octets"
    MAX-ACCESS  read-write
    STATUS      current
    DESCRIPTION 
        "This scalar defines, for GCP, the default maximum SCTP payload 
         size for outgoing packets.  Values greater than the association 
         MTU are ignored and have no effect.  The value determines the 
         maximum size (in octets) above which SCCP will fragment larger 
         DATA chunks into smaller DATA chunks, and beneath which SCTP 
         will bundle DATA chunks into a single packet or combine smaller 
         DATA chunks into larger DATA chunks.  Normally this value is 
         the association MTU value minus the size of the current IP and 
         SCTP headers, minus the size of one DATA chunk header.  When 
         set to a lower value, the lower value will be used.
         
         The default default allows the prevailing MTU to be controlling 
         (65536 octets).  The default default value is only applicable 
         when never set by any management station.  When set, the scalar 
         value must persist across system reboots."
    REFERENCE   
        "RFC 4960"
    DEFVAL      { 65536 }
    ::= { gcpSctpDefaults 2 }

gcpDefaultSctpHeartbeatItvl OBJECT-TYPE
    SYNTAX      TimeInterval
    UNITS       "centiseconds"
    MAX-ACCESS  read-write
    STATUS      current
    DESCRIPTION 
        "This scalar defines, for GCP, the default time interval (in 
         milliseconds) between successive HEARTBEAT messages used to 
         probe destination transport addresses for RTT calculation and 
         activity.  Valid values are zero (0), do not heartbeat, or 
         a value of 1 millisecond or greater.
         
         In general this value determines the amount of time that it 
         takes for an SCTP association to detect a failure on 
         a association which has no data to transmit or retransmit.
         
         M2PA, however, is used by MTP Level 3 which generates a test 
         message every T2, where T2 is defined in ITU-T Rec. Q.707 
         (1993) or ANSI T1.111.7 (2000) to have a range from 4 to 12 
         seconds.  Therefore, for M2PA, unless the SCTP heartbeat 
         interval is set below Q.707-T2, it will only have effect on 
         multi-homed associations for checking the status of non-primary 
         or non-CMT destinations.
         
         Reducing this value will reduce the amount of time taken to 
         detect primary and non-primary, non-CMT path, interface and 
         destination failures, but may only affect primary destinations 
         if reduced below the corresponding Q.707-T2 value.
         
         The default default value is that recommended by RFC 4960 (6000 
         centiseconds, or 60 seconds).  The default default value is 
         only applicable when never set by any management station.  When 
         set, the scalar value must persist across system reboots."
    REFERENCE   
        "RFC 4960 15. HB.interval, ITU-T Rec. Q.707 (1993), ANSI 
               T1.111.7 (2000)."
    DEFVAL      { 6000 }
    ::= { gcpSctpDefaults 3 }

gcpDefaultSctpHearbeat OBJECT-TYPE
    SYNTAX      TruthValue
    MAX-ACCESS  read-write
    STATUS      current
    DESCRIPTION 
        "This scalar defines, for GCP, by default whether HEARTBEAT 
         messages used to probe destination transport addresses for RTT 
         calculation and activity will be sent periodically.
         
         Disabling the heart beat mechanism reduces the protocol's 
         responsiveness in detection of failures and redirection of 
         traffic away from failed paths and interfaces, particularly, 
         for GCP, failed non-primary and non-CMT destinations in an 
         multi-homed association.  This scalar should normally be left 
         at its default value.
         
         The default default value from RFC 4960 is true(1).  The 
         default default value is only applicable when never set by any 
         management station.  When set, the scalar value must persist 
         across system reboots."
    REFERENCE   
        "RFC 4960"
    DEFVAL      { true }
    ::= { gcpSctpDefaults 4 }

gcpDefaultSctpRtoInitial OBJECT-TYPE
    SYNTAX      TimeInterval
    UNITS       "centiseconds"
    MAX-ACCESS  read-write
    STATUS      current
    DESCRIPTION 
        "This scalar defines, for GCP, the default initial time interval 
         (in milliseconds) that will be used as an initial RTO 
         (retransmission time out) value when sending packets to 
         a destination for the first time.  Valid values are zero or 
         greater but must be within the range gcpDefaultSctpRtoMin to 
         gcpDefaultSctpRtoMax.
         
         Note that, in general, the default RTO initial values should 
         not be less than the peer's maximum SACK delay, otherwise, 
         excessive retransmission might occur while the peer is delaying 
         acknowledgements.  That is, this value should be greater than 
         the corresponding gcpDefaultSctpSackDelay at the peer.
         
         The default default value is that value recommended by RFC 4960 
         (3000 milliseconds, or 3 seconds).  The default default value 
         is only applicable when never set by any management station.  
         When set, the scalar value must persist across system reboots."
    REFERENCE   
        "RFC 4960 15. RTO.Initial"
    DEFVAL      { 300 }
    ::= { gcpSctpDefaults 5 }

gcpDefaultSctpRtoMin OBJECT-TYPE
    SYNTAX      TimeInterval
    UNITS       "centiseconds"
    MAX-ACCESS  read-write
    STATUS      current
    DESCRIPTION 
        "This scalar defines, for GCP, the default minimum time interval 
         (in milliseconds) that will be used as an RTO (retransmission 
         time out) value when sending packets to a destination transport 
         address and expecting acknowledgements.  Valid values are zero 
         or greater but must be less than or equal to 
         gcpDefaultSctpRtoInitial and strictly less than 
         gcpDefaultSctpRtoMax.
         
         Note that, in general, the RTO minimum should not be less than 
         the peer's maximum SACK delay, otherwise, excessive 
         retransmissions might occur while the peer is delaying 
         acknowledgements.  That is, this value should not be less than 
         the corresponding gcpDefaultSctpSackDelay at the peer.
         
         The default default value is the value recommended by RFC 4960 
         (1000 milliseconds, or 1 second).  The default default value is 
         only applicable when never set by any management station.  When 
         set, the scalar value must persist across system reboots."
    REFERENCE   
        "RFC 4960 15. RTO.Min"
    DEFVAL      { 100 }
    ::= { gcpSctpDefaults 6 }

gcpDefaultSctpRtoMax OBJECT-TYPE
    SYNTAX      TimeInterval
    UNITS       "centiseconds"
    MAX-ACCESS  read-write
    STATUS      current
    DESCRIPTION 
        "This scalar defines, for GCP, the default maximum time interval 
         (in milliseconds) that will be used as an RTO (retransmission 
         timeout) value when sending packets to a destination transport 
         address and expecting acknowledgements.  Valid values are zero 
         or greater but must be greater than or equal to 
         gcpSctpRtoInitial and strictly greater than gcpSctpRtoMin.
         
         The default default value is the value recommended by RFC 4960 
         (60000 milliseconds, or 60 seconds).  The default default value 
         is only applicable when never set by any management station.  
         When set, the scalar value must persist across system reboots."
    REFERENCE   
        "RFC 4960 15. RTO.Max"
    DEFVAL      { 6000 }
    ::= { gcpSctpDefaults 7 }

gcpDefaultSctpPathMaxRetrans OBJECT-TYPE
    SYNTAX      Unsigned32
    UNITS       "retransmissions"
    MAX-ACCESS  read-write
    STATUS      current
    DESCRIPTION 
        "This scalar defines, for GCP, the default number of times that 
         SCTP will attempt retransmitting a packet to a given 
         destination transport address before it considers that 
         destination transport address inactive.  Valid values are zero 
         or greater.
         
         Adjusting this value has an effect on th period of time taken 
         to fail-over between destinations for multi-homed connections.  
         Lower values (including zero) will yield faster fail-over 
         response times.  Lower values, however, may cause thrashing 
         between destinations contributing to congestion in the network.  
         Default default values are applicable to Internet applications.
         
         The default default value is the value recommended in RFC 4960 
         (5 retransmissions).  The default default value is only 
         applicable when never set by any management station.  When set, 
         the scalar value must persist across system reboots."
    REFERENCE   
        "RFC 4960 15. Path.Max.Retrans"
    DEFVAL      { 5 }
    ::= { gcpSctpDefaults 8 }

gcpDefaultSctpCookieLife OBJECT-TYPE
    SYNTAX      TimeInterval
    UNITS       "centiseconds"
    MAX-ACCESS  read-write
    STATUS      current
    DESCRIPTION 
        "This scalar defines, for GCP, the default time interval (in 
         milliseconds) in conjunction with gcpSctpCookieInc beyond which 
         a COOKIE-ECHO received with a cookie sent in an INIT-ACK will 
         no longer be accepted.  For SCTP, this also limits the maximum 
         time interval for which the HMAC secret key for the cookie will 
         be valid.  Valid values are zero or greater.  Values of zero 
         will  be converted to a system clock tick.
         
         Reducing this value will increase the probability that passive 
         connection attempts will fail due to expired cookies.  
         Increasing the value will reduce the overall security of the 
         system by permitting attackers an increased interval within 
         which to crack HMACs and guess verification tags.  This value 
         may be adjusted in conjunction with gcpSctpCookieInc to meet 
         most objectives for successful passive connection attempts with 
         the best security afforded by smaller values of 
         gcpSctpCookieLife.
         
         Unfortunately, the gcpSctpCookieLife and gcpSctpCookieInc must 
         be adjusted to accommodate the slowest peer on the slowest 
         connection.  The default setting is adequate for Internet 
         applications.
         
         The default default value is the value recommended by RFC 4960 
         (6,000 centiseconds, or 60 seconds).  The default default value 
         is only applicable when never set by any management station.  
         When set, the scalar value must persist across system reboots."
    REFERENCE   
        "RFC 4960 15. Valid.Cookie.Life"
    DEFVAL      { 6000 }
    ::= { gcpSctpDefaults 9 }

gcpDefaultSctpCookieInc OBJECT-TYPE
    SYNTAX      TimeInterval
    UNITS       "centiseconds"
    MAX-ACCESS  read-write
    STATUS      current
    DESCRIPTION 
        "This scalar defines, for GCP, the default time increment (in 
         milliseconds) that will be added to the lifespan of the cookie 
         in an INIT-ACK if the received INIT requests cookie 
         preservative to lengthen the lifespan of the cookie.  Valid 
         values are zero or greater.
         
         This value can be adjusted in conjunction with 
         gcpSctpCookieLife to meet objectives of successful passive 
         connection attempts and security.
         
         The default default value is the value recommended in RFC 4960 
         5.2.6 (100 centiseconds, or 1 second).  The default default 
         setting is adequate for Internet applications.  The default 
         default value is only applicable when never set by any 
         management station.  When set, the scalar value must persist 
         across system reboots."
    REFERENCE   
        "RFC 4960, 5.2.6, 3)"
    DEFVAL      { 100 }
    ::= { gcpSctpDefaults 10 }

gcpDefaultSctpMaxInitRetries OBJECT-TYPE
    SYNTAX      Unsigned32
    UNITS       "retries"
    MAX-ACCESS  read-write
    STATUS      current
    DESCRIPTION 
        "This scalar defines, for GCP, the default number of times that 
         an INIT or COOKIE-ECHO will be resent to a given destination 
         before abandoning an active open attempt.  Value values are 
         zero or greater.
         
         The default default value is the value recommended by RFC 4960 
         (8 retries).  The default default value is only applicable when 
         never set by any management station.  When set, the scalar 
         value must persist across system reboots."
    REFERENCE   
        "RFC 4960 15. Max.Init.Retransmits"
    DEFVAL      { 8 }
    ::= { gcpSctpDefaults 11 }

gcpDefaultSctpMaxBurst OBJECT-TYPE
    SYNTAX      Unsigned32
    UNITS       "MTUs"
    MAX-ACCESS  read-write
    STATUS      current
    DESCRIPTION 
        "This scalar defines, for GCP, the default maximum number of 
         MTUs of new data chunks that will be sent in a burst in 
         accordance with SCTP Specification Errata and Issues, RFC 4460 
         and RFC 4960.
         
         The default default value is the value recommended in RFC 4960 
         (4 MTUs).  The default default value is only applicable when 
         never set by any management station.  When set, the scalar 
         value must persist across system reboots."
    REFERENCE   
        "RFC 4960 15. Max.Burst"
    DEFVAL      { 4 }
    ::= { gcpSctpDefaults 12 }

gcpDefaultSctpAssocMaxRetrans OBJECT-TYPE
    SYNTAX      Unsigned32
    UNITS       "retransmissions"
    MAX-ACCESS  read-write
    STATUS      current
    DESCRIPTION 
        "This scalar defines, for GCP, the default number of times that 
         the sending endpoint will attempt retransmitting a packet on 
         any active destination transport address before it aborts the 
         association.  Value values are zero or greater.
         
         This value should be larger than sum of the default path 
         maximum number of retransmission values of each of the 
         destinations.
         
         Setting this value to less than the sum of the default path 
         maximum retransmission values for all of the destinations has 
         the interesting effect of permitting a connection to persist 
         even when all destinations have been deemed inactive.
         
         The default default value is the value recommended in RFC 4960 
         (10 retransmissions).  The default default value is only 
         applicable when never set by any management station.  When set, 
         the scalar value must persist across system reboots."
    REFERENCE   
        "RFC 4960 15. Association.Max.Retrans"
    DEFVAL      { 10 }
    ::= { gcpSctpDefaults 13 }

gcpDefaultSctpSackDelay OBJECT-TYPE
    SYNTAX      TimeInterval (0..50)
    UNITS       "centiseconds"
    MAX-ACCESS  read-write
    STATUS      current
    DESCRIPTION 
        "This scalar defines, for GCP, the default interval of time (in 
         milliseconds) that will be used as an RTO (retransmission time 
         out) value when sending packets to a destination transport 
         address.  Valid values are zero or to 500 milliseconds (RFC 
         4960 forbids setting this value larger than 500 milliseconds).
         
         The default default value is the value recommended in RFC 4960 
         (200 milliseconds).  The default default value is only 
         applicable when never set by any management station.  When set, 
         the scalar value must persist across system reboots."
    REFERENCE   
        "RFC 4960 15. 6.2"
    DEFVAL      { 20 }
    ::= { gcpSctpDefaults 14 }

gcpDefaultSctpLifetime OBJECT-TYPE
    SYNTAX      TimeInterval
    UNITS       "centiseconds"
    MAX-ACCESS  read-write
    STATUS      current
    DESCRIPTION 
        "This scalar defines, for GCP, the default life time assigned to 
         user data to be sent on the association.
         
         The default default value is only applicable when never set by 
         any management station.  When set, the scalar value must 
         persist across system reboots."
    REFERENCE   
        "RFC 4960 10.1 E)"
    DEFVAL      { 0 }
    ::= { gcpSctpDefaults 15 }

gcpTables OBJECT IDENTIFIER
    ::= { gcpMIB 3 }

gcpMs OBJECT IDENTIFIER
    ::= { gcpTables 1 }

gcpMsTable OBJECT-TYPE
    SYNTAX      SEQUENCE OF GcpMsEntry
    MAX-ACCESS  not-accessible
    STATUS      current
    DESCRIPTION 
        "The Managed Switching Element represents, for 
         management purposes, an exchange, i.e. the aggregate of 
         traffic carrying devices, switching stages, controlling 
         and signalling means at a network node that enables 
         subscriber lines to be interconnected and packets to be 
         forwarded as required by individual users.
         
         The Managed Element object class is a class of managed 
         objects representing telecommunications equipment or 
         TMN entities (either groups or parts) within the 
         telecommunications network that performs managed 
         element functions, i.e.  provides support and/or 
         service to the subscriber. Managed elements may or may 
         not additionally perform mediation/OS functions. 
         A managed element communicates with the manager 
         (directly or indirectly) over one or more standard 
         Q-interfaces for the purpose of being monitored and/or 
         controlled. A managed element contains equipment that 
         may or may not be geographically distributed.  When the 
         attribute value change notification package is present, 
         the attributeValueChange notification defined in 
         Recommendation X.721 shall be emitted when the value of 
         one of the following attribute changes: alarm status, 
         user label, version, location name and current problem 
         list. For the above attributes that are in conditional 
         packages, the behaviour for emitting the attribute 
         value change notification applies only when the 
         corresponding conditional packages are present in the 
         managed object. When the state change notification 
         package is present, the stateChangeNotification defined 
         in Recommendation X.721 shall be emitted if the value 
         of administrative state or operational state or usage 
         state changes."
    REFERENCE   
        "ITU-T Rec. Q.751.1 (1996) managedSwitchingElement MOC.
         ANSI T1.116.1/2000 managedSwitchingElement MOC.
         ITU-T Rec. M.3100 (1995) managedElementR2 MOC."
    ::= { gcpMs 1 }

gcpMsEntry OBJECT-TYPE
    SYNTAX      GcpMsEntry
    MAX-ACCESS  not-accessible
    STATUS      current
    DESCRIPTION 
        "Each entry in the gcpMsTable represents a Managed Switching 
         Element.  See gcpMsTable for more information."
    REFERENCE   
        "ITU-T Rec. Q.751.1 (1996) managedSwitchingElement MO.
         ANSI T1.116.1/2000 managedSwitchingElement MO.
         ITU-T Rec. M.3100 (1995) managedElementR2 MO."
    INDEX       { gcpMsId }
    ::= { gcpMsTable 1 }

GcpMsEntry ::= SEQUENCE {
    gcpMsId                     Unsigned32,
    gcpMsName                   SnmpAdminString,
    gcpMsAlarmStatus            AlarmStatus,
    gcpMsOperationalState       OperationalState,
    gcpMsUsageState             UsageState,
    gcpMsManagedElementType     SnmpAdminString,
    gcpMsModelCode              SnmpAdminString,
    gcpMsVendorName             SnmpAdminString,
    gcpMsUserLabel              SnmpAdminString,
    gcpMsVersion                SnmpAdminString,
    gcpMsAsaProfilePointer      RowPointer,
    gcpMsNetworkElementAliases  SnmpAdminString,
    gcpMsRowStatus              RowStatus
}

gcpMsId OBJECT-TYPE
    SYNTAX      Unsigned32
    MAX-ACCESS  not-accessible
    STATUS      current
    DESCRIPTION 
        "This attribute is used for naming instances.  Provides 
         a Managed Switching Element identifier used to name 
         managed objects in this table."
    ::= { gcpMsEntry 1 }

gcpMsName OBJECT-TYPE
    SYNTAX      SnmpAdminString
    MAX-ACCESS  read-create
    STATUS      current
    DESCRIPTION 
        "Provides an optional administrative name for this 
         managed switching element.  It is typical to use the 
         common language name assigned to the element (e.g. 
         EDTNAB01DS1)."
    ::= { gcpMsEntry 2 }

gcpMsAlarmStatus OBJECT-TYPE
    SYNTAX      AlarmStatus
    MAX-ACCESS  read-create
    STATUS      current
    DESCRIPTION 
        "Provides the alarm status of the GCP managed switching 
         element following the AlarmStatus textual convention 
         and ITU-T Rec.  X.721 (1992) | ISO/IEC 10165-2 : 1992.
         
         - underRepair(0), the managed switching element is 
           currently being repaired; the operational state is 
           either disabled or enabled;
           
         - critical(1), one or more  critical alarms indicating 
           a fault have been detected in the managed switching 
           element and have not been cleared; the operational 
           state is either disabled or enabled;
           
         - major(2), one ore more major alarms indicating 
           a fault have been detected in the managed switching 
           element, and have not been cleared; the operational 
           state is enabled or disabled;
           
         - minor(3), one or more minor alarms indicating a fault 
           have been detected in the managed switching element, 
           and have not yet been cleared; the operational state 
           is enabled or disabled;
           
         - alarmOutstanding(4), one or more alarms have been 
           detected in the resource, the condition of which may 
           or may not be disabling.
           
         The presence of the above alarm state conditions do not 
         suppress the generation of future fault-related 
         notifications.
         
         Values that can be added to the set by a management 
         station includes only the underRepair(0) condition.  
         Values that can be removed from the set are 
         critical(1), major(2), minor(3), and 
         alarmOutstanding(4).  Removing conditions from the set 
         are for performing manual alarm clearing from 
         a management station."
    REFERENCE   
        "ITU-T Rec. Q.751.1 (1997), ANSI T1.116.1 (2000) 
               : alarmStatus attribute.
         ITU-T Rec. X.721 (1992) | ISO/IEC 10165-2 : 1992, 
               Attribute-ASN1Module.AlarmStatus.
         ITU-T Rec. X.731 (1992) | ISO/IEC 10164-2 : 1993, 
               Section 8.1.2.1."
    ::= { gcpMsEntry 3 }

gcpMsOperationalState OBJECT-TYPE
    SYNTAX      OperationalState
    MAX-ACCESS  read-only
    STATUS      current
    DESCRIPTION 
        "Provides the operational state of the GCP managed 
         switching element following the OperationalState 
         textual convention and ITU-T Rec. X.721 | ISO/IEC 
         10165-2.
         
          - disabled(0),
          - enabled(1),"
    REFERENCE   
        "ITU-T Rec. X.721 (1992) | ISO/IEC 10165-2 : 1992, 
               Attribute-ASN1Module.OperationalState.
         ITU-T Rec. X.731 (1992) | ISO/IEC 10164-2 : 1993, 
               Section 8.1.1.1.
         ITU-T Rec. Q.751.1 (1997), ANSI T1.116.1 (2000), 
               operationalState attribute."
    ::= { gcpMsEntry 4 }

gcpMsUsageState OBJECT-TYPE
    SYNTAX      UsageState
    MAX-ACCESS  read-only
    STATUS      current
    DESCRIPTION 
        "Provides the usage state of the GCP managed switching 
         element following the UsageState textual convention and 
         ITU-T Rec.  X.721 | ISO/IEC 10165-2.
         
          - idle(0),
          - active(1),
          - busy(2),"
    REFERENCE   
        "ITU-T Rec. X.721 | ISO/IEC 10165-2 usageState 
               attribute."
    ::= { gcpMsEntry 5 }

gcpMsManagedElementType OBJECT-TYPE
    SYNTAX      SnmpAdminString
    MAX-ACCESS  read-only
    STATUS      current
    DESCRIPTION 
        "Specifies the managed switching element type in 
         accordance with the SnmpAdminString textual 
         convention."
    ::= { gcpMsEntry 6 }

gcpMsModelCode OBJECT-TYPE
    SYNTAX      SnmpAdminString
    MAX-ACCESS  read-only
    STATUS      current
    DESCRIPTION 
        "Specifies the managed switching element model code in 
         accordance with the SnmpAdminString textual 
         convention."
    ::= { gcpMsEntry 7 }

gcpMsVendorName OBJECT-TYPE
    SYNTAX      SnmpAdminString
    MAX-ACCESS  read-only
    STATUS      current
    DESCRIPTION 
        "Specifies the managed switching element vendor name."
    ::= { gcpMsEntry 8 }

gcpMsUserLabel OBJECT-TYPE
    SYNTAX      SnmpAdminString
    MAX-ACCESS  read-create
    STATUS      current
    DESCRIPTION 
        "Specifies the managed switching element user label.  
         This value can be set to any string by management 
         stations and the agent or managed device will not 
         restrict the management station's ability to set this 
         value."
    ::= { gcpMsEntry 9 }

gcpMsVersion OBJECT-TYPE
    SYNTAX      SnmpAdminString
    MAX-ACCESS  read-only
    STATUS      current
    DESCRIPTION 
        "Specifies the managed switching element version."
    ::= { gcpMsEntry 10 }

gcpMsAsaProfilePointer OBJECT-TYPE
    SYNTAX      RowPointer
    MAX-ACCESS  read-create
    STATUS      current
    DESCRIPTION 
        "Provides a pointer to an alarm severity assignment 
         profile to be used for alarms generated by this managed 
         switching element, or zeroDotZero to use the default 
         mapping associated with the media gateway as described 
         in this MIB."
    REFERENCE   
        "ITU-T Rec. Q.751.1 (1997), ANSI T1.116.1 (2000), 
               alarmSeverityAssignmentProfilePointer attribute."
    DEFVAL      { zeroDotZero }
    ::= { gcpMsEntry 11 }

gcpMsNetworkElementAliases OBJECT-TYPE
    SYNTAX      SnmpAdminString
    MAX-ACCESS  read-create
    STATUS      current
    DESCRIPTION 
        "Specifies the managed switching element network element 
         aliases. This value can be set to any string by 
         management stations and the agent or managed device 
         will not restrict the management station's ability to 
         set this value."
    ::= { gcpMsEntry 12 }

gcpMsRowStatus OBJECT-TYPE
    SYNTAX      RowStatus
    MAX-ACCESS  read-create
    STATUS      current
    DESCRIPTION 
        "Provides a mechanism whereby management stations may 
         create and delete entries in this table.  Entries 
         created by management stations survive agent reboot."
    REFERENCE   
        "ITU-T Rec. M.3100 (1995) managedElement-network NAME 
               BINDING."
    ::= { gcpMsEntry 13 }

gcpMg OBJECT IDENTIFIER
    ::= { gcpTables 2 }

gcpMgTable OBJECT-TYPE
    SYNTAX      SEQUENCE OF GcpMgEntry
    MAX-ACCESS  not-accessible
    STATUS      current
    DESCRIPTION 
        "This table lists all of the Media Gateway devices known to this 
         managed system.  When the management view is that of a managed 
         system containing Media Gateway Controllers, this table 
         characterizes all of the MG with which a Media Gateway 
         Controller in the managed system might communicate or 
         reference.  When the management view is that of a managed 
         system containing Media Gateways, this table characterizes all 
         of the MG in the managed system as well as all of the MG that 
         might be backing up an MG within the managed system, or that an 
         MG within the managed system might be backing up.
         
         A physical Media Gateway may be partitioned into one or more 
         Virtual MGs (VMGs).  A Virtual MG consists of a set of 
         statically partitioned physical terminations and/or sets of 
         ephemeral terminations.  A physical termination is controlled by 
         one MGC.  The model does not require that other resources be 
         statically allocated, just terminations.  The mechanism for 
         allocating terminations to Virtual MGs is managed by this MIB.  
         Each of the virtual MGs appears to the MGC as a complete MG 
         client.
         
         A physical MG may have only one network interface, which must be 
         shared across virtual MGs.  In such a case, the packet/cell side 
         termination is shared.  It should be noted, however, that in 
         use, such interfaces require an ephemeral instance of the 
         termination to be created per flow, and thus sharing the 
         termination is straightforward.  This mechanism does lead to 
         a complication, namely that the MG must always know which of its 
         controlling MGCs should be notified if an event occurs on the 
         interface.
         
         In normal operation, the virtual MG will be instructed by the 
         MGC to create network flows (if it is the originating side), or 
         to expect flow requests (if it is the terminating side), and no 
         confusion will arise.  However, if an unexpected event occurs, 
         the virtual MG must know what to do with respect to the physical 
         resources it is controlling.
         
         If recovering from the event requires manipulation of a physical 
         interface's state, only one MGC should do so.  These issues are 
         resolved by allowing any of the MGCs to create Event Descriptors 
         to be notified of such events, but only one MGC can have 
         read/write access to the physical interface properties; all 
         other MGCs have read-only access.  The management mechanism is 
         used to designate which MGC has read/write capability, and is 
         designated the Master MGC.
         
         Each virtual MG has its own Root Termination.  In most cases, 
         the values for the properties of the Root Termination are 
         independently settable by each MGC.  Where there can only be one 
         value, the parameter is read-only to all but the Master MGC.
         
         ServiceChange may only be applied to a termination or set of 
         terminations partitioned to the Virtual MG or created (in the 
         case of ephemeral terminations) by that Virtual MG."
    ::= { gcpMg 1 }

gcpMgEntry OBJECT-TYPE
    SYNTAX      GcpMgEntry
    MAX-ACCESS  not-accessible
    STATUS      current
    DESCRIPTION 
        "Each row in the gcpMgTable represents a Media Gateway (MG) that 
         is known to the managed system.  This includes both Media 
         Gateways that are part of the managed systems, as well as Media 
         Gateways that are external to the managed system.  Media 
         Gateways are present in this table when:
         
         1. The MG is internal to the managed system.
            
         2. The MG is external to the managed system but is allowed to 
            communicate with an MGC internal to the managed system.
            
         3. The MG is external to the managed system but backs up or is 
            backed up by an MG internal to the managed system."
    INDEX       { gcpMsId, gcpMgId }
    ::= { gcpMgTable 1 }

GcpMgEntry ::= SEQUENCE {
    gcpMgId                 Unsigned32,
    gcpMgLocation           INTEGER,
    gcpMgName               CommonLanguageName,
    gcpMgDomainName         SnmpAdminString,
    gcpMgDeviceName         SnmpAdminString,
    gcpMgMtpAddress         NetworkPointCode,
    gcpMgAdminState         AdministrativeState,
    gcpMgOperState          OperationalState,
    gcpMgAlarmStatus        AlarmStatus,
    gcpMgAsaProfilePointer  RowPointer,
    gcpMgUsageState         UsageState,
    gcpMgAvailStatus        AvailabilityStatus,
    gcpMgProcStatus         ProceduralStatus,
    gcpMgPg                 Unsigned32,
    gcpMgStandbyStatus      StandbyStatus,
    gcpMgRowStatus          RowStatus
}

gcpMgId OBJECT-TYPE
    SYNTAX      Unsigned32
    MAX-ACCESS  not-accessible
    STATUS      current
    DESCRIPTION 
        "Provides a non-zero ordinal index into the gcpMgTable.  This 
         value may also be used as an identifier of a row (MG) in this 
         table."
    ::= { gcpMgEntry 1 }

gcpMgLocation OBJECT-TYPE
    SYNTAX      INTEGER { internal(1), external(2) }
    MAX-ACCESS  read-create
    STATUS      current
    DESCRIPTION 
        "Specifies the location of the MG.  The MG can be located:
         
         - internal(1), the MG is internal to the managed system; the 
           managed system has direct control of the MG entity (the MG 
           entity lives and dies with the managed system);
           
         - external(2), the MG is external to the managed system; the 
           managed system only has control of the MG using 
           a communications linkage and protocol.
           
         Note that a managed system does not need to consist of just MG 
         or just MGC, but can be a mixture of the two.  Also, not all 
         configurations will have external MG entities in this table 
         (communication may be between internal GCP entities only)."
    ::= { gcpMgEntry 2 }

gcpMgName OBJECT-TYPE
    SYNTAX      CommonLanguageName
    MAX-ACCESS  read-create
    STATUS      current
    DESCRIPTION 
        "Provides a COMMON LANGUAGE NAME for this MG."
    ::= { gcpMgEntry 3 }

gcpMgDomainName OBJECT-TYPE
    SYNTAX      SnmpAdminString
    MAX-ACCESS  read-create
    STATUS      current
    DESCRIPTION 
        "Specifies the domain name that will be reported by the 
         MG in H.248/MEGACO messages on communications linkages 
         that select domainName(2) in the gcpLinkageMgIdent 
         column of the gcpLinkageTable."
    ::= { gcpMgEntry 4 }

gcpMgDeviceName OBJECT-TYPE
    SYNTAX      SnmpAdminString
    MAX-ACCESS  read-create
    STATUS      current
    DESCRIPTION 
        "Specifies the device name that will be reported by the 
         MG in H.248/MEGACO messages on communications linkages 
         that select deviceName(3) in the gcpLinkageMgIdent 
         column of the gcpLinkageTable."
    ::= { gcpMgEntry 5 }

gcpMgMtpAddress OBJECT-TYPE
    SYNTAX      NetworkPointCode
    MAX-ACCESS  read-create
    STATUS      current
    DESCRIPTION 
        "Specifies the MTP address (point code) that will be 
         reported by the MG in H.248/MEGACO messages on 
         communications linkages that select mtpAddress(4) in 
         the gcpLinkageMgIdent column of the gcpLinkageTable."
    REFERENCE   
        "OPENSS7-SS7-MIB:NewtorkPointCode"
    ::= { gcpMgEntry 6 }

gcpMgAdminState OBJECT-TYPE
    SYNTAX      AdministrativeState
    MAX-ACCESS  read-create
    STATUS      current
    DESCRIPTION 
        "This attribute represents the administrative capability of the 
         Media Gateway to perform its function.  The following 
         administrative states are defined:
         
         - locked(0), use of the Media Gateway has been prohibited by 
           a management station; setting the value to locked(0) results 
           in the immediate and disruptive withdrawal from service of 
           the Media Gateway.
           
         - unlocked(1), use of the Media Gateway has been permitted by 
           a management station;
           
         - shuttingDown(2), use of the Media Gateway is administratively 
           permitted to existing instances of use only.  While the 
           system remains in the shutting down state, the management 
           station may at any time cause the Media Gateway to revert to 
           the unlocked(1) state; setting the Media Gateway to 
           shuttingDown(2) results in the graceful withdrawal from 
           service of the Media Gateway; once all users of the Media 
           Gateway have withdrawn, the state will change autonomously to 
           locked(0).
           
         Whenever the administrative state of a Media Gateway is 
         changed, a state change notification is generated."
    REFERENCE   
        "ITU-T Rec. X.721 (1992) | ISO/IEC 10165-2 : 1992, 
               administrativeState attribute."
    ::= { gcpMgEntry 7 }

gcpMgOperState OBJECT-TYPE
    SYNTAX      OperationalState
    MAX-ACCESS  read-only
    STATUS      current
    DESCRIPTION 
        "Provides the operational state of the Media Gateway in 
         accordance with the OperationalState textual convention and 
         ITU-T Rec.  X.721 | ISO/IEC 10165-2.  The defined states are:
         
         - enabled(0), the Media Gateway is operational and ready for 
           use;
           
         - disable(1), the Media Gateway is not available for use.
           
         A change in operational state shall generate a state change 
         notification."
    REFERENCE   
        "ITU-T Rec. X.721 (1992) | ISO/IEC 10165-2 : 1992, 
               operationalState attribute."
    ::= { gcpMgEntry 8 }

gcpMgAlarmStatus OBJECT-TYPE
    SYNTAX      AlarmStatus
    MAX-ACCESS  read-create
    STATUS      current
    DESCRIPTION 
        "Provides the alarm status of the MG following the 
         AlarmStatus textual convention and ITU-T Rec. X.721 
         (1992) | ISO/IEC 10165-2 : 1992.  This object is 
         set-valued and can report the following conditions:
         
         - underRepair(0), the MG is being repaired; the 
           operational state is disabled or enabled;
           
         - critical(1), one or more critical alarms indicating 
           a fault have been detected in the MG and have not 
           been cleared; the operational state is either 
           disabled or enabled;
           
         - major(2), one or more major alarms indicating a fault 
           have been detected in the MG, and have not been 
           cleared; the operational state is enabled or 
           disabled;
           
         - minor(3), one or more minor alarms indicating a fault 
           have been detected in the MG element, and have not 
           yet been cleared; 
           
         - alarmOutstanding(4), one or more alarms have been 
           detected in the resource, the condition of which may 
           or may not be disabling.
           
         The presence of the above alarm state conditions do not 
         suppress the generation of future fault-related 
         notifications.
         
         Values that can be added to the set by a management 
         station includes only the underRepair(0) condition.  
         Values that can be removed from the set are 
         critical(1), major(2), minor(3) and 
         alarmOutstanding(4).  Removing conditions from the set 
         are for performing manual alarm clearing from 
         a management station."
    REFERENCE   
        "ITU-T Rec. Q.751.1 (1997), ANSI T1.116.1 (2000) 
               : alarmStatus attribute.
         ITU-T Rec. X.721 (1992) | ISO/IEC 10165-2 : 1992, 
               Attribute-ASN1Module.AlarmStatus.
         ITU-T Rec. X.731 (1992) | ISO/IEC 10164-2 : 1993, 
               Section 8.1.2.1."
    ::= { gcpMgEntry 9 }

gcpMgAsaProfilePointer OBJECT-TYPE
    SYNTAX      RowPointer
    MAX-ACCESS  read-create
    STATUS      current
    DESCRIPTION 
        "Provides a pointer to an alarm severity assignment 
         profile to be used for alarms generated by this 
         media gateway, or zeroDotZero to use the default 
         mapping associated with the media gateway as described 
         in this MIB."
    REFERENCE   
        "ITU-T Rec. Q.751.1 (1997), ANSI T1.116.1 (2000), 
               alarmSeverityAssignmentProfilePointer attribute."
    DEFVAL      { zeroDotZero }
    ::= { gcpMgEntry 10 }

gcpMgUsageState OBJECT-TYPE
    SYNTAX      UsageState
    MAX-ACCESS  read-only
    STATUS      current
    DESCRIPTION 
        "Provides the usage state of the Media Gateway in accordance 
         with the UsageState textual convention and ITU-T Rec. X.721 
         | ISO/IEC 10165-2.  This object is single-valued and read only.  
         It can have one of the following values:
         
         - idle(0), the Media Gateway is not currently in use;
         
         - active(1), the Media Gateway is in use, and has sufficient 
           spare operating capacity to provide for additional users 
           simultaneously;
           
         - busy(2), the Media Gateway is in use, but it has no spare 
           operating capacity to provide for additional users at this 
           instant.
           "
    REFERENCE   
        "ITU-T Rec. X.721 (1992) | ISO/IEC 10165-2 : 1992, 
               Attribute-ASN1Module.UsageState.
         ITU-T Rec. X.731 (1992) | ISO/IEC 10164-2 : 1993, 
               Section 8.1.1.2."
    ::= { gcpMgEntry 11 }

gcpMgAvailStatus OBJECT-TYPE
    SYNTAX      AvailabilityStatus
    MAX-ACCESS  read-only
    STATUS      current
    DESCRIPTION 
        "This is the availability status of the Media Gateway in 
         accordance with the AvailabiltiyStatus textual convention and 
         ITU-T Rec. X.721 | ISO/IEC 10165-2.  This object is set-valued 
         and read-only and can have zero or more of the values that 
         follow.  When the value of this attribute is empty, this 
         implies that none of the status conditions described below are 
         present.
         
         - inTest(0), the Media Gateway is undergoing a test procedure.  
           If the administrative state is locked or shutting down, then 
           normal users are precluded from using the resource and the 
           control status attribute has the value reserved for test.  
           Tests that do not exclude additional users can be present in 
           any operational or administrative state but the reserved for 
           test condition should not be present.
           
         - failed(1), the Media Gateway has an internal fault that 
           prevents it from operating.  The operational state is 
           disabled.
           
         - powerOff(2), the Media Gateway requires power to be applied 
           and is not powered on.  For example, a fuse or other 
           protection device is known to have removed power or a low 
           voltage condition has been detected.  The operational state 
           is disabled.
           
         - offLine(3), the Media Gateway requires a routing operation to 
           be performed to place it online and make it available for 
           use.  The operation may be manual or automatic or both.  The 
           operational state is disabled.
           
         - offDuty(4), the Media Gateway has been made inactive by an 
           internal control process in accordance with a predetermined 
           time schedule.  Under normal conditions the control process 
           can be expected to reactivate the Media Gateway at some 
           scheduled time, and it is therefore considered to be 
           optional.  The operational state is either enabled or 
           disabled.
           
         - dependency(5), the Media Gateway cannot operate because some 
           other resource on which it depends is (i.e, a resource not 
           represented by the same managed object) unavailable.  For 
           example, a device is not accessible because its controller is 
           powered off.  The operational state is disabled.
           
         - degraded(6), the service available from the Media Gateway is 
           degraded in some respect, such as in speed or operating 
           capacity.  Failure of a test or an unacceptable performance 
           measurement has established that some or all services are not 
           functional or are degraded due to the presence of a defect.  
           However, the Media Gateway remains available for service, 
           either because some services are satisfactory or because 
           degraded service is preferable to no service at all.  The 
           operational state is enabled.
           
         - notInstalled(7), the managed object representing the Media 
           Gateway is not present, or is incomplete.  For example, 
           a plug-in module is missing, a cable is disconnected or 
           a software module is not loaded.  The operational state is 
           disabled.
           
         - logFull(8), this indicates a log full condition, the 
           semantics of which are defined in ITU-T Rec. X.735.
           "
    REFERENCE   
        "ITU-T Rec. X.721 (1992) | ISO/IEC 10165-2 : 1992, 
               Attribute-ASN1Module.AvailabilityStatus
         ITU-T Rec. X.731 (1992) | ISO/IEC 10164-2 : 1993, 
               Section 8.1.2.3."
    ::= { gcpMgEntry 12 }

gcpMgProcStatus OBJECT-TYPE
    SYNTAX      ProceduralStatus
    MAX-ACCESS  read-only
    STATUS      current
    DESCRIPTION 
        "Provides the procedural status of the Media Gateway in 
         accordance with the ProceduralStatus textual convention of the 
         OPENSS7-SMI-MIB and ITU-T Rec. X.721 | ISO/IEC 10165-2.  The 
         procedural status can have zero or more of the following 
         conditions:
         
         - initializationRequired(0), the MG requires initialization to 
           be invoked by the manager before it can perform its normal 
           functions, and this procedure has not been initiated.  The 
           management may be able to invoke such a initialization 
           through an action.  The terminating(4) condition may also be 
           present.  The operational state is disabled.
           
         - notInitialized(1), the MG requires initialization before it 
           can perform its normal functions, and this procedure has not 
           been initiated.  The MG initializes itself autonomously.  The 
           operational state is disabled.
           
         - initializing(2), the MG requires initialization before it can 
           perform its normal functions, and this procedure has been 
           initiated, but is not yet complete.  When this condition is 
           present, the initializationRequred(0) and notInitialized(1) 
           conditions are absent.  The operational state is disabled.
           
         - reporting(3), the MG has failed and is reporting failure.
           
         - terminating(4), the MG is in a termination phase.  If the MG 
           does not reinitialize itself autonomously, the 
           intializationRequired(0) condition is also present and the 
           operational state is disabled; otherwise, the operational 
           state is disabled.
           
         Note that when the MG in question is remote to the managed 
         system, this is the view of the procedural status of the MG as 
         discerned by the managed system and depends on the procedural 
         status of the communications linkage to the MG."
    REFERENCE   
        "ITU-T Rec. X.721 (1992) | ISO/IEC 10165-2 : 1992, 
               Attribute-ASN1Module.ProceduralStatus.
         ITU-T Rec. X.731 (1992) | ISO/IEC 10164-2 : 1993, 
               Section 8.1.2.2."
    ::= { gcpMgEntry 13 }

gcpMgPg OBJECT-TYPE
    SYNTAX      Unsigned32
    MAX-ACCESS  read-create
    STATUS      current
    DESCRIPTION 
        "Specifies the protection group to which this Media Gateway 
         belongs as an index into the protectionGroupTable.  The value 
         is the value of the protectionGroupId that indexes a specific 
         protection group within the protectionGroupTable.  When there 
         is no protection group associated with the Media Gateway, this 
         value is zero (0)."
    REFERENCE   
        "ITU-T Rec. M.3100 (2005) : protectionGroupR2 MOC
         ITU-T Rec. G.744.3 : protectionGroupR1 MOC"
    ::= { gcpMgEntry 14 }

gcpMgStandbyStatus OBJECT-TYPE
    SYNTAX      StandbyStatus
    MAX-ACCESS  read-create
    STATUS      current
    DESCRIPTION 
        "Provides the standby status of the Media Gateway.  This entry 
         is used to indicate MG mirroring arrangements such as IP 
         takeover.  The type is single-valued and read-only and can 
         assume the following values:
         
         - hotStandby(0), the Media Gateway is not providing service but 
           is operating in synchronism with another MG (on another host) 
           that is to be backed-up.  A Media Gateway  with a hot standby 
           status will be immediately able to take over the role of the 
           MG to be backed up, without the need for initialization 
           activity, and will contain the same information as the MG 
           being backed up.  The operational state during this status is 
           enabled(0) and the administrative state is unlocked(0).  The 
           availability status is offLine(3);
         
         - coldStandby(1), the Media Gateway is to back-up another MG 
           (perhaps on another host), but is not synchronized with that 
           resource.  A Media Gateway with a cold standby status will 
           not immediately be able to take over the role of a resource 
           to be backed up, and will require some initialization 
           activity.  The operational state is enabled(0) or 
           disabled(1); the administrative state is locked(0) or 
           unlocked(1); procedural status contains not initialized or 
           initialization required; availability status is offLine(3);
         
         - providingService(2), the back-up Media Gateway is providing 
           service and is backing up another MG (perhaps on a different 
           host).  The administrative state is unlocked(1); availability 
           status is online().
           
         This status is only meaningful when gcpMgPg is non-zero: that 
         is, the MG belongs to a protection group.  When the gcpMgPg is 
         zero (the MG is unprotected), this object will always report 
         providingService(2)."
    REFERENCE   
        "ITU-T Rec. X.721 (1992) | ISO/IEC 10165-2 : 1992, 
               Attribute-ASN1Module.StandbyStatus.
         ITU-T Rec. X.731 (1992) | ISO/IEC 10164-2 : 1993, 
               Section 8.1.2.5."
    ::= { gcpMgEntry 15 }

gcpMgRowStatus OBJECT-TYPE
    SYNTAX      RowStatus
    MAX-ACCESS  read-create
    STATUS      current
    DESCRIPTION 
        "Provides a mechanism whereby management stations may create or 
         delete rows in this table."
    REFERENCE   
        "STD 58, SNMPv2-TC RowStatus."
    ::= { gcpMgEntry 16 }

gcpMgc OBJECT IDENTIFIER
    ::= { gcpTables 3 }

gcpMgcTable OBJECT-TYPE
    SYNTAX      SEQUENCE OF GcpMgcEntry
    MAX-ACCESS  not-accessible
    STATUS      current
    DESCRIPTION 
        "This table lists all of the Media Gateway Controller devices 
         known to this managed system.  When the management view is that 
         of a managed system containing Media Gateways, this table 
         characterizes all of the MGC with which a Media Gateway in the 
         managed system might communicate or reference.  When the 
         management view is that of a managed system containing Media 
         Gateway Controllers, this table characterizes all of the MGC in 
         the managed system as well as all of the MGC that might be 
         backing up an MGC within the managed system, or that an MGC 
         within the manged system might be backing up."
    ::= { gcpMgc 1 }

gcpMgcEntry OBJECT-TYPE
    SYNTAX      GcpMgcEntry
    MAX-ACCESS  not-accessible
    STATUS      current
    DESCRIPTION 
        "Each row in the gcpMgcTable represents a Media Gateway 
         Controller (MGC) that is known to the managed system.  This 
         include both internal and external MGC.  MGC are present in 
         this table when:
         
         1. The MGC is internal to the managed system.
            
         2. The MGC is external to the managed system but an MG internal 
            to the managed system is configured to communicate with it.
            
         3. The MGC is external to the managed system but backs up or is 
            backed up by an MGC internal to the managed system."
    INDEX       { gcpMsId, gcpMgcId }
    ::= { gcpMgcTable 1 }

GcpMgcEntry ::= SEQUENCE {
    gcpMgcId                    Unsigned32,
    gcpMgcLocation              INTEGER,
    gcpMgcName                  CommonLanguageName,
    gcpMgcDomainName            SnmpAdminString,
    gcpMgcDeviceName            SnmpAdminString,
    gcpMgcMtpAddress            NetworkPointCode,
    gcpMgcAdminState            AdministrativeState,
    gcpMgcOperState             OperationalState,
    gcpMgcAlarmStatus           AlarmStatus,
    gcpMgcAsaProfilePointer     RowPointer,
    gcpMgcUsageState            UsageState,
    gcpMgcAvailStatus           AvailabilityStatus,
    gcpMgcProcStatus            ProceduralStatus,
    gcpMgcPg                    Unsigned32,
    gcpMgcStandbyStatus         StandbyStatus,
    gcpMgcRowStatus             RowStatus
}

gcpMgcId OBJECT-TYPE
    SYNTAX      Unsigned32
    MAX-ACCESS  not-accessible
    STATUS      current
    DESCRIPTION 
        "Provides a non-zero ordinal index into the gcpMgcTable.  This 
         value may also be used as an identifier of a row (MGC) in this 
         table."
    ::= { gcpMgcEntry 1 }

gcpMgcLocation OBJECT-TYPE
    SYNTAX      INTEGER { internal(1), external(2) }
    MAX-ACCESS  read-create
    STATUS      current
    DESCRIPTION 
        "Specifies the location of the MGC.  The MGC can be located:
         
         - internal(1), the MGC is internal to the managed system; the 
           managed system has direct control of the MGC entity (the MGC 
           entity lives and dies with the managed system);
           
         - external(2), the MGC is external to the managed system; the 
           managed system only has control of the MGC using 
           a communications linkage and protocol.
           
         Note that a managed system does not need to consist of just MGC 
         or just MGC, but can be a mixture of the two.  Also, not all 
         configurations will have external MGC entities in this table 
         (communication may be between internal GCP entities only)."
    ::= { gcpMgcEntry 2 }

gcpMgcName OBJECT-TYPE
    SYNTAX      CommonLanguageName
    MAX-ACCESS  read-create
    STATUS      current
    DESCRIPTION 
        "Provides a COMMON LANGUAGE NAME for this MG."
    ::= { gcpMgcEntry 3 }

gcpMgcDomainName OBJECT-TYPE
    SYNTAX      SnmpAdminString
    MAX-ACCESS  read-create
    STATUS      current
    DESCRIPTION 
        "Specifies the domain name that will be reported by the 
         MGC in H.248/MEGACO message on communications linkages 
         that select domainName(2) in the gcpLinkageMgcIdent 
         column of the gcpLinkageTable."
    ::= { gcpMgcEntry 4 }

gcpMgcDeviceName OBJECT-TYPE
    SYNTAX      SnmpAdminString
    MAX-ACCESS  read-create
    STATUS      current
    DESCRIPTION 
        "Specifies the device name that will be reported by the 
         MG in H.248/MEGACO messages on communications linkages 
         that select deviceName(3) in the gcpLinkageMgcIdent 
         column of the gcpLinkageTable."
    ::= { gcpMgcEntry 5 }

gcpMgcMtpAddress OBJECT-TYPE
    SYNTAX      NetworkPointCode
    MAX-ACCESS  read-create
    STATUS      current
    DESCRIPTION 
        "Specifies the MTP address (point code) that will be 
         reported by the MG in H.248/MEGACO messages on 
         communications linkages that select mtpAddress(4) in 
         the gcpLinkageMgcIdent column of the gcpLinkageTable."
    REFERENCE   
        "OPENSS7-SS7-MIB:NetworkPointCode"
    ::= { gcpMgcEntry 6 }

gcpMgcAdminState OBJECT-TYPE
    SYNTAX      AdministrativeState
    MAX-ACCESS  read-create
    STATUS      current
    DESCRIPTION 
        "This attribute represents the adminstrative capability of the 
         Media Gateway Controller to perform its function.  The 
         following administrative states are defined:
         
         - locked(0), use of the Media Gateway Controller has been 
           prohibited by a management station; setting the value to 
           locked(0) results in the immediate and disruptive withdrawa 
           from service of the Media Gateway Controller.
           
         - unlocked(1), use of the Media Gateway Controller has been 
           permitted by a management station;
           
         - shuttingDown(2), use of the Media Gateway Controller has been 
           administratively permitted to existing instances of use only.  
           While the system remains in the shutting down state, the 
           management station may at any time cause the Media Gateway 
           Controller to revert to the unlocked(1) state.  Setting the 
           Media Gateway Controller to shuttingDown(2) results in the 
           graceful withdrawal from service of the Media Gateway 
           Controller.  Once all users of the Media Gateway Controller 
           have withdrawn, the state will change autonomously to 
           locked(0).
         
         Whenever the administrative state of a Media Gateway Controller 
         is changed, a state change notification is generated."
    REFERENCE   
        "ITU-T Rec. X.721 (1992) | ISO/IEC 10165-2 : 1992, 
               administrativeState attribute."
    ::= { gcpMgcEntry 7 }

gcpMgcOperState OBJECT-TYPE
    SYNTAX      OperationalState
    MAX-ACCESS  read-create
    STATUS      current
    DESCRIPTION 
        "Provides the operational state of the Media Gateway Controller 
         in accordance with the OperationalState textual convention and 
         ITU-T Rec. X.721 | ISO/IEC 10165-2.  The defined states are:
         
         - enabled(0), the Media Gateway Controller is operational and 
           ready for use;
         - disabled(1), the Media Gateway Controller is not available 
           for use.
           
         A change in operational state shall generate a state change 
         notification."
    REFERENCE   
        "ITU-T Rec. X.721 (1992) | ISO/IEC 10165-2 : 1992, 
               operationalState attribute."
    ::= { gcpMgcEntry 8 }

gcpMgcAlarmStatus OBJECT-TYPE
    SYNTAX      AlarmStatus
    MAX-ACCESS  read-create
    STATUS      current
    DESCRIPTION 
        "Provides the alarm status of the MGC following the 
         AlarmStatus textual convention and ITU-T Rec. X.721 
         (1992) | ISO/IEC 10165-2 : 1992.  This object is 
         set-valued and can report the following conditions:
         
         - underRepair(0), the MGC is being repaired; the 
           operational state is disabled or enabled;
           
         - critical(1), one or more critical alarms indicating 
           a fault have been detected in the MGC and have not 
           been cleared; the operational state is either 
           disabled or enabled;
           
         - major(2), one or more major alarms indicating a fault 
           have been detected in the MGC, and have not been 
           cleared; the operational state is enabled or 
           disabled;
           
         - minor(3), one or more minor alarms indicating a fault 
           have been detected in the MGC element, and have not 
           yet been cleared; 
           
         - alarmOutstanding(4), one or more alarms have been 
           detected in the resource, the condition of which may 
           or may not be disabling.
           
         The presence of the above alarm state conditions do not 
         suppress the generation of future fault-related 
         notifications.
         
         Values that can be added to the set by a management 
         station includes only the underRepair(0) condition.  
         Values that can be removed from the set are 
         critical(1), major(2), minor(3) and 
         alarmOutstanding(4).  Removing conditions from the set 
         are for performing manual alarm clearing from 
         a management station."
    REFERENCE   
        "ITU-T Rec. Q.751.1 (1997), ANSI T1.116.1 (2000) 
               : alarmStatus attribute.
         ITU-T Rec. X.721 (1992) | ISO/IEC 10165-2 : 1992, 
               Attribute-ASN1Module.AlarmStatus.
         ITU-T Rec. X.731 (1992) | ISO/IEC 10164-2 : 1993, 
               Section 8.1.2.1."
    ::= { gcpMgcEntry 9 }

gcpMgcAsaProfilePointer OBJECT-TYPE
    SYNTAX      RowPointer
    MAX-ACCESS  read-create
    STATUS      current
    DESCRIPTION 
        "Provides a pointer to an alarm severity assignment 
         profile to be used for alarms generated by this media 
         gateway controller, or zeroDotZero to use the default 
         mapping associated with the media gateway controller as 
         described in this MIB."
    REFERENCE   
        "ITU-T Rec. Q.751.1 (1997), ANSI T1.116.1 (2000), 
               alarmSeverityAssignmentProfilePointer attribute."
    DEFVAL      { zeroDotZero }
    ::= { gcpMgcEntry 10 }

gcpMgcUsageState OBJECT-TYPE
    SYNTAX      UsageState
    MAX-ACCESS  read-create
    STATUS      current
    DESCRIPTION 
        "Provides the usage state of the Media Gateway Controller in 
         accordance with the UsageState textual convention and ITU-T 
         Rec. X.721 | ISO/IEC 10165-2.  This object is single-valued and 
         read only.  The defined states are:
         
         - idle(0), the Media Gateway Controller is not currently in 
           used;
           
         - active(1), the Media Gateway Controller is in use, and has 
           sufficient spare operating capacity to provide for additional 
           users simultaneously;
           
         - busy(2), the Media Gateway Controller is in use, but it has 
           no spare operating capacity to provide for additional users 
           at this instant."
    REFERENCE   
        "ITU-T Rec. X.721 (1992) | ISO/IEC 10165-2 : 1992, 
               Attribute-ASN1Module.UsageState.
         ITU-T Rec. X.731 (1992) | ISO/IEC 10164-2 : 1993, 
               Section 8.1.1.2."
    ::= { gcpMgcEntry 11 }

gcpMgcAvailStatus OBJECT-TYPE
    SYNTAX      AvailabilityStatus
    MAX-ACCESS  read-only
    STATUS      current
    DESCRIPTION 
        "Provides the availability status of the Media Gateway 
         Controller in accordance with the AvailabilityStatus textual 
         convention and ITU-T Rec. X.721 | ISO/IEC 10165-2.  This object 
         is set-valued and read-only and can report any set of the 
         following conditions:
         
         - inTest(0), the Media Gateway Controller is undergoing a test 
           procedure.  If the administrative state is locked(0), or 
           shuttingDown(2), then normal users are precluded from using 
           the MGC and the control status attribute has the value 
           reserved for test.  Tests that do not exclude additional 
           users can be present in any operational or administrative 
           state but the reserved for test condition should not be 
           present.
           
         - failed(1), the Media Gateway Controller has an internal fault 
           that prevents it from operating.  The operational state is 
           disabled.
           
         - powerOff(2), the Media Gateway Controller requires power to 
           be applied and is not powered on.  The operational state is 
           disabled.
           
         - offLine(3), the Media Gateway Controller requires a routing 
           operation to be performed to place it online and make it 
           available for use.  The operation may be manual or automatic 
           or both.  The operational state is disabled.
           
         - offDuty(4), the Media Gateway Controller has been made 
           inactive by an internal control process in accordance with 
           a predetermined time schedule.  Under normal conditions the 
           control process can be expected to reactivate the Media 
           Gateway Controller at some scheduled time, and it is 
           therefore considered to be optional.  The operational state 
           is either enabled or disable.
           
         - dependency(5), the Media Gateway Controller cannot operatre 
           because some other resource on which it depends is 
           unavailable.  The operational state is disabled.
           
         - degraded(6), the service available from the Media Gateway 
           Controller is degraded in some respect, such as in speed or 
           operating capacity.  Failure of a test or an unacceptable 
           performance measurement has established that some or all 
           services are not functional or are degraded due to the 
           presence of a defect.  However, the Media Gateway Controller 
           remains available for service, either because some services 
           are satisfactory or because degraded service is preferable to 
           no service at all.  The operational state is enabled.
           
         - notInstalled(7), the Media Gateway Controller is not present, 
           or is incomplete.  The operational state is disabled.
           
         - logFull(8), this indicates a log full condition, the 
           semantics of which are defined in ITU-T Rec. X.735.
         
         Note that these semantics are from the viewpoint of the managed 
         system.  When the MGC is external to the managed system, this 
         is the external view; where internal, the internal view.  Note 
         also that when the view is external that this is the view of 
         the MGC and not the availability status of the communications 
         linkage (which is handled by the gcpLinkageAvailStatus column 
         of the gcpLinkageTable)."
    REFERENCE   
        "ITU-T Rec. X.721 (1992) | ISO/IEC 10165-2 : 1992, 
               Attribute-ASN1Module.AvailabilityStatus
         ITU-T Rec. X.731 (1992) | ISO/IEC 10164-2 : 1993, 
               Section 8.1.2.3."
    ::= { gcpMgcEntry 12 }

gcpMgcProcStatus OBJECT-TYPE
    SYNTAX      ProceduralStatus
    MAX-ACCESS  read-only
    STATUS      current
    DESCRIPTION 
        "Provides the procedural status of the Media Gateway Controller 
         in accordance with the ProceduralStatus textual convention of 
         the OPENSS7-SMI-MIB and ITU-T Rec. X.721 | ISO/IEC 10165-2.  
         The procedural status can report any set of the following 
         conditions:
         
         - initializationRequired(0), the MGC requires initialization to 
           be invoked by the manager before it can perform its normal 
           functions, and this procedure has not been initiated.  The 
           management may be able to invoke such an initialization 
           through an action.  The terminating(4) condition may also be 
           present.  The operational state is disabled.
           
         - notInitialized(1), the MGC requires initialization before it 
           can perform its normal functions, and this procedure has not 
           been initiated.  The MGC initializes itself autonomously.  
           The operational state is disabled.
         
         - initializing(2), the MGC requires initialization before it can 
           perform its normal functions, and this procedure has been 
           initiated, but is not yet complete.  When this condition is 
           present, the initializationRequired(0) and notInitialized(1) 
           conditions are absent, since initialization has already 
           begun.  The operational state is disabled.
           
         - reporting(3), the MGC has failed and is reporting failure.
           
         - terminating(4), the MGC is in a termination phase.  If the 
           MGC does not reinitialize itself autonomously, the 
           initializationRequired(0) condition is also present and the 
           operational state is disabled; otherwise, the operational 
           state is disabled.
           
         Note that when the MGC in question is remote to the managed 
         system, this is the view of the procedural status of the remote 
         MGC as discerned by the managed system and depends on the 
         procedural status of the communications linkage to the MGC."
    REFERENCE   
        "ITU-T Rec. X.721 (1992) | ISO/IEC 10165-2 : 1992, 
               Attribute-ASN1Module.ProceduralStatus.
         ITU-T Rec. X.731 (1992) | ISO/IEC 10164-2 : 1993, 
               Section 8.1.2.2."
    ::= { gcpMgcEntry 13 }

gcpMgcPg OBJECT-TYPE
    SYNTAX      Unsigned32
    MAX-ACCESS  read-create
    STATUS      current
    DESCRIPTION 
        "Specifies the protection group corresponding to which this 
         Media Gateway Controller belongs as an index into the 
         protectionGroupTable.  The value is the value of the 
         protectionGroupId that indexes a specific protection group 
         within the protectionGroupTable.  When there is no protection 
         group associated with the Media Gateway Controller, this value 
         is zero (0)."
    REFERENCE   
        "ITU-T Rec. M.3100 (2005) : protectionGroupR2 MOC
         ITU-T Rec. G.744.3 : protectionGroupR1 MOC"
    ::= { gcpMgcEntry 14 }

gcpMgcStandbyStatus OBJECT-TYPE
    SYNTAX      StandbyStatus
    MAX-ACCESS  read-create
    STATUS      current
    DESCRIPTION 
        "Provides the standby status of the Media Gateway Controller, in 
         accordance with the StandbyStatus textual convention and ITU-T 
         Rec. X.721 | ISO/IEC 10165-2.  This entry is used to indicate 
         MGC sparing arrangements such as those described in ITU-T Rec. 
         H.248.1.  The type is single-valued and can assume one of the 
         following defined conditions:
         
         - hotStandby(0), the MGC is not providing service, but is 
           operating in synchronism with another MGC (on another host) 
           that is to be backed-up.  A Media Gateway Controller with 
           a hot standby status will be immediately able to take over 
           the role of the MGC to be backed up, without the need for 
           initialization activity, and will contain the same 
           information as the MGC being backed up.  The operational 
           state during this status is enabled(0) and the administrative 
           state is unlocked(0).  The availability status is offLine(3).
           
         - coldStandby(1), the MGC is to back-up another MGC (on another 
           host), but is not synchronized with that resource.  An MGC 
           with a cold standby status will not immediately be able to 
           take over the role of the MGC to be backed up, and will 
           require some initialization activity.  The operational state 
           is enabled(0) or disabled(1); the administrative state is 
           locked(0) or unlocked(1); the procedural status contains 
           notInitialized(1) or initializationRequired(0); availability 
           status is offLine(3).
           
         - providingService(2), the back-up MGC is providing service and 
           is backing up another MGC (on a different host).  The 
           administrative state is unlocked(1); availability status is 
           online.
           
         This status is only meaningful when gcpMgcPg is non-zero: that 
         is, the MGC belongs to a protection group.  When the gcpMgcPg 
         is zero (the MGC is unprotected), this object will always 
         report providingService(2)."
    REFERENCE   
        "ITU-T Rec. X.721 (1992) | ISO/IEC 10165-2 : 1992, 
               Attribute-ASN1Module.StandbyStatus.
         ITU-T Rec. X.731 (1992) | ISO/IEC 10164-2 : 1993, 
               Section 8.1.2.5."
    ::= { gcpMgcEntry 15 }

gcpMgcRowStatus OBJECT-TYPE
    SYNTAX      RowStatus
    MAX-ACCESS  read-create
    STATUS      current
    DESCRIPTION 
        "Provides a mechanism whereby management stations may create or 
         delete rows in this table."
    REFERENCE   
        "STD 58, SNMPv2-TC RowStatus."
    ::= { gcpMgcEntry 16 }

gcpLinkage OBJECT IDENTIFIER
    ::= { gcpTables 4 }

gcpLinkageTable OBJECT-TYPE
    SYNTAX      SEQUENCE OF GcpLinkageEntry
    MAX-ACCESS  not-accessible
    STATUS      current
    DESCRIPTION 
        "This table provides a view of the communications association 
         between MG and MGC entities as viewed by the managed system.  
         This table provides configuration information for managed 
         system that have either MGC or MG contained within the managed 
         system.  For a managed system of media gateways, this provides 
         the media gateway view of the communications link to each MGC 
         from each MG within the managed system, or MG that is backing 
         up or backed up by an MG within the managed system.."
    ::= { gcpLinkage 1 }

gcpLinkageEntry OBJECT-TYPE
    SYNTAX      GcpLinkageEntry
    MAX-ACCESS  not-accessible
    STATUS      current
    DESCRIPTION 
        "Each entry in the gcpLinkageTable represents a communications 
         association between a media gateway and a media gateway 
         controller.  The managed system will not form an active 
         communications association between an MG and MGC that is not 
         listed in this table."
    INDEX       { gcpMsId, gcpMgId, gcpMsId, gcpMgcId }
    ::= { gcpLinkageTable 1 }

GcpLinkageEntry ::= SEQUENCE {
    gcpLinkageType              TransportAddressType,
    gcpLinkageMgcMaster         INTEGER,
    gcpLinkageMgcAddress        TransportAddress,
    gcpLinkageMgAddress         TransportAddress,
    gcpLinkageMgcIdent          MegacoIdentSelection,
    gcpLinkageMgIdent           MegacoIdentSelection,
    gcpLinkageProfile           RowPointer,
    gcpLinkageProtocol          AutonomousType,
    gcpLinkageEncoding          MegacoEncoding,
    gcpLinkageAuthAccess        MegacoAuthenticatedAccess,
    gcpLinkageAdminState        AdministrativeState,
    gcpLinkageOperState         OperationalState,
    gcpLinkageProcStatus        ProceduralStatus,
    gcpLinkageAvailStatus       AvailabilityStatus,
    gcpLinkageAuthentication    MegacoAuthentication,
    gcpLinkageMit               TimeInterval,
    gcpLinkageRowStatus         RowStatus
}

gcpLinkageType OBJECT-TYPE
    SYNTAX      TransportAddressType
    MAX-ACCESS  read-create
    STATUS      current
    DESCRIPTION 
        "Specifies the type of transport addresses used in this 
         communications linkage in accordance with the 
         TransportAddressType textual convention of the 
         TRANSPORT-ADDRESS-MIB."
    ::= { gcpLinkageEntry 1 }

gcpLinkageMgcMaster OBJECT-TYPE
    SYNTAX      INTEGER { master(1), slave(2) }
    MAX-ACCESS  read-create
    STATUS      current
    DESCRIPTION 
        "Specifies whether the MGC in this control association is 
         a Master MGC for the physical MG; that is, whether the MGC is 
         permitted to modify shared physical interfaces.  When master(1), 
         the MGC is a Master; slave(2), otherwise.  Only one protection 
         group of MGCs can be designated as master(1) for a given host.  
         Setting a different protection group of MGCs to master(1) will 
         cause all other protection groups of MGCs to be set to slave(2).  
         Setting one MGC in a protection group to master(1) will result 
         in all other MGC in the protect group to be set to master(1).  
         The same is true for a slave(2) setting.  Both rules are in 
         effect when the setting defaults to msater(1), or when 
         protection groups are formed or severed.  An MGC; however, can 
         be master(1) for one set of virtual MGs, and slave(2) for 
         another.
         
         A physical MG that is partitioned into multiple Virtual MGs that 
         are controlled by different MGC must always know which of its 
         controlling MGCs should be notified if an event occurs on the 
         interface.  Manipulation of a physical interface shared by the 
         virtual MGs should only be performed by one MGC.  Any of the 
         MGCs is allowed to create Events Descriptors to be notified of 
         shared events, but only one MGC can have read/write access to 
         the physical interface properties; all other MGCs have read-only 
         access.  The MGC with the read/write access is designated the 
         Master MGC."
    REFERENCE   
        "ITU-T Recommendation H.248.1 (09/2005), Clause 11.1, Multiple 
               Virtual MGs."
    DEFVAL      { master }
    ::= { gcpLinkageEntry 2 }

gcpLinkageMgcAddress OBJECT-TYPE
    SYNTAX      TransportAddress
    MAX-ACCESS  read-create
    STATUS      current
    DESCRIPTION 
        "Specifies the transport address of the MGC entity in 
         the transport address domain specified by 
         gcpLinkageType in accordance with the TransportAddress 
         textual convention of the TRANSPORT-ADDRESS-MIB.
         
         Where the MGC is internal to the managed system, this 
         address represents one of the transport addresses on 
         which the MGC will listen for connections from MG that 
         it controls.  Where the MGC is external to the managed 
         system, this is the transport address to which the 
         corresponding MG will attempt to connect.
         
         Both IP address and port number must be fully 
         specified."
    ::= { gcpLinkageEntry 3 }

gcpLinkageMgAddress OBJECT-TYPE
    SYNTAX      TransportAddress
    MAX-ACCESS  read-create
    STATUS      current
    DESCRIPTION 
        "Specifies the transport address of the MG entity in the 
         transport address domain specified by gcpLinkageType in 
         accordance with the TransportAddress textual convention 
         of the TRANSPORT-ADDRESS-MIB.
         
         Where the MG is internal to the managed system, this 
         address represents the address from which the MG will 
         attempt to connect to the MGC.  Where the MGC is 
         internal to the managed system, this is a specification 
         of the transport address from which the MGC expects to 
         be contacted by the MG.
         
         Where the IPv4 address is 0.0.0.0, it specifies that 
         the MG can use any IP address.  Where the transport 
         port number is zero (0), it specifies that the MG can 
         use any port number."
    ::= { gcpLinkageEntry 4 }

gcpLinkageMgcIdent OBJECT-TYPE
    SYNTAX      MegacoIdentSelection
    MAX-ACCESS  read-create
    STATUS      current
    DESCRIPTION 
        "Specifies how a local MGC will identify itself and 
         other MGC, or how a remote MGC is expected to identify 
         itself and other MGC, in H.248 messages.  One of:
         
         - ipAddress(1), the MGC will identify itself and other 
           MGC by IPv4 or IPv6 address and transport port;
           
         - domainName(2), the MGC will identify itself and other 
           MGC by domain name;
           
         - deviceName(3), the MGC will identify itself and other 
           MGC by device path;
           
         - mtpAddress(4), the MGC will identify itself and other 
           MGC by MTP Point Code.
           
         The setting of this value has no effect on protocols 
         other than H.248.  The default value is determined by 
         the setting of gcpDefaultMgcoIdent."
    REFERENCE   
        "ITU-T Recommendation H.248.1 (09/2005), Annex A, Mid 
               CHOICE."
    ::= { gcpLinkageEntry 5 }

gcpLinkageMgIdent OBJECT-TYPE
    SYNTAX      MegacoIdentSelection
    MAX-ACCESS  read-create
    STATUS      current
    DESCRIPTION 
        "Specifies how a local MG will identify itself, or how 
         a remote MG is expected to identify itself, in H.248 
         messages.  One of:
         
         - ipAddress(1), the MG will identify itself by its IPv4 
           or IPv6 address and transport port;
         
         - domainName(2), the MG will identify itself by its 
           domain name;
           
         - deviceName(3), the MG will identify itself by its 
           device name;
           
         - mtpAddress(4), the MG will identify itself by its MTP 
           Point Code."
    ::= { gcpLinkageEntry 6 }

gcpLinkageProfile OBJECT-TYPE
    SYNTAX      RowPointer
    MAX-ACCESS  read-create
    STATUS      current
    DESCRIPTION 
        "Provides a pointer to a transport parameters profile to 
         be used for this communications linkage.  This can be 
         a profile from the gcpUdpProfileTable, 
         gcpTcpProfileTable or gcpSctpProfileTable, or any other 
         table of profile parameters known to the managed 
         system.
         
         When unspecified (set to zeroDotZero), the protocol 
         parameters from the corresponding set of default 
         scalars (e.g, gcpDefaultSctpNoDelay) are used instead 
         of a profile.
         
         Changes made to this profile might not be effective 
         until the communications linkage is cycled."
    DEFVAL      { zeroDotZero }
    ::= { gcpLinkageEntry 7 }

gcpLinkageProtocol OBJECT-TYPE
    SYNTAX      AutonomousType
    MAX-ACCESS  read-create
    STATUS      current
    DESCRIPTION 
        "Specifies the protocol variant and version to be used 
         on the association.  This is an autonomous type and any 
         value that is known to the managed system can be 
         specified.  Note that, as far as version is concerned, 
         this is the ``preferred'' version.  That is, this is 
         the version that the MG will attempt to negotiate, and 
         the maximum version that the MGC will offer in support."
    ::= { gcpLinkageEntry 8 }

gcpLinkageEncoding OBJECT-TYPE
    SYNTAX      MegacoEncoding
    MAX-ACCESS  read-create
    STATUS      current
    DESCRIPTION 
        "Specifies the encoding to use.  This object is single-valued 
         and can assume one of the following values:
         
         - unspecified(0), the encoding is not specified by the managed 
           system and must be determined by means other than 
           provisioning (e.g. well-known port number or negotiation).
           
         - binary(1), the binary encoding, such as that specified by 
           ITU-T Recommendation H.248.1 (09/2005) Annex A and Annex C is 
           to be used on the link.
           
         - text(2), the text encoding, such as that specified by ITU-T 
           Recommendation H.248.1 (09/2005) Annex B and Annex C is to be  
           used on the link.
           
         A change in the value of this object while the link is 
         operational will not be effective until the link is cycled."
    ::= { gcpLinkageEntry 9 }

gcpLinkageAuthAccess OBJECT-TYPE
    SYNTAX      MegacoAuthenticatedAccess
    MAX-ACCESS  read-create
    STATUS      current
    DESCRIPTION 
        "Specifies the authentication methods that will be accepted from 
         the remote entity on the linkage.  This object is set-valued 
         and can contain zero or more of the following:
         
         - none(0), association is permitted without authentication.
           
         - interim(1), the interim (IPv4) approach of ITU-T 
           Recommendation H.248.1 (09/2005) Clause 10.2 is 
           permitted.
           
         - tls(2), transport layer security is permitted.
           
         - ah(3), IPv6 authentication header is permitted.
           
         - esp(4), IPv6 encapsulated security payload is permitted.
           
         When a value is included in the set, it specifies that the 
         corresponding authentication method is permitted."
    ::= { gcpLinkageEntry 10 }

gcpLinkageAdminState OBJECT-TYPE
    SYNTAX      AdministrativeState
    MAX-ACCESS  read-create
    STATUS      current
    DESCRIPTION 
        "This object represents the administrative capability of the 
         linkage to support communication.  The following administrative 
         states are defined:
         
         - locked(0), use of the linkage for communications has been 
           prohibited by a management station; setting the value to 
           locked(0) results in the immediate and disruptive termination 
           of the association;
           
         - unlocked(1), use of the linkage for communications has been 
           permitted by a management station;
           
         - shuttingDown(2), use of the linkage for communication is 
           administratively permitted to existing instances of use only.  
           While the system remains in the shutting down state, the 
           management station may at any time cause the linkage to 
           revert to the unlocked(1) state; setting the linkage to 
           shuttingDown(2) results in the graceful withdrawal from 
           service of the communications linkage; once all users of the 
           linkage have withdrawn, the state will change autonomously to 
           locked(0).
           
         Whenever the administrative state of a linkage is changed, 
         a state change notification is generated."
    REFERENCE   
        "ITU-T Rec. X.721 (1992) | ISO/IEC 10165-2 : 1992, 
               administrativeState attribute."
    ::= { gcpLinkageEntry 11 }

gcpLinkageOperState OBJECT-TYPE
    SYNTAX      OperationalState
    MAX-ACCESS  read-only
    STATUS      current
    DESCRIPTION 
        "Provides the operational state of the linkage in accordance 
         with the OperationalState textual convention and ITU-T Rec. 
         X.721 | ISO/IEC 10165-2.  The defined states are:
         
         - enabled(0), the linkage is operational and is ready to 
           support communication between MG and MGC;
           
         - disabled(1), the linkage is not available for use and no 
           communication can be exchanged between MG and MGC on this 
           linkage.
           
         Note that a change in the operational state shall generate 
         a state change notification; also, a change to the disabled(1) 
         state may generate a communications error notification."
    REFERENCE   
        "ITU-T Rec. X.721 (1992) | ISO/IEC 10165-2 : 1992, 
               operationalState attribute."
    ::= { gcpLinkageEntry 12 }

gcpLinkageProcStatus OBJECT-TYPE
    SYNTAX      ProceduralStatus
    MAX-ACCESS  read-create
    STATUS      current
    DESCRIPTION 
        "Provides the procedural status of the communications linkage in 
         accordance with the ProceduralStatus textual convention of the 
         OPENSS7-SMI-MIB and ITU-T Rec. X.721 | ISO/IEC 10165-2.  The 
         procedural status can report any set of the following 
         conditions:
         
         - initializationRequired(0), the communications linkage 
           requires initialization to be invoked by the manager before 
           it can perform its normal functions, and this procedure has 
           not been initiated.  The management may be able to invoke 
           such initialization through an action.  The terminating 
           condition may also be present.  The operational state is 
           disabled.
           
         - notInitialized(1), the communications linkage requires 
           initialization before it can perform its normal functions, 
           and this procedure has not been initiated.  The 
           communications linkage initializes itself autonomously.  The 
           operational state is disabled.
           
         - initializing(2), the communications linkage requires 
           initialization before it can perform its normal functions, 
           and this procedure has been initiated, but is not yet 
           complete.  When this condition is present, the initialization 
           required condition is absent, since initialization has 
           already begun.  The operational state is disabled.
           
         - reporting(3), the communications linkage has failed and is 
           reporting failure.
           
         - terminating(4), the communications linkage is in 
           a termination phase.  If the linkage does not reinitialize 
           itself autonomously, the initialization required condition is 
           also present and the operational state is disabled; 
           otherwise, the operational state is disabled.
           
         Communications linkages use only the notInitialized(1), 
         initializing(1) and terminating(4) conditions.  Whenever any 
         of these three conditions are present, the operational state is 
         disabled."
    REFERENCE   
        "ITU-T Rec. X.721 (1992) | ISO/IEC 10165-2 : 1992, 
               Attribute-ASN1Module.ProceduralStatus.
         ITU-T Rec. X.731 (1992) | ISO/IEC 10164-2 : 1993, 
               Section 8.1.2.2."
    ::= { gcpLinkageEntry 13 }

gcpLinkageAvailStatus OBJECT-TYPE
    SYNTAX      AvailabilityStatus
    MAX-ACCESS  read-only
    STATUS      current
    DESCRIPTION 
        "Indicates the availability status of the communications linkage 
         in accordance with the AvailabilityStatus textual convention of 
         the OPENSS7-SMI-MIB and ITU-T Rec. X.721 | ISO/IEC 10165-2.  
         This object is set-valued and can contain zero or more of the 
         following conditions:
         
         - inTest(0), the communications linkage is undergoing a test 
           procedure.  When the administrative state is locked(0) or 
           shuttingDown(2), then normal users are precluded from using 
           the resource and the control status attribute has the value 
           reserved for test.  Test that do not exclude additional users 
           can be present in any operational or administrative state but 
           the reserved for test condition should not be present.
           
         - failed(1), the communications linkage has an internal fault 
           that prevents it from operating.  The operational state is 
           disabled.
           
         - powerOff(2), the communications linkage requires power to be 
           applied and is not powered on.  The operational state is 
           disabled.
           
         - offLine(3), the communications linkage requires a routing 
           operation to be performed to place it online and make it 
           available for use.  The operation may be manual or automatic 
           or both.  The operational state is disabled.
           
         - offDuty(4), the communications linkage has been made inactive 
           by an internal control process in accordance with 
           a predetermined time schedule.  Under normal conditions the 
           control process can be expected to reactivate the linkage at 
           some scheduled time, and it is therefore considered to be 
           optional.  The operational state is either enabled or 
           disabled.
           
         - dependency(5), the communications linkage cannot operate 
           because some other resource on which it depends is 
           unavailable.  The operational state is disabled.
           
         - degraded(6), the communications linkage is degraded in some 
           respect, such as in speed or operating capacity.  Failure of 
           a test or an unacceptable performance measurement has 
           established that some or all services are not functional or 
           are degraded due to the presence of a defect.  However, the 
           linkage remains available for service, either because some 
           services are satisfactory or because degraded service is 
           preferable to no service at all.  The operational state is 
           enabled.
           
         - notInstalled(7), the communications linkage is not present, 
           or is incomplete.  The operational state is disabled.
           
         - logFull(8), this indicates a log full condition, the 
           semantics of which are defined in ITU-T Rec. X.735."
    REFERENCE   
        "ITU-T Rec. X.721 (1992) | ISO/IEC 10165-2 : 1992, 
               Attribute-ASN1Module.AvailabilityStatus
         ITU-T Rec. X.731 (1992) | ISO/IEC 10164-2 : 1993, 
               Section 8.1.2.3."
    ::= { gcpLinkageEntry 14 }

gcpLinkageAuthentication OBJECT-TYPE
    SYNTAX      MegacoAuthentication
    MAX-ACCESS  read-only
    STATUS      current
    DESCRIPTION 
        "Indicates the authentication methods that is currently in 
         effect on an operational association.  This object is 
         single-values and can assume one of the following values:
         
         - none(0), no authentication is in effect.
           
         - interim(1), the interim (IPv4) approach of ITU-T 
           Recommendation H.248.1 (09/2005) Clause 10.2 is in 
           effect.
           
         - tls(2), transport layer security is in effect.
           
         - ah(3), IPv6 authentication header is in effect.
           
         - esp(4), IPv6 encapsulated security payload is in effect.
           
         When the association is not operational, this value will always 
         read the value of the last successful association, or none(0) 
         when no association was every formed."
    ::= { gcpLinkageEntry 15 }

gcpLinkageMit OBJECT-TYPE
    SYNTAX      TimeInterval (0..65535)
    UNITS       "centiseconds"
    MAX-ACCESS  read-create
    STATUS      current
    DESCRIPTION 
        "A maximum inactivity time value of zero (0) disabled inactivity 
         timing.
         
         An MGC that supports the ITU-T Rec. H.248.14 inactivity timer 
         package may detect whether or not the MG supports the package by 
         auditing it.  The MGC will set this maximum inactivity time on 
         the ROOT termination for the MG.  The MGC on the control 
         association should, regardless, ensure that the time between 
         messages sent to the MG never exceeds this period.  The MGC 
         ensures this by sending any message as a test or keep-alive 
         message (such as an empty Audit of ROOT) whenever no other 
         message is needed within the period.
         
         The MG will monitor incoming messages for periods of silence 
         exceeding this maximum inactivity time value.  On the detection 
         of an excessive period of silence, a Notify with the observed 
         event of inactivity timeout will be generated.  If the MGC has 
         failed, the event will not receive a reply.  If no reply is 
         received the MG will consider the MGC to have failed and will 
         follow the procedures of ITU-T Rec. H.248.1/11.5.
         
         The MG that detects the inactivity timeout will generate the 
         notification.
         
         Note that only SCTP is capable of monitoring communications 
         linkages without this mechanism; however, an active SCTP 
         association does not necessarily mean that an active MGC-MG 
         control association exists (the application on either end of the 
         SCTP association could have failed).
         
         Note that this value may be changed autonomously by the managed 
         system.  For example, the value can be changed at the MG by the 
         MGC by setting the Maximum Inactivity Timer property of the ROOT 
         termination at the MG."
    REFERENCE   
        "ITU-T Recommendation H.248.14 (03/2002), Maximum Inactivity 
               Time."
    ::= { gcpLinkageEntry 16 }

gcpLinkageRowStatus OBJECT-TYPE
    SYNTAX      RowStatus
    MAX-ACCESS  read-create
    STATUS      current
    DESCRIPTION 
        "Provides a mechanism whereby management stations may create and 
         destroy row in this table.  Note that the linkage must be 
         non-operational for a change in some values to take effect 
         (such as a transport address address)."
    REFERENCE   
        "STD 58, SNMPv2-TC RowStatus."
    ::= { gcpLinkageEntry 17 }

gcpUdpProfile OBJECT IDENTIFIER
    ::= { gcpTables 5 }

gcpUdpProfileTable OBJECT-TYPE
    SYNTAX      SEQUENCE OF GcpUdpProfileEntry
    MAX-ACCESS  not-accessible
    STATUS      current
    DESCRIPTION 
        "Provides a table of UDP transport protocol profiles (settings 
         of communications parameters) for reference by entries in the 
         gcpLinkageTable."
    ::= { gcpUdpProfile 1 }

gcpUdpProfileEntry OBJECT-TYPE
    SYNTAX      GcpUdpProfileEntry
    MAX-ACCESS  not-accessible
    STATUS      current
    DESCRIPTION 
        "Each entry in the gcpUdpProfileTable provides one set of UDP 
         communications parameters that are to be used on 
         a communications linkage that references the profile.  The 
         following rules must be observed:
         
         1. Entries in this table cannot be deleted while they are 
            referenced by an entry in column gcpLinkageProfile of table 
            gcpLinkageTable that references the entry.
            
         2. Changes to the values for a given profile entry are 
            effective immediately for operational communications 
            linkages that refer to this profile; non-operational 
            linkages will adopt the new values on the next cycle."
    INDEX       { gcpUdpProfileId }
    ::= { gcpUdpProfileTable 1 }

GcpUdpProfileEntry ::= SEQUENCE {
    gcpUdpProfileId     SimpleNameType,
    gcpUdpChecksum      TruthValue,
    gcpUdpRowStatus     RowStatus
}

gcpUdpProfileId OBJECT-TYPE
    SYNTAX      SimpleNameType (SIZE(1..32))
    MAX-ACCESS  not-accessible
    STATUS      current
    DESCRIPTION 
        "Provides an index into the gcpUdpProfileTable following 
         the SimpleNameType textual convention.  The value of 
         this string can be used to identify an entry in this 
         table."
    ::= { gcpUdpProfileEntry 1 }

gcpUdpChecksum OBJECT-TYPE
    SYNTAX      TruthValue
    MAX-ACCESS  read-create
    STATUS      current
    DESCRIPTION 
        "This column defines whether a UDP checksum will be 
         generated to cover the contents of the UDP payload.  
         When set to true(1), a UDP checksum will be generated; 
         when false(2), no UDP checksum will be generated.  The 
         default default value is false(2).
         
         The default value is determined by the setting of 
         gcpDefaultUdpChecksum."
    ::= { gcpUdpProfileEntry 2 }

gcpUdpRowStatus OBJECT-TYPE
    SYNTAX      RowStatus
    MAX-ACCESS  read-create
    STATUS      current
    DESCRIPTION 
        "Provides a mechanism whereby management stations, 
         following the RowStatus textual convention from the 
         SNMPv2-TC module, may create or destroy conceptual rows 
         in this table.
         
         Note that profiles in this table cannot be deleted 
         while they are referenced from an entry in the 
         gcpLinkageTable.  Changes made to values in a profile 
         will be effective immediately on operational 
         communications linkages that reference the profile from 
         the gcpLinkageTable."
    REFERENCE   
        "STD 58, SNMPv2-TC RowStatus."
    ::= { gcpUdpProfileEntry 3 }

gcpTcpProfile OBJECT IDENTIFIER
    ::= { gcpTables 6 }

gcpTcpProfileTable OBJECT-TYPE
    SYNTAX      SEQUENCE OF GcpTcpProfileEntry
    MAX-ACCESS  not-accessible
    STATUS      current
    DESCRIPTION 
        "Provides a table of TCP transport protocol profiles (settings 
         of communications parameters) for reference by entries in the 
         gcpLinkageTable."
    ::= { gcpTcpProfile 1 }

gcpTcpProfileEntry OBJECT-TYPE
    SYNTAX      GcpTcpProfileEntry
    MAX-ACCESS  not-accessible
    STATUS      current
    DESCRIPTION 
        "Each entry in the gcpTcpProfileTable provides one set of TCP 
         communications parameters that are to be used on 
         a communications linkage that references the profile.  The 
         following rules must be observed:
         
         1. Entries in this table cannot be deleted while they are 
            referenced by an entry in column gcpLinkageProfile of table 
            gcpLinkageTable that references the entry.
            
         2. Changes to the values for a given profile entry are 
            effective immediately for operational communications 
            linkages that refer to this profile; non-operational 
            linkages will adopt the new values on the next cycle."
    INDEX       { gcpTcpProfileId }
    ::= { gcpTcpProfileTable 1 }

GcpTcpProfileEntry ::= SEQUENCE {
    gcpTcpProfileId         SimpleNameType,
    gcpTcpNoDelay           TruthValue,
    gcpTcpMaxseg            Unsigned32,
    gcpTcpKeepAlive         TruthValue,
    gcpTcpKeepIdle          TimeInterval,
    gcpTcpKeepAliveItvl     TimeInterval,
    gcpTcpKeepCount         Unsigned32,
    gcpTcpSynRetrans        Unsigned32,
    gcpTcpWindowClamp       Unsigned32,
    gcpTcpRowStatus         RowStatus
}

gcpTcpProfileId OBJECT-TYPE
    SYNTAX      SimpleNameType (SIZE(1..32))
    MAX-ACCESS  not-accessible
    STATUS      current
    DESCRIPTION 
        "Provides an index into the gcpTcpProfileTable following the 
         SimpleNameType textual convention.  The value of this string 
         can be used to identify an entry in this table."
    ::= { gcpTcpProfileEntry 1 }

gcpTcpNoDelay OBJECT-TYPE
    SYNTAX      TruthValue
    MAX-ACCESS  read-create
    STATUS      current
    DESCRIPTION 
        "This column defines whether the Nagle algorithm should be 
         applied to TCP connections formed under this profile.  The 
         Nagle algorithm increases the size of the packets placed on the 
         network at the expense of delaying the transmission of some 
         data during congestion episodes.  When set to true(1), the 
         Nagle algorithm is suppressed; otherwise, set to false(2), the 
         Nagle algorithm is in effect.
         
         Under most circumstances, TCP sends data as soon as it is 
         presented.  When outstanding data has not yet been 
         acknowledged, it gathers small amounts of output to be sent in 
         a single packet once an acknowledgement is received.  For 
         a small number of clients, such as a window system (for 
         example, MIT X Window System) that send a stream of mouse 
         events which receive no replies, this packetisation may cause 
         significant delays.  This object is used to defeat this 
         algorithm.  Valid values are true(1) and false(2).
         
         The default value is determined by the setting of 
         gcpDefaultTcpNoDelay."
    REFERENCE   
        "RFC 793, RFC 1122, XNS 5.2"
    ::= { gcpTcpProfileEntry 2 }

gcpTcpMaxseg OBJECT-TYPE
    SYNTAX      Unsigned32 (536..65536)
    UNITS       "octets"
    MAX-ACCESS  read-create
    STATUS      current
    DESCRIPTION 
        "This column defines the maximum TCP segment size for outgoing 
         packets.  Values greater than the association MTU are ignored 
         and have no effect.  The value determines the maximum size (in 
         octets) above which TCP will fragment larger segments into 
         smaller ones, and beneath which TCP will combine segments into 
         a single one.  Normally this value is the MTU value minus the 
         size of the current IP and TCP headers.  When set to a lower 
         value, the lower value will be used.
         
         This column determines the maximum segment size for outgoing 
         packets.  Values greater than the association MTU are ignored 
         and have no effect.  The value determines the maximum size (in 
         octets) above which TCP will fragment larger data segments into 
         smaller ones.  Normally this value is the connection MTU value 
         minus the size of the current IP and TCP headers.  When set to 
         a lower value, the lower value will be used; however, the value 
         cannot be set to less than 536 minus the current IP and TCP 
         headers, also, the value cannot be set larger than the 
         connection MTU minus the size of the current IP and TCP 
         headers.
         
         The default value is determined by the setting of 
         gcpDefaultTcpMaxseg."
    REFERENCE   
        "RFC 793, RFC 1122, XNS 5.2"
    ::= { gcpTcpProfileEntry 3 }

gcpTcpKeepAlive OBJECT-TYPE
    SYNTAX      TruthValue
    MAX-ACCESS  read-create
    STATUS      current
    DESCRIPTION 
        "This column determines whether keep-alive messages used to 
         probe the destination transport address will be sent 
         periodically.  The default default value is the value 
         recommended by RFC 793, which is false(2).
         
         When true(1), a keep-alive timer is activated to monitor idle 
         connections that might no longer exist.  If a connection has 
         been idle since the last keep-alive timeout, a keep-alive 
         packet is sent to check if the connection is still alive or 
         broken.
         
         Keep-alive packets are not an explicit feature of TCP, and this 
         practise is not universally accepted.  According to RFC 1122 
         ``a keep-alive mechanism should only be invoked in service 
         applications that might otherwise hang indefinitely and consume 
         resources unnecessarily if a client crashes or aborts 
         a connection during a network failure.''
         
         Enabling keep-alive increases the protocol's responsiveness in 
         detection of failure and redirection of traffic away from 
         failed paths and interfaces.  However, TCP connections are far 
         less robust on noisy or congested links with keep-alive 
         enabled.  This column should normally be left at its default 
         value.
         
         The default value is determined by the setting of 
         gcpDefaultTcpKeepAlive."
    REFERENCE   
        "RFC 793, RFC 1122, XNS 5.2"
    ::= { gcpTcpProfileEntry 4 }

gcpTcpKeepIdle OBJECT-TYPE
    SYNTAX      TimeInterval
    UNITS       "centiseconds"
    MAX-ACCESS  read-create
    STATUS      current
    DESCRIPTION 
        "Specifies the minimum period of time that the connection must 
         remain idle before a keep-alive check is made.  No minimum is 
         signified by the value zero (0).  The default default value is 
         7200 seconds (2 hours).  An idle connection is terminated after 
         approximately an additional 11 minues (9 probes at an interval 
         of 75 seconds apart) when keep-alive is enabled.
         
         The default value is determined by the setting of 
         gcpDefaultTcpKeepIdle."
    ::= { gcpTcpProfileEntry 5 }

gcpTcpKeepAliveItvl OBJECT-TYPE
    SYNTAX      TimeInterval
    UNITS       "centiseconds"
    MAX-ACCESS  read-create
    STATUS      current
    DESCRIPTION 
        "Specifies the maximum interval between keep-alive attempts on 
         idle connections.
         
         When keep-alive is enabled (see gcpTcpKeepAlive), this value 
         determines the default keep-alive timeout.  The default default 
         value is the minimum recommended by RFC 1122 of 120 seconds (2 
         minutes).
         
         The default value is determined by the setting of 
         gcpDefaultTcpKeepAliveItvl."
    ::= { gcpTcpProfileEntry 6 }

gcpTcpKeepCount OBJECT-TYPE
    SYNTAX      Unsigned32
    UNITS       "attempts"
    MAX-ACCESS  read-create
    STATUS      current
    DESCRIPTION 
        "Specifies the maximum number of keep-alive probes that must 
         fail before the connection is deemed failed.
         
         The default default values is 9 attempts.
         
         The default value is determined by the setting of 
         gcpDefaultTcpKeepCount."
    ::= { gcpTcpProfileEntry 7 }

gcpTcpSynRetrans OBJECT-TYPE
    SYNTAX      Unsigned32 (0..255)
    UNITS       "retransmissions"
    MAX-ACCESS  read-create
    STATUS      current
    DESCRIPTION 
        "Specifies the maximum number of times that a SYN will be 
         retransmitted when attempting to establish a TCP connection.  
         Valid values are zero or greater.  The default default value is 
         5, which corresponds to 180 seconds.  Valid values are zero to 
         255.
         
         The default value is determined by the setting of 
         gcpDefaultTcpSynRetrans."
    ::= { gcpTcpProfileEntry 8 }

gcpTcpWindowClamp OBJECT-TYPE
    SYNTAX      Unsigned32 (536..65536)
    UNITS       "octets"
    MAX-ACCESS  read-create
    STATUS      current
    DESCRIPTION 
        "Specifies the maximum receive window that will be advertised.
         
         The default value is determined by the setting of 
         gcpDefaultTcpWindowClamp."
    ::= { gcpTcpProfileEntry 9 }

gcpTcpRowStatus OBJECT-TYPE
    SYNTAX      RowStatus
    MAX-ACCESS  read-create
    STATUS      current
    DESCRIPTION 
        "Provides a mechanism whereby management stations, following the 
         RowStatus textual convention from the SNMPv2-TC module, may 
         create or destroy conceptual rows in this table.
         
         Note that profiles in this table cannot be deleted while they 
         are referenced from an entry in the gcpLinkageTable.  Changes 
         made to values in a profile will be effective immediately on 
         operational communication linkages that reference the profile 
         from the gcpLinkageTable."
    REFERENCE   
        "STD 58, SNMPv2-TC RowStatus."
    ::= { gcpTcpProfileEntry 10 }

gcpSctpProfile OBJECT IDENTIFIER
    ::= { gcpTables 7 }

gcpSctpProfileTable OBJECT-TYPE
    SYNTAX      SEQUENCE OF GcpSctpProfileEntry
    MAX-ACCESS  not-accessible
    STATUS      current
    DESCRIPTION 
        "Provides a table of SCTP transport protocol profiles (settings 
         of communications parameters) for reference by entries in the 
         gcpLinkageTable."
    ::= { gcpSctpProfile 1 }

gcpSctpProfileEntry OBJECT-TYPE
    SYNTAX      GcpSctpProfileEntry
    MAX-ACCESS  not-accessible
    STATUS      current
    DESCRIPTION 
        "Each entry in the gcpSctpProfileTable provides one set of SCTP 
         communications parameters that are to be used on 
         a communications linkage that references the profile.  The 
         following rules must be observed:
         
         1. Entries in this table cannot be deleted while they are 
            referenced by an entry in column gcpLinkageProfile of table 
            gcpLinkageTable that references the entry.
            
         2. Changes to the values for a given profile entry are 
            effective immediately for operational communications 
            linkages that refer to this profile; non-operational 
            linkages will adopt the new values on the next cycle."
    INDEX       { gcpSctpProfileId }
    ::= { gcpSctpProfileTable 1 }

GcpSctpProfileEntry ::= SEQUENCE {
    gcpSctpProfileId        SimpleNameType,
    gcpSctpNoDelay          TruthValue,
    gcpSctpMaxseg           Unsigned32,
    gcpSctpHeartbeatItvl    TimeInterval,
    gcpSctpHearbeat         TruthValue,
    gcpSctpRtoInitial       TimeInterval,
    gcpSctpRtoMin           TimeInterval,
    gcpSctpRtoMax           TimeInterval,
    gcpSctpPathMaxRetrans   Unsigned32,
    gcpSctpCookieLife       TimeInterval,
    gcpSctpCookieInc        TimeInterval,
    gcpSctpMaxInitRetries   Unsigned32,
    gcpSctpMaxBurst         Unsigned32,
    gcpSctpAssocMaxRetrans  Unsigned32,
    gcpSctpSackDelay        TimeInterval,
    gcpSctpLifetime         TimeInterval,
    gcpSctpRowStatus        RowStatus
}

gcpSctpProfileId OBJECT-TYPE
    SYNTAX      SimpleNameType (SIZE(1..32))
    MAX-ACCESS  not-accessible
    STATUS      current
    DESCRIPTION 
        "Identifies a gcpSctpProfileEntry instance within the managed 
         switching element; this is an attribute type whose 
         distinguished value can be used as an RDN when naming an 
         instance of the gcpSctpProfileEntry."
    ::= { gcpSctpProfileEntry 1 }

gcpSctpNoDelay OBJECT-TYPE
    SYNTAX      TruthValue
    MAX-ACCESS  read-create
    STATUS      current
    DESCRIPTION 
        "This column defines whether the Nagle algorithm should be 
         applied to SCTP associations formed under this profile.  The 
         Nagle algorithm increases the size of the packets placed on the 
         network at the expense of delaying the transmission of some 
         data during congestion episodes.  When set to true(1), the 
         Nagle algorithm is suppressed; otherwise, set to false(2), the 
         Nagle algorithm is in effect.
         
         The default value is determined by the setting of 
         gcpDefaultSctpNoDelay."
    REFERENCE   
        "RFC 4960"
    ::= { gcpSctpProfileEntry 2 }

gcpSctpMaxseg OBJECT-TYPE
    SYNTAX      Unsigned32 (536..65536)
    UNITS       "octets"
    MAX-ACCESS  read-create
    STATUS      current
    DESCRIPTION 
        "This column defines the maximum SCTP payload size for outgoing 
         packets.  Values greater than the association MTU are ignored 
         and have no effect.  The value determines the maximum size (in 
         octets) above which SCCP will fragment larger DATA chunks into 
         smaller DATA chunks, and beneath which SCTP will bundle DATA 
         chunks into a single packet or combine smaller DATA chunks into 
         larger DATA chunks.  Normally this value is the association MTU 
         value must the size of the current IP and SCTP headers, minus 
         the size of one DATA chunk header.  When set to a lower value, 
         the lower value will be used.
         
         The default value is determined by the setting of 
         gcpDefaultSctpMaxseg."
    REFERENCE   
        "RFC 4960"
    ::= { gcpSctpProfileEntry 3 }

gcpSctpHeartbeatItvl OBJECT-TYPE
    SYNTAX      TimeInterval
    UNITS       "centiseconds"
    MAX-ACCESS  read-create
    STATUS      current
    DESCRIPTION 
        "This column defines the time interval (in milliseconds) between 
         successive HEARTBEAT messages used to probe destination 
         transport addresses for RTT calculation and activity.  Valid 
         values are zero (0) - do not heartbeat, or a value of 
         1 millisecond or greater.
         
         The default value is determined by the setting of 
         gcpDefaultHeartbeatItvl."
    REFERENCE   
        "RFC 4960"
    ::= { gcpSctpProfileEntry 4 }

gcpSctpHearbeat OBJECT-TYPE
    SYNTAX      TruthValue
    MAX-ACCESS  read-create
    STATUS      current
    DESCRIPTION 
        "This column determines whether HEARTBEAT messages used to probe 
         destination transport addresses for RTT calculation and 
         activity will be sent periodically.  The default default value 
         is the value recommended from RFC 4960 is true(1).
         
         Disabling heartbeats reduces the protocol's responsiveness in 
         detection of failures and redirection of traffic away from 
         failed paths and interfaces.  This column should normally be 
         left at its default value.
         
         The default value is determined by the setting of 
         gcpDefaultSctpHeartbeat."
    REFERENCE   
        "RFC 4960"
    ::= { gcpSctpProfileEntry 5 }

gcpSctpRtoInitial OBJECT-TYPE
    SYNTAX      TimeInterval
    UNITS       "centiseconds"
    MAX-ACCESS  read-create
    STATUS      current
    DESCRIPTION 
        "This column defines the initial time interval (in milliseconds) 
         that will be used as an initial RTO (retransmission timeout) 
         value when sending packets to a destination for the first time.  
         Valid values are zero or greater but must be within the range 
         gcpSctpRtoMin to gcpSctpRtoMax.  The default default value is 
         the value recommended by RFC 2960 and RFC 4960 (1000 
         milliseconds, or 1 second).
         
         Note that, in general, the RTO initial should not be less than 
         the peer's maximum SACK delay, otherwise, excessive 
         retransmission might occur while the peer is delaying 
         acknowledgements.
         
         The default value is determined by the setting of 
         gcpDefaultSctpRtoInitial."
    REFERENCE   
        "RFC 4960"
    ::= { gcpSctpProfileEntry 6 }

gcpSctpRtoMin OBJECT-TYPE
    SYNTAX      TimeInterval
    UNITS       "centiseconds"
    MAX-ACCESS  read-create
    STATUS      current
    DESCRIPTION 
        "This column defines the minimum timer interval (in 
         milliseconds) that will be used as an RTO (retransmission 
         timeout) value when sending packets to a destination transport 
         address and expecting acknowledgements.  Valid values are zero 
         or greater and must be less than or equal to gcpSctpRtoInitial 
         and strictly less than and gcpSctpRtoMax.  The default default 
         value is the value recommended by RFC 2960 and RFC 4960 (1000 
         milliseconds, or 1 second).
         
         Note that, in general, the RTO minimum should not be less than 
         the peer's maximum SACK delay, otherwise, excessive 
         retransmission might occur while the peer is delaying 
         acknowledgements.
         
         The default value is determined by the setting of 
         gcpDefaultSctpRtoMin."
    REFERENCE   
        "RFC 4960"
    ::= { gcpSctpProfileEntry 7 }

gcpSctpRtoMax OBJECT-TYPE
    SYNTAX      TimeInterval
    UNITS       "centiseconds"
    MAX-ACCESS  read-create
    STATUS      current
    DESCRIPTION 
        "This column defines the maximum time interval (in milliseconds) 
         that will be used as an RTO (retransmission timeout) value when 
         sending packets t a destination transport address and expecting 
         acknowledgements.  Valid values are zero or greater but must be 
         greater than or equal to gcpSctpRtoInitial and strictly 
         greater than gcpSctpRtoMin.  The default default value is the 
         value recommended by RFC 2960 and RFC 4960 (60000 milliseconds, 
         or 60 seconds).
         
         Note that, in general, the RTO maximum should not be less than 
         the peer's maximum SACK delay, otherwise, excessive 
         retransmission might occur while the peer is delaying 
         acknowledgements.
         
         The default value is determined by the setting of 
         gcpDefaultSctpRtoMax."
    REFERENCE   
        "RFC 4960"
    ::= { gcpSctpProfileEntry 8 }

gcpSctpPathMaxRetrans OBJECT-TYPE
    SYNTAX      Unsigned32
    UNITS       "retransmissions"
    MAX-ACCESS  read-create
    STATUS      current
    DESCRIPTION 
        "This column defines the number of times that SCTP will attempt 
         retransmitting a packet to a given destination transport 
         address before it considers that destination transport address 
         inactive.  Valid values are zero or greater.  The default 
         default value is the value recommended in RFC 4960 (5 
         retransmissions).
         
         Adjusting this value has an effect on the period of time taken 
         to fail-over between destinations for multi-homed connections.  
         Lower values (including zero) will yield faster fail-over 
         response times.  Lower values, however, may cause thrashing 
         between destinations contributing to congestion in the network.  
         Default values are applicable to Internet applications.
         
         The default value is determined by the setting of 
         gcpDefaultSctpPathMaxRetrans."
    REFERENCE   
        "RFC 4960"
    ::= { gcpSctpProfileEntry 9 }

gcpSctpCookieLife OBJECT-TYPE
    SYNTAX      TimeInterval
    UNITS       "centiseconds"
    MAX-ACCESS  read-create
    STATUS      current
    DESCRIPTION 
        "This column defines the time interval (in milliseconds) in 
         conjunction with gcpSctpCookieInc beyond which a COOKIE-ECHO 
         received with a cookie sent in an INIT-ACK will no longer be 
         accepted.  For SCTP, this also limits the maximum time interval 
         for which the HMAC secret key for the cookie will be valid.  
         Valid values are zero or greater.  Values of zero will  be 
         converted to a system clock tick.  The default default value is 
         the value recommended by RFC 4960 (60,000 milliseconds, or 60 
         seconds).
         
         Reducing this value will increase the probability that passive 
         connection attempts will fail due to expired cookies.  
         Increasing the value will reduce the overall security of the 
         system by permitting attackers an increased interval within 
         which to crack HMACs and guess verification tags.  This value 
         may be adjusted in conjunction with gcpSctpCookieInc to meet 
         most objectives for successful passive connection attempts with 
         the best security afforded by smaller values of 
         gcpSctpCookieLife.
         
         Unfortunately, the gcpSctpCookieLife and 
         gcpSctpCookieInc must be adjusted to accommodate the slowest 
         peer on the slowest connection.  The default setting is 
         adequate for Internet applications.
         
         The default value is determined by the setting of 
         gcpDefaultSctpCookieLife."
    REFERENCE   
        "RFC 4960"
    ::= { gcpSctpProfileEntry 10 }

gcpSctpCookieInc OBJECT-TYPE
    SYNTAX      TimeInterval
    UNITS       "centiseconds"
    MAX-ACCESS  read-create
    STATUS      current
    DESCRIPTION 
        "This column defines the time increment (in milliseconds) that 
         will be added to the lifespan of the cookie in an INIT-ACK if 
         the received INIT requests cookie preservative to lengthen the 
         lifespan of the cookie.  Valid values are zero or greater.  The 
         default default value is the value recommended in RFC 4960 
         5.2.6 (1000 milliseconds, or 1 second).
         
         This value can be adjusted in conjunction with 
         gcpSctpCookieLife to meet objectives of successful passive 
         connection attempts and security.  The default setting is 
         adequate for Internet applications.
         
         The default value is determined by the setting of 
         gcpDefaultSctpCookieInc."
    REFERENCE   
        "RFC 4960"
    ::= { gcpSctpProfileEntry 11 }

gcpSctpMaxInitRetries OBJECT-TYPE
    SYNTAX      Unsigned32
    UNITS       "retries"
    MAX-ACCESS  read-create
    STATUS      current
    DESCRIPTION 
        "This column defines the number of times that an INIT or 
         COOKIE-ECHO will be resent to a given destination before 
         abandoning an active open attempt.  Valid values are zero or 
         greater.  The default default value is the value recommended by 
         RFC 4960 (8 retries).
         
         The default value is determined by the setting of 
         gcpDefaultSctpMaxInitRetries."
    REFERENCE   
        "RFC 4960"
    ::= { gcpSctpProfileEntry 12 }

gcpSctpMaxBurst OBJECT-TYPE
    SYNTAX      Unsigned32
    UNITS       "MTUs"
    MAX-ACCESS  read-create
    STATUS      current
    DESCRIPTION 
        "This column defines the maximum number of MTUs of new data 
         chunks that will be sent in a burst in accordance with SCTP 
         Specification Errata and Issues, RFC 4460 and RFC 4960.  The 
         default default value is the value recommended in RFC 4960 (4 
         MTUs).
         
         The default value is determined by the setting of 
         gcpDefaultSctpMaxBurst."
    REFERENCE   
        "RFC 4960"
    ::= { gcpSctpProfileEntry 13 }

gcpSctpAssocMaxRetrans OBJECT-TYPE
    SYNTAX      Unsigned32
    UNITS       "retransmissions"
    MAX-ACCESS  read-create
    STATUS      current
    DESCRIPTION 
        "This column defines the number of times that the sending 
         endpoint will attempt retransmitting a packet on any active 
         destination transport address before it aborts the association.  
         Value values are zero or greater.  The default default value is 
         the value recommended in RFC 4960 (10 retransmissions).
         
         This value should be larger  than sum of the path maximum 
         number of retransmission values of each of the destinations.
         
         Setting this value to less than the sum of the path maximum 
         retransmission values for all of the destinations has the 
         interesting effect of permitting a connection to persist even 
         when all destinations have been deemed inactive.
         
         The default value is determined by the setting of 
         gcpDefaultAssocMaxRetrans."
    REFERENCE   
        "RFC 4960"
    ::= { gcpSctpProfileEntry 14 }

gcpSctpSackDelay OBJECT-TYPE
    SYNTAX      TimeInterval
    UNITS       "centiseconds"
    MAX-ACCESS  read-create
    STATUS      current
    DESCRIPTION 
        "This column defines the interval of time (in milliseconds) that 
         will be used as an RTO (retransmission timeout) value when 
         sending packets to a destination transport address.  Valid 
         values are zero or to 500 milliseconds (RFC 4960 forbids 
         setting this value larger than 500 milliseconds).  The default 
         default value is the value recommended in RFC 4960 (200 
         milliseconds).
         
         The default value is determined by the setting of 
         gcpDefaultSctpSackDelay."
    REFERENCE   
        "RFC 4960"
    ::= { gcpSctpProfileEntry 15 }

gcpSctpLifetime OBJECT-TYPE
    SYNTAX      TimeInterval
    UNITS       "centiseconds"
    MAX-ACCESS  read-create
    STATUS      current
    DESCRIPTION 
        "The default value is determined by the setting of 
         gcpDefaultSctpLifetime."
    REFERENCE   
        "RFC 4960"
    ::= { gcpSctpProfileEntry 16 }

gcpSctpRowStatus OBJECT-TYPE
    SYNTAX      RowStatus
    MAX-ACCESS  read-create
    STATUS      current
    DESCRIPTION 
        "Provides a mechanism whereby management stations, following the 
         RowStatus textual convention from the SNMPv2-TC module, may 
         create or destroy conceptual rows in this table.
         
         Note that profiles in this table cannot be deleted while they 
         are referenced from an entry in the gcpLinkageTable.  Changes 
         made to values in a profile will be effected immediately on 
         operational communication linkages that reference the profile 
         in the gcpLinkageTable."
    REFERENCE   
        "STD 58, SNMPv2-TC RowStatus."
    ::= { gcpSctpProfileEntry 17 }

gcpProtGroup OBJECT IDENTIFIER
    ::= { gcpTables 8 }

gcpProtGroupTable OBJECT-TYPE
    SYNTAX      SEQUENCE OF GcpProtGroupEntry
    MAX-ACCESS  not-accessible
    STATUS      current
    DESCRIPTION 
        "This table is used for representing a protect system.  The 
         gcpProtGroupInvokeProtection action switches always from 
         protected unit to protecting unit.  Either all or none of the 
         protection unit instances within a protection group shall have 
         a priority assigned.  It is to be noted that, before the 
         creation of the protection group, the supported-by-object-lists 
         (sbol) attribute of a reliable resource may pint to an 
         unreliable resource.  But, once the protection group is 
         created, the sbol attribute would start pointing to the 
         protection group object."
    REFERENCE   
        "ITU-T Rec. M.3100 (2005) : protectionGroupR2 MOC
         ITU-T Rec. G.744.3 : protectionGroupR1 MOC"
    ::= { gcpProtGroup 1 }

gcpProtGroupEntry OBJECT-TYPE
    SYNTAX      GcpProtGroupEntry
    MAX-ACCESS  not-accessible
    STATUS      current
    DESCRIPTION 
        "Each row in the gcpProtGroup table manages a protection group 
         of H.248 GCP entities.  A protection group is a group of 
         protecting and protection unis and the policies and 
         configuration of switchover within the protection group.  
         A separate side table (the gcpProtUnitTable) contains specifics 
         abouot the protection units themselves.  The rows of the 
         gcpProtGroupTable are indexed by the gcpProtGroupId that 
         identifies the protection group.  Values of the gcpProtGroupId 
         can be used to refer to an entry in this table."
    REFERENCE   
        "ITU-T Rec. G.744.3 : protectionGroup MOC"
    INDEX       { gcpProtGroupId }
    ::= { gcpProtGroupTable 1 }

GcpProtGroupEntry ::= SEQUENCE {
    gcpProtGroupId                      Unsigned32,
    gcpProtGroupOperState               OperationalState,
    gcpProtGroupAvailStatus             AvailabilityStatus,
    gcpProtGroupType                    INTEGER,
    gcpProtGroupRevertive               TruthValue,
    gcpProtGroupSBOLNumber              Unsigned32,
    gcpProtGroupWaitToRestoreTime       TimeInterval,
    gcpProtGroupSettingWindowTime       TimeInterval,
    gcpProtGroupReleaseingWindowTime    TimeInterval,
    gcpProtGroupHitsCount               Unsigned32,
    gcpProtGroupSwitchType              INTEGER,
    gcpProtGroupProtectedUnits          ProtectionUnits,
    gcpProtGroupProtectingUnits         ProtectionUnits,
    gcpProtGroupInvokeProtection        ActionOrResult,
    gcpProtGroupReleaseProtection       ActionOrResult,
    gcpProtGroupRowStatus               RowStatus
}

gcpProtGroupId OBJECT-TYPE
    SYNTAX      Unsigned32
    MAX-ACCESS  not-accessible
    STATUS      current
    DESCRIPTION 
        "Provides a non-zero ordinal index into the gcpPrtoGroupTable.  
         This unsigned integer uniquely identifies the protection group 
         within the managed system."
    ::= { gcpProtGroupEntry 1 }

gcpProtGroupOperState OBJECT-TYPE
    SYNTAX      OperationalState
    MAX-ACCESS  read-only
    STATUS      current
    DESCRIPTION 
        "Provides the operational state of the protection group in 
         accordance with the OperationalState textual convention of the 
         OPENSS7-SMI-MIB and ITU-T Rec. X.721 | ISO/IEC 10165-2.  This 
         object is single-value and read-only.  It can assume on of the 
         following defined states:
         
         - enabled(0), the protection group is operational an ready for 
           use;
           
         - disabled(1), the protection group is not available for use.
           
         A change in operational state shall generate a state change 
         notification."
    REFERENCE   
        "ITU-T Rec. X.721 (1992) | ISO/IEC 10165-2 : 1992, 
               operationalState attribute."
    ::= { gcpProtGroupEntry 2 }

gcpProtGroupAvailStatus OBJECT-TYPE
    SYNTAX      AvailabilityStatus
    MAX-ACCESS  read-only
    STATUS      current
    DESCRIPTION 
        "This attribute reflects the availability status of the 
         protection group in accordance with the AvailabilityStatus 
         textual convention of the OPENSS7-SMI-MIB and ITU-T Rec. X.721 
         | ISO/IEC 10165-2.  The object is single-valued and read-only.  
         It can assume one of the following defined values:
         
         - inTest(0): the protection group is undergoing a test 
           procedure;
         
         - failed(1): the protection group has an internal fault that 
           prevents it from operating; the operational state is 
           disabled(1);
         
         - powerOff(2): not used;
         
         - offLine(3): the protection group is off line; the operational 
           state is disabled(1);
         
         - offDuty(4): the protection group has been made inactive by an 
           internal control process in accordance with a predetermined 
           schedule;
         
         - dependency(5): the protection group cannot operate because 
           some other resource upon which it depends is unavailable; the 
           operational state is disabled(0);
         
         - degraded(6): the redundancy (or capacity) provided by the 
           protection group is degraded; however, the protection group 
           remains available for service, either because some services 
           are satisfactory or because degraded service is preferable to 
           no service at all; the operational state is enabled(1);
         
         - notInstalled(7): not used;
         
         - logFull(8): not used.
         
         No state change notification is generated when this attribute 
         chages value."
    REFERENCE   
        "ITU-T Rec. X.721 (1992) | ISO/IEC 10165-2 : 1992, 
               availabilityStatus attribute."
    ::= { gcpProtGroupEntry 3 }

gcpProtGroupType OBJECT-TYPE
    SYNTAX      INTEGER { plus(0), colon(1) }
    MAX-ACCESS  read-create
    STATUS      current
    DESCRIPTION 
        "This attribute specifies whether the protection scheme used is 
         1 + 1 (plus) or M:N (colon). M:N includes the cases where 
         M = 1 and/or N = 1.  Note that plus(0) tends to be 
         a hotStandby(0) scenario, whereas colon(1) tends to be 
         a coldStandby(1) scenario."
    REFERENCE   
        "ITU-T Rec. G.774.3 : protectionGroupType ATTRIBUTE"
    ::= { gcpProtGroupEntry 4 }

gcpProtGroupRevertive OBJECT-TYPE
    SYNTAX      TruthValue
    MAX-ACCESS  read-create
    STATUS      current
    DESCRIPTION 
        "This attribute specifies whether the protection scheme is 
         revertive or not.
         
         - true(1), the traffic is returned to the protected 
           gcpProtUnitId instance that initiated the switch after the 
           fault clears and the gcpProtGroupWaitToRestoreTime interval 
           (if any) has expired.
           
         - false(2), then after the fault has cleared, traffic does not 
           revert to the gcpProtUnitId that initiated the switch."
    REFERENCE   
        "ITU-T Rec. G.774.3 : revertive ATTRIBUTE"
    ::= { gcpProtGroupEntry 5 }

gcpProtGroupSBOLNumber OBJECT-TYPE
    SYNTAX      Unsigned32
    UNITS       "protection units"
    MAX-ACCESS  read-create
    STATUS      current
    DESCRIPTION 
        "The supported-by object list is an attribute type whose value 
         identifies a set of object instances which are capable of 
         directly affecting a given managed object.  The object 
         instances include both physical and logical objects. This 
         attribute does not force internal details to be specified, but 
         only the necessary level of detail required for management. If 
         the object instances supporting the managed object are unknown 
         to that object, then this attribute is an empty set.
         
         The list is provided in the gcpSbolTable indexed by the 
         gcpProtGroupId and the gcpSbolId that identifies a member of 
         the group.  This object reports the length of the list.  When 
         this value is zero (0), there are no entries in the 
         gcpSbolTable side-table fro this gcpProtGroupId."
    REFERENCE   
        "ITU-T Rec. M.3100 (1992) : supportedByObjectList 
               ATTRIBUTE"
    ::= { gcpProtGroupEntry 6 }

gcpProtGroupWaitToRestoreTime OBJECT-TYPE
    SYNTAX      TimeInterval
    UNITS       "centiseconds"
    MAX-ACCESS  read-create
    STATUS      current
    DESCRIPTION 
        "This attribute specifies the amount of time, in seconds, to 
         wait after a fault clears before restoring traffic to the 
         protected protection unit that initiated the switching.  Note 
         that this time only has an effect when gcpProtGroupRevertive is 
         true(1)."
    REFERENCE   
        "ITU-T Rec. G.774.3 : waitToRestoreTime ATTRIBUTE"
    ::= { gcpProtGroupEntry 7 }

gcpProtGroupSettingWindowTime OBJECT-TYPE
    SYNTAX      TimeInterval
    MAX-ACCESS  read-create
    STATUS      current
    DESCRIPTION 
        "This read-write attribute specifies the criteria of the 
         locked-in condition. The criteria includes the automatic 
         protection switching (APS) rate and the associated setting and 
         releasing time windows. If the number of APS of a Protection 
         Unit reaches the value specified in the hitsCount 
         (rtpswPgHitsCount) field within a moving time window of 
         specified length, the Protection Unit will enter the locked-in 
         condition.  Each switch to protection and its subsequent 
         release is considered as one hit. The length of the time window 
         for entering the locked-in condition is specified in the 
         settingWindowTime (gcpProtGroupSettingWindowTime) field.  Once 
         a Protection Unit is in the locked-in condition, future request 
         of APS will be denied until the locked-in condition is 
         released.  The release criterion is no APS request within 
         another moving time window.  The length of this time window is 
         specified in the releasingWindowTime 
         (gcpProtGroupReleasingWindowTime) field."
    REFERENCE   
        "ITU-T Rec. G.774.3 : lockedInCondition ATTRIBUTE"
    ::= { gcpProtGroupEntry 8 }

gcpProtGroupReleaseingWindowTime OBJECT-TYPE
    SYNTAX      TimeInterval
    MAX-ACCESS  read-create
    STATUS      current
    DESCRIPTION 
        "This read-write attribute specifies the criteria of the 
         locked-in condition. The criteria includes the automatic 
         protection switching (APS) rate and the associated setting and 
         releasing time windows. If the number of APS of a Protection 
         Unit reaches the value specified in the hitsCount 
         (gcpProtGroupHitsCount) field within a moving time window of 
         specified length, the Protection Unit will enter the locked-in 
         condition.  Each switch to protection and its subsequent 
         release is considered as one hit. The length of the time window 
         for entering the locked-in condition is specified in the 
         settingWindowTime (gcpProtGroupSettingWindowTime) field.  Once 
         a Protection Unit is in the locked-in condition, future request 
         of APS will be denied until the locked-in condition is 
         released.  The release criterion is no APS request within 
         another moving time window.  The length of this time window is 
         specified in the releasingWindowTime 
         (gcpProtGroupReleasingWindowTime) field."
    REFERENCE   
        "ITU-T Rec. G.774.3 : lockedInCondition ATTRIBUTE"
    ::= { gcpProtGroupEntry 9 }

gcpProtGroupHitsCount OBJECT-TYPE
    SYNTAX      Unsigned32
    MAX-ACCESS  read-create
    STATUS      current
    DESCRIPTION 
        "This read-write attribute specifies the criteria of the 
         locked-in condition. The criteria includes the automatic 
         protection switching (APS) rate and the associated setting and 
         releasing time windows. If the number of APS of a Protection 
         Unit reaches the value specified in the hitsCount 
         (gcpProtGroupHitsCount) field within a moving time window of 
         specified length, the Protection Unit will enter the locked-in 
         condition.  Each switch to protection and its subsequent 
         release is considered as one hit. The length of the time window 
         for entering the locked-in condition is specified in the 
         settingWindowTime (gcpProtGroupSettingWindowTime) field.  Once 
         a Protection Unit is in the locked-in condition, future request 
         of APS will be denied until the locked-in condition is 
         released.  The release criterion is no APS request within 
         another moving time window.  The length of this time window is 
         specified in the releasingWindowTime 
         (gcpProtGroupReleasingWindowTime) field."
    REFERENCE   
        "ITU-T Rec. G.774.3 : lockedInCondition ATTRIBUTE"
    ::= { gcpProtGroupEntry 10 }

gcpProtGroupSwitchType OBJECT-TYPE
    SYNTAX      INTEGER { manual(0), forced(1), lockout(2) }
    MAX-ACCESS  read-create
    STATUS      current
    DESCRIPTION 
        "The invoke and release protection actions can be used to 
         request a lockout, a forced switch, or a manual (i.e. normal 
         switch) on one or more protection unit instances contained in 
         the protection group.
          
         - manual(0): peforms a manual protection invocation (from 
           a protected unit to a protecting unit); or a manual 
           protection release (from a protecting unit to a protected 
           unit);
          
         - forced(1): performs a forced protection invocation (from 
           a protected unit to a protecting unit); or a forced 
           protection release (from a protecting unit to a protected 
           unit);
          
         - lockout(2): performs a lockout invocation (applying lockout 
           to protected and protecting units); or a lockout release 
           (removing lockout from protected and protecting units).
          
         This object is written with the switch type applicable to an 
         action before writting the gcpProtGroupInvokeProtection or 
         gcpProtGroupReleaseProtection objects to invoke the action.
          "
    REFERENCE   
        "ITU-T Rec. G.774.3 (2001) 
               : InvokeProtectionArgs.SwitchType
         ITU-T Rec. G.774.3 (2001) 
               : ReleaseProtectionArgs.SwitchType"
    ::= { gcpProtGroupEntry 11 }

gcpProtGroupProtectedUnits OBJECT-TYPE
    SYNTAX      ProtectionUnits
    MAX-ACCESS  read-create
    STATUS      current
    DESCRIPTION 
        "Specifies and indicates a list of protection units acting as 
         protected units within this protection group, using the 
         ProtectedUnits textual convention.
          
         When read, this object returns a list of all the protection 
         units in the protection group that are protected units.
          
         When written, this object accepts a list of zero or more 
         protection units in the protection group to be applied as the 
         protected units to either a concurrent or subsequent 
         invokeProtection or releaseProtection action.
          
         The value read from this object may not necessarily be the same 
         as the value last written.
          
         This object is written with the protected units applicable to 
         an action before writting the gcpProtGroupInvokeProtection or 
         gcpProtGroupReleaseProtection objects to invoke the action.
          "
    REFERENCE   
        "ITU-T Rec. G.774.3 (2001) 
               : InvokeProtectionArgs.ProtectionEntity
         ITU-T Rec. G.774.3 (2001) 
               : ReleaseProtectionArgs.ProtectionEntity"
    ::= { gcpProtGroupEntry 12 }

gcpProtGroupProtectingUnits OBJECT-TYPE
    SYNTAX      ProtectionUnits
    MAX-ACCESS  read-create
    STATUS      current
    DESCRIPTION 
        "Specifies and indicates a list of protection units acting as 
         protecting units within this protection group, using the 
         ProtectedUnits textual convention.
          
         When read, this object returns a list of all the protection 
         units in the protection group that are protecting units.
          
         When written, this object accepts a list of zero or more 
         protection units in the protection group to be applied as the 
         protecting units to either a concurrent or subsequent 
         invokeProtection or releaseProtection action.
          
         The value read from this object may not necessarily be the same 
         as the value last written.
          
         This object is written with the protecting units applicable to 
         an action before writting the gcpProtGroupInvokeProtection or 
         gcpProtGroupReleaseProtection objects to invoke the action.
          "
    REFERENCE   
        "ITU-T Rec. G.774.3 (2001) 
               : InvokeProtectionArgs.ProtectionEntity
         ITU-T Rec. G.774.3 (2001) 
               : ReleaseProtectionArgs.ProtectionEntity"
    ::= { gcpProtGroupEntry 13 }

gcpProtGroupInvokeProtection OBJECT-TYPE
    SYNTAX      ActionOrResult
    MAX-ACCESS  read-create
    STATUS      current
    DESCRIPTION 
        "The invokeProtection action can be used to request a lockout, 
         a forced switch, or a manual (i.e. normal switch) on one or 
         more protectionUnit instances contained in the protectionGroup 
         object.  The action argument contains a request (Forced Switch, 
         Manual Switch, or Lockout) and indications of the protected and 
         protecting units to which the request applies.  If a protecting 
         unit is identified in the protectedUnits field, or if 
         a protected unit is identified in the protectingUnits field, 
         the action fails.  If the request is Forced Switch or Manual 
         Switch, the protectedUnits field shall identify one or more 
         protection units.  If only one unit is identified in the 
         protectedUnits field, and there is only one protecting unit in 
         the protection group, the protectingUnits field may be omitted.  
         If the protectingUnits field is present, it shall identify the 
         same number of units as the protectedUnits field.  If the 
         request is Lockout, the protectionEntity field may be absent, 
         indicating that the request applies to all contained protection 
         units.  If the protectionEntity field is present, any number of 
         protection units may be identified in the protectedUnits and/or 
         protectingUnits field, and either field may be absent.  For 
         a Lockout request, the specified protected units and/or 
         protecting units are locked out.  For requests that cannot be 
         completed, either because the request is the protecting unit is 
         serving a request of higher priority (in the error parameter of 
         the CMIP APDU, reason: pre-empted), or failure occurs 
         (failure), or timeout occurs (timeout), the reply shall 
         indicate why the request could not be completed, and the 
         request shall not be made pending.  The CMIP error APDU 
         contains the failure reasons.
         
         Any write to this object invokes the protection for the 
         associated protection group.  The gcpProtGroupSwitchType is 
         used as the type of invocation; the last write to 
         gcpProtGroupgProtectedUnits specifies the list of protected 
         units; gcpProtGroupgProtectingUnits, protecting units.
         
         A read from this object returns the result of the last action 
         invoked.  It may have one of the following values:
         
         - success(0): indicates that the last action was successful;
           
         - pending(1): indicates that the action is pending;
           
         - failure(2): indicates that the last action failed;
           
         - timeout(3): indicates that the last action timed out; and,
           
         - preempted(4): indicates that the last action was prempted by 
           an operation of higher priority."
    REFERENCE   
        "ITU-T Rec. G.774.3 (2001) : invokeProtection ACTION"
    ::= { gcpProtGroupEntry 14 }

gcpProtGroupReleaseProtection OBJECT-TYPE
    SYNTAX      ActionOrResult
    MAX-ACCESS  read-create
    STATUS      current
    DESCRIPTION 
        "The releaseProtection action can be used to release a lockout, 
         a forced switch, or a manual (i.e. normal switch) on one or 
         more protectionUnit instances contained in the protectionGroup 
         object. The action argument contains a request (Forced Switch, 
         Manual Switch, or Lockout) and indications of the protected and 
         protecting units to which the request applies. If a protecting 
         unit is identified in the protectedUnits field, or if 
         a protected unit is identified in the protectingUnits field, 
         the action fails. If the request is Forced Switch or Manual 
         Switch, the protectedUnits field shall identify one or more 
         protection units, and the protectingUnits field shall be 
         omitted. For each identified protected unit, if it is not 
         switched to a protecting unit, the action fails. If the request 
         is Lockout, the protectionEntity field may be absent, 
         indicating that the request applies to all contained protection 
         units. If the protectionEntity field is present, any number of 
         protection units may be identified in the protectedUnits and/or 
         protectingUnits field, and either field may be absent. For 
         a Lockout request, the specified protected units and/or 
         protecting units are no longer locked out. That is, the 
         protected units are now under protection and the protecting 
         units are now capable of providing protection. For release 
         requests which cannot be completed, the reply shall indicate 
         why the request could not be completed.
         
         Any write to this object invokes the request for the associated 
         protection group.  The gcpProtGroupSwitchType is used as the 
         type of release; the last write to gcpProtGroupProtectedUnits 
         specifies the list of protected units; 
         gcpProtGroupProtectingUnits, protecting units.
         
         A read from this object returns the result of the last action 
         invoked.  It may have one of the following values:
         
         - success(0): indicates that the last action was successful;
         
         - pending(1): indicates that an action is pending;
         
         - failure(2): indicates that the last action failed; and,
         
         - timeout(3): indicates that the last action timed out."
    REFERENCE   
        "ITU-T Rec. G.774.3 (2001) : releaseProtection ACTION"
    ::= { gcpProtGroupEntry 15 }

gcpProtGroupRowStatus OBJECT-TYPE
    SYNTAX      RowStatus
    MAX-ACCESS  read-create
    STATUS      current
    DESCRIPTION 
        "Provides a mechanism whereby management stations may create and 
         delete entries in this table.  Rows may also be created and 
         deleted by the managed system as a part of system operation.
         
         If the name package is supported, a create request with a value 
         for the name attribute that is already used by another instance 
         of the same object class will be rejected."
    REFERENCE   
        "STD 58, SNMPv2-TC RowStatus."
    ::= { gcpProtGroupEntry 16 }

gcpSbolTable OBJECT-TYPE
    SYNTAX      SEQUENCE OF GcpSbolEntry
    MAX-ACCESS  not-accessible
    STATUS      current
    DESCRIPTION 
        "Proivdes a side-table for listing multiple suppported-by 
         objects in a list."
    ::= { gcpProtGroup 2 }

gcpSbolEntry OBJECT-TYPE
    SYNTAX      GcpSbolEntry
    MAX-ACCESS  not-accessible
    STATUS      current
    DESCRIPTION 
        "Each row in the table is indexed by the protection group 
         identifier (value of gcpProtGroupId) as well as an ordinal 
         supported-by object list index (gcpSbolId).  This second index 
         ranges is a positive non-zero ordinal that ranges from 1 to the 
         number of supported-by object provided in the 
         gcpProtGroupSBOLNumber column of the master table 
         (gcpProtGroupTable).  The contents of the row is the RowPointer 
         identifying the supported-by object at this ordinal."
    INDEX       { gcpProtGroupId, gcpSbolId }
    ::= { gcpSbolTable 1 }

GcpSbolEntry ::= SEQUENCE {
    gcpSbolId       Unsigned32,
    gcpSbolObject   RowPointer,
    gcpSbolStatus   RowStatus
}

gcpSbolId OBJECT-TYPE
    SYNTAX      Unsigned32
    MAX-ACCESS  not-accessible
    STATUS      current
    DESCRIPTION 
        "Provides a non-zero ordinal index that identifies the position 
         with the supported-by object list of a particular object.  It 
         ranges from 1 to the protGroupSBOLNumber column value for the 
         corresponding protGroupId value in the protectionGroupTable."
    ::= { gcpSbolEntry 1 }

gcpSbolObject OBJECT-TYPE
    SYNTAX      RowPointer
    MAX-ACCESS  read-create
    STATUS      current
    DESCRIPTION 
        "Identifies one supported-by object in the supported-by object 
         list for the indexed gcpProtGroupId, using the RowPointer 
         textual convention."
    ::= { gcpSbolEntry 2 }

gcpSbolStatus OBJECT-TYPE
    SYNTAX      RowStatus
    MAX-ACCESS  read-create
    STATUS      current
    DESCRIPTION 
        "Provides a mechanism whereby management stations may add or 
         remove rows from this table.  Removing an object from the 
         interior ordinal of a sub-list results in the renumbering of 
         the indices of subsequent objects.  Requesting creation of an 
         object that already exists and has different values than the 
         existing entry can be viewed as an insert by the managed 
         system, resulting in the renumbering of the indices of 
         subsequent objects."
    REFERENCE   
        "STD 58, SNMPv2-TC RowStatus."
    ::= { gcpSbolEntry 3 }

gcpProtUnit OBJECT IDENTIFIER
    ::= { gcpTables 9 }

gcpProtUnitTable OBJECT-TYPE
    SYNTAX      SEQUENCE OF GcpProtUnitEntry
    MAX-ACCESS  not-accessible
    STATUS      current
    DESCRIPTION 
        "A protection unit object represents a protected (i.e.  working, 
         regular, or preferred) unit or a protecting (i.e. backup or 
         standby) unit.  For a protecting protection unit, the attribute 
         protecting shall have the value TRUE.  For a protectd 
         protection unit, the attribute protecting shall have the value 
         FALSE.  The value of the unreliableResourcePointer attribute 
         points to an unreliable resource (e.g. equipment hardware or 
         termination point) that is associated with the protectionUnit 
         instance.  The value of the reliableResourcePointer attribute 
         points to a reliable resource (e.g. termination point) that is 
         associated with the protectionUnit instance.
         
         If the attributeValueChangeNotificationPackage is present, then 
         changes to the unreliableResourcePointer or the 
         reliableResourcePointer attribute shall cause an 
         attributeValueChange notification to be emitted.
         
         The protectionUnitR1 managed object class is used to manage the 
         protected (i.e. working, regular or preferred) or protecting 
         (i.e. backup or standby) resource in a protection system.  It 
         relates the resources (e.g. circuit packs) invokved in the 
         protection system and keeps track of the protection switching 
         status of the resources."
    REFERENCE   
        "ITU-T Rec. M.3100 (2005) : protectionUnitR1 MOC
         ITU-T Rec. G.774.3 : protectionUnit MOC"
    ::= { gcpProtUnit 1 }

gcpProtUnitEntry OBJECT-TYPE
    SYNTAX      GcpProtUnitEntry
    MAX-ACCESS  not-accessible
    STATUS      current
    DESCRIPTION 
        "Instances of the protectionUnitR1 managed object class may be 
         automatically created in the agent, e.g., immediately following 
         the initialization of the NE resources (e.g. such as circuit 
         pack) involved in the protection system, according to the 
         make-up and mode of the NE.  Instances of this entity may be 
         deleted by the agent, e.g. upon the deletion of the 
         corresponding resource objects.  The agent may also create and 
         delete instances of this object class to reflect local 
         modifications in the protection schemes.
         
         (Instances of this object class may also be created or deleted 
         as the result of management operations to the 
         protectionCoordinator object (defined in ITU-T Rec.  G.774.9) 
         of an NE, such as the establishProtection, dismissProtection 
         and modifyProtection actions.)
         
         Two or more instances of the protectUnitR1 object may exist 
         within an instance of the protectionGroupR2 object.
         
         An instance of the protectionUnitR1 object could contain an 
         instance of the protectionCurrentData object (defined in ITU-T 
         Rec. G.774.1).
         
         A protectionUnitR1 instance is related to instances of resource 
         entities (e.g. Circuit Pack) via the unreliableReourcePointer 
         attribute.  If the funciton of the resource entities (e.g. 
         timing function, transport termination point function, etc.) is 
         explicitly modelled as object instances in the NE, then 
         a protectionUnitR1 instance is also related to instances of the 
         modelled function entity via the reliableResourcePointer 
         attribute.
         
         This object class has the following attributes:
         
         - gcpProtUnitProtectionStatus: Protection Status R1.  This 
           read-only attribute indicates the status of the protection 
           switch in a Protection Unit object.  The following behaviour 
           applies to this attribute:
           
           - This attribute must be capable of indicating pending as 
             well as active switching requests relative to the 
             protection unit.  However, only one of the values lockout, 
             forced switch, or manual switch can be present at the same 
             time.
             
           - A protection system may support only a subset of the 
             allowable values of this attribute.  The subset of values 
             to be supported by a system is implementation-specific.
             
           - The syntax of this attribute indicates a subfield 
             'relatedUnit' that is of ASN.1 CHOICE of 
             'fromProtectionUnitNumber' and 'toProtectionUnitNumber'.  
             This subfield is used to indicate on which unit the service 
             is carried.
             
             - For a protected PU, both the fromProtectionUnitNumber 
               (fromPU#) and the toProtectionUnitNumber (toPU#) hold the 
               ID of the related protecting PU.  When switching to the 
               protecting PU (i.e. service will be carried by the 
               protecting PU), the toProtectionUnitNumber choice is 
               used.  When switching back to the protected PU (service 
               will be carried by the protected PU), the 
               fromProtectionUnitNumber choice is used.
               
             - For a protecting PU, both the fromProtectionUnitNumber 
               (fromPU#) and the toProtectionUnitNumber (toPU#) hold the 
               ID of the related protected PU.  When switching to the 
               protected PU (i.e. service will be carried by the 
               protected PU), the toProtectionUnitNumber choice is used.  
               When swtiching to the protecting PU (service will be 
               carried by the protecting PU), the 
               fromProtectionUnitNumber choice is used.
               
           - If a system can support protection switching due to 
             Resource Degrade (RD) besides Resource Fail (RF), 
             protection switching of RD is similar to that in the 
             subsequent description for RF.
             
           - The following allowable Protection Status values are 
             associated with each protected Protection Unit (PU).
             
             - No Request: No switch request is present on the unit.  In 
               this case, services is on the protected PU, status syntax 
               is noRequest.  For non-revertive system, the status 
               syntax of the related protecting PU is also noRequest.
               
             - Manual Switch to Protecting Unit Complete: The unit has 
               completed a Manual Switch.  In this case, service is on 
               the related protecting PU, status suntax of the protected 
               PU is manualSwitch (switchStatus: completed; relatedUnit 
               toPU#).  Status syntax of the related protecting PU is 
               manualSwitch (switchStatus: completed; relatedUnit: 
               fromPU#).
               
             - Release Failed: A time-out occurs while waiting for 
               a release.  In this case, service is still on the 
               protecting PU, status syntax is releaseFailed plus the 
               previous status, such as manualSwitch (switchStatus: 
               completed, relatedUnit: toPU#).  Status syntax of the 
               related protecting PU is still the previous status, such 
               as manualSwitch (switchStatus: completed; relatedUnit: 
               fromPU#).
               
             - Automatic Switch (RF) Pending: The unit has a Fail 
               condition present and the protecting unit is unavailable.  
               In this case, service is still on the protected PU, 
               status syntax is autoSwitch (switchStatus: pending; 
               relatedUnit: toPU#; reason: RF). Status syntax of the 
               related protecting PU is autoSwitch (switchStatus: 
               pending, relatedUnit: fromPU#; reason: RF) plus its 
               previous status.
               
             - Automatic Swtich (RF) Complete: The unit has completed an 
               Automatic Switch to the protecting unit due to an 
               Equipment Fail condition.  In this case, service is on 
               the related protecting PU, status syntax of the protected 
               PU is autoSwitch (switchStatus: completed; relatedUnit: 
               toPU#; reason: RF).  Status syntax of the related 
               protecting PU is autoSwitch (switchStatus: completed; 
               relatedUnit: fromPU#; reason: RF).
               
             - Automatic Switch (RF) Present, Operate failed: An 
               automatic switch (RF) request is in progress and 
               a time-out occurs while waiting for completion.  In this 
               case, service is still on the protected PU, status syntax 
               is autoSwitch (switchStatus: failed; relatedUnit: toPU#; 
               reason: RF).  Status syntax of the related protecting PU 
               is autoSwitch (switchStatus: pending;  relatedUnit: 
               fromPU#; reason: RF) plus its previous status."
    REFERENCE   
        "ITU-T Rec. M.3100 (2005) : protectionUnitR1 MOC
         ITU-T Rec. G.774.3 : protectionUnit MOC"
    INDEX       { gcpProtUnitId }
    ::= { gcpProtUnitTable 1 }

GcpProtUnitEntry ::= SEQUENCE {
    gcpProtUnitId                           Unsigned32,
    gcpProtUnitProtecting                   TruthValue,
    gcpProtUnitReliableResourcePointer      RowPointer,
    gcpProtUnitUnreliableResourcePointer    RowPointer,
    gcpProtUnitProtectionStatus             ProtectionStatus,
    gcpProtUnitRequestSource                INTEGER,
    gcpProtUnitSwitchStatus                 INTEGER,
    gcpProtUnitSwitchDirection              INTEGER,
    gcpProtUnitRelatedUnit                  Unsigned32,
    gcpProtUnitAutoSwitchReason             INTEGER,
    gcpProtUnitLockoutReleaseFailed         TruthValue,
    gcpProtUnitPriority                     Unsigned32,
    gcpProtUnitRowStatus                    RowStatus
}

gcpProtUnitId OBJECT-TYPE
    SYNTAX      Unsigned32 (1..255)
    MAX-ACCESS  not-accessible
    STATUS      current
    DESCRIPTION 
        "Provides an index into the protection unit table.  A maximum of 
         255 protection units are allowed per protection group.
         
         Protection Unit Id.  This read-only attribute provides a unique 
         name for the protection unit instance within the containing 
         protection group object."
    REFERENCE   
        "ITU-T Rec. G.774.3 : protectionUnitId ATTRIBUTE"
    ::= { gcpProtUnitEntry 1 }

gcpProtUnitProtecting OBJECT-TYPE
    SYNTAX      TruthValue
    MAX-ACCESS  read-create
    STATUS      current
    DESCRIPTION 
        "This attribute specifies the type of the protectionUnit. 
         A value of TRUE indicates that the protectionUnit is 
         a protecting (i.e. backup or standby) unit.  A value of FALSE 
         indicates that the protectionUnit is a protected (i.e. 
         a regular, working, or preferred) unit.
         
         This read-only attribute identifies whether or not the 
         protection unit is associated with a resource providing 
         a protecting (true) or protected (false) role in the protection 
         system."
    REFERENCE   
        "ITU-T Rec. G.774.3 : protecting ATTRIBUTE"
    ::= { gcpProtUnitEntry 2 }

gcpProtUnitReliableResourcePointer OBJECT-TYPE
    SYNTAX      RowPointer
    MAX-ACCESS  read-create
    STATUS      current
    DESCRIPTION 
        "The value of the reliableResourcePointerR1 attribute points to 
         the reliable resource(s) (e.g. the functional objects) that 
         is/are associated with the Protection Unit instance.
         
         Unreliable Resource Pointer.  This read-only attribute 
         identifies the unreliable resource (e.g. circuit pack entity) 
         associated with the protection unit object (e.g. the actual 
         protected or protecting resource).  The syntax of this 
         attribute is set-valued and could point to multiple instances 
         of unreliable resources when a set of resources forms an atomic 
         unit in the protection system."
    REFERENCE   
        "ITU-T Rec. M.3100 (2005) : reliableResourcePointer 
               ATTRIBUTE"
    ::= { gcpProtUnitEntry 3 }

gcpProtUnitUnreliableResourcePointer OBJECT-TYPE
    SYNTAX      RowPointer
    MAX-ACCESS  read-create
    STATUS      current
    DESCRIPTION 
        "The value of the unreliableResourcePointerR1 attribute points 
         to the unreliable resource(s) (e.g. circuit pack) that is/are 
         associated with the Protection Unit instance.
         
         Reliable Resource Pointer: This read-only attribute identifies 
         the reliable resource (i.e. the functional entity), if there is 
         any, associated with the protection unit.  The value of this 
         attribute of a protection unit (PU) will change when the PU is 
         involved in a protection switch or release.  For a protected 
         PU, when it is not switched, this attribute points to NULL.  
         For a protecting PU, when it is not switched, this attribute is 
         pointer to NULL, and when it is switched, this attribute is 
         point to the associated reliable resource (i.e. the functional 
         object).  The syntax of this attribute is set-valued and could 
         point to multiple instances of reliable resource when a set of 
         functional objects form an atomic unit in the protection 
         system.  Examples of usage of this attribute are provided in 
         M.3100 (2005) E.3."
    REFERENCE   
        "ITU-T Rec. M.3100 (2005) : unreliableResourcePointer 
               ATTRIBUTE"
    ::= { gcpProtUnitEntry 4 }

gcpProtUnitProtectionStatus OBJECT-TYPE
    SYNTAX      ProtectionStatus
    MAX-ACCESS  read-create
    STATUS      current
    DESCRIPTION 
        "
         - noRequest(0), no switch request is present for the 
           protection unit;
           
         - doNotRevert(1), the protection unit is providing 
           service and the protection group semantics does not 
           allow revertive behaviour; the switch status is 
           completed(2);
           
         - manualSwitch(2), when this condition is present, the 
           gcpProtUnitSwitchStatus indicates the current 
           switching status and the gcpProtUnitRequestSource 
           indicates the source of the switching request; the 
           gcpProtUnitRelatedUnit indicates the related 
           (switched to or switched from) unit, and the 
           gcpProtUnitSwitchDirection indicates the direction of 
           switching;
           
         - autoSwitch(3), when this condition is present, the 
           gcpProtUnitSwitchStatus indicates the current 
           switching status and the gcpProtUnitRequestSource 
           indicates the source of the switching request; the 
           gcpProtUnitRelatedUnit indicates the related 
           (switched to or switched from) unit, and the 
           gcpProtUnitSwitchDirection indicates the direction of 
           switching;
           
         - forcedSwitch(4), when this condition is present, the 
           gcpProtUnitSwitchStatus indicates the current 
           switching status and the gcpProtUnitRequestSource 
           indicates the source of the switching request; the 
           gcpProtUnitRelatedUnit indicates the related 
           (switched to or switched from) unit, and the 
           gcpProtUnitSwitchDirection indicates the direction of 
           switching;
           
         - lockout(5), the protection unit is locked out by 
           management action; when this condition is present, 
           the gcpProtUnitSwitchStatus indicates the current 
           switching status and the gcpProtUnitRequestSource 
           indicates the source of the lockout request;
           
         - releaseFailed(6), the protection unit is a protecting 
           unit and release to the protected unit has failed;
           
         - resourceFailed(7), the protection unit has failed;
           
         - lockedIn(8), the unit has reached its maximum number 
           of APS hits for the time window and is currently 
           locked-in.
         
         This attribute is used to indicate the status of the protection 
         switch in a protectionUnit instance. This attribute is 
         set-valued because some requests are allowed to be pending.
         
         The following rule shall be followed:
         
         Only one of the values lockout, forcedSwitch, or manualSwitch 
         can be present at the same time, either local or remote. It is 
         also possible to have two or more pending automatic switch 
         requests.
         
         The protectionStatus attribute of a protection Unit which 
         provides protection is used to hold the protection request 
         which is actually performed on that protectionUnit. Locally 
         invoked management operations (e.g. manual, forced, lockout 
         switch completions) can be overridden at the near end or the 
         far end, but may only be released at the near end. Single-ended 
         systems keep the status of local and far-end switch requests as 
         separate entities in the protectionStatus attribute.
         
         The remainder of this behaviour provides the allowable 
         protectionStatus attribute values for protected and protecting 
         units for both revertive and non-revertive systems.
         
         The following allowable protectionStatus values are associated 
         with each protected unit:
         
         - No Request: No switch request is present on the unit.
           
         - Manual Switch to Protecting Complete: The unit has completed 
           a Manual Switch. Release failed A switch has been released or 
           pre-empted and a timeout occurs while waiting for a release 
           of associated bridges, or the near-end switch.
           
         - Automatic Switch (SF) Pending: The unit has a Signal Fail 
           condition present and the protecting unit is unavailable.
           
         - Automatic Switch (SD) Pending: The unit has a Signal Degrade 
           condition present and the protecting unit is unavailable.
           
         - Automatic Switch (SF) Complete: The unit has completed an 
           Automatic Switch to the protecting unit due to a Signal Fail 
           condition.
           
         - Automatic Switch (SD) Complete: The unit has completed an 
           Automatic Switch to the protecting unit due to a Signal 
           Degrade condition.
           
         - Automatic Switch (SF) Present, Operate failed: An automatic 
           switch (SF) request is in progress and a time-out occurs 
           while waiting for completion.
           
         - Automatic Switch (SD) Present, Operate failed: An automatic 
           switch (SD) request is in progress and a time-out occurs 
           while waiting for completion. Force Switch Complete,
           
         - Automatic Switch (SF) Pending: The unit has completed a Force 
           Switch. Additionally, the unit has an automatic switch (SF) 
           pending.
           
         - Force Switch Complete, Automatic Switch (SD) Pending: The 
           unit has completed a Force Switch. Additionally, the unit has 
           an automatic switch (SD) pending.
           
         - Automatic Switch Complete, Wait-to-Restore: The unit has 
           completed an Automatic Switch to the protecting unit.
           
         - Force Switch Complete: The unit has completed a Force Switch 
           to the protecting unit.
           
         - Protected Unit Lockout Completed: The unit has been locked 
           out from the protecting unit.
           
         - Protected Unit Lockout complete, Operate Failed: The unit has 
           been locked out from the protecting unit, and, the previously 
           completed switch could not be released within the expected 
           time-out. When the switch is released, the operate failed 
           status is removed. Additionally, the non-revertive protected 
           protection unit has the following status values: Do Not 
           Revert The protected unit has been switched to the protecting 
           unit and the request to do so has been released. The switch 
           to the protecting unit is maintained.
           
         - Manual Switch to Protected Unit Complete: The unit has 
           completed a Manual Switch from the protecting unit to the 
           protected unit.
           
         - Force Switch to Protected Unit Complete: The unit has 
           completed a Force Switch from the protecting unit to the 
           protected unit.
           
         - Automatic Switch (SF) to Protected Unit Complete: The 
           protecting unit has a Signal Fail condition present and 
           traffic is now being carried on the protected unit.
           
         - Automatic Switch (SD) to Protected Unit Complete: The 
           protecting unit has a Signal Degrade condition present and 
           traffic is now being carried on the protected unit.
           
         - Automatic Switch (SD) to Protected Unit Complete, Signal 
           Degrade Present: The protecting unit has a Signal Degrade 
           condition present and traffic is now being carried on the 
           protected unit.  Additionally, the protected unit has 
           a Signal Degrade condition present.
           
         - Automatic Switch (SF) to Protected Unit Complete, Signal 
           Degrade Present: The protecting unit has a Signal Fail 
           condition present and traffic is now being carried on the 
           protected unit.  Additionally, the protected unit has 
           a Signal Degrade condition present.
           
         - Force Switch from Protecting Unit Complete, Automatic Switch 
           (SF) Pending: The unit has completed a Force Switch from the 
           protecting unit to the protected unit. Additionally, the 
           protected unit has an automatic switch (SF) condition 
           present.
           
         - Force Switch from Protecting Unit Complete, Automatic Switch 
           (SD) Pending: The unit has completed a Force Switch from the 
           protecting unit to the protected unit. Additionally, the 
           protected unit has an automatic switch (SD) condition 
           present. The following allowable protectionStatus values are 
           associated with each protecting unit: No Request No request 
           is present on the protecting unit.
           
         - Manual Switch to Protecting Unit Complete: The protected unit 
           has completed a Manual Switch.
           
         - Automatic Switch Complete (SF) to Protecting Unit: The 
           protected unit has completed an automatic switch (SF) to the 
           protecting unit.
           
         - Automatic Switch Complete (SD) to Protecting Unit: The 
           protected unit has completed an automatic switch (SD) to the 
           protecting unit.
           
         - Automatic Switch Complete (SD) to Protecting Unit, Protecting 
           Unit Signal Degraded: The protected unit has completed an 
           automatic switch to the protecting unit.  Additionally, the 
           protecting unit has a Signal Degrade condition present. This 
           applies to 1:n systems only.
           
         - Automatic Switch Complete (SF) to Protecting Unit, Protecting 
           Unit Signal Degraded: The protected unit has completed an 
           automatic switch to the protecting unit.  Additionally, the 
           protecting unit has a Signal Degrade condition present. This 
           applies to 1:n systems only.
           
         - Protecting Unit SD Present: The protecting unit has a Signal 
           Degrade condition present.  This state may also be a result 
           of invalid or toggling APS byte values. This applies to 1:n 
           systems only.
           
         - Protecting Unit SF Present: The protecting unit has a Signal 
           Fail condition present.  This state may also be a result of 
           invalid or toggling APS byte values.  This applies to 1:n 
           systems only.
           
         - Force Switch Complete to Protecting Unit: The unit has 
           completed a Force Switch of a protected unit to the 
           protecting unit.
           
         - Force Switch Complete to Protecting Unit, SD Present on 
           Protecting Unit: The unit has completed a Force Switch of 
           a protected unit to the protecting unit.  Additionally, there 
           is a Signal Degrade present on the protecting unit.
           
         - Force Switch Complete to Protecting, SF Present on Protecting 
           Unit: The unit has completed a Force Switch of a protected 
           unit to the protecting unit.  Additionally, there is a Signal 
           Fail (1 + 1 unidirectional systems only) present on the 
           protecting unit.
           
         - Protecting Unit Locked Out: The protecting unit has been 
           locked out.
           
         - Protecting Unit Locked Out, Release Failed: A release of 
           a lockout is in progress and a timeout occurs waiting for the 
           lockout condition to clear.  Additionally, the non-revertive 
           protecting unit has the following values: Do Not Revert The 
           protected unit has been switched to the protecting unit and 
           the request to do so has been released. The switch to the 
           protecting unit is maintained.
           
         - Manual Switch to Protected Unit Complete: The unit has 
           completed a Manual Switch from the protecting unit to the 
           protected unit.
           
         - Force Switch to Protected Unit Complete: The protecting unit 
           has completed a forced switch to the protected unit.
           
         - Force Switch to Protected Unit Complete, Protecting Unit 
           Signal Degraded: The protecting unit has completed a forced 
           switch to the protected unit.  Additionally, there is 
           a Signal Degrade condition on the protecting unit.
           
         - Force Switch to Protected Unit Complete, Protecting Unit 
           Signal Failed: The protecting unit shows a forced switch to 
           the protected unit.  Additionally, there is a Signal Fail 
           condition on the protecting unit.
           
         - Automatic Switch (SF) to Protected Unit Complete: The 
           protecting unit has a Signal Fail condition present and 
           traffic is now being carried on the protected unit.
           
         - Automatic Switch (SD) to Protected Unit Complete: The 
           protecting unit has a Signal Degrade condition present and 
           traffic is now being carried on the protected unit.
           
         - Automatic Switch Complete (SD) to Protecting, Automatic 
           Switch (SD) to Protected Unit Pending: The protected unit has 
           completed an automatic switch to the protecting unit.  
           Additionally, the protecting unit has a Signal Degrade 
           condition present.
           
         - Automatic Switch Complete (SF) to Protecting, Automatic 
           Switch (SD) to Protected Unit Pending: The protected unit has 
           completed an automatic switch to the protecting unit.  
           Additionally, the protecting unit has a Signal Degrade 
           condition present.
           
         APS timeout detected by the exerciser, or, during an attempt to 
         invoke a manual or forced switch will not be indicated as APS 
         failure (operate or release fail) in the protectionStatus 
         attribute. Instead, the actionReply for the invoked action will 
         report this.  Additionally, attribute lastAttemptResult will 
         provide a record of the failure, until a successful exercise or 
         protection switch causes this attribute to be cleared."
    REFERENCE   
        "ITU-T Rec. M.3100 (2005) : protectionStatusR1 
               ATTRIBUTE"
    ::= { gcpProtUnitEntry 5 }

gcpProtUnitRequestSource OBJECT-TYPE
    SYNTAX      INTEGER { local(0), remote(1) }
    MAX-ACCESS  read-create
    STATUS      current
    DESCRIPTION 
        "Indicates the source of a switching request when the protection 
         status is manualSwitch(2), autoSwitch(3), forcedSwitch(4) or 
         lockout(5).  The value indicates whether the source of the 
         request was local or remote.
         
         - local(0), when indicated for a manual or lockout switching 
           operation, the request was local to the system (e.g, from 
           a local EMS); when indicated for an automatic protection 
           switch, the detection of failure or degradation was detected 
           locally.
           
         - remote(1), when indicated for a manual or lockout switching 
           operation, the request was remote from the system (e.g, from 
           an NMS or a remote GCP entity); when indicated for an 
           automatic protection switch, the detection of failure or 
           degradation was detected remotely.
           
           "
    REFERENCE   
        "ITU-T Rec. G.774.3 SDHProtASN1:RequestSource"
    ::= { gcpProtUnitEntry 6 }

gcpProtUnitSwitchStatus OBJECT-TYPE
    SYNTAX      INTEGER { pending(0), completed(1), operateFailed(2) }
    MAX-ACCESS  read-only
    STATUS      current
    DESCRIPTION 
        "Indicates whether the status of the current protection switch 
         when gcpProtUnitProtectionStatus contains manualSwitch(2), 
         autoSwitch(3), forcedSwitch(4) or lockout(5).  The switch 
         status has the following defined states:
         
         - pending(0), the protection switch has been initiated but is 
           still pending;
           
         - completed(1), the protection switch has completed;
           
         - operateFailed(2), the protection switch has failed and the 
           switched-from protection unit is still the unit providing 
           service."
    REFERENCE   
        "ITU-T Rec. G.774.3 SDHProtASN1:SwitchStatus"
    ::= { gcpProtUnitEntry 7 }

gcpProtUnitSwitchDirection OBJECT-TYPE
    SYNTAX      INTEGER { from(1), to(2) }
    MAX-ACCESS  read-only
    STATUS      current
    DESCRIPTION 
        "Indicates whether the last protection switch resulting in the 
         current protection status was from the protection unit 
         specified in gcpProtUnitRelatedUnit, or to that unit.  This 
         value is only significant when the switching status is 
         manualSwitch(2), autoSwitch(3) or forcedSwitch(4)."
    REFERENCE   
        "ITU-T Rec. G.774.3 SDHProtASN1:FromAndToProtectionUnit"
    ::= { gcpProtUnitEntry 8 }

gcpProtUnitRelatedUnit OBJECT-TYPE
    SYNTAX      Unsigned32 (1..255)
    MAX-ACCESS  read-only
    STATUS      current
    DESCRIPTION 
        "Specifies the related unit when the switching status is 
         manualSwitch(2), autoSwitch(3) or forcedSwitch(4). This is the 
         index of the protection unit in the protection group that was 
         switched from or switched to.  When the current row is the unit 
         that was switched from, this value indicates the protection 
         unit that was switched to; otherwise, it indicates the unit 
         that was switched from.  The direction of protection switching 
         is indicated in the gcpProtUnitSwitchDirection column."
    REFERENCE   
        "ITU-T Rec. G.774.3 SDHProtASN1:FromAndToProtectionUnit"
    ::= { gcpProtUnitEntry 9 }

gcpProtUnitAutoSwitchReason OBJECT-TYPE
    SYNTAX      INTEGER { waitToRestore(0), signalDegrade(1), 
                    signalFail(2) }
    MAX-ACCESS  read-only
    STATUS      current
    DESCRIPTION 
        "Specifies the reason for the APS when the protection status is 
         autoSwitch(3). The reason can be one of the following defined 
         reasons:
         
         - waitToRestore(0),
         - signalDegrade(1),
         - signalFail(2),"
    REFERENCE   
        "ITU-T Rec. G.774.3 SDHProtASN1:AutoSwitchReason"
    ::= { gcpProtUnitEntry 10 }

gcpProtUnitLockoutReleaseFailed OBJECT-TYPE
    SYNTAX      TruthValue
    MAX-ACCESS  read-only
    STATUS      current
    DESCRIPTION 
        "This column is only significant when the 
         gcpProtUnitProtectionStatus is lockout(5) and a release 
         of the lockout(5) condition failed, leaving the 
         protection unit in the locked out condition.  For all 
         other conditions, this column reads false(2)."
    REFERENCE   
        "ITU-T Rec. M.3100 (2005) 
               ASN1DefinedTypesModule:ProtectionStatusR1"
    ::= { gcpProtUnitEntry 11 }

gcpProtUnitPriority OBJECT-TYPE
    SYNTAX      Unsigned32
    MAX-ACCESS  read-create
    STATUS      current
    DESCRIPTION 
        "This attribute specifies the priority of the service (e.g.  
         traffic) carried on the resource associated with the protected 
         protectionUnit instance. Valid values for this attribute are 
         integers, where the value 1 indicates the highest priority, and 
         a larger value indicates a lower priority. For a protecting 
         protectionUnit, the value of this attribute indicates the 
         priority of choice of the protecting protectionUnit relative to 
         other available protecting protectionUnit(s) within the same 
         protectionGroup.  The lower the value, the more preferred the 
         protectionUnit is relative to other protectionUnits.
         
         This read-write attribute specifies the priority of the service 
         carried on the resource associated with the protection unit 
         instance. Valid values for this attribute are integers, where 
         the value 1 indicates the highest priority, and a larger value 
         indicates a lower priority."
    REFERENCE   
        "ITU-T Rec. G.774.3 : priority ATTRIBUTE"
    ::= { gcpProtUnitEntry 12 }

gcpProtUnitRowStatus OBJECT-TYPE
    SYNTAX      RowStatus
    MAX-ACCESS  read-create
    STATUS      current
    DESCRIPTION 
        "Provides a mechanism whereby management stations may create or 
         delete entries in this table.  Rows may also be created and 
         deleted by the managed system as part of system operations."
    REFERENCE   
        "STD 58, SNMPv2-TC RowStatus."
    ::= { gcpProtUnitEntry 13 }

gcpRealm OBJECT IDENTIFIER
    ::= { gcpTables 10 }

gcpRealmTable OBJECT-TYPE
    SYNTAX      SEQUENCE OF GcpRealmEntry
    MAX-ACCESS  not-accessible
    STATUS      current
    DESCRIPTION 
        "This table defaults of the IP address realms known to 
         this managed system.  IP Address Realms are defined in 
         RFC 2663, clause 2.1, as a network domain in which the 
         network addresses are uniquely assigned to entities 
         such that datagrams can be routed to them.  Routing 
         protocols used within the network domain are 
         responsible for finding routes to entities given their 
         network addresses."
    REFERENCE
        "ITU-T Recommendation H.248.41 (05/2006) IP domain 
               connection package.
         RFC 2663, NAT Terminology and Considerations."
    ::= { gcpRealm 1 }

gcpRealmEntry OBJECT-TYPE
    SYNTAX      GcpRealmEntry
    MAX-ACCESS  not-accessible
    STATUS      current
    DESCRIPTION
        "IP Address Realm is defined in RFC 2663, clause 2.1, as 
         a network domain in which the network addresses are 
         uniquely assigned to entities such that datagrams can 
         be routed to them.  Routing protocols used within the 
         network domain are responsible for findng routes to 
         entities given their network addresses.
         
         The value of the IP realm identifier property is 
         a string, which may be in a domain name format, such as 
         `mynet.net', or any other string format.
         
         The IP realm identifier should be provisioned between 
         the MGC and the MG.  Each of the different IP realms 
         possibly interconnecting with an MG should have 
         a different identifier.  The MGC and the MG can 
         provisino a default IP realm and configure it on the 
         MG.  If the MGC sends a command to the MG to create an 
         IP-based H.248 termination without the IP realm 
         identifier property, the MG will consider it as 
         indicating the default realm.
         
         If the value of the IP realm identifier property sent 
         by the MGC cannot be recognized by the MG, the MG will 
         fail to create the IP-based H.248 termination and 
         return the corresponding error code to the MGC: 449 
         (Unsupported or Unknown Parameter or Property Value)."
    REFERENCE
        "ITU-T Recommendation H.248.41 (05/2006) IP domain 
               connection package.
         RFC 2663, NAT Terminology and Considerations."
    INDEX       { gcpMsId, gcpMgId, gcpRealmId }
    ::= { gcpRealmTable 1 }

GcpRealmEntry ::= SEQUENCE {
    gcpRealmId              Unsigned32,
    gcpRealmString          SnmpAdminString,
    gcpRealmTermsMax        Unsigned32,
    gcpRealmTermsCurrent    Gauge32,
    gcpRealmTermsHiWat      Gauge32,
    gcpRealmTermsLoWat      Gauge32,
    gcpRealmRowStatus       RowStatus
}

gcpRealmId OBJECT-TYPE
    SYNTAX      Unsigned32
    MAX-ACCESS  not-accessible
    STATUS      current
    DESCRIPTION 
        "Provides a non-zero ordinal index into the 
         gcpRealmTable.  The index one (1) has significant 
         meaning, it is the default realm that will be used if 
         a realm identifier property is not specified during the 
         formation of an ephemeral termination."
    ::= { gcpRealmEntry 1 }

gcpRealmString OBJECT-TYPE
    SYNTAX      SnmpAdminString
    MAX-ACCESS  read-create
    STATUS      current
    DESCRIPTION 
        "Specifies an IP address realm for use in the realm 
         identifier when creating ephemerial terminations."
    REFERENCE
        "ITU-T Recommendation H.248.41 (05/2006) IP domain 
               connection package.
         RFC 2663, NAT Terminology and Considerations."
    ::= { gcpRealmEntry 2 }

gcpRealmTermsMax OBJECT-TYPE
    SYNTAX      Unsigned32
    MAX-ACCESS  read-only
    STATUS      current
    DESCRIPTION 
        "Indicates the maximum number of ephemeral terminations 
         available in this IP address realm."
    ::= { gcpRealmEntry 3 }

gcpRealmTermsCurrent OBJECT-TYPE
    SYNTAX      Gauge32
    MAX-ACCESS  read-only
    STATUS      current
    DESCRIPTION 
        "Indicates the number of current ephemeral terminations 
         in use in this realm."
    ::= { gcpRealmEntry 4 }

gcpRealmTermsHiWat OBJECT-TYPE
    SYNTAX      Gauge32
    MAX-ACCESS  read-create
    STATUS      current
    DESCRIPTION 
        "Provides the high water mark of ephemeral terminations 
         in use since the last reset of this object.  The object 
         is reset by setting it to zero."
    DEFVAL      { 0 }
    ::= { gcpRealmEntry 5 }

gcpRealmTermsLoWat OBJECT-TYPE
    SYNTAX      Gauge32
    MAX-ACCESS  read-create
    STATUS      current
    DESCRIPTION 
        "Provides the low water mark of ephemeral terminations 
         in use since the last reset of this object.  The object 
         is reset by setting it gcpRealmTermsMax or higher."
    DEFVAL      { 4294967295 }
    ::= { gcpRealmEntry 6 }

gcpRealmRowStatus OBJECT-TYPE
    SYNTAX      RowStatus
    MAX-ACCESS  read-create
    STATUS      current
    DESCRIPTION 
        "Provides a mechanism whereby management stations may 
         create or destroy conceptual rows in this table."
    ::= { gcpRealmEntry 7 }

gcpInterface OBJECT IDENTIFIER
    ::= { gcpTables 11 }

gcpInterfaceTable OBJECT-TYPE
    SYNTAX      SEQUENCE OF GcpInterfaceEntry
    MAX-ACCESS  not-accessible
    STATUS      current
    DESCRIPTION 
        "This table specifies all of the IP interfaces known to 
         (used by) the GCP managed switching element."
    REFERENCE   
        "ITU-T Recommendation H.248.64 (12/2009)"
    ::= { gcpInterface 1 }

gcpInterfaceEntry OBJECT-TYPE
    SYNTAX      GcpInterfaceEntry
    MAX-ACCESS  not-accessible
    STATUS      current
    DESCRIPTION 
        "Each entry in the gcpInterfaceTable table is indexed by 
         the managed switching element identifier and interface 
         identifier for the interface as used by that managed 
         element.  Each entry contains the ifIndex value, MG 
         identifier, inteface type from an MG routing 
         perspective, the realm identifier (index into the 
         gcpRealmTable), and the termination identifier and 
         path."
    REFERENCE   
        "ITU-T Recommendation H.248.64 (12/2009)"
    INDEX       { gcpMsId, gcpInterfaceId }
    ::= { gcpInterfaceTable 1 }

GcpInterfaceEntry ::= SEQUENCE {
    gcpInterfaceId              Unsigned32,
    gcpInterfaceIfindex         Unsigned32,
    gcpInterfaceMgId            Unsigned32,
    gcpInterfaceType            INTEGER,
    gcpInterfaceRealm           Unsigned32,
    gcpInterfaceTermId          MegacoTerminationId,
    gcpInterfaceTermPath        MegacoTerminationPath,
    gcpInterfaceRowStatus       RowStatus
}

gcpInterfaceId OBJECT-TYPE
    SYNTAX      Unsigned32
    MAX-ACCESS  not-accessible
    STATUS      current
    DESCRIPTION 
        "Provides a non-zero oridinal sub-index into the 
         gcpInterfaceTable, identifying an L2 interface within 
         a managed switching element (host)."
    ::= { gcpInterfaceEntry 1 }

gcpInterfaceIfindex OBJECT-TYPE
    SYNTAX      Unsigned32
    MAX-ACCESS  read-create
    STATUS      current
    DESCRIPTION 
        "Specifies the interface index (value of ifIndex) of the 
         associated L2 interface.  Only one entry in this table 
         is permitted to assumed the value of a given interface.  
         The interface index must exist."
    ::= { gcpInterfaceEntry 2 }

gcpInterfaceMgId OBJECT-TYPE
    SYNTAX      Unsigned32
    MAX-ACCESS  read-create
    STATUS      current
    DESCRIPTION 
        "Specifies the virtual MG to which this interface is 
         assigned.  This gcpMsId and gcpMgId combination must 
         exist in the gcpMgTable."
    ::= { gcpInterfaceEntry 3 }

gcpInterfaceType OBJECT-TYPE
    SYNTAX      INTEGER { b2b(1), iipr(2), ripr(3), nipr(4) }
    MAX-ACCESS  read-create
    STATUS      current
    DESCRIPTION 
        "
         - b2b(1), back-to-back IP host mode;
           
         - iipr(2), interface IPR context type of IP router 
           mode;
           
         - ripr(3), route IPR context type of IP router mode;
           
         - nipr(4), NAT IPR context type of IP router mode."
    REFERENCE   
        "ITU-T Recommendation H.248.64 (12/2009), 10.1.1."
    ::= { gcpInterfaceEntry 4 }

gcpInterfaceRealm OBJECT-TYPE
    SYNTAX      Unsigned32
    MAX-ACCESS  read-create
    STATUS      current
    DESCRIPTION 
        "Specifies the realm to which the interface belongs.  
         The value of this conceptual column is the value of the 
         index into the gcpRealmTable that corresponds to the 
         realm to which the interface belongs."
    ::= { gcpInterfaceEntry 5 }

gcpInterfaceTermId OBJECT-TYPE
    SYNTAX      MegacoTerminationId
    MAX-ACCESS  read-create
    STATUS      current
    DESCRIPTION 
        "Specifies the GCP termination identifier that is used 
         to control the properties of, or otherwise specify, 
         this interface."
    ::= { gcpInterfaceEntry 6 }

gcpInterfaceTermPath OBJECT-TYPE
    SYNTAX      MegacoTerminationPath
    MAX-ACCESS  read-create
    STATUS      current
    DESCRIPTION 
        "Specifies the GCP termination path that is used to 
         control the properties of, or otherwise specify, this 
         interface."
    ::= { gcpInterfaceEntry 7 }

gcpInterfaceRowStatus OBJECT-TYPE
    SYNTAX      RowStatus
    MAX-ACCESS  read-create
    STATUS      current
    DESCRIPTION 
        "Provides a mechanism whereby management stations may 
         create or destroy conceptual rows in this table."
    ::= { gcpInterfaceEntry 8 }

gcpAddress OBJECT IDENTIFIER
    ::= { gcpTables 12 }

gcpAddressTable OBJECT-TYPE
    SYNTAX      SEQUENCE OF GcpAddressEntry
    MAX-ACCESS  not-accessible
    STATUS      current
    DESCRIPTION 
        "This table contains the IP addresses that are available 
         to MG."
    ::= { gcpAddress 1 }

gcpAddressEntry OBJECT-TYPE
    SYNTAX      GcpAddressEntry
    MAX-ACCESS  not-accessible
    STATUS      current
    DESCRIPTION 
        "Each row in this table is indexed by the managed 
         switching element identifier, the MG identifier, the IP 
         Realm, the interface, and the address identifier.  Each 
         row contains the address type and address, along with 
         a port range that is usable by the MG."
    INDEX       { gcpMsId, gcpMgId, gcpRealmId, gcpInterfaceId, 
                  gcpAddressId }
    ::= { gcpAddressTable 1 }

GcpAddressEntry ::= SEQUENCE {
    gcpAddressId            Unsigned32,
    gcpAddressInterface     Unsigned32,
    gcpAddressType          InetAddressType,
    gcpAddressAddr          InetAddress,
    gcpAddressPortRanges    PortRange,
    gcpAddressRowStatus     RowStatus
}

gcpAddressId OBJECT-TYPE
    SYNTAX      Unsigned32
    MAX-ACCESS  not-accessible
    STATUS      current
    DESCRIPTION
        "Provides a non-zero ordinal index into this table."
    ::= { gcpAddressEntry 1 }

gcpAddressInterface OBJECT-TYPE
    SYNTAX      Unsigned32
    MAX-ACCESS  read-create
    STATUS      current
    DESCRIPTION
        "Specifies the address interface."
    ::= { gcpAddressEntry 3 }

gcpAddressType OBJECT-TYPE
    SYNTAX      InetAddressType
    MAX-ACCESS  read-create
    STATUS      current
    DESCRIPTION
        "Specifies the address type in accordance with the 
         InetAddressType textual convention of the 
         INET-ADDRESS-MIB.  This dictates the type of address 
         that is contained in the gcpAddressAddr column."
    REFERENCE
        "RFC 4001, INET-ADDRESS-MIB:InetAddressType."
    ::= { gcpAddressEntry 4 }

gcpAddressAddr OBJECT-TYPE
    SYNTAX      InetAddress
    MAX-ACCESS  read-create
    STATUS      current
    DESCRIPTION
        "Specifies the address, which is of type gcpAddressType, 
         in accordance with the InetAddress textual convention 
         of the INET-ADDRESS-MIB."
    REFERENCE
        "RFC 4001, INET-ADDRESS-MIB:InetAddress."
    ::= { gcpAddressEntry 5 }

gcpAddressPortRanges OBJECT-TYPE
    SYNTAX      PortRange
    MAX-ACCESS  read-create
    STATUS      current
    DESCRIPTION
        "Specifies the port range which is the range of port 
         numbers that are available for use for ephemeral 
         connections."
    ::= { gcpAddressEntry 6 }

gcpAddressRowStatus OBJECT-TYPE
    SYNTAX      RowStatus
    MAX-ACCESS  read-create
    STATUS      current
    DESCRIPTION
        "Provides a mechanism whereby management stations may 
         create or destroy conceptual rows in this table."
    ::= { gcpAddressEntry 7 }

gcpOids OBJECT IDENTIFIER
    ::= { gcpMIB 4 }

gcpProtocols OBJECT IDENTIFIER
    ::= { gcpOids 1 }

gcpProtocolSgcp OBJECT-IDENTITY
    STATUS      current
    DESCRIPTION 
        "The SGCP protocol."
    ::= { gcpProtocols 1 }

gcpProtocolIdcp OBJECT-IDENTITY
    STATUS      current
    DESCRIPTION 
        "The IDCP protocol."
    ::= { gcpProtocols 2 }

gcpProtocolMgcp OBJECT-IDENTITY
    STATUS      current
    DESCRIPTION 
        "The MGCP protocol as described in RFC 2705."
    REFERENCE   
        "RFC 2705"
    ::= { gcpProtocols 3 }

gcpProtocolMegaco OBJECT-IDENTITY
    STATUS      current
    DESCRIPTION 
        "The MEGACO/H.248 protocol as described in RFCs."
    ::= { gcpProtocols 4 }

gcpProtocolMegacoV1 OBJECT-IDENTITY
    STATUS      current
    DESCRIPTION 
        "The MEGACO protocol Version 1."
    ::= { gcpProtocolMegaco 1 }

gcpProtocolMegacoV2 OBJECT-IDENTITY
    STATUS      current
    DESCRIPTION 
        "The MEGACO protocol Version 2."
    ::= { gcpProtocolMegaco 2 }

gcpProtocolMegacoV3 OBJECT-IDENTITY
    STATUS      current
    DESCRIPTION 
        "The MEGACO protocol Version 3."
    ::= { gcpProtocolMegaco 3 }

gcpProtocolH248 OBJECT-IDENTITY
    STATUS      current
    DESCRIPTION 
        "The MEGACO/H.248 protocol as described in ITU-T Rec. 
         H.248.1."
    REFERENCE   
        "ITU-T Recommendation H.248.1 (09/2005)"
    ::= { gcpProtocols 5 }

gcpProtocolH248v1 OBJECT-IDENTITY
    STATUS      current
    DESCRIPTION 
        "The H.248 protocol Version 1."
    REFERENCE   
        "ITU-T Recommendation H.248.1 (09/2005)"
    ::= { gcpProtocolH248 1 }

gcpProtocolH248v2 OBJECT-IDENTITY
    STATUS      current
    DESCRIPTION 
        "The H.248 protocol Version 2."
    REFERENCE   
        "ITU-T Recommendation H.248.1 (09/2005)"
    ::= { gcpProtocolH248 2 }

gcpProtocolH248v3 OBJECT-IDENTITY
    STATUS      current
    DESCRIPTION 
        "The H.248 protocol Version 3."
    REFERENCE   
        "ITU-T Recommendation H.248.1 (09/2005)"
    ::= { gcpProtocolH248 3 }

gcpProtocolCbc OBJECT-IDENTITY
    STATUS      current
    DESCRIPTION 
        "The CBC protocol as described in ITU-T Rec. Q.1950."
    REFERENCE   
        "ITU-T Recommendation Q.1950."
    ::= { gcpProtocols 6 }

gcpProtocolBgc OBJECT-IDENTITY
    STATUS      current
    DESCRIPTION 
        "The BGC protocol as described in ETSI ES 283 018."
    REFERENCE   
        "ETSI ES 283 018 V2.7.2 (2010-01)."
    ::= { gcpProtocols 7 }

gcpGroups OBJECT IDENTIFIER
    ::= { gcpMIB 5 }

gcpCompliance OBJECT IDENTIFIER
    ::= { gcpMIB 6 }

gcpProtectionSwitchReport NOTIFICATION-TYPE
    OBJECTS     { tmnObjectInstance, gcpOldProtectionStatus, 
                  gcpOldRequestSource, gcpOldSwitchStatus, 
                  gcpOldSwitchDirection, gcpOldRelatedUnit, 
                  gcpOldAutoSwitchReason, gcpNewProtectionStatus, 
                  gcpNewRequestSource, gcpNewSwitchStatus, 
                  gcpNewSwitchDirection, gcpNewRelatedUnit, 
                  gcpNewAutoSwitchReason }
    STATUS      current
    DESCRIPTION 
        "Provides a notification of a protection switching event.  The 
         tnmObjectInstance identifies the protect unit by object 
         identifier (a RowPointer to the row in the gcpProtUnitTable for 
         which the protection switch occurred.  The additional 
         information includes both the old protection status and the new 
         protection status."
    ::= { gcpNotifications 1 }

gcpMgFailure NOTIFICATION-TYPE
    OBJECTS     { tmnObjectInstance }
    STATUS      current
    DESCRIPTION 
        "The object instance reported in the this failure notification is 
         the RowPointer to the entry of the media gateway that failed, or 
         is failing, in the gcpMgTable.
         
         If an MG fails, but is capable of sending a message to the MGC, 
         it sends a ServiceChange with an appropriate method (Graceful or 
         Forced) and specifies the Root TerminationID.  When it returns 
         to service, it sends a ServiceChange with a ``Restart'' 
         ServiceChangeMethod.
         
         Allowing the MGC to send duplicate messages to both MGs 
         accommodates pairs of MGs that are capable of redundant fail-over 
         of one of the MGs.  Only the Working MG shall accept or reject 
         transactions.  Upon fail-over, the primary MG sends 
         a ServiceChange Command with a ``Failover'' method and a ``MG 
         Impending Failure'' reason.  The MGC then uses the secondary MG 
         as the active MG.  When the error condition is repaired, the 
         working MG can send a ``ServiceChange'' with a ``Restart'' 
         ServiceChangeMethod.
         
         NOTE -- that redundant failover MGs require a reliable transport, 
         because the protocol provides no means for a secondary MG 
         running ALF to acknowledge messages sent from the MGC."
    REFERENCE
        "ITU-T Recommendation H.248.1 (09/2005), Clause 11.4, Failure of 
               a MG."
    ::= { gcpNotifications 2 }

gcpMgcFailure NOTIFICATION-TYPE
    OBJECTS     { tmnObjectInstance }
    STATUS      current
    DESCRIPTION 
        "If the MG detects a failure of its controlling MGC, it attempts to 
         contact the next MGC on its pre-provisioned list.  It starts its 
         attempts at the beginning (primary MGC), unless that was the MGC that 
         failed, in which case it starts at its first secondary MGC.  It sends 
         a ServiceChange message with a ``Failover'' method and a ``MGC 
         Impending Failure'' reason.  If the MG is unable to establish a control 
         relationship with any MGC, it shall wait a random amount of time as 
         described in ITU-T Rec.  H.248.1/9.2 and then start again contacting 
         its primary, and (if necessary) its secondary MGCs.  When contacting 
         its previous controlling MGC, the MG sends the ServiceChagne message 
         with ``Disconnected'' method.
         
         In partial failure, or for manual maintenance reasons, an MGC may wish 
         to direct its controlled MGs to use a different MGC.  To do so, it 
         sends a ServiceChange method to the MG with a ``Handoff'' method, and 
         its designated replacement in ServiceChangeMgcID.  If ``Handoff'' is 
         supported, the MGC shall send a ServiceChange message with 
         a ``Handoff'' method and a ``MGC directed change'' reason to the 
         designated MGC.  If it fails to get a rely from the designated MGC, the 
         MG shall behave as if its MGC failed, and start contacting secondary 
         MGCs as specified in the previous paragraph.  If the MG is unabled to 
         establish a control relationship with any MGC, it shall wait a random 
         amount of time as described in ITU-T Rec.  H.248.1/9.2 and then start 
         contacting its primary, and if necessary, its secondary MGCs again.
         
         No recommendation is made on how the MGCs invoked in the hand-off 
         maintain state information; this is considered to be out of scope of 
         this Recommendation.  The MGC and MG may take the following steps when 
         hand-off occurs.  When the MGC iinitiates a hand-off, the handover should 
         be transparent to operations on the Media Gateway.  Transactions can be 
         executed in any order, and could be in progress when the ServiceChange 
         is executed.  Accordingly, commands in progress continue and replies to 
         all commands from the original MGC must be sent to the transport 
         address from which they were sent.  If the service relationship with 
         the sending MGC has ended, the replies should be discarded.  The MG may 
         receive outstanding transaction replies from the new MGC.  No new 
         messages shall be sent to the new MGC until the control association is 
         established.  Repeated transaction requests shall be directed to the 
         new MGC.  The MG shall maintain the state of all terminations and 
         contexts.
         
         It is possible that the MGC could be implemented in such a way that 
         a failed MGC is replaced by a working MGC where the identity of the new 
         MGC is the same as the failed one.  In such a case, the 
         ServiceChangeMgcID would be specified with the previous value and the 
         MG shall behave as if the value was changed, and send a ServiceChange 
         message as above.
         
         Pairs of MGCs that are capable of redundant fail-over can notify the 
         controlled MGCs of the fail-over by the above mechanism. "
    REFERENCE
        "ITU-T Recommendation H.248.1 (09/2005), Clause 11.5, Failure of 
               an MGC."
    ::= { gcpNotifications 3 }

gcpLinkageFailure NOTIFICATION-TYPE
    OBJECTS     { tmnObjectInstance }
    STATUS      current
    DESCRIPTION 
        "Monitoring the MGC-MG control association is essential for high 
         availability networks.  This may be realized by continuously checking 
         the MGC-MG interconnection (link state).  Many transports provide this 
         functionality, so a mandatory protocol mechanism is unnecessary.
         
         For those transports transports that do not provide link state 
         monitoring, this functionality can be acheived in the H.248 protocol by 
         utilizing the existing messaging.  In the absence of any H.248 
         messaging, the MGC may use an AuditValue Command on Root with an empty 
         AuditDescriptor to detect the loss of communications with the MG.  The 
         MG can detect the communications loss itself through the use of the 
         Inactivity Timer Package (ITU-T Rec. H.248.14)."
    REFERENCE   
        "ITU-T Recommendation H.248.1 (09/2005), Clause 11.6, MGC-MG control 
               associaiton monitoring.
         ITU-T Recommendation H.248.14."
    ::= { gcpNotifications 4 }

gcpInactivityTimeout NOTIFICATION-TYPE
    OBJECTS     { tmnObjectInstance, gcpLinkageMit }
    STATUS      current
    DESCRIPTION 
        "This notification is generated by an MG when it detects 
         inactivity from and MGC on a control association.  It is 
         generated regardless of whether the MGC will reply to any 
         resulting Notify command sent to the MGC as a result of the 
         timeout.
         
         This notification is generated by an MGC when it receives 
         a Notify with an observed event of `Inactivity Timeout' from the 
         associated MG, in accordance with the procedures of ITU-T Rec. 
         H.248.14.
         
         The parameters of the notification are the RowPointer indexing 
         the entry in the gcpLinkageTable for which the inactivity was 
         detected, and the setting of gcpLinkageMit that was in effect 
         when the inactivity was detected."
    REFERENCE   
        "ITU-T Recommendation H.248.14 (03/2002), Inactivity Timer 
               Package, Clause 5.5, Procedures.
         ITU-T Recommendation H.248.1 (09/2005), Clause 11.5, Failure of 
               an MGC."
    ::= { gcpNotifications 5 }

gcpMgColdStart NOTIFICATION-TYPE
    OBJECTS     { tmnObjectInstance }
    STATUS      current
    DESCRIPTION 
        "Provides a notification when an MG initiates a cold start or an 
         MGC detects that at attached MG is cold starting.
         
         A MG is pre-provisioned with a primary (protected) and 
         optionally an ordered list of secondary (protecting) MGCs.  
         Upon a cold start of the MG, it will issue a ServiceChange 
         Command with a ``Restart'' method, on the Root Termination to 
         its primary MGC.  If the MGC accepts the MG, it sends 
         a TransactionReply not including a ServiceChangeMgcID parameter.  
         If the MGC does not accept the MG's registration, it sends 
         a TransactionReply, providing the address of an alternate MGC to 
         be contacted by including a ServiceChangeMgcID parameter.
         
         If the MG receives a TransactionReply that includes 
         a ServiceChangeMgcID parameter, it sends a ServiceChange to the 
         MGC specified in the ServiceChangeMgcID.  It continues this 
         process until it gets a controlling MGC to accept its 
         registration, or it fails to get a reply.  Upon failure to 
         obtain a reply, either from the primary MGC, or a designated 
         successor, the MG tries its pre-provisioned secondary MGCs, in 
         order.  If the MGC is unable to establish a control relationship 
         with any MGC, it shall wait a random amount of time as described 
         in ITU-T Rec. H.248.1/9.2 and then start contacting its primary, 
         and if necessary, its secondary MGCs again.
         
         It is possible that the reply to a ServiceChange with Restart 
         will be lost, and a command will be received by the MG prior to 
         the receipt of the ServiceChange response.  The MG shall issue 
         Error Code 505 (TransactionRequest Received before 
         a SericeChange Reply has been received)."
    REFERENCE   
        "ITU-T Recommendation H.248.1 (09/2005), Clause 11.2, Cold 
               start."
    ::= { gcpNotifications 6 }

gcpOnOccEvent NOTIFICATION-TYPE
    OBJECTS     { tmnObjectInstance, tmnProbableCause, 
                  tmnPerceivedSeverity }
    STATUS      current
    DESCRIPTION 
        "Provides a notification that is used for MG or MGC 
         on-occurrence events that do not use the communicationsAlarm 
         notification."
    ::= { gcpNotifications 7 }

gcpNotificationGroup NOTIFICATION-GROUP
    NOTIFICATIONS { gcpProtectionSwitchReport, gcpMgColdStart, 
                  gcpOnOccEvent, gcpMgFailure, gcpMgcFailure, 
                  gcpLinkageFailure, gcpInactivityTimeout }
    STATUS      current
    DESCRIPTION 
        "A collection of all of the accessible notifications in this 
         module."
    ::= { gcpGroups 1 }

gcpObjectGroup OBJECT-GROUP
    OBJECTS     { gcpOldProtectionStatus, gcpOldRequestSource, 
                  gcpOldSwitchStatus, gcpOldSwitchDirection, 
                  gcpOldRelatedUnit, gcpOldAutoSwitchReason, 
                  gcpNewProtectionStatus, gcpNewRequestSource, 
                  gcpNewSwitchStatus, gcpNewSwitchDirection, 
                  gcpNewRelatedUnit, gcpNewAutoSwitchReason, 
                  gcpDefaultMgcoIdent, gcpDefaultUdpChecksum, 
                  gcpDefaultTcpNoDelay, gcpDefaultTcpMaxseg, 
                  gcpDefaultTcpKeepAlive, gcpDefaultTcpKeepIdle, 
                  gcpDefaultTcpKeepAliveItvl, gcpDefaultTcpKeepCount, 
                  gcpDefaultTcpSynRetrans, gcpDefaultTcpWindowClamp, 
                  gcpMsName, gcpMsAlarmStatus, gcpMsOperationalState, 
                  gcpMsUsageState, gcpMsManagedElementType, 
                  gcpMsModelCode, gcpMsVendorName, gcpMsUserLabel, 
                  gcpMsVersion, gcpMsAsaProfilePointer, 
                  gcpMsNetworkElementAliases, gcpMsRowStatus, 
                  gcpMgLocation, gcpMgName, gcpMgDomainName, 
                  gcpMgDeviceName, gcpMgMtpAddress, gcpMgAdminState, 
                  gcpMgOperState, gcpMgAlarmStatus, 
                  gcpMgAsaProfilePointer, gcpMgUsageState, 
                  gcpMgAvailStatus, gcpMgProcStatus, gcpMgPg, 
                  gcpMgStandbyStatus, gcpMgRowStatus, gcpMgcLocation, 
                  gcpMgcName, gcpMgcDomainName, gcpMgcDeviceName, 
                  gcpMgcMtpAddress, gcpMgcAdminState, gcpMgcOperState, 
                  gcpMgcAlarmStatus, gcpMgcAsaProfilePointer, 
                  gcpMgcUsageState, gcpMgcAvailStatus, gcpMgcProcStatus, 
                  gcpMgcPg, gcpMgcStandbyStatus, gcpMgcRowStatus, 
                  gcpLinkageType, gcpLinkageMgcAddress, 
                  gcpLinkageMgAddress, gcpLinkageMgcIdent, 
                  gcpLinkageMgIdent, gcpLinkageProfile, 
                  gcpLinkageProtocol, gcpLinkageEncoding, 
                  gcpLinkageAuthAccess, gcpLinkageAdminState, 
                  gcpLinkageOperState, gcpLinkageProcStatus, 
                  gcpLinkageAvailStatus, gcpLinkageAuthentication, 
                  gcpLinkageRowStatus, gcpUdpChecksum, gcpUdpRowStatus, 
                  gcpTcpNoDelay, gcpTcpMaxseg, gcpTcpKeepAlive, 
                  gcpTcpKeepIdle, gcpTcpKeepAliveItvl, gcpTcpKeepCount, 
                  gcpTcpSynRetrans, gcpTcpWindowClamp, gcpTcpRowStatus, 
                  gcpDefaultSctpNoDelay, gcpDefaultSctpMaxseg, 
                  gcpDefaultSctpHeartbeatItvl, gcpDefaultSctpHearbeat, 
                  gcpDefaultSctpRtoInitial, gcpDefaultSctpRtoMin, 
                  gcpDefaultSctpRtoMax, gcpDefaultSctpPathMaxRetrans, 
                  gcpDefaultSctpCookieLife, gcpDefaultSctpCookieInc, 
                  gcpDefaultSctpMaxInitRetries, gcpDefaultSctpMaxBurst, 
                  gcpDefaultSctpAssocMaxRetrans, gcpDefaultSctpSackDelay, 
                  gcpDefaultSctpLifetime, gcpSctpNoDelay, gcpSctpMaxseg, 
                  gcpSctpHeartbeatItvl, gcpSctpHearbeat, 
                  gcpSctpRtoInitial, gcpSctpRtoMin, gcpSctpRtoMax, 
                  gcpSctpPathMaxRetrans, gcpSctpCookieLife, 
                  gcpSctpCookieInc, gcpSctpMaxInitRetries, 
                  gcpSctpMaxBurst, gcpSctpAssocMaxRetrans, 
                  gcpSctpSackDelay, gcpSctpLifetime, gcpSctpRowStatus, 
                  gcpProtGroupOperState, gcpProtGroupAvailStatus, 
                  gcpProtGroupType, gcpProtGroupRevertive, 
                  gcpProtGroupSBOLNumber, gcpProtGroupWaitToRestoreTime, 
                  gcpProtGroupSettingWindowTime, 
                  gcpProtGroupReleaseingWindowTime, 
                  gcpProtGroupHitsCount, gcpProtGroupSwitchType, 
                  gcpProtGroupProtectedUnits, 
                  gcpProtGroupProtectingUnits, 
                  gcpProtGroupInvokeProtection, 
                  gcpProtGroupReleaseProtection, gcpProtGroupRowStatus, 
                  gcpSbolObject, gcpSbolStatus, gcpProtUnitProtecting, 
                  gcpProtUnitReliableResourcePointer, 
                  gcpProtUnitUnreliableResourcePointer, 
                  gcpProtUnitProtectionStatus, gcpProtUnitRequestSource, 
                  gcpProtUnitSwitchStatus, gcpProtUnitSwitchDirection, 
                  gcpProtUnitRelatedUnit, gcpProtUnitAutoSwitchReason, 
                  gcpProtUnitLockoutReleaseFailed, gcpProtUnitPriority, 
                  gcpProtUnitRowStatus, gcpDefaultMgcoExecutionTime, 
                  gcpDefaultMgcoProvRespTimer, 
                  gcpDefaultMgcpPendingLimit, gcpDefaultMgcoLongTimer, 
                  gcpDefaultMgcoRtoInit, gcpDefaultMgcoRtoMin, 
                  gcpDefaultMgcoRtoMax, gcpLinkageMgcMaster, 
                  gcpLinkageMit, gcpRealmString, gcpRealmTermsMax, 
                  gcpRealmTermsCurrent, gcpRealmTermsHiWat, 
                  gcpRealmTermsLoWat, gcpRealmRowStatus, 
                  gcpInterfaceIfindex, gcpInterfaceMgId, 
                  gcpInterfaceType, gcpInterfaceRealm, 
                  gcpInterfaceTermId, gcpInterfaceTermPath, 
                  gcpInterfaceRowStatus, gcpAddressInterface, 
                  gcpAddressType, gcpAddressAddr, gcpAddressPortRanges, 
                  gcpAddressRowStatus }
    STATUS      current
    DESCRIPTION 
        "A collection of all of the accessible objects in this 
         module."
    ::= { gcpGroups 2 }

gcpSctpObjectGroup OBJECT-GROUP
    OBJECTS     { gcpDefaultSctpNoDelay, gcpDefaultSctpMaxseg, 
                  gcpDefaultSctpHeartbeatItvl, gcpDefaultSctpHearbeat, 
                  gcpDefaultSctpRtoInitial, gcpDefaultSctpRtoMin, 
                  gcpDefaultSctpRtoMax, gcpDefaultSctpPathMaxRetrans, 
                  gcpDefaultSctpCookieLife, gcpDefaultSctpCookieInc, 
                  gcpDefaultSctpMaxInitRetries, gcpDefaultSctpMaxBurst, 
                  gcpDefaultSctpAssocMaxRetrans, gcpDefaultSctpSackDelay, 
                  gcpDefaultSctpLifetime, gcpSctpNoDelay, gcpSctpMaxseg, 
                  gcpSctpHeartbeatItvl, gcpSctpHearbeat, 
                  gcpSctpRtoInitial, gcpSctpRtoMin, gcpSctpRtoMax, 
                  gcpSctpPathMaxRetrans, gcpSctpCookieLife, 
                  gcpSctpCookieInc, gcpSctpMaxInitRetries, 
                  gcpSctpMaxBurst, gcpSctpAssocMaxRetrans, 
                  gcpSctpSackDelay, gcpSctpLifetime, gcpSctpRowStatus }
    STATUS      current
    DESCRIPTION 
        "A collection of all of the accessible objects necessary to 
         support SCTP as a transport for GCP."
    ::= { gcpGroups 3 }

gcpFullCompliance MODULE-COMPLIANCE
    STATUS      current
    DESCRIPTION 
        "Provides a compliance profile that provides full compliance to 
         this mib."

    MODULE      -- this module

        MANDATORY-GROUPS        { gcpNotificationGroup, gcpObjectGroup }

        GROUP   gcpSctpObjectGroup
        DESCRIPTION   
              "Groups that provide optional capabilities."

    MODULE OPENSS7-SMI-MIB

        GROUP   attributeValueChangeNotificationPackage
        DESCRIPTION   
              "PRESENT IF the attributeValueChangeNotification defined in 
               'ITU-T Rec. X.721 (1992) | ISO/IEC 10165-2 : 1992' is supported 
               by an instance of this class."

        GROUP   createDeleteNotificationsPackage
        DESCRIPTION   
              "PRESENT IF the objectCreation and objectDeletion notifications 
               defined in ITU-T Rec. X.721 (1992) | ISO/IEC 10165-2 : 1992 are 
               supported by an instance of this class."

        GROUP   communicationsAlarmPackage
        DESCRIPTION   
              "PRESENT IF the communicationsAlarm notification defined 
               in ITU-T Rec. X.721 (1992) | ISO/IEC 10165-2 : 1992 is 
               supported by an instance of this class."

    ::= { gcpCompliance 1 }

END -- end of module OPENSS7-GCP-MIB.
