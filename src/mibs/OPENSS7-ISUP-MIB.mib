-- vim: ft=mib comments=\f\b\:\"ITU\-T,\f\b\:ITU\-T,\f\:\",\b\:\-\-,\:\-\-,\f\b\:\-,\f\b\:\· fo+=tcqlornw12 tw=64 ai nocin nosi sts=4 sw=4 et
-- =============================================================================
-- 
-- @(#) src/mibs/OPENSS7-ISUP-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-ISUP-MIB DEFINITIONS ::= BEGIN

IMPORTS
    GraphicString, MtpCongestedState, MtpCongestionLevel, 
    MtpPointCodeFormat, MtpSapAddress, MtpUserPart, MtpUserPartStatus, 
    NetworkPointCode
        FROM OPENSS7-MTP-MIB
    openss7Q751
        FROM OPENSS7-SMI
    AdministrativeState, AlarmStatus, AvailabilityStatus, ControlStatus, 
    OperationalState, ProceduralStatus, SimpleNameType, StandbyStatus, 
    SystemTimingSource, UsageState
        FROM OPENSS7-SMI-MIB
    Ss7ProtocolVariant, ss7ProtocolItut
        FROM OPENSS7-SS7-MIB
    ActionOrResult, CircuitIdentificationCode, CommonLanguageName
        FROM OPENSS7-TC
    ProtectionStatus, ProtectionUnits
        FROM OPENSS7-TMN-SMI
    SnmpAdminString
        FROM SNMP-FRAMEWORK-MIB
    MODULE-COMPLIANCE, OBJECT-GROUP
        FROM SNMPv2-CONF
    Integer32, MODULE-IDENTITY, OBJECT-IDENTITY, OBJECT-TYPE, Unsigned32, 
    zeroDotZero
        FROM SNMPv2-SMI
    RowPointer, RowStatus, TEXTUAL-CONVENTION, TimeInterval, TruthValue
        FROM SNMPv2-TC;

isupMIB MODULE-IDENTITY
    LAST-UPDATED "201112101120Z"
    ORGANIZATION 
        "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         E-mail: bidulock@openss7.org"
    DESCRIPTION 
        "This is a MIB providing management information is 
         accordance with ITU-T Rec. Q.751.1, ITU-T Rec. 
         Q.2751.1, ANSI T1.116.1, as well as ITU-T Rec. Q.826.
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201112101120Z"
    DESCRIPTION 
        "Corrections an smilint workup."
    REVISION    "200810092250Z"
    DESCRIPTION 
        "First release of this module."
    ::= { openss7Q751 3 }


SignallingCapabilities ::= TEXTUAL-CONVENTION
    STATUS      current
    DESCRIPTION 
        "This textual convention provides, in accordance with ITU-T Rec. 
         M.3100, the signalling capabilities of a trunk group."
    REFERENCE   
        "ITU-T Rec. M.3100 (2005) ASN1DefinedTypesModule.SignallingCapabilities."
    SYNTAX      INTEGER { isup(0), isup92(1), itutNo5(2), r2(3), 
                    itutNo6(4), tup(5) }

InformationTransferCapabilities ::= TEXTUAL-CONVENTION
    STATUS      current
    DESCRIPTION 
        "This textual convention provides, in accordance with ITU-T Rec. 
         M.3100, the information transfer capabilities of a trunk group.  
         The object with this textual convention as its syntax specifies 
         the different service types such as speech, 64 kbits 
         unrestricted data supported by a circuit or group of circuits."
    REFERENCE   
        "ITU-T Rec. M.3100 (2005) ASN1DefinedTypesModule.InformationTransferCapabilities."
    SYNTAX      INTEGER { speech(0), audio3pt1(1), audio7(2), 
                    audioComb(3), digitalRestricted56(4), 
                    digitalUnrestricted64(5) }

CircuitDirectionality ::= TEXTUAL-CONVENTION
    STATUS      current
    DESCRIPTION 
        "This textual convention provides, in accordance with ITU-T Rec. 
         M.3100, the circuit directionatliy of a trunk group.  The 
         object with this textual convention as its syntax specifies the 
         different directionality of a circuit or trunk group."
    REFERENCE   
        "ITU-T Rec. M.3100 (2005) ASN1DefinedTypesModule.CircuitDirectionality."
    SYNTAX      INTEGER { onewayOut(0), onewayIn(1), twoway(2) }

TransmissionCharacteristics ::= TEXTUAL-CONVENTION
    STATUS      current
    DESCRIPTION 
        "This textual convention provides, in accordance with ITU-T Rec. 
         M.3100, the transmission characteristics of a trunk group.  The 
         object with this textual convention as its syntax specifies the 
         different transmission characteristics such as satellite, echo 
         control supported or not supported by the trunk group.  The bit 
         positions are set to indicate if a particular characteristic is 
         supported."
    REFERENCE   
        "ITU-T Rec. M.3100 (2005) ASN1DefinedTypesModule.TransmissionCharacteristics."
    SYNTAX      BITS { satellite(0), dCME(1), echoControl(2) }

TrunkGroupList ::= TEXTUAL-CONVENTION
    DISPLAY-HINT "4d,"
    STATUS      current
    DESCRIPTION 
        "This textual convention provides a mechanism for providing an 
         ordered list of trunk groups.  The octet string must be a 
         multiple of 4 octets in length.  Each four octets represents 
         (in network byte order) an index into the trunk group table 
         (isupTgTable) of an existing conceptual row corresponding to a 
         trunk group."
    SYNTAX      OCTET STRING

TrunkGroupSelection ::= TEXTUAL-CONVENTION
    DISPLAY-HINT "1d,"
    STATUS      current
    DESCRIPTION 
        "This textual convention provides a sequence of trunk group 
         selections.  Each octet in the octet string indicates the 
         position (0..255) of a trunk group identifier in a trunk group 
         list as represented by an instance of an object with syntax 
         TrunkGroupList.  When the trunk group list is empty, the trunk 
         group selection must also be empty.  When the trunk group list 
         contains `N' trunk groups, the value of each octet in the trunk 
         group selection must be have a value corresponding to an 
         ordinal position within the trunk group list, that is within 
         the range (0..(N-1))."
    SYNTAX      OCTET STRING (SIZE(0..256))

TrunkGroupProportions ::= TEXTUAL-CONVENTION
    DISPLAY-HINT "1d,"
--  UNITS "%"
    STATUS      current
    DESCRIPTION 
        "This textual convention provides a mechanism for providing a 
         list of proportions for proportional bidding overflow routes.  
         Each octet in the string provides a integer percentage that 
         applies to an ordinal list of trunk group selections (see 
         the TrunkGroupList textual convention).  Each octet must have a 
         value in the range (0..100), and the sum of the values of all 
         the octets in the string must be 100.  When the string is 
         shorter than the available trunk group selections, trunk group 
         selections that correspond to ordinal positions beyond the end 
         of the string assume the value zero (0).  The length of the 
         octet string must not be longer than the number of trunk group 
         selections to which it applies.
         
         For example, the value 30,30,40 (as an octet string: '1E1E28'X) 
         specifies that the proportion for the first trunk group 
         selection is 30%, 30% for the second, 40% for the third, and 0% 
         for any others."
    SYNTAX      OCTET STRING


-- ProtectionUnits ::= TEXTUAL-CONVENTION
--     DISPLAY-HINT "1d,"
--     STATUS      current
--     DESCRIPTION 
--      "This textual convention provides a mechanism for providing a 
--       list of protection units within a protection group.  Each octet 
--       in the string provides the isupPuId portion of an index into the 
--       isupPuTable corresponding to the protection unit.  The isupPgId 
--       associated with the entry using this textual convention as its 
--       SYNTAX      field, provides the isupPgId portion of the index into 
--       the isupPuTable corresponding to the protection unit.  Because 
--       the isupPuId can only have values (0..255), up to 255 protect 
--       units in the list can be specified in this way."
--     SYNTAX      OCTET STRING (SIZE(0..255))

RangeAndStatus ::= TEXTUAL-CONVENTION
--  DISPLAY-HINT "1d,1h-"
    STATUS      current
    DESCRIPTION 
        "Provides the range and status of an ISUP circuit group.  The 
         value consists of one octet that specifies the range of the 
         circuits in the circuit group followed by zero to four octets 
         specifying the status of the circuits in the circuit group."
    REFERENCE   
        "ITU-T Rec. Q.763 (1996) : Range and Status parameter."
    SYNTAX      OCTET STRING (SIZE(1..5))

ContinuityCheck ::= TEXTUAL-CONVENTION
    STATUS      current
    DESCRIPTION 
        "Specifies the basis under which continuity checks are performed 
         for outgoing calls on circuits associated with the object that 
         uses this textual convention in its SYNTAX clause.
         
         - unknown(0), the basis for continuity checks is unknown or 
           unspecified;
         - none(1), no continuity checks are performed on outgoing 
           calls;
         - statistical(2), continuity checks are performed on a 
           statistical basis (proportional) on outgoing calls; and,
         - perCall(3), continiuty checks are performed per-call on 
           outgoing calls.
         
         When the basis for continuity checks is unknown or unspecified, 
         unknown(0), the agent may provide a suitable default."
    REFERENCE   
        "ITU-T Rec. Q.764 (1996).
         ANSI T1.113.4/2000."
    SYNTAX      INTEGER { unknown(0), none(1), statistical(2), 
                    perCall(3) }

isupNotifications OBJECT IDENTIFIER
    ::= { isupMIB 0 }

isupObjects OBJECT IDENTIFIER
    ::= { isupMIB 1 }

-- ==========================================================================
-- ISUP TABLES
-- ==========================================================================

isupTables OBJECT IDENTIFIER
    ::= { isupObjects 1 }

isupMs OBJECT IDENTIFIER
    ::= { isupTables 1 }

isupMsTable OBJECT-TYPE
    SYNTAX      SEQUENCE OF IsupMsEntry
    MAX-ACCESS  not-accessible
    STATUS      current
    DESCRIPTION 
        "The Managed Switching Element represents, for management 
         purposes, an exchange, i.e. the aggregate of traffic carrying 
         devices, switching stages, controlling and signalling means at 
         a network node that enables subscriber lines to be 
         interconnected and packets to be forwarded as required by 
         individual users.
         
         The Managed Element object class is a class of managed objects 
         representing telecommunications equipment or TMN entities 
         (either groups or parts) within the telecommunications network 
         that performs managed element functions, i.e.  provides support 
         and/or service to the subscriber. Managed elements may or may 
         not additionally perform mediation/OS functions. A managed 
         element communicates with the manager (directly or indirectly) 
         over one or more standard Q-interfaces for the purpose of being 
         monitored and/or controlled. A managed element contains 
         equipment that may or may not be geographically distributed.  
         When the attribute value change notification package is 
         present, the attributeValueChange notification defined in 
         Recommendation X.721 shall be emitted when the value of one of 
         the following attribute changes: alarm status, user label, 
         version, location name and current problem list. For the above 
         attributes that are in conditional packages, the behaviour for 
         emitting the attribute value change notification applies only 
         when the corresponding conditional packages are present in the 
         managed object. When the state change notification package is 
         present, the stateChangeNotification defined in Recommendation 
         X.721 shall be emitted if the value of administrative state or 
         operational state or usage state changes."
    REFERENCE   
        "ITU-T Rec. Q.751.1 (1996) managedSwitchingElement MOC.
         ANSI T1.116.1/2000 managedSwitchingElement MOC.
         ITU-T Rec. M.3100 (1995) managedElementR2 MOC."
    ::= { isupMs 1 }

isupMsEntry OBJECT-TYPE
    SYNTAX      IsupMsEntry
    MAX-ACCESS  not-accessible
    STATUS      current
    DESCRIPTION 
        "Each entry in this table is indexed by the managed 
         switching element identifier.  Each row contains the 
         characteristics and operational status of one managed 
         switching element."
    REFERENCE   
        "ITU-T Rec. Q.751.1 (1996) managedSwitchingElement MO.
         ANSI T1.116.1/2000 managedSwitchingElement MO.
         ITU-T Rec. M.3100 (1995) managedElementR2 MO."
    INDEX       { isupMsId }
    ::= { isupMsTable 1 }

IsupMsEntry ::= SEQUENCE {
    isupMsId                        Unsigned32,
    isupMsName                      SnmpAdminString,
    isupMsAlarmStatus               AlarmStatus,
    isupMsOperationalState          OperationalState,
    isupMsUsageState                UsageState,
    isupMsVendorName                SnmpAdminString,
    isupMsUserLabel                 SnmpAdminString,
    isupMsVersion                   SnmpAdminString,
    isupMsLocationName              CommonLanguageName,
    isupMsPrimaryTimingSource       SystemTimingSource,
    isupMsPrimaryTimingObject       RowPointer,
    isupMsSecondaryTimingSource     SystemTimingSource,
    isupMsSecondaryTimingObject     RowPointer,
    isupMsAsaProfilePointer         RowPointer,
    isupMsManagedElementType        SnmpAdminString,
    isupMsModelCode                 SnmpAdminString,
    isupMsNetworkElementAliases     SnmpAdminString,
    isupMsRowStatus                 RowStatus
}

isupMsId OBJECT-TYPE
    SYNTAX      Unsigned32
    MAX-ACCESS  not-accessible
    STATUS      current
    DESCRIPTION 
        "Provides a non-zero ordinal index into the ISUP managed system 
         table."
    ::= { isupMsEntry 1 }

isupMsName OBJECT-TYPE
    SYNTAX      SnmpAdminString
    MAX-ACCESS  read-create
    STATUS      current
    DESCRIPTION 
        "Provides an optional administrative name for this managed 
         switching element.  It is typical to use the common language 
         name assigned to the element (e.g. EDTNAB01DS1)."
    ::= { isupMsEntry 2 }

isupMsAlarmStatus OBJECT-TYPE
    SYNTAX      AlarmStatus
    MAX-ACCESS  read-create
    STATUS      current
    DESCRIPTION 
        "Provides the alarm status of the MTP managed switching element 
         following the AlarmStatus textual convention and ITU-T Rec. 
         X.721 (1992) | ISO/IEC 10165-2 : 1992.
         
          - underRepair(0),
          - critical(1),
          - major(2),
          - minor(3),
          - alarmOutstanding(4),"
    REFERENCE   
        "ITU-T Rec. Q.751.1 (1997), ANSI T1.116.1 (2000) : alarmStatus 
             attribute.
         ITU-T Rec. X.721 (1992) | ISO/IEC 10165-2 : 1992, 
             Attribute-ASN1Module.AlarmStatus.
         ITU-T Rec. X.731 (1992) | ISO/IEC 10164-2 : 1993, 
             Section 8.1.2.1."
    ::= { isupMsEntry 3 }

isupMsOperationalState OBJECT-TYPE
    SYNTAX      OperationalState
    MAX-ACCESS  read-only
    STATUS      current
    DESCRIPTION 
        "Provides the operational state of the signalling point 
         following the OperationalState textual convention and ITU-T 
         Rec. X.721 | ISO/IEC 10165-2.
         
          - disabled(0),
          - enabled(1),"
    REFERENCE   
        "ITU-T Rec. X.721 (1992) | ISO/IEC 10165-2 : 1992, 
             Attribute-ASN1Module.OperationalState.
         ITU-T Rec. X.731 (1992) | ISO/IEC 10164-2 : 1993, 
             Section 8.1.1.1.
         ITU-T Rec. Q.751.1 (1997), ANSI T1.116.1 (2000), 
             operationalState attribute."
    DEFVAL      { disabled }
    ::= { isupMsEntry 4 }

isupMsUsageState OBJECT-TYPE
    SYNTAX      UsageState
    MAX-ACCESS  read-only
    STATUS      current
    DESCRIPTION 
        "Provides the usage state of the MTP managed switching element 
         following the UsageState textual convention and ITU-T Rec. 
         X.721 | ISO/IEC 10165-2.
         
          - idle(0),
          - active(1),
          - busy(2),"
    REFERENCE   
        "ITU-T Rec. X.721 | ISO/IEC 10165-2 usageState attribute."
    DEFVAL      { idle }
    ::= { isupMsEntry 5 }

isupMsVendorName OBJECT-TYPE
    SYNTAX      SnmpAdminString
    MAX-ACCESS  read-only
    STATUS      current
    DESCRIPTION 
        "The vendor name attribute type identifies the vendor of the 
         associated managed object."
    REFERENCE   
        "ITU-T Rec. M.3100 (2005) : vendorName ATTRIBUTE."
    ::= { isupMsEntry 6 }

isupMsUserLabel OBJECT-TYPE
    SYNTAX      SnmpAdminString
    MAX-ACCESS  read-create
    STATUS      current
    DESCRIPTION 
        "The user label attribute type assigns a user friendly name to 
         the associated object."
    REFERENCE   
        "ITU-T Rec. M.3100 (2005) : userLabel ATTRIBUTE."
    ::= { isupMsEntry 7 }

isupMsVersion OBJECT-TYPE
    SYNTAX      SnmpAdminString
    MAX-ACCESS  read-only
    STATUS      current
    DESCRIPTION 
        "The version attribute type identifies the version of the 
         associated managed object."
    REFERENCE   
        "ITU-T Rec. M.3100 (2005) : version ATTRIBUTE."
    ::= { isupMsEntry 8 }

isupMsLocationName OBJECT-TYPE
    SYNTAX      CommonLanguageName
    MAX-ACCESS  read-create
    STATUS      current
    DESCRIPTION 
        "The location name attribute type identifies a location."
    REFERENCE   
        "ITU-T Rec. M.3100 (2005) : locationName ATTRIBUTE."
    ::= { isupMsEntry 9 }

isupMsPrimaryTimingSource OBJECT-TYPE
    SYNTAX      SystemTimingSource
    MAX-ACCESS  read-only
    STATUS      current
    DESCRIPTION 
        "Provides the primary timing source for the managed switching 
         element.  This object can have values:
         
         - none(0), no primary timing source;
         
         - internal(1), the primary timing source is internal to the 
           managed switching element;
         
         - external(2), the primary timing source is external to the 
           managed switching element;
         
         - slaved(3), the primary timing source is slaved from a network 
           interface to the managed switching element.
           
         Not all values are necessarily supported by all agents.
         
         A typical SONET/SDH switching element will take its primary 
         timing slaved(3) from a network interface."
    REFERENCE   
        "ITU-T Rec. M.3100 (2005) : SystemTiming.sourceType."
    ::= { isupMsEntry 10 }

isupMsPrimaryTimingObject OBJECT-TYPE
    SYNTAX      RowPointer
    MAX-ACCESS  read-only
    STATUS      current
    DESCRIPTION 
        "Provides the object identifier of the managed object 
         responsible for providing the primary timing source.
         
         A typical SONET/SDH managed switching element will identify the 
         network interface from which it takes is primary slaved(3) 
         timing."
    REFERENCE   
        "ITU-T Rec. M.3100 (2005) : SystemTiming.sourceID."
    DEFVAL      { zeroDotZero }
    ::= { isupMsEntry 11 }

isupMsSecondaryTimingSource OBJECT-TYPE
    SYNTAX      SystemTimingSource
    MAX-ACCESS  read-only
    STATUS      current
    DESCRIPTION 
        "Provides the secondary timing source for the managed switching 
         element.  This object can have values:
         
         - none(0), no secondary timing source;
         
         - internal(1), the secondary timing source is internal to the 
           managed switching element;
         
         - external(2), the secondary timing source is external to the 
           managed switching element.
         
         - slaved(3), the secondary timing source is slaved from a 
           network interface to the managed switching element.
         
         Not all values are necessarily supported by all agents.
         
         A typical SONET/SDH managed switching element will take its 
         secondary timing source from an internal(1) clock."
    REFERENCE   
        "ITU-T Rec. M.3100 (2005) : SystemTiming.sourceType."
    ::= { isupMsEntry 12 }

isupMsSecondaryTimingObject OBJECT-TYPE
    SYNTAX      RowPointer
    MAX-ACCESS  read-only
    STATUS      current
    DESCRIPTION 
        "Provides the object identifier of the managed object 
         responsible for providing the secondary timing source.
         
         A typical SONET/SDH managed switching element will identify the 
         internal clock from which it takes is secondary internal(1) 
         timing."
    REFERENCE   
        "ITU-T Rec. M.3100 (2005) : SystemTiming.sourceID."
    DEFVAL      { zeroDotZero }
    ::= { isupMsEntry 13 }

isupMsAsaProfilePointer OBJECT-TYPE
    SYNTAX      RowPointer
    MAX-ACCESS  read-create
    STATUS      current
    DESCRIPTION 
        "Provides a pointer to an alarm severity assignment profile to 
         be used for alarms generated by this managed switching element, 
         or zeroDotZero."
    REFERENCE   
        "ITU-T Rec. Q.751.1 (1997), ANSI T1.116.1 (2000), 
             alarmSeverityAssignmentProfilePointer attribute."
    DEFVAL      { zeroDotZero }
    ::= { isupMsEntry 14 }

isupMsManagedElementType OBJECT-TYPE
    SYNTAX      SnmpAdminString
    MAX-ACCESS  read-only
    STATUS      current
    DESCRIPTION 
        "This attribute holds a set of either textual strings or values 
         from a predefined set (object identifiers), that describe the 
         generic type of the network element modelled by the 
         ManagedElementR2 instance.  Mutliple managed element type 
         values may be used to describe hybrid equipment."
    REFERENCE   
        "ITU-T Rec. M.3100 (2005) : managedElementType ATTRIBUTE."
    ::= { isupMsEntry 15 }

isupMsModelCode OBJECT-TYPE
    SYNTAX      SnmpAdminString
    MAX-ACCESS  read-only
    STATUS      current
    DESCRIPTION 
        "This attribute stores the product model code of the network 
         element.  The product model code is the manufacturer's model 
         identification information.  It is vendor-provided information 
         that the vendor uses to distinguish the network element amoung 
         a family of products.  This attribute is useful for OSSs 
         performing equipment discovery and inventory processes."
    REFERENCE   
        "ITU-T Rec. M.3100 (2005) : modelCode ATTRIBUTE."
    ::= { isupMsEntry 16 }

isupMsNetworkElementAliases OBJECT-TYPE
    SYNTAX      SnmpAdminString
    MAX-ACCESS  read-create
    STATUS      current
    DESCRIPTION 
        "This attribute is used to hold aliases given by the EMS to a 
         certain Managed Element instances.  Having such aliases 
         availabl via the EMS/NMS interface is useful for relating 
         Network Element names entered at the EMS, vita the Graphical MS 
         user interface.  More importantly, these aliases may appear in 
         alarms sent to the NMS to recognize such aliases to perform 
         alarm correlation or other fault and performance functions."
    ::= { isupMsEntry 17 }

isupMsRowStatus OBJECT-TYPE
    SYNTAX      RowStatus
    MAX-ACCESS  read-create
    STATUS      current
    DESCRIPTION 
        "Provides a mechanism whereby management stations may create or 
         delete entries in this table.  Rows may also be created and 
         deleted by the managed system as part of system operations."
    REFERENCE   
        "STD 58, SNMPv2-TC RowStatus.
         ITU-T Rec. M.3100 (1995) managedElement-network NAME BINDING."
    ::= { isupMsEntry 18 }

-- ==========================================================================
-- ISUP Protection Group Table

isupPg OBJECT IDENTIFIER
    ::= { isupTables 2 }

isupPgTable OBJECT-TYPE
    SYNTAX      SEQUENCE OF IsupPgEntry
    MAX-ACCESS  not-accessible
    STATUS      current
    DESCRIPTION 
        "This object class is used for representing a protection system. 
         The invokeProtection action switches always from protected unit 
         to protecting unit.  Either all or none of the Protection Unit 
         instances within an Protection Group object shall have the 
         priorityPkg package.  It is to be noted that, before the 
         creation of the protectionGroupR2 object, the supported by 
         object list (sbol) attribute of a reliable resource such as 
         termination point object may point to an unreliable resource 
         object such as circuit pack.  But once the protection group 
         object is created, the sbol attribute would start pointing at 
         the protection group object"
    REFERENCE   
        "ITU-T Rec. M.3100 (2005) : protectionGroupR2 MOC
         ITU-T Rec. G.744.3 : protectionGroupR1 MOC"
    ::= { isupPg 1 }

isupPgEntry OBJECT-TYPE
    SYNTAX      IsupPgEntry
    MAX-ACCESS  not-accessible
    STATUS      current
    DESCRIPTION 
        "Each row in this table is indexed by protection group 
         identifier.  Each row contains the characteristics and 
         operational status of the protection group."
    REFERENCE   
        "ITU-T Rec. G.744.3 : protectionGroup MOC"
    INDEX       { isupPgId }
    ::= { isupPgTable 1 }

IsupPgEntry ::= SEQUENCE {
    isupPgId                        Unsigned32,
    isupPgOperState                 OperationalState,
    isupPgAvailStatus               AvailabilityStatus,
    isupPgType                      INTEGER,
    isupPgRevertive                 TruthValue,
    isupPgSupportedByObjectList     RowPointer,
    isupPgWaitToRestoreTime         TimeInterval,
    isupPgSettingWindowTime         TimeInterval,
    isupPgReleasingWindowTime       TimeInterval,
    isupPgHitsCount                 Unsigned32,
    isupPgSwitchType                INTEGER,
    isupPgProtectedUnits            ProtectionUnits,
    isupPgProtectingUnits           ProtectionUnits,
    isupPgInvokeProtection          ActionOrResult,
    isupPgReleaseProtection         ActionOrResult,
    isupPgRowStatus                 RowStatus
}

isupPgId OBJECT-TYPE
    SYNTAX      Unsigned32
    MAX-ACCESS  not-accessible
    STATUS      current
    DESCRIPTION 
        "Provides a non-zero ordinal index into the protection 
         group table.  This ordinal index can be used to 
         identify the protection group within the managed system 
         or network."
    ::= { isupPgEntry 1 }

isupPgOperState OBJECT-TYPE
    SYNTAX      OperationalState
    MAX-ACCESS  read-only
    STATUS      current
    DESCRIPTION 
        "Provides the operational state of the protection group 
         following the OperationalState textual convention of 
         the OPENSS7-SMI-MIB module and ITU-T Rec. X.721 
         | ISO/IEC 10165-2.
         
         - disabled(0), the protection group is inoperable;
         - enabled(1), the protection group is operable.
           
         When the protection group is operable, the operational 
         state shall have the value enabled(1); otherwise it 
         shall have the value disabled(0).  Transitions of 
         operational state shall be reported using a state 
         change notification.  A protection group cannot be 
         created in the enabled(1) operational state."
    REFERENCE   
        "ITU-T Rec. X.721 (1992) | ISO/IEC 10165-2 : 1992, 
             Attribute-ASN1Module.OperationalState."
    ::= { isupPgEntry 2 }

isupPgAvailStatus OBJECT-TYPE
    SYNTAX      AvailabilityStatus
    MAX-ACCESS  read-only
    STATUS      current
    DESCRIPTION 
        "Provides the availability status of the protection 
         group following the AvailabilityStatus textual 
         convention of the OPENSS7-SMI-MIB module and ITU-T Rec. 
         X.721 | ISO/IEC 10165-2.
         
         - inTest(0), not used;
         - failed(1), the protection group has failed;
         - powerOff(2), not used;
         - offLine(3), not used;
         - offDuty(4), not used;
         - dependency(5), the availability status is dependent 
           on a sufficient number of members in the protection 
           group becoming available;
         - degraded(6), the protection group is available but 
           heavily loaded;
         - notInstalled(7), the protection group has not be 
           populated;
         - logFull(8), not used.
           
         When the value set is empty, the protection group is 
         allowed, available and is functioning normally, when 
         operational state is enabled(1)."
    REFERENCE   
        "ITU-T Rec. X.721 | ISO/IEC 10165-2, availabilityStatus 
             attribute."
    ::= { isupPgEntry 3 }

isupPgType OBJECT-TYPE
    SYNTAX      INTEGER { plus(0), colon(1) }
    MAX-ACCESS  read-create
    STATUS      current
    DESCRIPTION 
        "This attribute specifies whether the protection scheme used is 
         1 + 1 (plus) or M:N (colon). M:N includes the cases where M = 1 
         and/or N = 1."
    REFERENCE   
        "ITU-T Rec. G.774.3 : protectionGroupType ATTRIBUTE"
    ::= { isupPgEntry 4 }

isupPgRevertive OBJECT-TYPE
    SYNTAX      TruthValue
    MAX-ACCESS  read-create
    STATUS      current
    DESCRIPTION 
        "This attribute indicates whether the protection scheme is 
         revertive or not. If the value of this attribute is TRUE, the 
         traffic is returned to the protected protectionUnit instance 
         that initiated the switch after the fault clears and the 
         waitToRestoreTime interval (if any) has expired. If the value 
         of this attribute is FALSE, then after the fault has cleared, 
         traffic does not revert to the protectionUnit that initiated 
         the switch."
    REFERENCE   
        "ITU-T Rec. G.774.3 : revertive ATTRIBUTE"
    ::= { isupPgEntry 5 }

isupPgSupportedByObjectList OBJECT-TYPE
    SYNTAX      RowPointer
    MAX-ACCESS  read-create
    STATUS      current
    DESCRIPTION 
        "The Supported By Object List is an attribute type whose value 
         identifies a set of object instances which are capable of 
         directly affecting a given managed object. The object instances 
         include both physical and logical objects. This attribute does 
         not force internal details to be specified, but only the 
         necessary level of detail required for management. If the 
         object instances supporting the managed object are unknown to 
         that object, then this attribute is an empty set."
    REFERENCE   
        "ITU-T Rec. M.3100 (1992) : supportedByObjectList ATTRIBUTE"
    ::= { isupPgEntry 6 }

isupPgWaitToRestoreTime OBJECT-TYPE
    SYNTAX      TimeInterval
    MAX-ACCESS  read-create
    STATUS      current
    DESCRIPTION 
        "This attribute specifies the amount of time, in seconds, to 
         wait after a fault clears before restoring traffic to the 
         protected protectionUnit that initiated the switching."
    REFERENCE   
        "ITU-T Rec. G.774.3 : waitToRestoreTime ATTRIBUTE"
    ::= { isupPgEntry 7 }

isupPgSettingWindowTime OBJECT-TYPE
    SYNTAX      TimeInterval
    MAX-ACCESS  read-create
    STATUS      current
    DESCRIPTION 
        "This read-write attribute specifies the criteria of the 
         locked-in condition. The criteria includes the automatic 
         protection switching (APS) rate and the associated setting and 
         releasing time windows. If the number of APS of a Protection 
         Unit reaches the value specified in the hitsCount field within 
         a moving time window of specified length, the Protection Unit 
         will enter the locked-in condition. Each switch to protection 
         and its subsequent release is considered as one hit. The length 
         of the time window for entering the locked-in condition is 
         specified in the settingWindowTime field. Once a Protection 
         Unit is in the locked-in condition, future request of APS will 
         be denied until the locked-in condition is released. The 
         release criterion is no APS request within another moving time 
         window. The length of this time window is specified in the 
         releasingWindowTime field."
    REFERENCE   
        "ITU-T Rec. G.774.3 : lockedInCondition ATTRIBUTE"
    ::= { isupPgEntry 8 }

isupPgReleasingWindowTime OBJECT-TYPE
    SYNTAX      TimeInterval
    MAX-ACCESS  read-create
    STATUS      current
    DESCRIPTION 
        "This read-write attribute specifies the criteria of the 
         locked-in condition. The criteria includes the automatic 
         protection switching (APS) rate and the associated setting and 
         releasing time windows. If the number of APS of a Protection 
         Unit reaches the value specified in the hitsCount field within 
         a moving time window of specified length, the Protection Unit 
         will enter the locked-in condition. Each switch to protection 
         and its subsequent release is considered as one hit. The length 
         of the time window for entering the locked-in condition is 
         specified in the settingWindowTime field. Once a Protection 
         Unit is in the locked-in condition, future request of APS will 
         be denied until the locked-in condition is released. The 
         release criterion is no APS request within another moving time 
         window. The length of this time window is specified in the 
         releasingWindowTime field."
    REFERENCE   
        "ITU-T Rec. G.774.3 : lockedInCondition ATTRIBUTE"
    ::= { isupPgEntry 9 }

isupPgHitsCount OBJECT-TYPE
    SYNTAX      Unsigned32
    MAX-ACCESS  read-only
    STATUS      current
    DESCRIPTION 
        "This read-write attribute specifies the criteria of the 
         locked-in condition. The criteria includes the automatic 
         protection switching (APS) rate and the associated setting and 
         releasing time windows. If the number of APS of a Protection 
         Unit reaches the value specified in the hitsCount field within 
         a moving time window of specified length, the Protection Unit 
         will enter the locked-in condition. Each switch to protection 
         and its subsequent release is considered as one hit. The length 
         of the time window for entering the locked-in condition is 
         specified in the settingWindowTime field. Once a Protection 
         Unit is in the locked-in condition, future request of APS will 
         be denied until the locked-in condition is released. The 
         release criterion is no APS request within another moving time 
         window. The length of this time window is specified in the 
         releasingWindowTime field."
    REFERENCE   
        "ITU-T Rec. G.774.3 : lockedInCondition ATTRIBUTE"
    ::= { isupPgEntry 10 }

isupPgSwitchType OBJECT-TYPE
    SYNTAX      INTEGER { manual(0), forced(1), lockout(2) }
    MAX-ACCESS  read-create
    STATUS      current
    DESCRIPTION 
        "The invoke and release protection actions can be used to 
         request a lockout, a forced switch, or a manual (i.e. normal 
         switch) on one or more protection unit instances contained in 
         the protection group.
         
         - manual(0): peforms a manual protection invocation (from a 
           protected unit to a protecting unit); or a manual protection 
           release (from a protecting unit to a protected unit);
         
         - forced(1): performs a forced protection invocation (from a 
           protected unit to a protecting unit); or a forced protection 
           release (from a protecting unit to a protected unit);
         
         - lockout(2): performs a lockout invocation (applying lockout 
           to protected and protecting units); or a lockout release 
           (removing lockout from protected and protecting units).
         
         This object is written with the switch type applicable to an 
         action before writting the isupPgInvokeProtection or 
         isupPgReleaseProtection objects to invoke the action."
    REFERENCE   
        "ITU-T Rec. G.774.3 (2001) : InvokeProtectionArgs.SwitchType
         ITU-T Rec. G.774.3 (2001) : ReleaseProtectionArgs.SwitchType"
    ::= { isupPgEntry 11 }

isupPgProtectedUnits OBJECT-TYPE
    SYNTAX      ProtectionUnits
    MAX-ACCESS  read-create
    STATUS      current
    DESCRIPTION 
        "Specifies and indicates a list of protection units acting as 
         protected units within this protection group, using the 
         ProtectedUnits textual convention.
         
         When read, this object returns a list of all the protection 
         units in the protection group that are protected units.
         
         When written, this object accepts a list of zero or more 
         protection units in the protection group to be applied as the 
         protected units to either a concurrent or subsequent 
         invokeProtection or releaseProtection action.
         
         The value read from this object may not necessarily be the same 
         as the value last written.
         
         This object is written with the protected units applicable to 
         an action before writting the isupPgInvokeProtection or 
         isupPgReleaseProtection objects to invoke the action."
    REFERENCE   
        "ITU-T Rec. G.774.3 (2001) : InvokeProtectionArgs.ProtectionEntity
         ITU-T Rec. G.774.3 (2001) : ReleaseProtectionArgs.ProtectionEntity"
    ::= { isupPgEntry 12 }

isupPgProtectingUnits OBJECT-TYPE
    SYNTAX      ProtectionUnits
    MAX-ACCESS  read-create
    STATUS      current
    DESCRIPTION 
        "Specifies and indicates a list of protection units acting as 
         protecting units within this protection group, using the 
         ProtectedUnits atextual convention.
         
         When read, this object returns a list of all the protection 
         units in the protection group that are protecting units.
         
         When written, this object accepts a list of zero or more 
         protection units in the protection group to be applied as the 
         protecting units to either a concurrent or subsequent 
         invokeProtection or releaseProtection action.
         
         The value read from this object may not necessarily be the same 
         as the value last written.
         
         This object is written with the protecting units applicable to 
         an action before writting the isupPgInvokeProtection or 
         isupPgReleaseProtection objects to invoke the action."
    REFERENCE   
        "ITU-T Rec. G.774.3 (2001) : InvokeProtectionArgs.ProtectionEntity
         ITU-T Rec. G.774.3 (2001) : ReleaseProtectionArgs.ProtectionEntity"
    ::= { isupPgEntry 13 }

isupPgInvokeProtection OBJECT-TYPE
    SYNTAX      ActionOrResult
    MAX-ACCESS  read-create
    STATUS      current
    DESCRIPTION 
        "The invokeProtection action can be used to request a lockout, a 
         forced switch, or a manual (i.e. normal switch) on one or more 
         protectionUnit instances contained in the protectionGroup 
         object. The action argument contains a request (Forced Switch, 
         Manual Switch, or Lockout) and indications of the protected and 
         protecting units to which the request applies. If a protecting 
         unit is identified in the protectedUnits field, or if a 
         protected unit is identified in the protectingUnits field, the 
         action fails. If the request is Forced Switch or Manual Switch, 
         the protectedUnits field shall identify one or more protection 
         units. If only one unit is identified in the protectedUnits 
         field, and there is only one protecting unit in the protection 
         group, the protectingUnits field may be omitted. If the 
         protectingUnits field is present, it shall identify the same 
         number of units as the protectedUnits field. If the request is 
         Lockout, the protectionEntity field may be absent, indicating 
         that the request applies to all contained protection units. If 
         the protectionEntity field is present, any number of protection 
         units may be identified in the protectedUnits and/or 
         protectingUnits field, and either field may be absent. For a 
         Lockout request, the specified protected units and/or 
         protecting units are locked out. For requests which cannot be 
         completed, either because the request is the protecting unit is 
         serving a request of higher priority (in the error parameter of 
         the CMIP APDU, reason: pre-empted), or failure occurs 
         (failure), or timeout occurs (timeout), the reply shall 
         indicate why the request could not be completed, and the 
         request shall not be made pending. The CMIP error APDU contains 
         the failure reasons.
         
         Any write to this object invokes the protection for the 
         associated protection group.  The isupPgSwitchType is used as 
         the type of invocation; the last write to isupPgProtectedUnits 
         specifies the list of protected units; isupPgProtectingUnits, 
         protecting units.
         
         A read from this object returns the result of the last action 
         invoked.  It may have one of the following values:
         
         - success(0): indicates that the last action was successful;
         
         - pending(1): indicates that an action is pending;
         
         - failure(2): indicates that the last action failed;
         
         - timeout(3): indicates that the last action timed out; and,
         
         - preempted(4): indicates that the last action was preempted by 
           an operation of higher priority."
    REFERENCE   
        "ITU-T Rec. G.774.3 (2001) : invokeProtection ACTION"
    ::= { isupPgEntry 14 }

isupPgReleaseProtection OBJECT-TYPE
    SYNTAX      ActionOrResult
    MAX-ACCESS  read-create
    STATUS      current
    DESCRIPTION 
        "The releaseProtection action can be used to release a lockout, 
         a forced switch, or a manual (i.e. normal switch) on one or 
         more protectionUnit instances contained in the protectionGroup 
         object. The action argument contains a request (Forced Switch, 
         Manual Switch, or Lockout) and indications of the protected and 
         protecting units to which the request applies. If a protecting 
         unit is identified in the protectedUnits field, or if a 
         protected unit is identified in the protectingUnits field, the 
         action fails. If the request is Forced Switch or Manual Switch, 
         the protectedUnits field shall identify one or more protection 
         units, and the protectingUnits field shall be omitted. For each 
         identified protected unit, if it is not switched to a 
         protecting unit, the action fails. If the request is Lockout, 
         the protectionEntity field may be absent, indicating that the 
         request applies to all contained protection units. If the 
         protectionEntity field is present, any number of protection 
         units may be identified in the protectedUnits and/or 
         protectingUnits field, and either field may be absent. For a 
         Lockout request, the specified protected units and/or 
         protecting units are no longer locked out. That is, the 
         protected units are now under protection and the protecting 
         units are now capable of providing protection. For release 
         requests which cannot be completed, the reply shall indicate 
         why the request could not be completed.
         
         Any write to this object invokes the request for the associated 
         protection group.  The isupPgSwitchType is used as the type of 
         release; the last write to isupPgProtectedUnits specifies the 
         list of protected units; isupPgProtectingUnits, protecting 
         units.
         
         A read from this object returns the result of the last action 
         invoked.  It may have one of the following values:
         
         - success(0): indicates that the last action was successful;
         
         - pending(1): indicates that an action is pending;
         
         - failure(2): indicates that the last action failed; and,
         
         - timeout(3): indicates that the last action timed out."
    REFERENCE   
        "ITU-T Rec. G.774.3 (2001) : releaseProtection ACTION"
    ::= { isupPgEntry 15 }

isupPgRowStatus OBJECT-TYPE
    SYNTAX      RowStatus
    MAX-ACCESS  read-create
    STATUS      current
    DESCRIPTION 
        "Provides a mechanism whereby management stations may create and 
         delete entries in this table.  Rows may also be created and 
         deleted by the managed system as a part of system operation.
         
         If the name packate is supported: a create request with a value 
         for the name attribute that is already used by another instance 
         of the same object class will be rejected."
    REFERENCE   
        "STD 58, SNMPv2-TC RowStatus."
    ::= { isupPgEntry 16 }


-- ==========================================================================
-- ISUP Protection Unit Table

isupPu OBJECT IDENTIFIER
    ::= { isupTables 3 }

isupPuTable OBJECT-TYPE
    SYNTAX      SEQUENCE OF IsupPuEntry
    MAX-ACCESS  not-accessible
    STATUS      current
    DESCRIPTION 
        "This object class is used for representing protection 
         units within protection groups."
    REFERENCE   
        "ITU-T Rec. M.3100 (2005) : protectionUnitR1 MOC
         ITU-T Rec. G.774.3 : protectionUnit MOC"
    ::= { isupPu 1 }

isupPuEntry OBJECT-TYPE
    SYNTAX      IsupPuEntry
    MAX-ACCESS  not-accessible
    STATUS      current
    DESCRIPTION 
        "Each row in this table is indexed by protect group 
         identifier and protection unit identifier.  Each row 
         contains the characteristics and operational status of 
         a protection unit within a protection group."
    REFERENCE   
        "ITU-T Rec. M.3100 (2005) : protectionUnitR1 MOC
         ITU-T Rec. G.774.3 : protectionUnit MOC"
    INDEX       { isupPgId, isupPuId }
    ::= { isupPuTable 1 }

IsupPuEntry ::= SEQUENCE {
    isupPuId                            Unsigned32,
    isupPuProtecting                    TruthValue,
    isupPuReliableResourcePointer       RowPointer,
    isupPuUnreliableResourcePointer     RowPointer,
    isupPuProtectionStatus              ProtectionStatus,
    isupPuSwitchStatus                  INTEGER,
    isupPuFromProtectionUnitNumber      Unsigned32,
    isupPuToProtectionUnitNumber        Unsigned32,
    isupPuAutoSwitchReason              INTEGER,
    isupPuLockoutReleaseFailed          TruthValue,
    isupPuPriority                      Unsigned32,
    isupPuRowStatus                     RowStatus
}

isupPuId OBJECT-TYPE
    SYNTAX      Unsigned32 (0..255)
    MAX-ACCESS  not-accessible
    STATUS      current
    DESCRIPTION 
        "Provides an index into the protection unit table.  A maximum of 
         255 protection units are allowed per protection group."
    REFERENCE   
        "ITU-T Rec. G.774.3 : protectionUnitId ATTRIBUTE"
    ::= { isupPuEntry 1 }

isupPuProtecting OBJECT-TYPE
    SYNTAX      TruthValue
    MAX-ACCESS  read-create
    STATUS      current
    DESCRIPTION 
        "This attribute specifies the type of the protectionUnit. A 
         value of TRUE indicates that the protectionUnit is a protecting 
         (i.e. backup or standby) unit.  A value of FALSE indicates that 
         the protectionUnit is a protected (i.e. a regular, working, or 
         preferred) unit."
    REFERENCE   
        "ITU-T Rec. G.774.3 : protecting ATTRIBUTE"
    ::= { isupPuEntry 2 }

isupPuReliableResourcePointer OBJECT-TYPE
    SYNTAX      RowPointer
    MAX-ACCESS  read-create
    STATUS      current
    DESCRIPTION 
        "The value of the reliableResourcePointerR1 attribute points to 
         the reliable resource(s) (e.g. the functional objects) that 
         is/are associated with the Protection Unit instance."
    REFERENCE   
        "ITU-T Rec. M.3100 (2005) : reliableResourcePointer ATTRIBUTE"
    ::= { isupPuEntry 3 }

isupPuUnreliableResourcePointer OBJECT-TYPE
    SYNTAX      RowPointer
    MAX-ACCESS  read-create
    STATUS      current
    DESCRIPTION 
        "The value of the unreliableResourcePointerR1 attribute points 
         to the unreliable resource(s) (e.g. circuit pack) that is/are 
         associated with the Protection Unit instance."
    REFERENCE   
        "ITU-T Rec. M.3100 (2005) : unreliableResourcePointer ATTRIBUTE"
    ::= { isupPuEntry 4 }

isupPuProtectionStatus OBJECT-TYPE
    SYNTAX      ProtectionStatus
    MAX-ACCESS  read-create
    STATUS      current
    DESCRIPTION 
        "This attribute is used to indicate the status of the protection 
         switch in a protectionUnit instance. This attribute is 
         set-valued because some requests are allowed to be pending.
         
         The following rule shall be followed:
         
         Only one of the values lockout, forcedSwitch, or manualSwitch 
         can be present at the same time, either local or remote. It is 
         also possible to have two or more pending automatic switch 
         requests.
         
         The protectionStatus attribute of a protection Unit which 
         provides protection is used to hold the protection request 
         which is actually performed on that protectionUnit. Locally 
         invoked management operations (e.g. manual, forced, lockout 
         switch completions) can be overridden at the near end or the 
         far end, but may only be released at the near end. Single-ended 
         systems keep the status of local and far-end switch requests as 
         separate entities in the protectionStatus attribute.
         
         The remainder of this behaviour provides the allowable 
         protectionStatus attribute values for protected and protecting 
         units for both revertive and non-revertive systems.
         
         The following allowable protectionStatus values are associated 
         with each protected unit:
         
         - No Request: No switch request is present on the unit.
         
         - Manual Switch to Protecting Complete: The unit has completed 
           a Manual Switch. Release failed A switch has been released or 
           pre-empted and a timeout occurs while waiting for a release 
           of associated bridges, or the near-end switch.
         
         - Automatic Switch (SF) Pending: The unit has a Signal Fail 
           condition present and the protecting unit is unavailable.
         
         - Automatic Switch (SD) Pending: The unit has a Signal Degrade 
           condition present and the protecting unit is unavailable.
         
         - Automatic Switch (SF) Complete: The unit has completed an 
           Automatic Switch to the protecting unit due to a Signal Fail 
           condition.
         
         - Automatic Switch (SD) Complete: The unit has completed an 
           Automatic Switch to the protecting unit due to a Signal 
           Degrade condition.
         
         - Automatic Switch (SF) Present, Operate failed: An automatic 
           switch (SF) request is in progress and a time-out occurs 
           while waiting for completion.
         
         - Automatic Switch (SD) Present, Operate failed: An automatic 
           switch (SD) request is in progress and a time-out occurs 
           while waiting for completion. Force Switch Complete,
         
         - Automatic Switch (SF) Pending: The unit has completed a Force 
           Switch. Additionally, the unit has an automatic switch (SF) 
           pending.
         
         - Force Switch Complete, Automatic Switch (SD) Pending: The 
           unit has completed a Force Switch. Additionally, the unit has 
           an automatic switch (SD) pending.
         
         - Automatic Switch Complete, Wait-to-Restore: The unit has 
           completed an Automatic Switch to the protecting unit.
         
         - Force Switch Complete: The unit has completed a Force Switch 
           to the protecting unit.
         
         - Protected Unit Lockout Completed: The unit has been locked 
           out from the protecting unit.
         
         - Protected Unit Lockout complete, Operate Failed: The unit has 
           been locked out from the protecting unit, and, the previously 
           completed switch could not be released within the expected 
           time-out. When the switch is released, the operate failed 
           status is removed. Additionally, the non-revertive protected 
           protection unit has the following status values: Do Not 
           Revert The protected unit has been switched to the protecting 
           unit and the request to do so has been released. The switch 
           to the protecting unit is maintained.
         
         - Manual Switch to Protected Unit Complete: The unit has 
           completed a Manual Switch from the protecting unit to the 
           protected unit.
         
         - Force Switch to Protected Unit Complete: The unit has 
           completed a Force Switch from the protecting unit to the 
           protected unit.
         
         - Automatic Switch (SF) to Protected Unit Complete: The 
           protecting unit has a Signal Fail condition present and 
           traffic is now being carried on the protected unit.
         
         - Automatic Switch (SD) to Protected Unit Complete: The 
           protecting unit has a Signal Degrade condition present and 
           traffic is now being carried on the protected unit.
         
         - Automatic Switch (SD) to Protected Unit Complete, Signal 
           Degrade Present: The protecting unit has a Signal Degrade 
           condition present and traffic is now being carried on the 
           protected unit.  Additionally, the protected unit has a 
           Signal Degrade condition present.
         
         - Automatic Switch (SF) to Protected Unit Complete, Signal 
           Degrade Present: The protecting unit has a Signal Fail 
           condition present and traffic is now being carried on the 
           protected unit.  Additionally, the protected unit has a 
           Signal Degrade condition present.
         
         - Force Switch from Protecting Unit Complete, Automatic Switch 
           (SF) Pending: The unit has completed a Force Switch from the 
           protecting unit to the protected unit. Additionally, the 
           protected unit has an automatic switch (SF) condition 
           present.
         
         - Force Switch from Protecting Unit Complete, Automatic Switch 
           (SD) Pending: The unit has completed a Force Switch from the 
           protecting unit to the protected unit. Additionally, the 
           protected unit has an automatic switch (SD) condition 
           present. The following allowable protectionStatus values are 
           associated with each protecting unit: No Request No request 
           is present on the protecting unit.
         
         - Manual Switch to Protecting Unit Complete: The protected unit 
           has completed a Manual Switch.
         
         - Automatic Switch Complete (SF) to Protecting Unit: The 
           protected unit has completed an automatic switch (SF) to the 
           protecting unit.
         
         - Automatic Switch Complete (SD) to Protecting Unit: The 
           protected unit has completed an automatic switch (SD) to the 
           protecting unit.
         
         - Automatic Switch Complete (SD) to Protecting Unit, Protecting 
           Unit Signal Degraded: The protected unit has completed an 
           automatic switch to the protecting unit.  Additionally, the 
           protecting unit has a Signal Degrade condition present. This 
           applies to 1:n systems only.
         
         - Automatic Switch Complete (SF) to Protecting Unit, Protecting 
           Unit Signal Degraded: The protected unit has completed an 
           automatic switch to the protecting unit.  Additionally, the 
           protecting unit has a Signal Degrade condition present. This 
           applies to 1:n systems only.
         
         - Protecting Unit SD Present: The protecting unit has a Signal 
           Degrade condition present.  This state may also be a result 
           of invalid or toggling APS byte values. This applies to 1:n 
           systems only.
         
         - Protecting Unit SF Present: The protecting unit has a Signal 
           Fail condition present.  This state may also be a result of 
           invalid or toggling APS byte values. This applies to 1:n 
           systems only.
         
         - Force Switch Complete to Protecting Unit: The unit has 
           completed a Force Switch of a protected unit to the 
           protecting unit.
         
         - Force Switch Complete to Protecting Unit, SD Present on 
           Protecting Unit: The unit has completed a Force Switch of a 
           protected unit to the protecting unit. Additionally, there is 
           a Signal Degrade present on the protecting unit.
         
         - Force Switch Complete to Protecting, SF Present on Protecting 
           Unit: The unit has completed a Force Switch of a protected 
           unit to the protecting unit. Additionally, there is a Signal 
           Fail (1 + 1 unidirectional systems only) present on the 
           protecting unit.
         
         - Protecting Unit Locked Out: The protecting unit has been 
           locked out.
         
         - Protecting Unit Locked Out, Release Failed: A release of a 
           lockout is in progress and a timeout occurs waiting for the 
           lockout condition to clear. Additionally, the non-revertive 
           protecting unit has the following values: Do Not Revert The 
           protected unit has been switched to the protecting unit and 
           the request to do so has been released. The switch to the 
           protecting unit is maintained.
         
         - Manual Switch to Protected Unit Complete: The unit has 
           completed a Manual Switch from the protecting unit to the 
           protected unit.
         
         - Force Switch to Protected Unit Complete: The protecting unit 
           has completed a forced switch to the protected unit.
         
         - Force Switch to Protected Unit Complete, Protecting Unit 
           Signal Degraded: The protecting unit has completed a forced 
           switch to the protected unit.  Additionally, there is a 
           Signal Degrade condition on the protecting unit.
         
         - Force Switch to Protected Unit Complete, Protecting Unit 
           Signal Failed: The protecting unit shows a forced switch to 
           the protected unit.  Additionally, there is a Signal Fail 
           condition on the protecting unit.
         
         - Automatic Switch (SF) to Protected Unit Complete: The 
           protecting unit has a Signal Fail condition present and 
           traffic is now being carried on the protected unit.
         
         - Automatic Switch (SD) to Protected Unit Complete: The 
           protecting unit has a Signal Degrade condition present and 
           traffic is now being carried on the protected unit.
         
         - Automatic Switch Complete (SD) to Protecting, Automatic 
           Switch (SD) to Protected Unit Pending: The protected unit has 
           completed an automatic switch to the protecting unit.  
           Additionally, the protecting unit has a Signal Degrade 
           condition present.
         
         - Automatic Switch Complete (SF) to Protecting, Automatic 
           Switch (SD) to Protected Unit Pending: The protected unit has 
           completed an automatic switch to the protecting unit.  
           Additionally, the protecting unit has a Signal Degrade 
           condition present.
         
         APS timeout detected by the exerciser, or, during an attempt to 
         invoke a manual or forced switch will not be indicated as APS 
         failure (operate or release fail) in the protectionStatus 
         attribute. Instead, the actionReply for the invoked action will 
         report this. Additionally, attribute lastAttemptResult will 
         provide a record of the failure, until a successful exercise or 
         protection switch causes this attribute to be cleared."
    REFERENCE   
        "ITU-T Rec. M.3100 (2005) : protectionStatusR1 ATTRIBUTE"
    ::= { isupPuEntry 5 }

isupPuSwitchStatus OBJECT-TYPE
    SYNTAX      INTEGER { pending(0), completed(1), operateFailed(2) }
    MAX-ACCESS  read-create
    STATUS      current
    DESCRIPTION 
        "This object provides additional information in 
         conjunction with the protection status.  It provides 
         the status of a protection switch event.
         
         - pending(0), an automatic switch request was issued, 
           but the protecting unit is unavailable;
         - completed(1), the unit has completed an automatic 
           switch to the protecting unit;
         - operateFailed(2), an automatic switch request is in 
           progress and a time-out occurred while waiting for 
           completion.
           
         During a protection switch, the status is pending(0).  
         Once the protection switch has completed or terminated 
         due to failure, the protection unit will remain in the 
         completed(1) or operateFailed(2) states until another 
         automatic protection switch request occurs."
    ::= { isupPuEntry 6 }

isupPuFromProtectionUnitNumber OBJECT-TYPE
    SYNTAX      Unsigned32
    MAX-ACCESS  read-create
    STATUS      current
    DESCRIPTION 
        "This object provides additional information in 
         conjunction with the protection status.  It specifies 
         the protection unit number which is being removed from 
         service as part of the switch.  When no protection unit 
         is being switched from, the value of this object will 
         be zero (0)."
    ::= { isupPuEntry 7 }

isupPuToProtectionUnitNumber OBJECT-TYPE
    SYNTAX      Unsigned32
    MAX-ACCESS  read-create
    STATUS      current
    DESCRIPTION 
        "This object provides additional information in 
         conjunction with the protection status.  It specifies 
         the protection unit number which is being placed into 
         service as part of the switch.  When no protection unit 
         is being switched to, the value of this object will be 
         zero (0)."
    ::= { isupPuEntry 8 }

isupPuAutoSwitchReason OBJECT-TYPE
    SYNTAX      INTEGER { waitToRestore(0), resourceDegrade(1), 
                    resourceFailed(2) }
    MAX-ACCESS  read-create
    STATUS      current
    DESCRIPTION 
        "This object provides additional information in 
         conjunction with the protection status.  It specifies 
         the reason for an automatic protection switching event.
         
         - waitToRestore(0), the unit has completed an automatic 
           switch to the protecting unit and is waiting for the 
           protected unit to be restored;
         - resourceDegrade(1), the primary or priority 
           protection unit is degraded;
         - resourceFailed(1), the primary or priority protection 
           unit has failed."
    ::= { isupPuEntry 9 }

isupPuLockoutReleaseFailed OBJECT-TYPE
    SYNTAX      TruthValue
    MAX-ACCESS  read-create
    STATUS      current
    DESCRIPTION 
        "This object provides additional information in 
         conjunction with the protection status.  It specifies, 
         as a truth value, whether the protecting unit has been 
         locked out."
    ::= { isupPuEntry 10 }

isupPuPriority OBJECT-TYPE
    SYNTAX      Unsigned32
    MAX-ACCESS  read-create
    STATUS      current
    DESCRIPTION 
        "This attribute specifies the priority of the service (e.g. 
         traffic) carried on the resource associated with the protected 
         protectionUnit instance. Valid values for this attribute are 
         integers, where the value 1 indicates the highest priority, and 
         a larger value indicates a lower priority. For a protecting 
         protectionUnit, the value of this attribute indicates the 
         priority of choice of the protecting protectionUnit relative to 
         other available protecting protectionUnit(s) within the same 
         protectionGroup. The lower the value, the more preferred the 
         protectionUnit is relative to other protectionUnits."
    REFERENCE   
        "ITU-T Rec. G.774.3 : priority ATTRIBUTE"
    ::= { isupPuEntry 11 }

isupPuRowStatus OBJECT-TYPE
    SYNTAX      RowStatus
    MAX-ACCESS  read-create
    STATUS      current
    DESCRIPTION 
        "Provides a mechanism whereby management stations may create or 
         delete entries in this table.  Rows may also be created and 
         deleted by the managed system as part of system operations."
    REFERENCE   
        "STD 58, SNMPv2-TC RowStatus."
    ::= { isupPuEntry 12 }

-- ====================================================================
-- ISUP Linkage Table

isupLg OBJECT IDENTIFIER
    ::= { isupTables 4 }

isupLgTable OBJECT-TYPE
    SYNTAX      SEQUENCE OF IsupLgEntry
    MAX-ACCESS  not-accessible
    STATUS      current
    DESCRIPTION 
        "This is a protocol linkage table.  There exists and entry in 
         this table for each separate provision of the underlying 
         service (MTP Access Point) to the superior protocol machine 
         (ISDN User Part).  Its definition permits it to be created and 
         deleted explicitly by management operation, but in some systems 
         it will exist inherently and neither creation nor deletion by 
         management operation will be possible.  Name binding are 
         defined for both cases.
         
         When the linkage is operable, the operationalState shall have 
         the value 'enabled'; otherwise it shall have the value 
         'disable'.   Transitions of operationalState shall be reported 
         using the stateChange notification.  A linkage MO may be 
         created in the 'enabled' operational state."
    REFERENCE   
        "ITU-T Rec. X.283 (1993) | ISO/IEC 10733 : 1992 : linkage MOC."
    ::= { isupLg 1 }

isupLgEntry OBJECT-TYPE
    SYNTAX      IsupLgEntry
    MAX-ACCESS  not-accessible
    STATUS      current
    DESCRIPTION 
        "Provides an entry in the ISUP linkage table (isupLgTable).  
         Each entry in the table associates a local ISUP SAP 
         (isupSpEntry) with an MTP provider (isupMtpEntry).  Note that a 
         given MTP provider (isupMtpEntry) may support zero or more ISUP 
         SAPs."
    REFERENCE   
        "ITU-T Rec. X.283 (1993) | ISO/IEC 10733 : 1992 : linkage MOC."
    INDEX       { isupLgId }
    ::= { isupLgTable 1 }

IsupLgEntry ::= SEQUENCE {
    isupLgId                    Unsigned32,
    isupLgOperationalState      OperationalState,
    isupLgAdministrativeState   AdministrativeState,
    isupLgSnServiceProvider     RowPointer,
    isupLgSnSap                 RowPointer,
    isupLgOperationalProtocols  BITS,
    isupLgOperationalSubsets    BITS,
    isupLgRowStatus             RowStatus
}

isupLgId OBJECT-TYPE
    SYNTAX      Unsigned32
    MAX-ACCESS  not-accessible
    STATUS      current
    DESCRIPTION 
        "Provides a non-zero ordinal index for the ISUP linkage in the 
         isupLgTable."
    ::= { isupLgEntry 1 }

isupLgOperationalState OBJECT-TYPE
    SYNTAX      OperationalState
    MAX-ACCESS  read-only
    STATUS      current
    DESCRIPTION 
        "Provides the operational state of the ISUP linkage following 
         the OperationalState textual convention of the OPENSS7-SMI-MIB 
         module and ITU-T Rec. X.721 | ISO/IEC 10165-2.
         
         - disabled(0): the links is inoperable;
         - enabled(1): the linkage is operable.
         
         When the linkage is operable, the operational state shall have 
         the value enabled(1); otherwise it shall have the value 
         disabled(0).  Transitions of operational state shall be 
         reported using a state change notification.  A linkage may be 
         created in the enabled(1) operational state."
    REFERENCE   
        "ITU-T Rec. X.721 (1992) | ISO/IEC 10165-2 : 1992, 
             Attribute-ASN1Module.OperationalState."
    DEFVAL      { disabled }
    ::= { isupLgEntry 2 }

isupLgAdministrativeState OBJECT-TYPE
    SYNTAX      AdministrativeState
    MAX-ACCESS  read-create
    STATUS      current
    DESCRIPTION 
        "Provides the administrative state of the ISDN user part 
         following the AdministrativeState textual convention and ITU-T 
         Rec. X.721 | ISO/IEC 10165-2.
         
         - locked(0), the ISUP linkage is administratively prohibited 
           from use;
         
         - unlocked(1), the ISUP linkage is administratively permitted 
           for use; and,
         
         - shuttingDown(2), not used."
    REFERENCE   
        "ITU-T Rec. X.721 (1992) | ISO/IEC 10165-2 : 1992, 
             Attribute-ASN1Module.AdministrativeState.
         ITU-T Rec. X.283 (1997) | ISO/IEC 10733 : 1998 : 
             administrativeState ATTRIBUTE."
    ::= { isupLgEntry 3 }

isupLgSnServiceProvider OBJECT-TYPE
    SYNTAX      RowPointer
    MAX-ACCESS  read-create
    STATUS      current
    DESCRIPTION 
        "Distinguished name of the SN service provider MO.  This 
         attribute identifies the subnetwork entity to be used to 
         support the linkage, when enabled.  The subnetwork service 
         provider may be in the Datalink Layer, or it may be in the 
         Network Layer.
         
         The value of this object is a pointer to a corresponding entry  
         in the isupMtpTable specifying the underlying MTP service 
         provider that supports the ISUP SAP.  Where the value of this 
         object does not correspond to an entry in the isupMtpTable, the 
         agent may refuse row creation.
         
         If the linkage is created by management operation, the initial 
         value of this object shall be specified during row creation.  
         Otherwise, the value shall be determined in an implementation 
         specific manner."
    REFERENCE   
        "ITU-T Rec. X.283 (1993) | ISO/IEC 10733 : 1992 : 
             sN-ServiceProvider ATTRIBUTE."
    ::= { isupLgEntry 4 }

isupLgSnSap OBJECT-TYPE
    SYNTAX      RowPointer
    MAX-ACCESS  read-create
    STATUS      current
    DESCRIPTION 
        "Distinguished name of the service provider SAP MO (if present).  
         This is obtained via an internal interface when the linkage is 
         enabled.  The sN-SAP may be a relationship to a SAP MO in the 
         Datalink Layer, or it may be a relationship to another Managed 
         Object within the Network Layer which is not a SAP MO.
         
         The value of this object is a pointer to a corresponding entry 
         in the isupSpTable or isupSrTable specifying the ISUP SAP 
         supported by this linkage.  Where the value of this object does 
         not correspond to an existing entry in the isupSpTable nor 
         isupSrTable, the agent may refuse row creation.
         
         When the value of this object corresponds to an entry in the 
         isupSpTable, it corresponds to a binding for the near-end 
         signalling point code of the isupSpEntry.  When the value of 
         this object corresponds to an entry in the isupSrTable, it 
         corresponds to a binding for the near-end and far-end 
         signalling point codes.  This later form of binding is not 
         necessarily supported by all MTP providers."
    REFERENCE   
        "ITU-T Rec. X.283 (1993) | ISO/IEC 10733 : 1992 : sN-SAP 
             ATTRIBUTE."
    ::= { isupLgEntry 5 }

isupLgOperationalProtocols OBJECT-TYPE
    SYNTAX      BITS { protocol(0) }
    MAX-ACCESS  read-create
    STATUS      current
    DESCRIPTION 
        "Specifies the protocols that are operational on the 
         ISUP to underlying MTP SAP linkage."
    ::= { isupLgEntry 6 }

isupLgOperationalSubsets OBJECT-TYPE
    SYNTAX      BITS { subset(0) }
    MAX-ACCESS  read-create
    STATUS      current
    DESCRIPTION 
        "Specifies the subsets of the protocols that are 
         operational on the ISUP to underlying MTP SAP linkage."
    ::= { isupLgEntry 7 }

isupLgRowStatus OBJECT-TYPE
    SYNTAX      RowStatus
    MAX-ACCESS  read-create
    STATUS      current
    DESCRIPTION 
        "Provides a mechanism whereby management stations may create and 
         delete entries in this table.  Rows may also be created and 
         deleted by the managed system as a part of system operation."
    REFERENCE   
        "STD 58, SNMPv2-TC RowStatus."
    ::= { isupLgEntry 8 }

-- ====================================================================

isupMtp OBJECT IDENTIFIER
    ::= { isupTables 5 }

isupMtpTable OBJECT-TYPE
    SYNTAX      SEQUENCE OF IsupMtpEntry
    MAX-ACCESS  not-accessible
    STATUS      current
    DESCRIPTION 
        "This is an MTP-SAP table that defines the MTP SAPs (users) that 
         are available at a signaling point."
    REFERENCE   
        "ITU-T Rec. Q.751.1 (1997), ANSI T1.116.1 (2000), mtpAccessPoint 
         MOC."
    ::= { isupMtp 1 }

isupMtpEntry OBJECT-TYPE
    SYNTAX      IsupMtpEntry
    MAX-ACCESS  not-accessible
    STATUS      current
    DESCRIPTION 
        "This is an MTP-SAP entry that defines the MTP-SAPs (users) that 
         are available at a signalling point.
         
         The sap2Address attribute contains the address of the 
         mtpAccessPoint. It contains the Signalling Point Code (SPC), 
         Service Indicator (SI) and MTP Network Identity (NI).
         
         The sapId attribute is used in naming instances of the 
         mtpAccessPoint managed object class.
         
         The userEntityNames attribute contains the distinguished names 
         of the managed objects that represent the user entities that 
         are using the mtpAccessPoint, e.g. the SCCP instance.
         
         The providerEntityNames attribute contains the distinguished 
         names of the managed objects that represent the provider 
         entities that are supporting the mtpAccessPoint, i.e. the 
         instance of the MTP.
         
         A mtpAccessPoint can have the MTP status: allowed, this means 
         that the mtpAccessPoint is accessible and is functioning 
         normally; congested, this means that the mtpAccessPoint is 
         accessible but the path to it is heavily loaded; prohibited, 
         this means that the mtpAccessPoint not accessible.
         
         If the ss7OnOccEventPackage is present, event notifications 
         with the following probable causes can apply: Probable Cause = 
         001 (localUserPartUnavailable)"
    REFERENCE   
        "ITU-T Rec. Q.751.1 (1997), ANSI T1.116.1 (2000), mtpAccessPoint 
         MO."
    INDEX       { isupMsId, isupSpId, isupMtpId }
    ::= { isupMtpTable 1 }

IsupMtpEntry ::= SEQUENCE {
    isupMtpId                       Unsigned32,
    isupMtpAddress                  MtpSapAddress,
    isupMtpUserPart                 MtpUserPart,
    isupMtpUserPartStatus           MtpUserPartStatus,
    isupMtpUserEntityNames          RowPointer,
    isupMtpProviderEntityNames      RowPointer,
    isupMtpUsageState               UsageState,
    isupMtpAsaProfilePointer        RowPointer,
    isupMtpName                     SimpleNameType,
    isupMtpLongMessageSupported     TruthValue,
    isupMtpRowStatus                RowStatus
}

isupMtpId OBJECT-TYPE
    SYNTAX      Unsigned32
    MAX-ACCESS  not-accessible
    STATUS      current
    DESCRIPTION 
        "Provides an index into the MTP-SAP table.  Provides an index 
         relative to the MTP level 3 index, of the MTP access point."
    REFERENCE   
        "ITU-T Rec. Q.751.1 (1997), ANSI T1.116.1 (2000),
         ITU-T Rec. X.723 | ISO/IEC 10165-5, sapId attibute."
    ::= { isupMtpEntry 1 }

isupMtpAddress OBJECT-TYPE
    SYNTAX      MtpSapAddress
    MAX-ACCESS  read-only
    STATUS      current
    DESCRIPTION 
        "Provides the cardinal number of SAP address components that 
         exist for this MTP access point in the mtpSap2AddressTable side 
         table.
         
         The sap2Address attribute contains the address of the 
         mtpAccessPoint. It contains the Signalling Point Code (SPC), 
         Service Indicator (SI) and MTP Network Identity (NI).
         
         Provides the MTP User Part (SI value) associated with this MTP 
         user."
    REFERENCE   
        "ITU-T Rec. Q.751.1 (1997), ANSI T1.116.1 (2000),
         ITU-T Rec. X.723 | ISO/IEC 10165-5, sap2Address attibute."
    ::= { isupMtpEntry 2 }

isupMtpUserPart OBJECT-TYPE
    SYNTAX      MtpUserPart
    MAX-ACCESS  read-create
    STATUS      current
    DESCRIPTION 
        "Provides the cardinal number of SAP address components that 
         exist for this MTP access point in the mtpSap2AddressTable side 
         table.
         
         The sap2Address attribute contains the address of the 
         mtpAccessPoint. It contains the Signalling Point Code (SPC), 
         Service Indicator (SI) and MTP Network Identity (NI).
         
         Provides the MTP User Part (SI value) associated with this MTP 
         user."
    REFERENCE   
        "ITU-T Rec. Q.751.1 (1997), ANSI T1.116.1 (2000),
         ITU-T Rec. X.723 | ISO/IEC 10165-5, sap2Address attibute."
    ::= { isupMtpEntry 3 }

isupMtpUserPartStatus OBJECT-TYPE
    SYNTAX      MtpUserPartStatus
    MAX-ACCESS  read-create
    STATUS      current
    DESCRIPTION 
        "Provides, using the MtpUserPartStatus textual convention, the 
         status of the MTP-SAP as well a allowing management stations to 
         control the individual user part status for MTP-SAP that have 
         no MTP User.  Values are:
         
          - unknown(0), the status of the user, when not present, is 
            unknown;
          - inaccessible(1), the user, when not present, is 
            inaccessible;
          - unequipped(2), the statu of the user, when not present, is 
            unequipped.
         
         When the user part is present (the usage state is idle(0)), 
         this value is inaccessible(1).  Note that management stations 
         may only set these values for MTP-SAPs that are not in active 
         use by an MTP-user (i.e. those for which the usage state is 
         idle(0))."
    REFERENCE   
        "mtpSapUsageState"
    ::= { isupMtpEntry 4 }

isupMtpUserEntityNames OBJECT-TYPE
    SYNTAX      RowPointer
    MAX-ACCESS  read-only
    STATUS      current
    DESCRIPTION 
        "Provides the user entity name that exists for the MTP access 
         point.  Specifies an entry in the ISDN user part table that 
         defines the ISDN user part that this MTP service access point 
         supports.  Each MTP access point has one and only one ISDN user 
         part.
         
         This object points to a row in the isupSpTable.
         
         When a null string is specified upon creation of a row, the 
         agent may refuse creation of the row or it may use default 
         information instead.  When a non-null string is specified upon 
         creation of a row, the agent may refuse creation of the row 
         when:
         
         1. the string does not reference the ISDN user part table 
            (isupSpTable);
         2. the string references an entry that does not exist in the 
            ISDN user part table (isupSpEntry).
         
         Once the MTP service access point row has been created wtih a 
         non-null string, alterations made to the MTP service access 
         point attributes might or might not change the characteristics 
         of existing and operational ISDN user parts.  The managed 
         system might also refuse to alter this object while the 
         operational state is other than disabled(0)."
    REFERENCE   
        "ITU-T Rec. Q.751.1 (1997), ANSI T1.116.1 (2000),
         ITU-T Rec. X.723 | ISO/IEC 10165-5, userEntityNames attibute."
    ::= { isupMtpEntry 5 }

isupMtpProviderEntityNames OBJECT-TYPE
    SYNTAX      RowPointer
    MAX-ACCESS  read-create
    STATUS      current
    DESCRIPTION 
        "Provides the provider entity name that exists for the MTP 
         access point."
    REFERENCE   
        "ITU-T Rec. Q.751.1 (1997), ANSI T1.116.1 (2000),
         ITU-T Rec. X.723 | ISO/IEC 10165-5, providerEntityNames 
             attibute."
    ::= { isupMtpEntry 6 }

isupMtpUsageState OBJECT-TYPE
    SYNTAX      UsageState
    MAX-ACCESS  read-only
    STATUS      current
    DESCRIPTION 
        "Provides the usage state of the MTP service access point 
         following the UsageState textual convention and ITU-T Rec. 
         X.721 | ISO/IEC 10165-2.
         
          - idle(0), no user part is attached to the MTP-SAP (note that 
            management stations may set the MTP user part status in this 
            state);
          - active(1), a user part exists and is attached to the 
            MTP-SAP;
          - busy(2), a user part exists and is passing traffic but 
            congesetion exists in the path toward the MTP user.
           
         Note that management stations may set values for the MTP user 
         part status when this value is idle(0)."
    REFERENCE   
        "ITU-T Rec. X.721 | ISO/IEC 10165-2 usageState attribute."
    ::= { isupMtpEntry 7 }

isupMtpAsaProfilePointer OBJECT-TYPE
    SYNTAX      RowPointer
    MAX-ACCESS  read-create
    STATUS      current
    DESCRIPTION 
        "Provides a pointer to a row in another table that contains the 
         alarm severity assignment profile, or zeroDotZero when no alarm 
         severity assignment profile has been specified."
    REFERENCE   
        "ITU-T Rec. Q.751.1 (1997), ANSI T1.116.1 (2000),
         ITU-T Rec. M.3100, alarmSeverityAssignmentProfilePointer 
             attibute."
    DEFVAL      { zeroDotZero }
    ::= { isupMtpEntry 8 }

isupMtpName OBJECT-TYPE
    SYNTAX      SimpleNameType
    MAX-ACCESS  read-create
    STATUS      current
    DESCRIPTION 
        "Provides an additional administrative name for the MTP access 
         point.
         
         Provides an optional administrative name for this entry in the 
         MTP-SAP table.  MTP-SAP are typically names using, as a prefix, 
         the common language name of the managed switching element at 
         which they appear, concetentated with the name of the MTP User 
         (e.g. EDTAB01DS1 ISUP)."
    REFERENCE   
        "ITU-T Rec. Q.751.1 (1997), ANSI T1.116.1 (2000),
             mtpAccessPointName attibute."
    ::= { isupMtpEntry 9 }

isupMtpLongMessageSupported OBJECT-TYPE
    SYNTAX      TruthValue
    MAX-ACCESS  read-create
    STATUS      current
    DESCRIPTION 
        "This attribute defines whether messages longer than 272 octets 
         are supported."
    REFERENCE   
        "ITU-T Rec. Q.2751.1 (1997), longMessageSupported attribute."
    ::= { isupMtpEntry 10 }

isupMtpRowStatus OBJECT-TYPE
    SYNTAX      RowStatus
    MAX-ACCESS  read-create
    STATUS      current
    DESCRIPTION 
        "Provides a mechanism whereby management stations may create and 
         delete entries in this table.  Rows may also be created and 
         deleted by the managed system as a part of system operation.
         
         If the name package is supported: a create request with a value 
         for the name attribute that is already used by another instance 
         of the same object class will be rejected."
    REFERENCE   
        "STD 58, SNMPv2-TC RowStatus.
         ITU-T Rec. Q.751.1 (1997) : mtpSignPoint-mtpAccessPoint NAME 
             BINDING."
    ::= { isupMtpEntry 11 }


-- ====================================================================

isupNa OBJECT IDENTIFIER
    ::= { isupTables 6 }

isupNaTable OBJECT-TYPE
    SYNTAX      SEQUENCE OF IsupNaEntry
    MAX-ACCESS  not-accessible
    STATUS      current
    DESCRIPTION 
        "Provides the network appearance table that defines all of the 
         SS7 networks to which a managed switching element may attach."
    REFERENCE   
        "ITU-T Rec. M.3100 (1995) network MOC."
    ::= { isupNa 1 }

isupNaEntry OBJECT-TYPE
    SYNTAX      IsupNaEntry
    MAX-ACCESS  not-accessible
    STATUS      current
    DESCRIPTION 
        "Each entry in the network appearance profile table represetns a 
         unique combination of network appearance protocol parameters 
         and options.
         
         Provides an entry in the network table.  Each entry provides 
         fundamental information about the network as well as protocol 
         profile defaults for ISDN user parts created for operation 
         in each network."
    REFERENCE   
        "ITU-T Rec. M.3100 (1995) network MO."
    INDEX       { isupNaId }
    ::= { isupNaTable 1 }

IsupNaEntry ::= SEQUENCE {
    isupNaId                Integer32,
    isupNaProtocolVariant   Ss7ProtocolVariant,
    isupNaProtocolYear      INTEGER,
    isupNaProtocolOptions   BITS,
    isupNaPointCodeFormat   MtpPointCodeFormat,
    isupNaSlsLength         INTEGER,
    isupNaSpDefault         SimpleNameType,
    isupNaName              SnmpAdminString,
    isupNaRowStatus         RowStatus
}

isupNaId OBJECT-TYPE
    SYNTAX      Integer32 (1..255)
    MAX-ACCESS  not-accessible
    STATUS      current
    DESCRIPTION 
        "Provides a non-zero ordinal index for the network table.  The 
         index is restricted in the range 1..255 because the value is 
         also used as the first octet of a NetworkPointCode texutal 
         convention.
         
         Provides an ordinal simple name type index into this table.  
         This can be a print-formatted decimal number or a string.  Some 
         implementations may require that this index be formatted as a 
         print-formatted decimal number.
         
         Provides an index into the network profile table, mtpNaProfileTable.  
         Rows in this table can be referred to using this index or using 
         the RowPointer pointer.  The index value zero (0) has special 
         semantics: the zero index contains default default values."
    REFERENCE   
        "ITU-T Rec. M.3100 (1995) newtorkId ATTRIBUTE."
    ::= { isupNaEntry 1 }

isupNaProtocolVariant OBJECT-TYPE
    SYNTAX      Ss7ProtocolVariant
    MAX-ACCESS  read-create
    STATUS      current
    DESCRIPTION 
        "Provides the primary protocol variant used at the network 
         appearance using the Ss7ProtocolVariant textual convention from 
         the OPENSS7-SS7-MIB module.  This describes the major protocol 
         variant, such as ANSI, ETSI, ITU-T, using an object-identity.  
         All signalling points in the network appearance are expected to 
         signal using this protocol variant.
         
         Provides the SS7 protocol variant by standards body and year of 
         issue.  Years are based on the corresponding ITU-T Plenary 
         Session year, not the actually publish date of the 
         specification or standard.  This is an autonomous type so 
         vendor-specific extensions or localizations are permitted.  The 
         agent can refuse a management station SET operation for this 
         field with an object identifier that the agent does not 
         recognize.  The default is the current ITU-T standards 
         specifications."
    DEFVAL      { ss7ProtocolItut }
    ::= { isupNaEntry 2 }

isupNaProtocolYear OBJECT-TYPE
    SYNTAX      INTEGER { yCurrent(0), y1980(1980), y1984(1984), 
                    y1988(1988), y1992(1992), y1996(1996), y2000(2000), 
                    y2004(2004), y2008(2008) }
    MAX-ACCESS  read-create
    STATUS      current
    DESCRIPTION 
        "Specifies the year of the protocol variant which corresponds to 
         the network appearance.  All signalling points in the network 
         appearance are expected to be compatible to this MTP signalling 
         protocol version.  Provides a protocol issue year within the 
         major protocol variant.  Typical values are 1988, 1992, 1996, 
         2000, etc."
    DEFVAL      { yCurrent }
    ::= { isupNaEntry 3 }

isupNaProtocolOptions OBJECT-TYPE
    SYNTAX      BITS { none(0) }
    MAX-ACCESS  read-create
    STATUS      current
    DESCRIPTION 
        "Specifies the ISUP national and international protocol options 
         associated with the network appearance.  This can be used, for 
         example, to refine ITU-T and ANSI based protocol variants.
         
         This object simply describes the capabilities and policies 
         present at the network appearance.  It does not say anything 
         about the capabilities of signalling points that are connected 
         to this network.
         
         This is for convenience or for modifying existing standards to 
         suit other protocol variants.  The value for existing standards 
         can be deduced from the standard and the year.  Some 
         implementations may provide this object with a MAX-ACCESS 
         clause of read-only.
         
         When a row is created without specifying a value for this 
         column, a suitable default based on the protocol variant and 
         year should be completed by the agent."
    ::= { isupNaEntry 4 }

isupNaPointCodeFormat OBJECT-TYPE
    SYNTAX      MtpPointCodeFormat
    MAX-ACCESS  read-create
    STATUS      current
    DESCRIPTION 
        "Provides the format of point codes used in the signalling 
         network using the MtpPointCodeFormat textual convention.  This 
         convention provides for a three-octet octet string that 
         contains the size (in bits) of the network, cluster and member 
         elements of the signalling point code.  For ITU-T, ETSI and 
         ITU-T or ETSI-based networks, this is 3-8-3; for ANSI and 
         ANSI-based networks, this is 8-8-8.
         
         This is for convenience as the value can be deduced from the 
         protocol variant and year, so this object might be provided 
         with a MAX-ACCESS clause of read-only by some implementations."
    DEFVAL      { "\x03\x08\x03" }
    ::= { isupNaEntry 5 }

isupNaSlsLength OBJECT-TYPE
    SYNTAX      INTEGER { sls4bits(4), sls5bits(5), sls8bits(8) }
    UNITS       "bits"
    MAX-ACCESS  read-create
    STATUS      current
    DESCRIPTION 
        "Provides the length of the signalling link selection field 
         (SLS) in bits.  This can be one of the following values:
         
          - sls4bits(4): the 4-bit signalling link selection field 
            provided by international and ITU-T based networks;
          - sls5bits(5): the 5-bit signalling link selection field 
            provided by older ANSI and ANSI-based networks;
          - sls8bits(8): the 8-bit signalling link selection field 
            provided by more recent ANSI and ANSI-based networks.
         
         This is for convenience as the value can be deduced from the 
         protocol variant and year, so this object might be provided 
         with a MAX-ACCESS clause of read-only by some implementations."
    DEFVAL      { sls4bits }
    ::= { isupNaEntry 6 }

isupNaSpDefault OBJECT-TYPE
    SYNTAX      SimpleNameType
    MAX-ACCESS  read-create
    STATUS      current
    DESCRIPTION 
        "Provides a reference to a signalling point protocol profile 
         that will be used as a default when creating signalling points 
         that communicate on this network.  When this value is not 
         specified on creation, the default from the network protocol 
         profile will be used.
         
         Specifies the default signalling point protocol profile that 
         will be used when creating signalling points that appear in 
         this network.
         
         When non-null, provides the name or index of a signalling point 
         profile table entry (mtpSpProfileEntry) that contains the 
         signalling point protocol profile to be used as a default when 
         creating signalling points that appear in this signalling 
         network.  Agents may refuse creation of rows that have non-null 
         strings in this column that:
         
          1. does not refer to the signalling point profile table 
             (mtpSpProfileTable);
          2. refers to a non-existent entry in the signalling point 
             profile table (mtpSpProfileEntry).
         
         When null, it specifies that a signalling point protocol 
         profile must be specified when creating signalling points that 
         appear in this network."
    DEFVAL      { "" }
    ::= { isupNaEntry 7 }

isupNaName OBJECT-TYPE
    SYNTAX      SnmpAdminString
    MAX-ACCESS  read-create
    STATUS      current
    DESCRIPTION 
        "Provides an optional administrative name for this network.  
         This column is optional and will be a null string if not 
         specified.
         
         Provides an administrative name for the SS7 signalling network.  
         When non-null, this must be a unique string within this table.  
         Agents may refuse creation of row that has a non-null 
         administrative name that is already used by another row in the 
         table."
    REFERENCE   
        "ITU-T Rec. M.3100 (1995) userLabel ATTRIBUTE."
    ::= { isupNaEntry 8 }

isupNaRowStatus OBJECT-TYPE
    SYNTAX      RowStatus
    MAX-ACCESS  read-create
    STATUS      current
    DESCRIPTION 
        "Provides a mechanism whereby management stations may add an 
         delete conceptual rows in this table.  Row entries are 
         persistent across and agent reboot.  Before a row can be 
         deleted from the table, there must be no signalling points that 
         refer to it.
         
         Index zero (0) is special in that it provides default network 
         characteristics when no network is specified, additional rows 
         in this table may represent standard defaults for specific 
         protocol variants and years.  Managed system may refuse removal 
         of rows in this table that represents default entries.
         
         Requests to delete rows in this table that are referenced by a 
         row in the signalling point table (mtpSpTable) may be refused.  
         The agent may refuse changing columns in rows in this table for 
         which there are active signalling points.
         
         Rows in this table are persistent across an agent reboot."
    REFERENCE   
        "STD 58, SNMPv2-TC RowStatus."
    ::= { isupNaEntry 9 }


-- ====================================================================

isupSp OBJECT IDENTIFIER
    ::= { isupTables 7 }

isupSpTable OBJECT-TYPE
    SYNTAX      SEQUENCE OF IsupSpEntry
    MAX-ACCESS  not-accessible
    STATUS      current
    DESCRIPTION 
        "Provides the ISDN User part table that defines the ISDN 
         user parts provided by a managed switching element.  Each ISDN 
         User Part is associated with a network appearance entry (from 
         the isupNaTable) that provides information about the network to 
         which the ISDN User Part is attached."
    ::= { isupSp 1 }

isupSpEntry OBJECT-TYPE
    SYNTAX      IsupSpEntry
    MAX-ACCESS  not-accessible
    STATUS      current
    DESCRIPTION 
        "Provides an entry in the ISDN User Part table.  Each entry 
         provides fundamental information about the ISDN User Part as 
         well as protocol profile defaults for signalling relations 
         to other ISDN User Parts.
         
         ISDN User Parts are contained by managed switching elements.  
         Normally there is only one managed switching element per host."
    REFERENCE   
        "ITU-T Rec. Q.751.1 (1997), ANSI T1.116.1 (2000), mtpSignPoint 
         MO."
    INDEX       { isupMsId, isupSpId }
    ::= { isupSpTable 1 }

IsupSpEntry ::= SEQUENCE {
    isupSpId                        Unsigned32,
    isupSpPointCode                 NetworkPointCode,
    isupSpType                      INTEGER,
    isupSpProceduralStatus          ProceduralStatus,
    isupSpAvailabilityStatus        AvailabilityStatus,
    isupSpVersion                   GraphicString,
    isupSpName                      SimpleNameType,
    isupSpNaPointer                 RowPointer,
    isupSpOptions                   BITS,
    isupSpAlarmStatus               AlarmStatus,
    -- derived from X.723:clProtocolMachine
    isupSpOperationalState          OperationalState,
    isupSpTotalRemoteSAPs           Unsigned32,
    -- derived from X.283:cLNS
    isupSpAdministrativeState       AdministrativeState,
    isupSpSupportedProtocols        BITS,
    isupSpOperationalSystemType     INTEGER,
    isupSpActivate                  ActionOrResult,
    isupSpDeactivate                ActionOrResult,
    isupSpRowStatus                 RowStatus
}

isupSpId OBJECT-TYPE
    SYNTAX      Unsigned32
    MAX-ACCESS  not-accessible
    STATUS      current
    DESCRIPTION 
        "Provides a non-zero ordinal sub-index into the ISDN User Part 
         table.  This attribute is used for naming instances.  ISDN User 
         Parts are contained by managed switching elements and the 
         managed switching element id is used to name instances of ISDN 
         User Parts."
    REFERENCE   
        "ITU-T Rec. Q.751.1 (1997), ANSI T1.116.1 (2000), mtpSignPointId 
             attribute.
         ITU-T Rec. X.723 (1993) | ISO/IEC 10165-5 : 1993 : 
             clProtocolMachineId ATTRIBUTE."
    ::= { isupSpEntry 1 }

isupSpPointCode OBJECT-TYPE
    SYNTAX      NetworkPointCode
    MAX-ACCESS  read-create
    STATUS      current
    DESCRIPTION 
        "Specifies the network signalling point code associated  with 
         this ISDN User Part.
         
         This attribute represents the pointcode of a certain ISUP.  
         Note that point codes are 14-bit for ITU (0..16383) and 24-bit 
         for ANSI (0..16777215)."
    REFERENCE   
        "ITU-T Rec. Q.751.1 (1997), ANSI T1.116.1 (2000), pointCode 
             attribute."
    DEFVAL      { "\x00\x00\x00\x00" }
    ::= { isupSpEntry 2 }

isupSpType OBJECT-TYPE
    SYNTAX      INTEGER { endOffice(0), accessGateway(1), localTandem(2), 
                    tollTandem(3), accessTandem(4), 
                    internationalGateway(5), internationalTransit(6) }
    MAX-ACCESS  read-create
    STATUS      current
    DESCRIPTION 
        "This object represents the exchange type:
         
         - endOffice(0):
         - accessGateway(1):
         - localTandem(2):
         - tollTandem(3):
         - accessTandem(4):
         - internationalGateway(5):
         - internationalTransit(6):"
    DEFVAL      { endOffice }
    ::= { isupSpEntry 3 }

isupSpProceduralStatus OBJECT-TYPE
    SYNTAX      ProceduralStatus
    MAX-ACCESS  read-only
    STATUS      current
    DESCRIPTION 
        "Provides the procedural status of the ISDN User Part following 
         the ProceduralStatus textual convention of the OPENSS7-SMI-MIB 
         module and ITU-T Rec. X.721 | ISO/IEC 10165-2.
         
          - initializationRequired(0), ISUP restart procedures are 
            required but have not yet been initiated;
         
          - notInitialized(1), the ISUP is not initialized and needs to 
            be started;
         
          - initializing(2), indicated during ISUP restart and present 
            until the ISUP restart procedure completes;
         
          - reporting(3), unused;
          - terminating(4), unused."
    REFERENCE   
        "ITU-T Rec. X.721 | ISO/IEC 10165-2, proceduralStatus 
             attribute.
         ITU-T Rec. Q.751.1 (1997), ANSI T1.116.1 (2000) : 
             proceduralStatus attribute."
    DEFVAL      { {initializationRequired} }
    ::= { isupSpEntry 4 }

isupSpAvailabilityStatus OBJECT-TYPE
    SYNTAX      AvailabilityStatus
    MAX-ACCESS  read-only
    STATUS      current
    DESCRIPTION 
        "Provides the availability status of the ISDN User Part 
         following the AvailabilityStatus textual convention of the 
         OPENSS7-SMI-MIB module and ITU-T Rec. X.721 | ISO/IEC 10165-2.
         
          - inTest(0),
          - failed(1),
          - powerOff(2),
          - offLine(3),
          - offDuty(4),
          - dependency(5),
          - degraded(6), the ISUP is congested, accessible but heavily 
            loaded;
          - notInstalled(7),
          - logFull(8),
         
         When the value set is empty, the ISUP is allowed, accessible 
         and is functioning normally, when operational state is 
         enabled(1)."
    REFERENCE   
        "ITU-T Rec. X.721 | ISO/IEC 10165-2, availabilityStatus 
             attribute.
         ITU-T Rec. Q.751.1 (1997), ANSI T1.116.1 (2000), 
             availabilityStatus attribute."
    ::= { isupSpEntry 5 }

isupSpVersion OBJECT-TYPE
    SYNTAX      GraphicString
    MAX-ACCESS  read-create
    STATUS      current
    DESCRIPTION 
        "Provides the version of the ISDN User Part."
    REFERENCE   
        "ITU-T Rec. Q.751.1 (1997), ANSI T1.116.1 (2000), version 
         attribute."
    DEFVAL      { "ITU-T Q.764 1999" }
    ::= { isupSpEntry 6 }

isupSpName OBJECT-TYPE
    SYNTAX      SimpleNameType
    MAX-ACCESS  read-create
    STATUS      current
    DESCRIPTION 
        "This attribute is an additional name for instances of the 
         mtpSignPoint managed object class.
         
         Provides an optional administrative name for this signalling 
         point.  It is typical to use as a prefix the common language 
         name associated with the corresponding managed switching 
         element (e.g. ETDNAB01DS1SP0)."
    REFERENCE   
        "ITU-T Rec. Q.751.1 (1997), ANSI T1.116.1 (2000), 
             mtpSignPointName attribute."
    ::= { isupSpEntry 7 }

isupSpNaPointer OBJECT-TYPE
    SYNTAX      RowPointer
    MAX-ACCESS  read-create
    STATUS      current
    DESCRIPTION 
        "Specifies an entry in the network appearance table that defines 
         the network into which this ISDN user part connects.  Each 
         ISUP appears in one and only one network appearance.  This 
         value must be specified when creating the ISDN user part row.
         
         This attribute points to the instance of the class 
         networkAppearance, containing the Q.764, Q.765 and Q.767 
         network-supported options for the network in which this 
         signalling point appears.
         
         When a null string is specified upon creation of a row, the 
         agent may refuse creation of the row or it may use default 
         information instead.  When a non-null string is specified upon 
         creation of a row, the agent may refuse creation of the row 
         when:
         
         1. the string does not reference the network appearance table 
            (isupNaTable);
         2. the string references an entry that does not exist in the 
            network appearance table (isupNaEntry).
         
         Once the ISDN user part row has been created with a non-null 
         string, alterations made to the network appearance attributes 
         might or might not change the characteristics of existing and 
         operational ISDN user parts.  The manged system might also 
         refuse to alter this object while the operational state is 
         other than disabled(0)."
    ::= { isupSpEntry 8 }

isupSpOptions OBJECT-TYPE
    SYNTAX      BITS { none(0) }
    MAX-ACCESS  read-create
    STATUS      current
    DESCRIPTION 
        "Specifies additional information about this ISDN user part.  
         This value is set-valued and may contain the following:
         
         Not all combinations of flag values are valid.  Not all valid 
         combination of flags are applicable to all protocol variants.
         
         These options correspond to the capabilities of the signaling 
         point regardless of the capabilities of remote signaling 
         points to which this SP communicates.  The options associated 
         with a signaling relation will be a subset of these options."
    ::= { isupSpEntry 9 }

isupSpAlarmStatus OBJECT-TYPE
    SYNTAX      AlarmStatus
    MAX-ACCESS  read-create
    STATUS      current
    DESCRIPTION 
        "Provides the alarm status of the ISDN user part following the 
         AlarmStatus textual convention and ITU-T Rec. X.721 (1992) | 
         ISO/IEC 10165-2 : 1992.
         
          - underRepair(0),
          - critical(1),
          - major(2),
          - minor(3),
          - alarmOutstanding(4),"
    REFERENCE   
        "ITU-T Rec. Q.751.1 (1997), ANSI T1.116.1 (2000) : alarmStatus 
             attribute.
         ITU-T Rec. X.721 (1992) | ISO/IEC 10165-2 : 1992, 
             Attribute-ASN1Module.AlarmStatus.
         ITU-T Rec. X.731 (1992) | ISO/IEC 10164-2 : 1993, 
             Section 8.1.2.1."
    ::= { isupSpEntry 10 }

isupSpOperationalState OBJECT-TYPE
    SYNTAX      OperationalState
    MAX-ACCESS  read-only
    STATUS      current
    DESCRIPTION 
        "Provides the operational state of the ISDN User Part following 
         the OperationalState textual convention of the OPENSS7-SMI-MIB 
         module and ITU-T Rec. X.721 | ISO/IEC 10165-2.
         
          - disabled(0), the ISUP signaling point is not operable (that 
            is, the ISUP user part is inaccessible from the SS7 
            network); and,
         
          - enabled(1), the ISUP signaling point is operable (that is, 
            the ISUP user part is accessible from the SS7 network)."
    REFERENCE   
        "ITU-T Rec. X.721 (1992) | ISO/IEC 10165-2 : 1992, 
             Attribute-ASN1Module.OperationalState.
         ITU-T Rec. X.731 (1992) | ISO/IEC 10164-2 : 1993, 
             Section 8.1.1.1.
         ITU-T Rec. Q.751.1 (1997), ANSI T1.116.1 (2000), 
             operationalState attribute."
    DEFVAL      { disabled }
    ::= { isupSpEntry 11 }

isupSpTotalRemoteSAPs OBJECT-TYPE
    SYNTAX      Unsigned32
    MAX-ACCESS  read-only
    STATUS      current
    DESCRIPTION 
        "Counts the number of remote (N) SAPs that the containing 
         clProtocolMachine has communicated with.  Incremented by 1 
         every time communication with a remote (N) SAP is acheived."
    REFERENCE   
        "ITU-T Rec. X.723 (1993) | ISO/IEC 10165-5 : 1993 : 
             totalRemoteSAPs ATTRIBUTE."
    ::= { isupSpEntry 12 }

isupSpAdministrativeState OBJECT-TYPE
    SYNTAX      AdministrativeState
    MAX-ACCESS  read-create
    STATUS      current
    DESCRIPTION 
        "Provides the administrative state of the ISDN user part 
         following the AdministrativeState textual convention and ITU-T 
         Rec. X.721 | ISO/IEC 10165-2.
         
          - locked(0), the ISDN user part is administratively prohibited 
            from use; the operational state is disabled(0);
         
          - unlocked(1), the ISDN user part is administratively 
            permitted for use; the operational state is enabled(1);
         
          - shuttingDown(2), not used."
    REFERENCE   
        "ITU-T Rec. X.721 (1992) | ISO/IEC 10165-2 : 1992, 
             Attribute-ASN1Module.AdministrativeState.
         ITU-T Rec. X.283 (1997) | ISO/IEC 10733 : 1998 : 
             administrativeState ATTRIBUTE."
    DEFVAL      { locked }
    ::= { isupSpEntry 13 }

isupSpSupportedProtocols OBJECT-TYPE
    SYNTAX      BITS { none(0) }
    MAX-ACCESS  read-create
    STATUS      current
    DESCRIPTION 
        "The set of Connectionless Network protocols supported by this 
         instance of the cLNS protocol machine, expressed except where 
         otherwise indicated (for example because there are more than 
         one protocol described in a single International Standard) as 
         the registered object identifiers of the relevant International 
         Standard. The operation of a particular protocol over a 
         particular linkage is determined by the linkage 
         operationalProtocols attribute. The value of the 
         supportedProtocols attribute is determined by the 
         implementation."
    REFERENCE   
        "ITU-T Rec. X.283 (1997) | ISO/IEC 10733 : 1998 : 
             supportedProtocols ATTRIBUTE."
    ::= { isupSpEntry 14 }

isupSpOperationalSystemType OBJECT-TYPE
    SYNTAX      INTEGER { eS(0), iS(2) }
    MAX-ACCESS  read-only
    STATUS      current
    DESCRIPTION 
        "The system role in which this instance is operating. A value of 
         ES indicates that the system shall perform no forwarding 
         operations upon non-local PDUs. A value of IS indicates that 
         the system is permitted to perform forwarding operations, but 
         the decision to forward individual PDUs, or not to forward 
         them, shall be taken on the basis of the available routing 
         information.
         
         For normal ISUP operation, this value will always be eS(0)."
    REFERENCE   
        "ITU-T Rec. X.283 (1997) | ISO/IEC 10733 : 1998 : 
             operationalSystemType ATTRIBUTE."
    DEFVAL      { eS }
    ::= { isupSpEntry 15 }

isupSpActivate OBJECT-TYPE
    SYNTAX      ActionOrResult
    MAX-ACCESS  read-create
    STATUS      current
    DESCRIPTION 
        "Models a CMIP action command and result.  Writing any 
         value results in the invocation of the activation of an 
         ISUP User Part.  Reading the value provides the current 
         result of the invocation of the action."
    ::= { isupSpEntry 16 }

isupSpDeactivate OBJECT-TYPE
    SYNTAX      ActionOrResult
    MAX-ACCESS  read-create
    STATUS      current
    DESCRIPTION 
        "Models a CMIP action command and result.  Writing any 
         value results in the invocation of the deactivation of 
         the ISUP User Part.  Reading the value provides the 
         current result of the invocation of the 
         action."
    ::= { isupSpEntry 17 }

isupSpRowStatus OBJECT-TYPE
    SYNTAX      RowStatus
    MAX-ACCESS  read-create
    STATUS      current
    DESCRIPTION 
        "Provides a mechanism whereby management stations may create or 
         delete entires in this table.  Entries created by management 
         stations must survive an agent reboot.  Entries cannot be 
         deleted from this table when referenced by other tables.  
         Entries cannot be deleted while they contain subtending table 
         entries.
         
         An ISDN user part can be created by an operator or 
         automatically.
         
         If the name package is supported: a create request with a value 
         for the name attribute that is already used by another instance 
         of the same object class will be rejected.  An ISDN user part 
         can be deleted if and only if it does not contain any other 
         managed object class instances, except for contained 
         measurements (see the OPENSS7-ISUP-OM-MIB module)."
    REFERENCE   
        "STD 52, SNMPv2-TC RowStatus.
         ITU-T Rec. Q.751.1 (1997) : 
             managedSwitchingElement-mtpSignPoint NAME BINDING."
    ::= { isupSpEntry 18 }

-- ====================================================================

isupSr OBJECT IDENTIFIER
    ::= { isupTables 8 }

isupSrTable OBJECT-TYPE
    SYNTAX      SEQUENCE OF IsupSrEntry
    MAX-ACCESS  not-accessible
    STATUS      current
    DESCRIPTION 
        "This table contain conceptual rows that correspond to 
         signalling relations between two SS7 ISUP signalling points: a 
         near-end and far-end signalling point."
    ::= { isupSr 1 }

isupSrEntry OBJECT-TYPE
    SYNTAX      IsupSrEntry
    MAX-ACCESS  not-accessible
    STATUS      current
    DESCRIPTION 
        "Each entry in this table corresponds to an ISUP signaling 
         relation between two signalling points.  The near-end ISUP 
         signaling point is provided by the indices for the entry 
         (isupMsId and isupSpId).  The far-end ISUP signaling point is 
         provided by the destination signaling point code (isupSrDest).  
         An association between this signaling relation and an MTP 
         provider is made with an isupLgEntry.  That entry either 
         associates the isupSpEntry corresponding to the near-end ISUP 
         signalling point with an MTP provider (isupMtpEntry), or 
         directly associates this isupSrEntry with an MTP provider 
         (isupMtpEntry)."
    INDEX       { isupMsId, isupSpId, isupSrId }
    ::= { isupSrTable 1 }

IsupSrEntry ::= SEQUENCE {
    isupSrId                        Unsigned32,
    isupSrDest                      NetworkPointCode,
    isupSrOptions                   BITS,
    isupSrSlsAssignment             INTEGER,
    isupSrAdminState                AdministrativeState,
    isupSrOpState                   OperationalState,
    isupSrAsaProfilePointer         RowPointer,
    isupSrCongestedState            MtpCongestedState,
    isupSrCongestionLevel           MtpCongestionLevel,
    isupSrLoadsharingInformation    OCTET STRING,
    isupSrLoadsharingObject         RowPointer,
    isupSrRemoteExchangeLabel       CommonLanguageName,
    isupSrName                      SimpleNameType,
    isupSrProfile                   SimpleNameType,
    isupSrAlarmStatus               AlarmStatus,
    isupSrRowStatus                 RowStatus
}

isupSrId OBJECT-TYPE
    SYNTAX      Unsigned32
    MAX-ACCESS  not-accessible
    STATUS      current
    DESCRIPTION 
        "Provides a non-zero ordinal index into the ISUP signaling 
         relation table."
    ::= { isupSrEntry 1 }

isupSrDest OBJECT-TYPE
    SYNTAX      NetworkPointCode
    MAX-ACCESS  read-create
    STATUS      current
    DESCRIPTION 
        "Provides the network point code of the destination that 
         is associated with a signalling relation."
    REFERENCE   
        "ITU-T Rec. Q.751.1 (1997), ANSI T1.116.1 (2000), PointCode"
    DEFVAL      { "\x00\x00\x00\x00" }
    ::= { isupSrEntry 2 }

isupSrOptions OBJECT-TYPE
    SYNTAX      BITS { srCluster(0), srXferFunc(1), srSecurity(2), 
                    srAdjacent(3) }
    MAX-ACCESS  read-create
    STATUS      current
    DESCRIPTION 
        "This object indicates some additional information associated 
         with the signalling relation.  The object is set-valued and can 
         contain the following:
         
         - srCluster(0), the route set corresponds to a cluster route 
           (cluster routing is only defined by ANSI);
         
         - srXferFunc(1), the destination signalling point associatedw 
           with the route set has the transfer function;
         
         - srSecurity(2), the destination signalling point associated 
           with the route set has security screening applied;
         
         - srAdjacent(3), the destination signalling point associated 
           with the route set is an adjacent signalling point (may not 
           be combined with 'srCluster').
         
         Not all combinations of flags are legal.  Not all flag 
         combinations are applicable to all protocol variants."
    DEFVAL      { {srSecurity} }
    ::= { isupSrEntry 3 }

isupSrSlsAssignment OBJECT-TYPE
    SYNTAX      INTEGER { cIC(0), circuitNumber(1), dynamic(2) }
    MAX-ACCESS  read-create
    STATUS      current
    DESCRIPTION 
        "Specifies the form of SLS (Signaling Link Selection) assignment 
         for ISUP messages relating to the same call within the 
         signaling relation.  There are three ways of performing SLS 
         assignment as follows:
         
         - cIC(0): SLS assignment is based on the value of the circuit 
           identification code for the circuit to which the ISUP 
           messages relate;
         
         - circuitNumber(1): SLS assignment is based on the circuit 
           number for the circuit to which the ISUP messages relate; 
           and,
         
         - dynamic(2): SLS assignment is based on an algorithmic 
           approach: the last SLS assignment for the signalling relation 
           is remembered and the next SLS assignment is incremented by 
           one and masked with the SLS mask.
         
         ITU-T international specifications provide that the SLS value 
         is assigned according to cIC(0) or circuitNumber(1).  ANSI does 
         not specify the method of circuit assignment but should 
         normally be specified as dynamic(2), particularly where the SLS 
         field is 8-bits."
    DEFVAL      { cIC }
    ::= { isupSrEntry 4 }

isupSrAdminState OBJECT-TYPE
    SYNTAX      AdministrativeState
    MAX-ACCESS  read-create
    STATUS      current
    DESCRIPTION 
        "Provides the administrative state of the signalling route set 
         network element part following the AdministrativeState textual 
         convention and ITU-T Rec. X.721 | ISO/IEC 10165-2.
         
          - locked(0), the signalling route set is administratively 
            prohibited from use;
         
          - unlocked(1), the signalling route set is administratively 
            permitted for use;
         
          - shuttingDown(2), not used."
    REFERENCE   
        "ITU-T Rec. X.721 (1992) | ISO/IEC 10165-2 : 1992, 
             Attribute-ASN1Module.AdministrativeState.
         ITU-T Rec. Q.826 (02/2000), ANSI T1.116.1 (2000), 
             administrativeState attribute."
    DEFVAL      { locked }
    ::= { isupSrEntry 5 }

isupSrOpState OBJECT-TYPE
    SYNTAX      OperationalState
    MAX-ACCESS  read-create
    STATUS      current
    DESCRIPTION 
        "Provides the operational state of the signalling route set 
         network element part following the OperationalState textual 
         convention and ITU-T Rec. X.721 | ISO/IEC 10165-2.
         
         - disabled(0), the destination is inaccessible due to the 
           unavailability of all routes in the route set;
         
         - enabled(1), the destination is accessible: at least one 
           signalling route in the route set is available."
    REFERENCE   
        "ITU-T Rec. X.721 (1992) | ISO/IEC 10165-2 : 1992, 
             Attribute-ASN1Module.OperationalState.
         ITU-T Rec. X.731 (1992) | ISO/IEC 10164-2 : 1993, 
             Section 8.1.1.1.
         ITU-T Rec. Q.751.1 (1997), ANSI T1.116.1 (2000), 
             operationalState attribute."
    DEFVAL      { disabled }
    ::= { isupSrEntry 6 }

isupSrAsaProfilePointer OBJECT-TYPE
    SYNTAX      RowPointer
    MAX-ACCESS  read-create
    STATUS      current
    DESCRIPTION 
        "Provides a pointer to an alarm severity assignment profile to 
         be used for alarms generated by this signalling route set 
         network element part, or zeroDotZero."
    REFERENCE   
        "ITU-T Rec. Q.751.1 (1997), ANSI T1.116.1 (2000), 
             alarmSeverityAssignmentProfilePointer attribute."
    DEFVAL      { zeroDotZero }
    ::= { isupSrEntry 7 }

isupSrCongestedState OBJECT-TYPE
    SYNTAX      MtpCongestedState
    MAX-ACCESS  read-create
    STATUS      current
    DESCRIPTION 
        "This attribute is used to reflect route set congestion, when 
         multiple congestion levels are not used.  Its value is 
         congested(1) in case of route set congestion and 
         notCongested(0) otherwise.  Its value is changed by the managed 
         system.  Transitions to and from the congested state are 
         indicated with a qualityOfServiceAlarm.
         
         Note that a route set can be administratively locked, and still 
         congested."
    REFERENCE   
        "ITU-T Rec. Q.751.1 (1997), ANSI T1.116.1 (2000), congestedState 
             attribute."
    ::= { isupSrEntry 8 }

isupSrCongestionLevel OBJECT-TYPE
    SYNTAX      MtpCongestionLevel
    MAX-ACCESS  read-create
    STATUS      current
    DESCRIPTION 
        "This attribute is used to reflect route set congestion, when 
         multiple congestion levels are used.  Its value in case of no 
         congestion is none(0), and has the value congestionLevel1(1), 
         congestionLevel2(2) or congestionLevel(3) when congested.  Its 
         value is changed by the managed system.  Transitions to an from 
         a congestion level are indicated by a qualityOfServiceAlarm.
         
         Note that a route set can be administratively locked, and still 
         congested."
    REFERENCE   
        "ITU-T Rec. Q.751.1 (1997), ANSI T1.116.1 (2000), 
             congestionLevel attribute."
    DEFVAL      { none }
    ::= { isupSrEntry 9 }

isupSrLoadsharingInformation OBJECT-TYPE
    SYNTAX      OCTET STRING
    MAX-ACCESS  read-create
    STATUS      current
    DESCRIPTION 
        "This attribute contains specific information for target 
         specific loadsharing via the current routes working on a 
         routeset basis via the current routes.  This information can be 
         used by e.g. the referenced mtpLoadsharingObjectFor-RouteSet to 
         execute the target specific loadsharing."
    REFERENCE   
        "ITU-T Rec. Q.751.1 (1997), ANSI T1.116.1 (2000), 
             loadsharingInformationRouteSetNePart attribute."
    ::= { isupSrEntry 10 }

isupSrLoadsharingObject OBJECT-TYPE
    SYNTAX      RowPointer
    MAX-ACCESS  read-create
    STATUS      current
    DESCRIPTION 
        "This attribute is used to reference implementation dependent 
         loadsharing object class instances needed to model 
         implementation dependent mechanisms for loadsharing over 
         linksets working on a routeset basis."
    REFERENCE   
        "ITU-T Rec. Q.751.1 (1997), ANSI T1.116.1 (2000), 
             mtpLoadsharingObjectForRouteSetNePartPointer attribute."
    DEFVAL      { zeroDotZero }
    ::= { isupSrEntry 11 }

isupSrRemoteExchangeLabel OBJECT-TYPE
    SYNTAX      CommonLanguageName
    MAX-ACCESS  read-create
    STATUS      current
    DESCRIPTION 
        "This attribute specifies the remote exchange which contains the 
         mtpSignPoint with the point code equal to the 
         signRouteSetNePartId."
    REFERENCE   
        "ITU-T Rec. Q.751.1 (1997), ANSI T1.116.1 (2000), 
             remoteExchangeLabel attribute."
    ::= { isupSrEntry 12 }

isupSrName OBJECT-TYPE
    SYNTAX      SimpleNameType
    MAX-ACCESS  read-create
    STATUS      current
    DESCRIPTION 
        "Provides an optional administrative name for this signalling 
         route set.  It is typical to name signalling route sets using 
         the common language name of the managed switching element at 
         which the route terminates (e.g. EDTNAB01DS1).
         
         Identifies a signRouteSetNePart instance within the managed 
         object class; its value is unique within the signRouteSetNePart 
         object class.  In this attribute implementation or 
         administration dependent information - like used for naming 
         schemes - can be stored.  If at creation time the value of this 
         attribute given for the instance to be created already exists 
         in another signRouteNePart instance, then the creation is 
         rejected and not carried out."
    REFERENCE   
        "ITU-T Rec. Q.751.1 (1997), ANSI T1.116.1 (2000), 
             signRouteSetNePartName attribute."
    ::= { isupSrEntry 13 }

isupSrProfile OBJECT-TYPE
    SYNTAX      SimpleNameType
    MAX-ACCESS  read-create
    STATUS      current
    DESCRIPTION 
        "Provides the index into the signalling route set profile table 
         corresponding to the signalling route set profile used by this 
         signalling route set.  The profile consists of timer values for 
         timers concerned with MTP Level 3 route set proceudres."
    DEFVAL      { "" }
    ::= { isupSrEntry 14 }

isupSrAlarmStatus OBJECT-TYPE
    SYNTAX      AlarmStatus
    MAX-ACCESS  read-create
    STATUS      current
    DESCRIPTION 
        "Provides the alarm status of the MTP signalling route set 
         following the AlarmStatus textual convention and ITU-T Rec. 
         X.721 (1992) | ISO/IEC 10165-2 : 1992.
         
         - underRepair(0), set by the management station when a repair 
           action has been initiated as a result of an alarm; reset by 
           the management station when a repair action has completed;
         
         - critical(1), set by the agent when the far-end ISUP user is 
           unequipped;
         
         - major(2), set by the agent when the far-end signaling point 
           is inaccessible or congested, the far-end ISUP user is 
           inaccessible or congested; may be reset (but not set) by a 
           management station;
         
         - minor(3), set by the agent when a call establishment is 
           attempted to an unequipped circuit identification code, or a 
           circuit validation test fails;
         
         - alarmOutstanding(4), set by the agent whenever an alarm is 
           outstanding; may be cleared by a management station."
    REFERENCE   
        "ITU-T Rec. Q.751.1 (1997), ANSI T1.116.1 (2000) : alarmStatus 
             attribute.
         ITU-T Rec. X.721 (1992) | ISO/IEC 10165-2 : 1992, 
             Attribute-ASN1Module.AlarmStatus.
         ITU-T Rec. X.731 (1992) | ISO/IEC 10164-2 : 1993, 
             Section 8.1.2.1."
    ::= { isupSrEntry 15 }

isupSrRowStatus OBJECT-TYPE
    SYNTAX      RowStatus
    MAX-ACCESS  read-create
    STATUS      current
    DESCRIPTION 
        "Provides a mechanism whereby management stations may create and 
         delete entries in this table.  This object is used by a 
         management station SET operation to create a new entry in this 
         table.
         
         If the name package is supported: a create request with a value 
         for the name attribute that is already used by another instance 
         of the same object class will be rejected.  A delete request is 
         rejected, if the administrativeState of the signRouteSetNePart 
         does not equal locked."
    REFERENCE   
        "STD 58, SNMPv2-TC RowStatus.
         ITU-T Rec. Q.751.1 (1997) : mtpSignPoint-signRouteSetNePart 
             NAME BINDING."
    ::= { isupSrEntry 16 }

-- ====================================================================
-- ISUP Overflow Route Table

isupRt OBJECT IDENTIFIER
    ::= { isupTables 9 }

isupRtTable OBJECT-TYPE
    SYNTAX      SEQUENCE OF IsupRtEntry
    MAX-ACCESS  not-accessible
    STATUS      current
    DESCRIPTION 
        "This table describes a set of trunk groups for which a certain 
         algorithm is used to assign traffic to a trunk group (of the 
         traffic offered to the set).  This includes the detailed 
         information how the traffic is distributed over the elements in 
         the set.  The trunk groups referenced can be of different 
         characteristics, but shall be of the directionality one-way 
         outgoing or two-way.
         
         Three algorithms are used to assign traffic to the set of trunk 
         groups:
         
         - The sequential algorithm:  The trunk groups are ordered in a 
           list.  The sequential algorithm starts searching for an 
           available trunk group at the first element of the list.
         
         - The cyclic algorithm:  The trunk groups are also ordered in a 
           list.  The cyclic algorithm remembers the trunk group found 
           in the previous serach (for another call) and starts 
           searching for an available trunk group beginning with the 
           next element in the list.
         
         - The proportional bidding algorithm: Traffic is distributed 
           over rows according to a certain assigned percentage.  Every 
           row consists of trunk groups in an ordered list.  If a call 
           is assigned to a row, then the search for an available trunk 
           group will be done in a sequential way within the ordered 
           list.  The sum of the rows percentage shall be 100%."
    REFERENCE   
        "ITU-T Rec. Q.826 (02/2000) : cepsgComb MOC."
    ::= { isupRt 1 }

isupRtEntry OBJECT-TYPE
    SYNTAX      IsupRtEntry
    MAX-ACCESS  not-accessible
    STATUS      current
    DESCRIPTION 
        "Each row in this table is indexed by the route 
         identifier that is used to identify an instance of an 
         overflow route.  Each row contains the characteristics 
         and operaitonal status of an overflow route."
    REFERENCE   
        "ITU-T Rec. Q.826 (02/2000) : cepsgComb MOC."
    INDEX       { isupRtId }
    ::= { isupRtTable 1 }

IsupRtEntry ::= SEQUENCE {
    isupRtId                    Unsigned32,
    isupRtTrunkGroupList        TrunkGroupList,
    isupRtUsedAlgorithm         INTEGER,
    isupRtSelection             TrunkGroupSelection,
    isupRtProportionList        TrunkGroupProportions,
    isupRtPossibilitiesInList   TrunkGroupSelection,
    isupRtUserLabel             SnmpAdminString,
    isupRtProcStatus            ProceduralStatus,
    isupRtControlStatus         ControlStatus,
    isupRtAdminState            AdministrativeState,
    isupRtOperState             OperationalState,
    isupRtUsageState            UsageState,
    isupRtRowStatus             RowStatus
}

isupRtId OBJECT-TYPE
    SYNTAX      Unsigned32
    MAX-ACCESS  not-accessible
    STATUS      current
    DESCRIPTION 
        "This object provides an non-zero ordinal index into the 
         isupRtTable table used to identify an instance of an overflow 
         route."
    REFERENCE   
        "ITU-T Q.826 (02/2000) : cepsgCombId ATTRIBUTE."
    ::= { isupRtEntry 1 }

isupRtTrunkGroupList OBJECT-TYPE
    SYNTAX      TrunkGroupList
    MAX-ACCESS  read-only
    STATUS      current
    DESCRIPTION 
        "This object lists the trunk groups belonging to this overflow 
         route using the TrunkGroupList textual convention.  It is 
         automatically updated by the agent as trunk groups are added 
         and removed from the isupTgTable.  The trunk group selections 
         contained in the isupRtSelection and isupRtTgSelectionTable are 
         referenced against the ordinal positions in this list."
    REFERENCE   
        "ITU-T Q.826 (02/2000) : cepsgCombSelection ATTRIBUTE."
    ::= { isupRtEntry 2 }

isupRtUsedAlgorithm OBJECT-TYPE
    SYNTAX      INTEGER { sequential(0), cyclic(1), 
                    proportionalBidding(2) }
    MAX-ACCESS  read-create
    STATUS      current
    DESCRIPTION 
        "This attribute describes the algorithm that is used for the 
         selection of a trunk group on outgoing calls: sequential, 
         cyclic or proportional bidding.  This algorithm effects 
         overflow (as defined in ITU-T Rec. Q.12) and alternative 
         routing: that is, trunk groups may involve different near or 
         far end exchanges.
         
         - sequential(0): The trunk groups are ordered in a list.  The 
           sequential algorithm starts searching for an available trunk 
           group at the first element in the list.  The list is provided 
           by the trunk group selection (isupRtSelection).  This is a 
           common overflow method for overflowing from a one-way 
           outgoing trunk group to a two-way trunk group (to avoid 
           glare).  It is also common for alternate routing for 
           overflowing from a high usage trunk group to a lower usage 
           trunk group.
         
         - cyclic(1):  The trunk groups are also ordered in a list.  The 
           cyclic algorithm remembers the trunk group found in the 
           previous search (for another call) and starts searching for 
           an available trunk group beginning with the next element in 
           the list.  The list is provided by the trunk group selection 
           (isupRtSelection).  This is a common overflow method for 
           effectively combining a number of trunk groups into a single 
           large trunk group.
         
         - proportionalBidding(2):  Traffic is distributed over rows 
           according to a certain assigned percentage.  Every row 
           consists of trunk groups in an ordered list.  If a call is 
           assigned to a row, then the search for an available trunk 
           group will be done in a sequential way within the ordered 
           list.  The sum of the rows percentage shall be 100%.  The 
           table for a given overflow route is provided by the overflow 
           route trunk group selection table (isupRtTgSelectionTable).
         
         The default value is sequential(0)."
    REFERENCE   
        "ITU-T Rec. Q.826 (02/2000) : usedAlgorithm ATTRIBUTE.
         ITU-T Rec. Q.826 (02/2000) : ASN1TypeModule.UsedAlgorithm.
         ITU-T Rec. Q.12 : definition of overflow."
    DEFVAL      { sequential }
    ::= { isupRtEntry 3 }

isupRtSelection OBJECT-TYPE
    SYNTAX      TrunkGroupSelection
    MAX-ACCESS  read-create
    STATUS      current
    DESCRIPTION 
        "This object provides the ordered list of trunk group selections 
         for this overflow route following the TrunkGroupSelection 
         textual convetion referenced to the trunk group list 
         (isupRtTrunkGroupList).
         
         When the sequential(0) algorithm is used, the algorithm starts 
         searching for an available trunk group at the first element in 
         the list.  This is a common overflow route algorithm, where the 
         trunk groups in this list correspond to a simple overflow list 
         of one-way outgoing and two-way trunk groups.
         
         When the cyclic(1) algorithm is used, the algorithm remembers 
         the trunk group found in the previous search (for another call) 
         and starts searching for an available trunk group beginning 
         with the next element in the list, wrapping to the beginning of 
         the list if necessary.  This is a less common overflow route 
         algorithm, where multiple trunk groups are effectively joined 
         into a single trunk group.
         
         When the proportionalBidding(2) algorithm is used, this list is 
         not used and the elements in the isupRtTgSelectionTable are 
         used instead.  This object then provides access to only the 
         first ordinal trunk group selection entry in the proportional 
         bidding table.  See the isupRtTgSelectionTable for more 
         information on proportional bidding.
         
         Initially this object will be a null list (''X).  If there are 
         no trunk groups in the trunk group list, this object must 
         remain a null list (''X).
         
         If ordinal values corresponding to trunk groups in the trunk 
         group list are present in this selection list, and any of those 
         trunk groups are later deleted or moved from under the overflow  
         route through management actions, the agent shall remove the 
         trunk group from the trunk group list, remove the reference 
         from this selection list, and adjust the ordinal values in the 
         trunk group list and this selection to reflect the new 
         positions of trunk groups in the trunk group list."
    REFERENCE   
        "ITU-T Rec. Q.826 (02/2000) : cepsgCombSelection ATTRIBUTE."
    ::= { isupRtEntry 4 }

isupRtProportionList OBJECT-TYPE
    SYNTAX      TrunkGroupProportions
    MAX-ACCESS  read-create
    STATUS      current
    DESCRIPTION 
        "When the used algorithm is proportional bidding, this object 
         provides the proportions (percentages) that apply to each 
         ordinal value (row) in the isupRtTgSelectionTable, following 
         the TrunkGroupProportions textual convention.  When there 
         are no ordinal values in the isupRtTgSelectionTable, this value 
         is a null octet string.  When the used algorithm is sequential 
         or cyclic, the value of this object is undefined."
    REFERENCE   
        "ITU-T Rec. Q.826 (02/2000) : cepsgCombSelection ATTRIBUTE."
    ::= { isupRtEntry 5 }

isupRtPossibilitiesInList OBJECT-TYPE
    SYNTAX      TrunkGroupSelection
    MAX-ACCESS  read-only
    STATUS      current
    DESCRIPTION 
        "This attribute gives the set of trunk groups found in the 
         isupRtSelection.  It is automatically updated to be kept in 
         synchronization as the trunk groups are updated in the 
         isupRtSelectionTable.  This attribute is used to support 
         filtering under CMIP and for convenience under SNMP."
    REFERENCE   
        "ITU-T Rec. Q.826 (02/2000) : possibilitiesInList ATTRIBUTE."
    ::= { isupRtEntry 6 }

isupRtUserLabel OBJECT-TYPE
    SYNTAX      SnmpAdminString
    MAX-ACCESS  read-create
    STATUS      current
    DESCRIPTION 
        "This attribute assigns a user friendly name to a route 
         instance.  This attribute is defined in ITU-T M.3100.  When 
         present (not null) the agent may require that the string be 
         unique over all the rows in this table.  An attempt by a 
         management station to assign a value that is not unique over 
         the rows in this table may be refused by the agent."
    REFERENCE   
        "ITU-T Rec. M.3100 (2005) : userLabel ATTRIBUTE.
         ITU-T Rec. Q.826 (02/2000) : userLabel ATTRIBUTE."
    ::= { isupRtEntry 7 }

isupRtProcStatus OBJECT-TYPE
    SYNTAX      ProceduralStatus
    MAX-ACCESS  read-only
    STATUS      current
    DESCRIPTION 
        "Provides the procedural status of the overflow route in 
         accordance with ITU-T Rec. X.721 | ISO/IEC 10165-2 and the 
         ProceduralStatus textual convention of the OPENSS7-SMI-MIB.
         
         - initializationRequired(0): the overflow route requires 
           initialization by a management station before it can process 
           calls;
         - notInitialized(1): the overflow route is not initialized;
         - initializing(2): the overflow route is initializing but has 
           not yet completed initialization;
         - reporting(3): not used;
         - terminating(4): the overflow route is in the termination 
           phase."
    REFERENCE   
        "ITU-T Rec. X.721 (1992) | ISO/IEC 10165-2 : 1992, 
               Attribute-ASN1Module.ProceduralStatus.
         ITU-T Rec. X.731 (1992) | ISO/IEC 10164-2 : 1993, 
               Section 8.1.2.2.
         ITU-T Rec. Q.826 (02/2000) : cepsgComb.proceduralStatus."
    ::= { isupRtEntry 8 }

isupRtControlStatus OBJECT-TYPE
    SYNTAX      ControlStatus
    MAX-ACCESS  read-create
    STATUS      current
    DESCRIPTION 
        "Provides the control status of the overflow route in accordance 
         with ITU-T Rec. X.721 | ISO/IEC 10165-2 and the ControlStatus 
         textual convention of the OPENSS7-SMI-MIB.
         
         - subjectToTest(0): the overflow route is available for calls 
           but is subject to test procedures;
         - partOfServicesLocked(1): the overflow route is partially 
           unavailable to handle calls; (for example, a trunk group in 
           the overflow route is administratively locked);
         - reservedForTest(2): the overflow route is unavailable for 
           calls and is reserved for testing;
         - suspended(3): the overflow route is administratively 
           suspended; established calls might not be cleared but no call 
           processing requests will be performed until the suspension is 
           lifted."
    REFERENCE   
        "ITU-T Rec. X.721 (1992) | ISO/IEC 10165-2 : 1992, 
               Attribute-ASN1Module.ControlStatus.
         ITU-T Rec. X.731 (1992) | ISO/IEC 10164-2 : 1993, 
               Section 8.1.2.4.
         ITU-T Rec. Q.826 (02/2000) : cepsgComb.controlStatus."
    ::= { isupRtEntry 9 }

isupRtAdminState OBJECT-TYPE
    SYNTAX      AdministrativeState
    MAX-ACCESS  read-create
    STATUS      current
    DESCRIPTION 
        "Provides the administrative state of the overflow route in 
         accordance with ITU-T Rec. X.721 | ISO/IEC 10165-2 and the 
         AdministrativeState textual convention of the OPENSS7-SMI-MIB.
         
         - locked(0): the overflow route is administratively prohibited 
           from processing calls;
         - unlocked(1): the overflow route is administratively permitted 
           to process calls;
         - shuttingDown(2): the overflow route is administratively 
           permitted to process existing calls but prohibited from 
           processing new calls; once all existing calls release the 
           state will move to locked(0).
         
         This object may be set by a management station to block or 
         unblock new and existing calls from being offerred via this 
         route."
    REFERENCE   
        "ITU-T Rec. X.721 (1992) | ISO/IEC 10165-2 : 1992, 
               Attribute-ASN1Module.AdministrativeState.
         ITU-T Rec. X.731 (1992) | ISO/IEC 10164-2 : 1993, 
               Section 8.1.1.3.
         ITU-T Rec. Q.826 (02/2000) : cepsgComb.administrativeState."
    ::= { isupRtEntry 10 }

isupRtOperState OBJECT-TYPE
    SYNTAX      OperationalState
    MAX-ACCESS  read-only
    STATUS      current
    DESCRIPTION 
        "Provides the operational state of the overflow route in 
         accordance with the OperationalState textual convention of the 
         OPENSS7-SMI-MIB.
         
         - disabled(0): the overflow route is inoerpable and unable to 
           process calls;
         
         - enabled(1): the overflow route is enabled and able to process 
           calls."
    REFERENCE   
        "ITU-T Rec. X.721 (1992) | ISO/IEC 10165-2 : 1992, 
               Attribute-ASN1Module.OperationalState.
         ITU-T Rec. X.731 (1992) | ISO/IEC 10164-2 : 1993, 
               Section 8.1.1.1.
         ITU-T Rec. Q.826 (02/2000) : cepsgComb.operationalState."
    ::= { isupRtEntry 11 }

isupRtUsageState OBJECT-TYPE
    SYNTAX      UsageState
    MAX-ACCESS  read-only
    STATUS      current
    DESCRIPTION 
        "Provides the usage state of the overflow route in accordance 
         with ITU-T Rec. X.721 | ISO/IEC 10165-2 and the UsageState 
         textual convention of the OPENSS7-SMI-MIB.  It reflects the 
         current usage of the overflow route as follows:
         
         - idle(0): the overflow route is idle and no calls are 
           currently in progress or established that utilizes the 
           overflow route;
         
         - active(1): the overflow route is active, calls are currently 
           in process or established that utilized the overflow route;
         
         - busy(2): the overflow route is busy with current calls in 
           progress or established calls; either the overflow route is 
           completely exhausted, or the high water mark associated with 
           the overflow route has been reached."
    REFERENCE   
        "ITU-T Rec. X.721 (1992) | ISO/IEC 10165-2 : 1992, 
               Attribute-ASN1Module.UsageState.
         ITU-T Rec. X.731 (1992) | ISO/IEC 10164-2 : 1993, 
               Section 8.1.1.2.
         ITU-T Rec. Q.826 (02/2000) : cepsgComb.usageState."
    DEFVAL      { idle }
    ::= { isupRtEntry 12 }

isupRtRowStatus OBJECT-TYPE
    SYNTAX      RowStatus
    MAX-ACCESS  read-create
    STATUS      current
    DESCRIPTION 
        "Provides a mechanism whereby management stations may create and 
         delete entries in this table.  Rows may be created and deleted 
         by the managed system as part of system operations.
         
         Entries can only be deleted when they have no associated 
         isupTgTable entries.  That is, the isupRtTrunkGroupList must be 
         empty before an entry can be deleted."
    REFERENCE   
        "STD 58, SNMPv2-TC RowStatus.
         ITU-T Rec. Q.826 (2000) : cepsgComb-managedElement NB."
    ::= { isupRtEntry 13 }

-- ==========================================================================
-- ISUP Trunk Group Selection Table

isupRtTgSelection OBJECT IDENTIFIER
    ::= { isupTables 10 }

isupRtTgSelectionTable OBJECT-TYPE
    SYNTAX      SEQUENCE OF IsupRtTgSelectionEntry
    MAX-ACCESS  not-accessible
    STATUS      current
    DESCRIPTION 
        "This is the ISUP trunk group selection table.  This table 
         provides an ordinal list of trunk group selection entries for 
         each overflow route that uses the proportional bidding 
         algorithm.  Each entry in the ordinal list for the overflow 
         route represents a sequential list of trunk groups that 
         correspond to the proportion specified as a percentage."
    ::= { isupRtTgSelection 1 }

isupRtTgSelectionEntry OBJECT-TYPE
    SYNTAX      IsupRtTgSelectionEntry
    MAX-ACCESS  not-accessible
    STATUS      current
    DESCRIPTION 
        "Provides an entry in the ISUP trunk group selection table."
    INDEX       { isupRtId, isupRtTgSelectionIndex }
    ::= { isupRtTgSelectionTable 1 }

IsupRtTgSelectionEntry ::= SEQUENCE {
    isupRtTgSelectionIndex          Unsigned32,
    isupRtTgSelectionOrdinal        Unsigned32,
    isupRtTgSelectionProportion     Unsigned32,
    isupRtTgSelectionList           TrunkGroupSelection,
    isupRtTgSelectionRowStatus      RowStatus
}

isupRtTgSelectionIndex OBJECT-TYPE
    SYNTAX      Unsigned32
    MAX-ACCESS  not-accessible
    STATUS      current
    DESCRIPTION 
        "Provides an index into the trunk group selection table for an 
         indexed overflow route.  The value of this index is not 
         significant.  Ordinal values of the entries that correspond to 
         a given overflow route are, instead, given by the 
         isupRtTgSelectionOrdinal object in the same conceptual row."
    ::= { isupRtTgSelectionEntry 1 }

isupRtTgSelectionOrdinal OBJECT-TYPE
    SYNTAX      Unsigned32
    MAX-ACCESS  read-only
    STATUS      current
    DESCRIPTION 
        "This object's value provides the current ordinal position 
         (0..255) of the trunk group list associated with this 
         conceptual row for the currently indexed overflow route.  This 
         ordinal position in the ISUP overflow route protpotion list 
         object, isupRtProportionList, for the indexed overflow route 
         gives the percentage allocation for the trunk group selection 
         list sepecified by the value of the ISUP overflow route trunk 
         group selection list object, isupRtTgSelectionList, in this 
         row.  The percentage value is also reflected (read-only) in the 
         ISUP overflow route trunk group selection proportion object, 
         isupRtTgSelectionProportion.  As conceptual rows are added and 
         deleted from this table, the values of the remaining ordinals 
         will be adjusted by the agent to reflect the new ordering.  
         Elements in the ISUP overflow route proportion list, 
         isupRtProportionList, will also be changed by the agent to 
         reflect the new sequence."
    ::= { isupRtTgSelectionEntry 2 }

isupRtTgSelectionProportion OBJECT-TYPE
    SYNTAX      Unsigned32 (0..100)
    UNITS       "%"
    MAX-ACCESS  read-only
    STATUS      current
    DESCRIPTION 
        "Specifies the percentage distribution of the proportional 
         bidding algorithm that is to be assigned to the trunk group 
         selection list for this conceptual row.  This is a read-only 
         object and is provided for the convenience of the management 
         station.  The value reflected here can be changed by management 
         stations by altering the isupRtProportionList object in the 
         isupRtTable."
    ::= { isupRtTgSelectionEntry 3 }

isupRtTgSelectionList OBJECT-TYPE
    SYNTAX      TrunkGroupSelection
    MAX-ACCESS  read-create
    STATUS      current
    DESCRIPTION 
        "Specifies a list of trunk group selections that correspond to 
         this conceptual row in the table.  The selections are 
         associated with the percentage distribution provided in the 
         isupRtTgSelectionProportion object in the same conceptual row 
         as an instance of this object.  The TrunkGroupSelection textual 
         convention is used to specify a sequence or ordinal values from 
         the isupRtTrunkGroupList.  When trunk groups are deleted from 
         an overflow route, the ordinal value in the 
         isupRtTrunkGroupList are adjusted by the agent, and the ordinal 
         values in the corresponding conceptual rows of this table for 
         this object are also adjusted by the agent.  Note that this 
         object can be a null octet string."
    ::= { isupRtTgSelectionEntry 4 }

isupRtTgSelectionRowStatus OBJECT-TYPE
    SYNTAX      RowStatus
    MAX-ACCESS  read-create
    STATUS      current
    DESCRIPTION 
        "Provides a mechanism whereby management stations may create or 
         delete entries in this table.  Rows may also be created and 
         deleted by the managed system as part of system operations.
         
         Note that entries in this table are only visible for overflow 
         routes with a used algorithm of proportional bidding.  When the 
         overflow route algorithm is changed from proportional bidding, 
         the entries for the overflow route will vanish from this table.  
         However, if the used algorithm is changed back to proportional 
         bidding, the agent may restore the previous entries to this 
         table, with any necessary corrections in ordinal values and 
         positions effected."
    REFERENCE   
        "STD 58, SNMPv2-TC RowStatus."
    ::= { isupRtTgSelectionEntry 5 }

-- ==========================================================================
-- ISUP Trunk Group Table

isupTg OBJECT IDENTIFIER
    ::= { isupTables 11 }

isupTgTable OBJECT-TYPE
    SYNTAX      SEQUENCE OF IsupTgEntry
    MAX-ACCESS  not-accessible
    STATUS      current
    DESCRIPTION 
        "A set of circuit end points that directly interconnects one 
         exchange with another, having common values for the attributes 
         listed in this package. Note that the term exchange includes 
         PBX where applicable.
         
         See clause 6.7. This OC represents a set of circuit end points 
         with similar characteristics. A circuit end point subgroup can 
         be of type one-way incoming, one-way outgoing, or two-way. For 
         type two-way, conditional packages incomingCepsgPackage and 
         outgoingCepsgPackage have both to be instantiated"
    REFERENCE   
        "ITU-T Rec. Q.826 (02/2000) : cepsg MOC"
    ::= { isupTg 1 }

isupTgEntry OBJECT-TYPE
    SYNTAX      IsupTgEntry
    MAX-ACCESS  not-accessible
    STATUS      current
    DESCRIPTION 
        "Each entry in this table is indexed by a trunk group 
         identifier.  Each row contains characteristics and 
         operational status of one trunk group."
    REFERENCE   
        "ITU-T Rec. Q.826 (02/2000) : cepsg MOC"
    INDEX       { isupTgId }
    ::= { isupTgTable 1 }

IsupTgEntry ::= SEQUENCE {
    -- inherited from ITU-T Rec. M.3100:circuitEndPointSubgroup
    isupTgId                                Unsigned32,
    isupTgNumberOfCircuits                  Unsigned32,
    isupTgLabelOfFarEndExchange             CommonLanguageName,
    isupTgSignallingCapabilities            SignallingCapabilities,
    isupTgInformationTransferCapabilities   InformationTransferCapabilities,
    isupTgCircuitDirectionality             CircuitDirectionality,
    isupTgTransmissionCharacteristics       TransmissionCharacteristics,
    isupTgUserLabel                         SnmpAdminString,
    -- defined in ITU-T Rec. Q.826:cepsg
    isupTgAdminState                        AdministrativeState,
    isupTgAssocSignRouteSetNePart           Unsigned32,
    isupTgBoundaryCrossing                  INTEGER, -- national(0), international(1)
-- incomingCepsgPackage
--      isupTgPrefixDigits
--          DigitString,
-- outgoingCepsgPackage
    isupTgSearchMethod                      INTEGER,
-- originForRebuildingPackage
--      isupTgOriginForRebuilding
--          SimpleNameType,
-- originForAnalysisPackage
--      isupTgOriginForAnalysis
--          SimpleNameType,
-- originForRoutingPackage
--      isupTgOriginForRouting
--          SimpleNameType,
-- originForPreparationPackage
--      isupTgOriginForPreparation
--          SimpleNameType,
-- termForPreparationPackage
--      isupTgTermForPreparation
--          SimpleNameType,
-- specificSignSystemPackage
--      isupTgLanguageDigitProc
--          SimpleNameType,
-- twowayCepsgPackage
    isupTgPrefTrafficRedirect               INTEGER,
-- carrierPackage
    isupTgSuppressOwnCac                    TruthValue,
    -- The following are for ANSI T1.113/2000 support
    isupTgCarrierType                       INTEGER,
    isupTgDoubleSeizureControl              INTEGER,
    isupTgAlarmCarrier                      INTEGER,
    isupTgContCheck                         ContinuityCheck,
    isupTgContCheckRatio                    Unsigned32,
    --
    isupTgPg                                Unsigned32,
    isupTgStandbyStatus                     StandbyStatus,
    isupTgAlarmStatus                       AlarmStatus,
    isupTgRowStatus                         RowStatus
}

isupTgId OBJECT-TYPE
    SYNTAX      Unsigned32
    MAX-ACCESS  not-accessible
    STATUS      current
    DESCRIPTION 
        "Provides a non-zero ordinal index into the overflow 
         route table."
    REFERENCE   
        "ITU-T Rec. M.3100 (2005) : circuitEndPointSubgroupId ATTRIBUTE."
    ::= { isupTgEntry 1 }

isupTgNumberOfCircuits OBJECT-TYPE
    SYNTAX      Unsigned32
    MAX-ACCESS  read-only
    STATUS      current
    DESCRIPTION 
        "Specifies the number of circuits in the trunk group to which 
         this conceptual row corresponds.  This number changes as 
         management stations add or delete circuits from this trunk 
         group."
    REFERENCE   
        "ITU-T Rec. M.3100 (2005) : numberOfCircuits ATTRIBUTE."
    ::= { isupTgEntry 2 }

isupTgLabelOfFarEndExchange OBJECT-TYPE
    SYNTAX      CommonLanguageName
    MAX-ACCESS  read-create
    STATUS      current
    DESCRIPTION 
        "Provides a name to the far end exchange terminating this trunk 
         group using the CommonLanguageName textual convention."
    REFERENCE   
        "ITU-T Rec. M.3100 (2005) : labelOfFarEndExchange ATTRIBUTE."
    ::= { isupTgEntry 3 }

isupTgSignallingCapabilities OBJECT-TYPE
    SYNTAX      SignallingCapabilities
    MAX-ACCESS  read-only
    STATUS      current
    DESCRIPTION 
        "Specifies the signalling types supported by this trunk group.  
         One of the following values is assigned by the agent:
         
         - isup(0), ISUP signalling supported;
         - isup92(1), ISUP (1992) signalling supported;
         - itu-tNo5(2), ITU R5 signalling supported (not used);
         - r2(3), ITU R2 signalling supported (not used);
         - itu-tNo6(4), ITU R6 signalling supported (not used);
         - tup(5), TUP signalling supported (not used).
         
         For ISUP, the agent will always return either isup(0) or 
         isup92(1)."
    REFERENCE   
        "ITU-T Rec. M.3100 (2005) : signallingCapabilities ATTRIBUTE."
    ::= { isupTgEntry 4 }

isupTgInformationTransferCapabilities OBJECT-TYPE
    SYNTAX      InformationTransferCapabilities
    MAX-ACCESS  read-create
    STATUS      current
    DESCRIPTION 
        "Indicates the information transfer capabilities of the trunks 
         in the trunk group.  A higher ordinal value indicates that all 
         lower ordinal values are also supported.
         
         - speech(0), speech;
         - audio3pt1(1), 3.1 kHz audio;
         - audio7(2), 7 kHz audio;
         - audioComb(3), audio;
         - digitalRestricted56(4), 56 kbps restricted digial 
           information;
         - digitalUnrestricted64(5), 64 kbps unrestricted digital 
           information.
         
         The default value is 64 kbps unrestricted digital information."
    REFERENCE   
        "ITU-T Rec. M.3100 (2005) : informationTransferCapabilities ATTRIBUTE."
    DEFVAL      { digitalUnrestricted64 }
    ::= { isupTgEntry 5 }

isupTgCircuitDirectionality OBJECT-TYPE
    SYNTAX      CircuitDirectionality
    MAX-ACCESS  read-create
    STATUS      current
    DESCRIPTION 
        "Specifies the directionality of the trunks in the trunk 
         group.  The directionality can be one of the following:
         
         - onewayOut(0), one-way outgoing;
         - onewayIn(1), one-way incoming;
         - twoway(2), two-way.
         
         The default is twoway(2)."
    REFERENCE   
        "ITU-T Rec. M.3100 (2005) : circuitDirectionality ATTRIBUTE."
    DEFVAL      { twoway }
    ::= { isupTgEntry 6 }

isupTgTransmissionCharacteristics OBJECT-TYPE
    SYNTAX      TransmissionCharacteristics
    MAX-ACCESS  read-create
    STATUS      current
    DESCRIPTION 
        "This object is set-valued and specifies the different 
         transmission characteristics such as satellite, echo control 
         supported or not supported by the trunk group. The bit 
         positions are set to indicate if a particular characteristic is 
         supported.  Members of the set include the following:
         
         - satellite(0), indicates that a satellite is included in 
           the transmission path;
         - dCME(1), indicates that digital circuit multiplier equipment 
           is included in the transmission path;
         - echoControl(2), indicates that the circuit is capable of echo 
           control.
         
         The default is the empty set."
    REFERENCE   
        "ITU-T Rec. M.3100 (2005) : transmissionCharacteristics ATTRIBUTE."
    ::= { isupTgEntry 7 }

isupTgUserLabel OBJECT-TYPE
    SYNTAX      SnmpAdminString
    MAX-ACCESS  read-create
    STATUS      current
    DESCRIPTION 
        "Provides an administrative label for the trunk group."
    REFERENCE   
        "ITU-T Rec. M.3100 (2005) : userLabel ATTRIBUTE."
    ::= { isupTgEntry 8 }

isupTgAdminState OBJECT-TYPE
    SYNTAX      AdministrativeState
    MAX-ACCESS  read-create
    STATUS      current
    DESCRIPTION 
        "This attribute indicates whether the trunk group is 
         administratively permitted to be offered traffic (value 
         `unlocked') or not (value `locked').  When moved to the locked 
         state calls are not automatically cleared.  Note that this 
         state does not control traffic originating on trunks contained 
         in this trunk group.  Only the locked and unlocked values are 
         supported (i.e. shutting down is not a valid state).
         
         - locked(0), the trunk group is administratively prohibited 
           from sending traffic to trunks in this trunk group;
         
         - unlocked(1), the trunk group is administratively permitted to 
           send traffic to trunks in this trunk group;
         
         - shuttingDown(2), not used.
         
         Trunk groups are created, by default, in the locked(0) state."
    REFERENCE   
        "ITU-T Rec. Q.826 (02/2000) : cepsg.administrativeState
         ITU-T Rec. X.721 | ISO/IEC 10165-2 : 1992 : administrativeState"
    DEFVAL      { locked }
    ::= { isupTgEntry 9 }

isupTgAssocSignRouteSetNePart OBJECT-TYPE
    SYNTAX      Unsigned32
    MAX-ACCESS  read-create
    STATUS      current
    DESCRIPTION 
        "The value of this column is an index into the ISUP signalling 
         relation table (isupSrTable) that identifies the SS7 signalling 
         relation between two exchanges that will be used for signalling 
         with respect to a trunk in the trunk group.  The conceptual row 
         in the isupSrTable associated with the index must exist.
         
         This attribute references a signRouteSetNePart instance from 
         ITU-T Q.751.1/ANSI T1.116.1 that represents the signalling 
         point of the adjacent exchange connected to the trunk group.  
         The attribute references no object instance (default value) for 
         non-SS7 procedures."
    REFERENCE   
        "ITU-T Rec. Q.826 (02/2000) : assocSignRouteSetNePart ATTRIBUTE.
         ITU-T Rec. Q.751.1 : signRouteSetNePart MOC."
    ::= { isupTgEntry 10 }

isupTgBoundaryCrossing OBJECT-TYPE
    SYNTAX      INTEGER { national(0), international(1) }
    MAX-ACCESS  read-create
    STATUS      current
    DESCRIPTION 
        "This attribute indicates whether the trunk group contains only 
         trunks terminating circuits which cross international or 
         organizational boundaries.
         
         - national(0), the trunks cross organizational (national) 
           boundaries;
         - international(1), the trunks cross international boundaries.
         
         The default value is `national(0)'."
    REFERENCE   
        "ITU-T Rec. Q.826 (02/2000) : boundaryCrossing ATTRIBUTE."
    DEFVAL      { national }
    ::= { isupTgEntry 11 }

-- isupTgPrefixDigits OBJECT-TYPE
--     SYNTAX      DigitString
--     MAX-ACCESS  read-create
--     STATUS      current
--     DESCRIPTION 
--      "This attribute defines the digit string that has to be inserted 
--       in front of the destination code arriving at the exchange.  An 
--       empty digit string, which is the default value, means that no 
--       digits have to be inserted.  The attribute is only applicable 
--       for trunk groups that have directionality incoming or two-way."
--     REFERENCE   
--      "ITU-T Rec. Q.826 (02/2000) : prefixDigits ATTRIBUTE."
--     ::= { isupTgEntry xxx }

isupTgSearchMethod OBJECT-TYPE
    SYNTAX      INTEGER { fifoEvenElseLifoOdd(0), fifoOddElseLifoEven(1), 
                    fifoEvenGrpElseLifoOddGrp(2), 
                    fifoOddGrpElseLifoEvenGrp(3), fifo(4), 
                    forwardSequential(5), backwardSequential(6), 
                    forwardOddElseBackwardEven(7), 
                    forwardEvenElseBackwardOdd(8), forwardCyclic(9), 
                    backwardCyclic(10), random(11), lifo(12) }
    MAX-ACCESS  read-create
    STATUS      current
    DESCRIPTION 
        "This attribute is applicable if the trunk group has 
         directionality one-way outgoing or two-way.  This attribute 
         describes the method to select idle circuits within a trunk 
         group.  The following algorithms are defined for that purpose:
         
         - fifoEvenElseLifoOdd(0): priority for idle list with even CIC.  
           The idle circuits are distributed in two lists.  One list 
           contains only idle circuits with even CICs, the other list 
           contains only idle circuits with odd CICs.  The circuits of 
           the even CIC list are first choice, the circuits of the odd 
           CIC list are selected if the even CIC list is empty.  The 
           FIFO (LRU) method is used for even CIC list, the LIFO (MRU) 
           method is used for the odd CIC list.
         
         - fifoOddElseLifoEven(1): priority for idle list with odd CIC.  
           Same as fifoEvenElseLifoOdd(0), except the roles of the Even 
           and Odd lists are reversed.
           
         - fifoEvenGrpElseLifoOddGrp(2): priority for idle list with 
           even group CIC.  The idle circuits are distributed in two 
           lists.  One list contains only idle circuits with an even 
           value of the integer part of the expression CIC divided by 
           16, the other list contains only idle circuits with an odd 
           value for the integer part of the express CIC divided by 16.  
           The circuits of the even group CIC list are first choice, the 
           circuits of the odd group CIC list are selected if the even 
           group CIC list is empty.  The FIFO (LRU) method is used for 
           the even group CIC list, the LIFO (MRU) method is used for 
           the even group CIC list.
           
         - fifoOddGrpElseLifoEvenGrp(3): priority for idle list with odd 
           group CIC.  Same as fifoEvenGrpElseLifoOddGrp(2), except the 
           roles of the Even and Odd lists are reversed.
           
         - fifo(4): FIFO (LRU) method for idle list.  This algorithm 
           uses only one list for idle circuits.  The FIFO (LRU) method 
           is used to select the circuits.
           
         - forwardSequential(5): idle circuit with lowest CIC.  This 
           algorithm selects the idle circuit with the lowest 
           circuit/CIC number.
           
         - backwardSequential(6): idle circuit with highest CIC.  This 
           algorithm selects the idle circuit with the highest 
           circuit/CIC number.
           
         - forwardOddElseBackwardEven(7): lowest odd CIC or highest even 
           CIC.  This algorithm selects the idle circuit with the lowest 
           odd circuit/CIC number.  If no idle circuit with an odd 
           circuit/CIC number is available, it selects the idle circuit 
           with the highest even circuit/CIC number.
         
         - forwardEvenElseBackwardOdd(8): lowest even CIC or highest odd 
           CIC.  Same as search method, forwardOddElseBackwardEven(7), 
           except the roles of even and odd circuits are reversed.
         
         - forwardCyclic(9): cyclic search ascending order of CICs.  
           This algorithm selects the idle circuit with the lowest 
           circuit/CIC number that is larger than the circuit/CIC number 
           of the previously selected circuit.  If no such idle circuit 
           exists, it selects the idle circuit/CIC with the lowest 
           circuit/CIC number that is less than the circuit/CIC number 
           of the previously selected circuit.
         
         - backwardCyclic(10): cyclic search descending order of CICs.  
           This algorithm selects the idle circuit with the highest 
           circuit/CIC number that is less than the circuit/CIC number 
           of the previously selected circuit.  If no such idle circuit 
           exists, it selects the idle circuit/CIC with the highest 
           circuit/CIC number that is larger than the circuit/CIC number 
           of the previously selected circuit.
         
         - random(11): random idle circuit.  This algorithm selects an 
           idle circuit at random.
         
         - lifo(12): LIFO (MRU) method for idle list.  This algorithm 
           uses only one list for idle circuits.  The LIFO (MRU) method 
           is used to select the circuits.
         
         Not all search methods are necessarily supported by all 
         implementations.  Some search methods are more applicable to 
         analog trunks; others for digital trunks.  Complementary search 
         methods should be used at either end of a two-way trunk to 
         reduce glare."
    REFERENCE   
        "ITU-T Rec. Q.826 (02/2000) : searchMethod ATTRIBUTE."
    ::= { isupTgEntry 12 }

isupTgPrefTrafficRedirect OBJECT-TYPE
    SYNTAX      INTEGER { incoming(1), outgoing(2), 
                    outgoingFirstChoice(3) }
    MAX-ACCESS  read-create
    STATUS      current
    DESCRIPTION 
        "This attribute specifies, for trunk groups with directionality 
         two-way, the preferred traffic direction in case of seizure 
         conflicts.  If two exchanges at the end of a trunk group try to 
         seize the same circuit, then this attribute determines how to 
         resolve the conflict.
         
         - incoming(1): The incoming seizure is preferred for this trunk 
           group (this is equivalent to 'none' for ANSI);
         
         - outgoing(2): The outgoing seizure is preferred for this trunk 
           group (this is equivalent to 'all' for ANSI);
         
         - outgoingFirstChoiceList(3): the outgoing seizure is preferred 
           for this trunk group, if the seizure is performed on a 
           circuit of the first choice list.  Otherwise the incoming 
           seizure is preferred.  This value can only be used if the 
           attribute isupTgSearchMethod indicates an algorithm that uses 
           a first choice list.  (This is equivalent to ANSI 'odd' or 
           'even' method when the primary list corresponds to odd or 
           even CICs.
           
         The default value for one-way incoming trunks is incoming(1); 
         for one-way outgoing trunks is outgoing(2); and for two-way 
         trunks is outgoingFirstChoiceList(3)."
    REFERENCE   
        "ITU-T Rec. Q.826 (02/2000) : prefTrafficRedirect ATTRIBUTE."
    ::= { isupTgEntry 13 }

isupTgSuppressOwnCac OBJECT-TYPE
    SYNTAX      TruthValue
    MAX-ACCESS  read-create
    STATUS      current
    DESCRIPTION 
        "This attribute describes whether the own CAC (carrier access 
         code) shall be suppressed, i.e. whether the TNS parameter will 
         be suppressed and/or whether CAC will be taken out of digit 
         string.  This attribute is applicable if the possibility to 
         administer suppression of own carrier codes has to be provided 
         and if the trunk group has directionality one-way incoming 
         or two-way."
    REFERENCE   
        "ITU-T Rec. Q.826 (02/2000) : suppressOwnCac ATTRIBUTE."
    ::= { isupTgEntry 14 }

isupTgCarrierType OBJECT-TYPE
    SYNTAX      INTEGER { unknown(0), analog(1), digital(2), mixed(3) }
    MAX-ACCESS  read-create
    STATUS      current
    DESCRIPTION 
        "Specifies the carrier type used on trunks in the trunk group.  
         The carrier type can be one of the following:
         
         - unknown(0), the carrier type is unknown or unspecified;
         - analog(1), the carrier is an analog carrier;
         - digital(2), the carrier is a digital carrier;
         - mixed(3), the carrier is a mixture of analog and digital 
           carriers.
         
          The default is digital(2)."
    REFERENCE   
        "ITU-T Rec. Q.826 (02/2000) : carrierType ATTRIBUTE."
    DEFVAL      { digital }
    ::= { isupTgEntry 15 }

isupTgDoubleSeizureControl OBJECT-TYPE
    SYNTAX      INTEGER { none(0), odd(1), even(2), all(3) }
    MAX-ACCESS  read-only
    STATUS      current
    DESCRIPTION 
        "
         - none(0), the near exchange controls on no dual seizures and 
           yeilds to all incoming seizures.  This value is returned when 
           isupTgPrefTrafficRedirect is incoming(1).
         
         - odd(1), the near exchange controls on dual seizures on CICs 
           that are odd and yeilds to incoming seizures on CICs that are 
           even.  This value is returned when isupTgPrefTrafficRedirect 
           is outgoingFirstChoiceList(3) and isupTgSearchMethod is 
           fifoEvenElseLifoOdd(0), fifoEvenGrpElseLifoOddGrp(2), or 
           forwardEvenElseBackwardOdd(8).
         
         - even(2), the near exchange controls on dual seizures on CICs 
           that are even and yeilds to incoming seizures on CICs that 
           are odd.  This value is returned when 
           isupTgPrefTrafficRedirect is outgoingFirstChoiceList(3) and 
           isupTgSearchMethod is fifoOddElseLifoEven(1), 
           fifoOddGrpElseLifoEvenGrp(3) or 
           forwardOddElseBackwardEven(7).
         
         - all(3), the near exchange controls on all dual seizures and 
           yeilds to no incoming seizures.  This value is returned when 
           isupTgPrefTrafficRedirect is outgoing(2)."
    ::= { isupTgEntry 16 }

isupTgAlarmCarrier OBJECT-TYPE
    SYNTAX      INTEGER { unknown(0), hardware(1), 
                    softwareWithoutRelease(2), 
                    softwareImmediateRelease(3) }
    MAX-ACCESS  read-create
    STATUS      current
    DESCRIPTION 
        "Specifies the carrier group alarm.  The value can be one of the 
         following:
         
         - unknown(0): the source of the carrier group alarm is unknown;
         
         - hardware(1): the source of the carrier group alarm is an 
           alarm channel associated with local and remote facility 
           groups;
         
         - softwareWithoutRelease(2): the source of the carrier group 
           alarm is software synthesized and when failure is detected, 
           circuits are blocked without releasing active calls;
         
         - softwareImmediateRelease(3): the source of the carrier group 
           alarm is software synthesized and when failure is detected, 
           circuits are blocked and active calls are immediately 
           released.
         
         When circuit groups are passed through digital multiplex 
         or cross connect equipment withou intermediate carrier groups, 
         hardware carrier alarms are sufficient.  However, when circuit 
         groups pass through digital multiplex and cross-connect 
         equipment where intermediate facility groups exist without 
         transparent passing of alarms to either the near or far end 
         facility groups, software carrier alarms are required.  An 
         example of the former is one stage of transmuxing or 
         aggregation.  An example of the later is two or more stages of 
         transmuxing or aggregation.
         
         Note that setting of software carrier group alarm value, 
         softwareWithoutRelease(2) or softwareImmediateRelease(3), does 
         not preclude the ISUP from issuing blocking messages that are 
         hardware related (i.e. that derive from local facility group 
         alarms).  Also, setting of software carrier group alarm values 
         have no effect unless continuity checks are also performed on 
         the trunk group on either a statistical or per-call basis.
         
         Software carrier group alarm is not supported by ITU-T Rec. 
         Q.674, but is specified in ANSI T1.113.4/2000 Annex C.  As some 
         protocol variants do not support other than the `hardware(1)' 
         setting, the default value is always `hardware(1)'.  Some 
         managed systems may refuse to set this object to a value other 
         than hardware(1)."
    REFERENCE   
        "ANSI T1.113.3/2000 Circuit Group Characteristics Indicator
         ANSI T1.113.4/2000 Annex C"
    ::= { isupTgEntry 17 }

isupTgContCheck OBJECT-TYPE
    SYNTAX      ContinuityCheck
    MAX-ACCESS  read-create
    STATUS      current
    DESCRIPTION 
        "Specifies the basis under which continuity checks are 
         performed for outgoing calls on the overflow route.
         
         - unknown(0), the basis for continuity checks is 
           unknown or unspecified;
         - none(1), no continuity checks are performed on 
           outgoing calls for this overflow route;
         - statistical(2), continuity checks are performed on 
           a statistical basis (proportional) on outgoing calls; 
           and,
         - perCall(3), continuity checks are performed per-call 
           on outgoing calls."
    ::= { isupTgEntry 18 }

isupTgContCheckRatio OBJECT-TYPE
    SYNTAX      Unsigned32 (0..1000)
    MAX-ACCESS  read-create
    STATUS      current
    DESCRIPTION 
        "Specifies the number of calls for which continuity test 
         procedures apply to at least one call.  When isupTgContCheck is 
         unknown(0) or none(1), the value returned will be zero (0).  
         When isupTgContCheck is perCall(3), the value returned will be 
         one (1).  When isupTgContCheck is statistical(2), the value 
         returned will be in the range (2..1000).  For statistical 
         continuity checks, the default value is 10 (1 in 10 calls 
         subject to continuity checks).
         
         Note that this value is only defined when the trunk group is 
         either one-way outgoing or two-way.  Otherwise, the value 
         returned shall be zero (0)."
    ::= { isupTgEntry 19 }

isupTgPg OBJECT-TYPE
    SYNTAX      Unsigned32
    MAX-ACCESS  read-only
    STATUS      current
    DESCRIPTION 
        "Indicates the protect group corresponding to this trunk group 
         as an index into the isupPgTable of the protection group that 
         is protecting this trunk group.  The value is the value of the 
         isupPgId that indexes a specific protection group within the 
         isupPgTable.  When there is no protection group associated with 
         the trunk group, this value is zero (0).
         
         Note that the protection group for a trunk group must be the 
         same as the protection group of circuit group to which any of 
         its trunks belong."
    ::= { isupTgEntry 20 }

isupTgStandbyStatus OBJECT-TYPE
    SYNTAX      StandbyStatus
    MAX-ACCESS  read-only
    STATUS      current
    DESCRIPTION 
        "Provides the standby status of the trunk group in accordance 
         with ITU-T Rec. X.721 | ISO/IEC 10165-2 and the StandbyStatus 
         textual convension of the OPENSS7-SMI-MIB.  The standby status 
         can have one of the following values:
         
         - hotStandby(0), the trunk group is not providing service but 
           is in synchronism with another resource providing service 
           which this resource is protecting;
         
         - coldStandby(1), the trunk group is not providing service, yet 
           is initialized and another resources is providing service 
           which this resource is protecting;
         
         - providingService(2), the trunk group is providing service.
         
         Details of the status of protected and protecting resources are 
         provided in the protection group object associated with this 
         trunk group (see isupTgPg)."
    REFERENCE   
        "ITU-T Rec. X.721 (1992) | ISO/IEC 10165-2 : 1992, 
               Attribute-ASN1Module.StandbyStatus.
         ITU-T Rec. X.731 (1992) | ISO/IEC 10164-2 : 1993, 
               Section 8.1.2.5."
    ::= { isupTgEntry 21 }

isupTgAlarmStatus OBJECT-TYPE
    SYNTAX      AlarmStatus
    MAX-ACCESS  read-create
    STATUS      current
    DESCRIPTION 
        "Provides the alarm status of the trunk group using the 
         AlarmStatus textual convention of the OPENSS7-SMI-MIB module 
         and ITU-T Rec. X.721 (1992) | ISO/IEC 10165-2.
         
         - underRepair(0), set by the management station when a repair 
           action has been initiated as a result of an alarm; reset by 
           the management station when a repair action has completed;
         
         - critical(1), set by the agent when all available trunks in 
           the group are in use, no available idle trunks exist, and 
           there is no overflow route for the trunk group for a given 
           call; may be cleared by a management station;
         
         - major(2), set by the agent when the high water mark for the 
           trunk group has been exceeded and no overflow route exists 
           for a given call, or when there is no available idle trunk 
           and either no overflow route exists, or the overflow route is 
           an alternate route; may be cleared by a management station; 
           the high water mark can be set using the OPENSS7-ISUP-OM-MIB 
           module;
         
         - minor(3), set by the agent when trunks within the trunk group 
           become unavailable for use; and, may be cleared by a 
           management station;
         
         - alarmOutstanding(4), set by the agent whenever an alarm is 
           outstanding; may be cleared by a management station.
         
         Alarms generated for trunk groups are primarily quality of 
         service alarms.  Critical alarms occur when all available trunk 
         in the trunk group are in use, no available idle trunks 
         exist, and there is no overflow route for the trunk group for 
         a call.  Major alarms occur when the high water mark for the 
         trunk group has been exceeded and no overflow route exists for 
         the trunk group for a call.  Minor alarms occur when there are 
         trunks within the trunk group that are unavailable."
    ::= { isupTgEntry 22 }

isupTgRowStatus OBJECT-TYPE
    SYNTAX      RowStatus
    MAX-ACCESS  read-create
    STATUS      current
    DESCRIPTION 
        "Provides a mechanism whereby management stations may create and 
         delete entries in this table.  Rows may also be created and 
         deleted by the managed system as part of system operations.
         
         Entries may be deleted when they have no associated isupCtTable 
         entries.  That is, where there does not exist an isupCtTable 
         entry with a value of isupCtTg corresponding to the index of 
         the row to be deleted.
         
         Entries may also be deleted when they have associated 
         isupCtTable entries.  That is, any isupCtTable entry with a 
         value of isupCtTg corresponding to the index of the row to be 
         deleted will also be deleted from the isupCtTable, or the 
         isupCtTg object will be driven to zero (0)."
    REFERENCE   
        "STD 58, SNMPv2-TC RowStatus.
         ITU-T Rec. Q.826 (2000) : cepsg-managedElement-DelCep NB.
         ITU-T Rec. Q.826 (2000) : cepsg-managedElement-NoDelCep NB."
    ::= { isupTgEntry 23 }

-- ==========================================================================
-- ISUP Circuit Group Table

isupCg OBJECT IDENTIFIER
    ::= { isupTables 12 }

isupCgTable OBJECT-TYPE
    SYNTAX      SEQUENCE OF IsupCgEntry
    MAX-ACCESS  not-accessible
    STATUS      current
    DESCRIPTION 
        "
         
         There are several mechanisms for assigning the signalling link 
         selection value to ISUP messages, as follows:
         
         - SLS based on the circuit number;
         - SLS based on the circuit identification code; and,
         - SLS assigned dynamically to calls within a signalling 
           relation.
         
         Some additional information provided to support ANSI 
         T1.113/2000 and ANSI circuit validation tests are as follows:
         
         - circuit group carrier: whether the carrier is digital, 
           analog, mixed or unknown;
         - double seizing control: whether none, all, odd or even;
         - alarm carrier: hardware, software or unknown;
         - continuity check requirements: none, statistical, per-call, 
           or unknown.
         
         Note that circuit groups can be split across trunk groups; 
         however, if the circuit group is protected by a protection 
         group, the same protection group must protect the trunk group 
         to which trunks in this circuit group belong."
    ::= { isupCg 1 }

isupCgEntry OBJECT-TYPE
    SYNTAX      IsupCgEntry
    MAX-ACCESS  not-accessible
    STATUS      current
    DESCRIPTION 
        "
         Note that circuit groups can be split across trunk groups; 
         however, if the circuit group is protected by a protection 
         group, the same protection group must protect the trunk group 
         to which trunks in this circuit group belong.  If a management 
         station attempts to create a circuit that involves different 
         protection groups for the associated circuit group and trunk 
         group, addition of the circuit may be refused for inconsistent 
         information.
         
         For ITU-T Rec. Q.76x and national variants based on ITU-T Rec. 
         Q.76x, circuit identification codes must be assigned so that 
         the low order bits of the CIC identify the channel within a 
         primary multiplex group at the near-end termination point.  In 
         this case, explicit(0) circuit grouping is sufficient.
         
         For ANSI T1.113/2000, circuit identification codes have no 
         assignment rules (they might or might no be channel based in 
         the low order bits of the CIC).  Also, in ANSI T1.113/2000, 
         software synthesized carrier alarms may represent intermediate 
         multiplexed primary carriers, requiring disjoint (in CIC) sets 
         of circuits in circuit groups.  Therefore, both explicit(0) and 
         predetermined(1) carri"
    INDEX       { isupCgId }
    ::= { isupCgTable 1 }

IsupCgEntry ::= SEQUENCE {
    isupCgId                Unsigned32,
    isupCgCIC               CircuitIdentificationCode,
    isupCgOperationalState  OperationalState,
    isupCgAlarmStatus       AlarmStatus,
    -- The following are for ANSI T1.113/2000 support
    isupCgRangeType         INTEGER,
    isupCgRangeAndStatus    RangeAndStatus,
    isupCgCarrierType       INTEGER,
    isupCgAlarmCarrier      INTEGER,
    isupCgContCheck         ContinuityCheck,
    isupCgContCheckRatio    Unsigned32,
    --
    isupCgPg                Unsigned32,
    isupCgStandbyStatus     StandbyStatus,
    isupCgRowStatus         RowStatus
}

isupCgId OBJECT-TYPE
    SYNTAX      Unsigned32
    MAX-ACCESS  not-accessible
    STATUS      current
    DESCRIPTION 
        "This object provides an index into the isupCgTable.  Each value 
         of the index corresponds to a unique instance of a circuit 
         group within the managed switching element."
    REFERENCE   
        "ITU-T Rec. Q.826 (02/2000) cepsgId ATTRIBUTE"
    ::= { isupCgEntry 1 }

isupCgCIC OBJECT-TYPE
    SYNTAX      CircuitIdentificationCode
    MAX-ACCESS  read-create
    STATUS      current
    DESCRIPTION 
        "This attribute indicates the circuit identification code (CIC) 
         of the circuit group.  It is normally the lowest assignable CIC 
         within a primary multiplex group.
         
         The circuit identification code is an identifier that is used 
         by TUP or ISUP to refer to a circuit in signaling messages 
         passed between exchanges.  It must be unique between two 
         signaling points, and, therefore, the value can only be 
         assigned to one of the circuit groups between two signaling 
         points.  Provisioning an exchange with multiple signaling 
         points is a way to exapand the available CIC values to be 
         assigned to circuits between exchanges.
         
         Some protocol variants of TUP and ISUP only support a 12-bit 
         CIC.  In such cases, the CIC has the range (0..4095).  Many 
         recent protocol variants of ISUP support a 16-bit CIC, and thus 
         the range in those cases is (0..65535).  Some protocol variants 
         (e.g. ANSI T1.113/2000) support both 12-bit and 16-bit CICs to 
         support older exchanges.  The range of this object is, 
         therefore, a function of the signalling relation to which this 
         circuit group belongs: that is, the capabilities of both the 
         near-end and far-end exchange for the circuit.  Therefore, 
         managed systems may reject CICs in the range (4096..65535) 
         where CIC values in that range are outside the capabilities of 
         either the near-end or far-end exchange."
    REFERENCE   
        "ITU-T Rec. Q.826 (02/2000) : cIC ATTRIBUTE."
    ::= { isupCgEntry 2 }

isupCgOperationalState OBJECT-TYPE
    SYNTAX      OperationalState
    MAX-ACCESS  read-only
    STATUS      current
    DESCRIPTION 
        "Provides the operational state of the circuit group in 
         accordance with ITU-T Rec. X.721 | ISO/IEC 10165-2 and the 
         OperationalState textual convention of the OPENSS7-SMI-MIB.  
         This state can return the following values:
         
          - disabled(0): the circuit group is inoperable and unable to 
            provide service;
         
          - enabled(1): the circuit group is partially or fully operable 
            and available for use."
    REFERENCE   
        "ITU-T Rec. X.721 (1992) | ISO/IEC 10165-2 : 1992, 
               Attribute-ASN1Module.OperationalState.
         ITU-T Rec. X.731 (1992) | ISO/IEC 10164-2 : 1993, 
               Section 8.1.1.1.
         ITU-T Rec. Q.826 (02/2001) : cepsg.operationalState."
    ::= { isupCgEntry 3 }

isupCgAlarmStatus OBJECT-TYPE
    SYNTAX      AlarmStatus
    MAX-ACCESS  read-create
    STATUS      current
    DESCRIPTION 
        "Provides the alarm status of the circuit group using the 
         AlarmStatus textual convention of the OPENSS7-SMI-MIB module 
         and ITU-T Rec. X.721 (1992) | ISO/IEC 10165-2.
         
         - underRepair(0), set by the management station when a repair 
           action has been initiated as a result of an alarm; reset by 
           the management station when a repair action has completed;
         
         - critical(1), not used;
         
         - major(2), set by the agent when a circuit group has been 
           locally or remotely blocked due to hardware-oriented failure 
           or software-oriented failure with immediate release, cleared 
           by the agent when the block is released; may be cleared (but 
           not set) by a management station;
         
         - minor(3), set by the agent when a circuit group has been 
           locally or remotely blocked due to software-oriented failure 
           without immediate release, cleared by the agent when the 
           block is released; may be cleared (but not set) by a 
           management station; also set when there is an error in a 
           circuit group blocking, unblocking, reset or query operation 
           or a circuit validation test fails for a circuit in the 
           circuit group;
         
         - alarmOutstanding(4), set by the agent whenever an alarm is 
           oustanding, cleared by the agent whenever no alarm is 
           outstanding; may be cleared (but not set) by a management 
           station.
         
         Alarms generated for circuit groups are primarily 
         communications alarms or quality of service alarms."
    ::= { isupCgEntry 4 }

isupCgRangeType OBJECT-TYPE
    SYNTAX      INTEGER { explicit(0), predetermined(1) }
    MAX-ACCESS  read-create
    STATUS      current
    DESCRIPTION 
        "Specifies whether circuit group procedures (blocking, 
         unblocking, reset, query) treat this circuit group as 
         explicit(0) or predetermined(1).
         
         - explicit(0): the default, indicates that the circuit group 
           contains circuits with CIC values that are within the scope 
           of the range and status parameter of ISUP.
         
         - predetermined(1): indicates that the circuit group contains 
           circuits with CIC values that are outside the scope of the 
           range and status parameter of ISUP, or that are otherwise 
           predetermined.  This value is only suitable for protocol 
           variants such as ANSI T1.113/2000 that provide for 
           predetermined circuit groups.
         
         Although a management station may specify this value when 
         creating a row in this table, the value may be changed from 
         explicit(0) to predetermined(1) by the managed system as a 
         result of the addition of circuits to the circuit group that 
         cause the range of circuits to extend beyond that provided for 
         in the ISUP range and status parameter, where the ISUP protocol 
         variant supports predetermined circuit groups."
    DEFVAL      { explicit }
    ::= { isupCgEntry 5 }

isupCgRangeAndStatus OBJECT-TYPE
    SYNTAX      RangeAndStatus
    MAX-ACCESS  read-only
    STATUS      current
    DESCRIPTION 
        "Provides the range and status of the circuit group using the 
         RangeAndStatus textual-convention.  The value indicates the 
         span of CIC values within the trunk group as a value (0..30) 
         and a bit pattern that identifies which CIC values within the 
         range represent circuits under ISUP control."
    REFERENCE   
        "ITU-T Rec. Q.763 (1996) : Range and Status parameter.
         ANSI T1.113/2000 : Range and Status parameter."
    DEFVAL      { "\x00\x00\x00\x00" }
    ::= { isupCgEntry 6 }

isupCgCarrierType OBJECT-TYPE
    SYNTAX      INTEGER { unknown(0), analog(1), digital(2), mixed(3) }
    MAX-ACCESS  read-only
    STATUS      current
    DESCRIPTION 
        "Indicates the carrier type associate with the circuit group.  
         The purpose of this object is to reflect that value that will 
         be returned by an ANSI T1.113/2000 circuit validation test.
         
         The value can be one of the following:
         
         - unknown(0), the carrier type is unknown or unspecified;
         
         - analog(1), the carrier is an analog carrier;
         
         - digital(2), the carrier is a digital carrier;
         
         - mixed(3), the carrier is a mixture of analog and digital 
           carriers.
         
         Newly created rows in this table will have the value of this 
         field initialized to unknown(2).  The agent may change the 
         value of this object from unknown(2) to analog(1), digital(2) 
         or mixed(3), on the first assignment of a circuit to this 
         circuit group.
         
         The typical value is digital(2)."
    ::= { isupCgEntry 7 }

isupCgAlarmCarrier OBJECT-TYPE
    SYNTAX      INTEGER { unknown(0), hardware(1), 
                    softwareWithoutRelease(2), 
                    softwareImmediateRelease(3) }
    MAX-ACCESS  read-create
    STATUS      current
    DESCRIPTION 
        "Specifies the carrier group alarm.  The value can be one of the 
         following:
         
         - unknown(0): the source of the carrier group alarm is unknown 
           or unspecified;
         
         - hardware(1): the source of the carrier group alarm is 
           an alarm channel associated with the facility group;
         
         - softwareWithoutRelease(2): the source of the carrier group 
           alarm is software synthesized and when failure is detected, 
           circuits are blocked `without release';
         
         - softwareImmediateRelease(3): the source of the carrier group 
           alarm is software synthesized and when failure is detected, 
           circuits are blocked with `immediate release'.
         
         Note that setting of software carrier group alarm value, 
         softwareWithoutRelease(2) or softwareImmediateRelease(3), does 
         not preclude the ISUP from issuing blocking messages that are 
         hardware related.
         
         Software carrier group alarm is not supported by ITU-T Rec. 
         Q.674, but is specified in ANSI T1.113.4/2000 Annex C.  As some 
         protocol variants do not support other than the `hardware(1)' 
         setting, the default value is always `hardware(1)'.  Some 
         managed systems may refuse to set this object to a value other 
         than hardware(1)."
    REFERENCE   
        "ANSI T1.113.4/2000 Annex C"
    DEFVAL      { hardware }
    ::= { isupCgEntry 8 }

isupCgContCheck OBJECT-TYPE
    SYNTAX      ContinuityCheck
    MAX-ACCESS  read-create
    STATUS      current
    DESCRIPTION 
        "Specifies the basis under which continuity checks are performed 
         for outgoing calls on circuits within the circuit group.  The 
         basis can be one of the following:
         
         - unknown(0): the basis for continuity checks is unknown or 
           unspecified;
         
         - none(1): no continuity checks are performed on outgoing 
           calls;
         
         - statistical(2): continuity checks are performed on a 
           statistical basis (proportional) on outgoing calls; and,
         
         - perCall(3): continuity checks are performed per-calls on 
           outgoing calls.
         
         For analog circuits with pilot supervision it is sufficient to 
         perform the continuity-check on a statistical basis or by test 
         calls.  For analog circuits not using pilot supervision a 
         continuity-check should be performed on a per-call basis.
         
         For mixed circuit groups (that is, analog and digital 
         circuits), a continuity-check should be performed on a 
         statistical basis or per-call basis.  Within mixed connections, 
         that is, connections composed of circuits with and without 
         continuity check on a statistical or per-call basis, it shall 
         be ensured that the continuity signal be forwarded to the 
         destination point although no continuity-check may have been 
         performed on one or more parts of the end-to-end connection.
         
         For circuit groups comprised of all digital circuits, in normal 
         operation, the continuity check will not be performed.  
         However, the continuity check should be permitted on digital 
         circuits as well as analog circuits as part of the circuit 
         turn-up procedures in an identical manner as on analog 
         circuits.
         
         For ANSI, circuit adminstrative errors as well as circuit 
         identity misunderstanding between SS7 exchanges should be 
         resolved with the circuit validation test.
         
         For transmission systems having some inherent fault indication 
         features giving an indication to the switching system in case 
         of fault, a continuity-check is not required.  However, a 
         per-call or a statistical continuity check may be needed on 
         fully digital circuits when circuits or bundles of circuits in 
         primary multiplex groups are droppend or inserted en route 
         between switches, and alarm indications carried on bits of the 
         primary multiplex frame structure are lost in passing thorugh 
         an intermediate transmission facility that does not relay them 
         transparently.  Typically, per call continuity-checks may be 
         needed when the transmission link between switches contains a 
         TDMA satellite system, a digital circuit multiplication system 
         or a digital access and cross connection system, where fault 
         indications are lost."
    REFERENCE   
        "ITU-T Rec. Q.764.
         ANSI T1.113.4/2000."
    ::= { isupCgEntry 9 }

isupCgContCheckRatio OBJECT-TYPE
    SYNTAX      Unsigned32 (0..1000)
    MAX-ACCESS  read-create
    STATUS      current
    DESCRIPTION 
        "Specifies the number of calls for which continuity test 
         procedures apply to at least one call.  When isupCgContCheck is 
         unknown(0) or none(1), the value returned will be zero (0).  
         When isupCgContCheck is perCall(3), the value returned will be 
         one (1).  When isupCgContCheck is statistical(2), the value 
         returned will be in the range (2..1000).  For statistical 
         continuity checks, the default value is 10 (1 in 10 calls 
         subject to continuity checks).
         
         Note that this value is only defined when the trunk group is 
         either one-way outgoing or two-way.  Otherwise, the value 
         returned shall be zero (0)."
    ::= { isupCgEntry 10 }

isupCgPg OBJECT-TYPE
    SYNTAX      Unsigned32
    MAX-ACCESS  read-create
    STATUS      current
    DESCRIPTION 
        "Specifies the protection group as an index into the isupPgTable 
         of the protection group that is protecting this circuit group."
    ::= { isupCgEntry 11 }

isupCgStandbyStatus OBJECT-TYPE
    SYNTAX      StandbyStatus
    MAX-ACCESS  read-only
    STATUS      current
    DESCRIPTION 
        "Provides the standby status of the circuit group in accordance 
         with ITU-T Rec. X.721 | ISO/IEC 10165-2 and the StandbyStatus 
         textual convention of the OPENSS7-SMI-MIB.  The standby status 
         can have one of the following values:
         
         - hotStandby(0), the circuit group is not providing service but 
           is in synchronism with another resource providing service 
           which this resource is protecting.
         
         - coldStandby(1), the circuit group is not providing service, 
           yet is initialized and another resource is providing service 
           which this resource is protecting;
         
         - providingService(2), the circuit group is providing service.
         
         Details of the status of protected and protecting resources are 
         provided in the protection group object associated with this 
         circuit group (see isupCgPg)."
    REFERENCE   
        "ITU-T Rec. X.721 (1992) | ISO/IEC 10165-2 : 1992, 
               Attribute-ASN1Module.StandbyStatus.
         ITU-T Rec. X.731 (1992) | ISO/IEC 10164-2 : 1993, 
               Section 8.1.2.5."
    ::= { isupCgEntry 12 }

isupCgRowStatus OBJECT-TYPE
    SYNTAX      RowStatus
    MAX-ACCESS  read-create
    STATUS      current
    DESCRIPTION 
        "Provides a mechanism whereby management stations may create or 
         delete entries in this table.  Rows may also be created and 
         deleted by the managed system as part of system operations."
    REFERENCE   
        "STD 58, SNMPv2-TC RowStatus."
    ::= { isupCgEntry 13 }


-- ==========================================================================
-- ISUP Circuit Table

isupCt OBJECT IDENTIFIER
    ::= { isupTables 13 }

isupCtTable OBJECT-TYPE
    SYNTAX      SEQUENCE OF IsupCtEntry
    MAX-ACCESS  not-accessible
    STATUS      current
    DESCRIPTION 
        "This table describes circuits.  One circuit can belong to only 
         one set of circuit end-points, the trunk group (circuit end 
         point subgroup)."
    REFERENCE   
        "ITU-T Rec. Q.826 (02/2002) : cep MOC"
    ::= { isupCt 1 }

isupCtEntry OBJECT-TYPE
    SYNTAX      IsupCtEntry
    MAX-ACCESS  not-accessible
    STATUS      current
    DESCRIPTION 
        "Each entry in this table describes a single circuit.
         
         Each circuit can belong to a single circuit group.  A circuit 
         group is a group of circuits grouped from a maintenance 
         perspective.  Circuit groups represent circuits that are 
         channels in a primary multiplex group.
         
         Each circuit can belong to a single trunk group."
    INDEX       { isupCtId }
    ::= { isupCtTable 1 }

IsupCtEntry ::= SEQUENCE {
    isupCtId                Unsigned32,
    isupCtCg                Unsigned32,
    isupCtTg                Unsigned32,
    isupCtAdminState        AdministrativeState,
    isupCtUsageState        UsageState,
    isupCtCtpbInstance      RowPointer,
    isupCtCircuitNumber     Unsigned32,
    isupCtOfficeEquip       SnmpAdminString,
    isupCtCIC               CircuitIdentificationCode,
    isupCtRowStatus         RowStatus
}

isupCtId OBJECT-TYPE
    SYNTAX      Unsigned32
    MAX-ACCESS  not-accessible
    STATUS      current
    DESCRIPTION 
        "This object provides an index into the isupCtTable.  Each value 
         of the index corresponds to a unique instance of a circuit 
         within the managed switching element."
    REFERENCE   
        "ITU-T Rec. Q.826 (02/2000): cepId ATTRIBUTE"
    ::= { isupCtEntry 1 }

isupCtCg OBJECT-TYPE
    SYNTAX      Unsigned32
    MAX-ACCESS  read-create
    STATUS      current
    DESCRIPTION 
        "This object identifies the circuit group to which this circuit 
         belongs.  The value of this object is an index into the 
         isupCgTable that corresponds to the circuit group to which this 
         circuit belongs.  Each circuit can belong to one circuit group.  
         A circuit group is a group of circuits that are associated from 
         a maintenance perspective.  Circuit groups represent circuits 
         that are channels in a primary multiplex group.
         
         In the case where the circuit identification code (isupCtCIC) 
         implies the circuit group to which this circuit belongs, this 
         object will have a value of zero (0) indicating that the 
         circuit group to which it belongs is implied by the value of 
         its circuit identification code.  This is the default."
    DEFVAL      { 0 }
    ::= { isupCtEntry 2 }

isupCtTg OBJECT-TYPE
    SYNTAX      Unsigned32
    MAX-ACCESS  read-create
    STATUS      current
    DESCRIPTION 
        "This object identifies the trunk group to which this circuit 
         belongs.  The value of this object is an index into the 
         isupTgTable that corresponds to the trunk group to which this 
         circuit belongs.  Each circuit belongs to a trunk group.  A 
         trunk group is a group of circuits (trunks) that share 
         characteristics of the trunk group (e.g.  directionality and 
         originating and terminating exchanges)."
    REFERENCE   
        "ITU-T Rec. Q.826 (02/2000): cep-cepsg NAME BINDING"
    ::= { isupCtEntry 3 }

isupCtAdminState OBJECT-TYPE
    SYNTAX      AdministrativeState
    MAX-ACCESS  read-create
    STATUS      current
    DESCRIPTION 
        "This attribute indicates whether the circuit end point is 
         administratively permitted to carry traffic (value `unlocked') 
         or not (value `locked').  When in the locked state normal 
         traffic may not be carried (i.e. the usage state must be idle).  
         If placed directly into the locked state any existing call is 
         cleared.  If placed into the shutting down state an existing 
         call is not cleared but when the call does clear via normal 
         means the administrative state will transition to the locked 
         state (and the circuit will have a usage state of idle).  Test 
         calls and other testing procedures may be performed in the 
         locked state.
         
         - locked(0), the circuit is administratively prohibited form 
           use;
         - unlocked(1), the circuit is administratively permitted for 
           use;
         - shuttingDown(2), the circuit will be administratively 
           prohibited from use, however, first existing calls on the 
           circuit will be allowed to terminate normally."
    REFERENCE   
        "ITU-T Rec. Q.826 (02/2000): cep.administrativeState ATTRIBUTE
         ITU-T Rec. X.721 | ISO/IEC 10165-2 : 1992 : administrativeState"
    DEFVAL      { locked }
    ::= { isupCtEntry 4 }

isupCtUsageState OBJECT-TYPE
    SYNTAX      UsageState
    MAX-ACCESS  read-only
    STATUS      current
    DESCRIPTION 
        "This attribute indicates whether there is traffic using the 
         circuit.  Changes to the values of this attribute do not 
         generate state change notifications.  Note that the value of 
         this attribute may not accurately reflect the usage of the 
         circuit if it is queried using multiple object operations.  The 
         initial value is idle.
         
         - idle(0), the circuit is idle;
         - active(1), the circuit is active;
         - busy(2), not used."
    REFERENCE   
        "ITU-T Rec. Q.826 (02/2000) : cep.usageState ATTRIBUTE
         ITU-T Rec. X.721 | ISO/IEC 10165-2 : 1992 : usageState"
    DEFVAL      { idle }
    ::= { isupCtEntry 5 }

isupCtCtpbInstance OBJECT-TYPE
    SYNTAX      RowPointer
    MAX-ACCESS  read-create
    STATUS      current
    DESCRIPTION 
        "This attribute points to an instance of a subclass of the OC 
         ITU-T Recommendation M.3100: 
         connectionTerminationPointBidirectional. Only one circuit in 
         the switch may point to a particular connectionTerminationPoint 
         managed object.
         
         The agent does not necessarily support row pointers to all 
         managed objects.  The value, when present,  must correspond to 
         an entry in a channel table that identifies the channel.  The 
         agent may require that the value identify a row in a specific 
         global channel table (in which case, an index value would be 
         sufficient).  When the value is not present (zeroDotZero), no 
         connection termination point bidrirectional isntance is 
         identified and the ISUP user must be able to identify the 
         appropriate equipment from other information such as the 
         circuit identifier; trunk group and circuit number; or, the 
         signaling relation and circuit identification code."
    REFERENCE   
        "ITU-T Rec. Q.826 (02/2000) : ctpbInstance ATTRIBUTE."
    DEFVAL      { zeroDotZero }
    ::= { isupCtEntry 6 }

isupCtCircuitNumber OBJECT-TYPE
    SYNTAX      Unsigned32
    MAX-ACCESS  read-create
    STATUS      current
    DESCRIPTION 
        "This attribute indicates the logical circuit end point number 
         within the containing trunk group.  It is unique within the 
         containing trunk group.  It provides for the ordering of the 
         circuit instances contained within a trunk group to support 
         such functions as hunting.
         
         Circuit numbers need only be assigned to circuits within a 
         trunk group when the isupCtCIC value is not sufficient for this 
         purpose.  When the isupCtCIC value is sufficient to effect the 
         intended search method for selecting circuits on one-way 
         outgoing and two-way trunk groups, this value should be set to 
         zero (0), the default, for all of the circuits in the trunk 
         group."
    REFERENCE   
        "ITU-T Rec. Q.826 (02/2000) : circuitNumber ATTRIBUTE."
    DEFVAL      { 0 }
    ::= { isupCtEntry 7 }

isupCtOfficeEquip OBJECT-TYPE
    SYNTAX      SnmpAdminString
    MAX-ACCESS  read-create
    STATUS      current
    DESCRIPTION 
        "This attribute references the physical equipment the circuit 
         end point is associated with.  If the instance choice is used, 
         it references an instance of the OC ITU-T Rec. M.3100: 
         circuitPack.  If the string choice is used, the value is 
         technology specific."
    REFERENCE   
        "ITU-T Rec. Q.826 (02/2000) : officeEquip ATTRIBUTE."
    ::= { isupCtEntry 8 }

isupCtCIC OBJECT-TYPE
    SYNTAX      CircuitIdentificationCode
    MAX-ACCESS  read-create
    STATUS      current
    DESCRIPTION 
        "This attribute indicates the circuit identification code (CIC) 
         of the circuit which is terminated by the circuit end point.  
         This attribute is applicable if SS7 is used.
         
         The circuit identification code is an identifier that is used 
         by TUP and ISUP to refer to a circuit in signalling messages 
         passed between exchanges.  It must be unique between two 
         signalling points, and, therefore, the value can only be 
         assigned to one of the circuits between two signalling points.  
         Provisioning an exchange with multiple signalling point codes 
         is a way to expand the available CIC values to be assigned to 
         circuits between exchanges.
         
         Some protocol variants of TUP and ISUP only support a 12-bit 
         CIC.  In such cases, the CIC has the range (0..4095).  Many 
         recent protocol variants of ISUP support a 16-bit CIC, and thus 
         the range in those cases is (0..65535).  Some protocol variants 
         (e.g. ANSI T1.113/2000) support both 12-bit and 16-bit CICs to 
         support older exchanges.  The range of this object is, 
         therefore, a function of the signalling relation for the trunk 
         group to which this circuit belongs: that is, the capabilities 
         of both the near-end and far-end exchange for the circuit.  
         Therefore, managed systems may reject CICs in the range 
         (4096..65535) where CIC values in that range are outside the 
         capabilities of either the near-end or far-end exchange.
         
         Mismatches between the CIC and the equipment identifier for the 
         circuit at either end of the trunk can render the circuit 
         unusable.  Verification of the mapping between CIC and 
         equipment identifier can be performing using the continuity 
         test proceedures of ITU-T TUP and ISUP, and using the circuit 
         validation test procedures of ANSI ISUP."
    REFERENCE   
        "ITU-T Rec. Q.826 (02/2000) : cIC ATTRIBUTE."
    ::= { isupCtEntry 9 }

isupCtRowStatus OBJECT-TYPE
    SYNTAX      RowStatus
    MAX-ACCESS  read-create
    STATUS      current
    DESCRIPTION 
        "Provides a mechanism whereby management stations may create or 
         delete entries in this table.  Rows may also be created and 
         deleted by the managed system as part of system operations.
         
         When created by management stations, entries in this table have 
         no other entries in other tables associated with the newly 
         created circuit.  Before an entry may be deleted by a 
         management station, all side-tables that use the isupCtId as an 
         index or which reference this row in the table using the 
         RowPointer or SimpleNameType textual convention must be deleted 
         or altered respectively."
    REFERENCE   
        "STD 58, SNMPv2-TC RowStatus"
    ::= { isupCtEntry 10 }

isupScalars OBJECT IDENTIFIER
    ::= { isupObjects 2 }

isupDefaults OBJECT IDENTIFIER
    ::= { isupScalars 1 }

isupNotifs OBJECT IDENTIFIER
    ::= { isupObjects 3 }

isupOids OBJECT IDENTIFIER
    ::= { isupObjects 4 }

isupProtocols OBJECT IDENTIFIER
    ::= { isupOids 1 }

isupProbableCauses OBJECT IDENTIFIER
    ::= { isupOids 2 }

isupSpecificProblems OBJECT IDENTIFIER
    ::= { isupOids 3 }

-- =====================================================================
--
-- The TMN (Q.751.2) way of providing on-occurence events from Q.752 
-- notifications is to provide a special ss7OnOccEvent notification 
-- which performs double duty as a communicationsAlarm (that is, it 
-- contains the same information as a communicationsAlarm).  That 
-- approach is duplicated here to limit the number of unique 
-- notifications necessary to represent all of the events to one, which 
-- also provides alarms.
--

-- ITU-T Rec. Q.751.2 sccpSpecificExtensions
-- sccpSpecificExtensions OBJECT IDENTIFIER
--     ::= { ccitt(0) recommendation(0) q(17) omap(751) sccp(2) informationModel(0) specificExtensions(0) }


isupSpecificExtensions OBJECT IDENTIFIER
    ::= { isupOids 4 }

t17Timeout OBJECT-IDENTITY
    STATUS      current
    DESCRIPTION 
        "ProbableCause.  This object identity is used with probableCause 
         in the ss7OnOccEvent or communicationsAlarm notification.  
         Probable Cause = 1201 (t17Timeout) which represents measurement 
         Q.752/12.1.
         
         Timer T17 is started when the first RSC is sent to reset a 
         circuit.  When T17 expires before an RLC message is received, 
         an alarm with this probable cause is generated.  Cleared when a 
         RLC message is properly received for the circuit."
    REFERENCE   
        "ITU-T Rec. Q.752 (1997) : Table 12, 12.1,
         ANSI T1.116.1 (2000D) : Table 12, 12.1"
    ::= { isupSpecificExtensions 1201 }

t23Timeout OBJECT-IDENTITY
    STATUS      current
    DESCRIPTION 
        "ProbableCause.  This object identity is used with probableCause 
         in the ss7OnOccEvent or communicationsAlarm notification.  
         ProbableCause = 1202 (t23Timeout) which represents measurement 
         Q.752/12.2.
         
         Timer T23 is started when the first GRS message is sent to 
         reset a circuit group.  When T23 expires before a GRA message 
         is received, an alarm with this probable cause is generated.  
         Cleared when a GRA message is properly received for the circuit 
         group."
    REFERENCE   
        "ITU-T Rec. Q.752 (1997) : Table 12, 12.2,
         ANSI T1.116.1 (2000D) : Table 12, 12.2"
    ::= { isupSpecificExtensions 1202 }

t5Timeout OBJECT-IDENTITY
    STATUS      current
    DESCRIPTION 
        "ProbableCause.  This object identity is used with probableCause 
         in the ss7OnOccEvent or communicationsAlarm notification.  
         Probable Cause = 1205 (t5Timeout) which represents measurement 
         Q.752/12.5.
         
         Timer T5 is started when the first REL message is sent to 
         release a circuit.  When T5 expires before an RLC message is 
         received, an alarm with this probable cause is generated.  
         Cleared when a RLC message is properly received for the 
         circuit."
    REFERENCE   
        "ITU-T Rec. Q.752 (1997) : Table 12, 12.5,
         ANSI T1.116.1 (2000D) : Table 12, 12.5"
    ::= { isupSpecificExtensions 1205 }

abnormalRelease OBJECT-IDENTITY
    STATUS      current
    DESCRIPTION 
        "ProbableCause.  This object identity is used with probableCause 
         in the ss7OnOccEvent or communicationsAlarm notification.  
         Probable Cause = 1206 (abnormalRelease) which represents 
         measurement Q.752/12.6.
         
         Abnormal release occurs when a REL with cause message other 
         than normal release is received.  When this happens, an alarm 
         with this probable cause is generated.  The alarm is not 
         cleared."
    REFERENCE   
        "ITU-T Rec. Q.752 (1997) : Table 12, 12.6,
         ANSI T1.116.1 (2000D) : Table 12, 12.6"
    ::= { isupSpecificExtensions 1206 }

hardwareBlocking OBJECT-IDENTITY
    STATUS      current
    DESCRIPTION 
        "ProbableCause.  This object identity is used with probableCause 
         in the ss7OnOccEvent or communicationsAlarm notification.  
         Probable Cause = 1207 (hardwareBlocking) which represents 
         measurement Q.752/12.7.
         
         When a circuit or circuit group is hardware blocked (blocked 
         with immediate release), an alarm with this probable cause is 
         generated.  When the circuit or circuit group is unblocked, the 
         alarm is cleared."
    REFERENCE   
        "ITU-T Rec. Q.752 (1997) : Table 12, 12.7,
         ANSI T1.116.1 (2000D) : Table 12, 12.7"
    ::= { isupSpecificExtensions 1207 }

missingCGBA OBJECT-IDENTITY
    STATUS      current
    DESCRIPTION 
        "ProbableCause.  This object identity is used with probableCause 
         in the ss7OnOccEvent or communicationsAlarm notification.  
         Probable Cause = 1208 (missingCGBA) which represents 
         measurement Q.752/12.8.
         
         When an acknowledgement does not exist for a circuit in a CGBA 
         message that was requested in a CGB message, an alarm with this 
         probable cause is generated.  The alarm is not cleared."
    REFERENCE   
        "ITU-T Rec. Q.752 (1997) : Table 12, 12.8,
         ANSI T1.116.1 (2000D) : Table 12, 12.8"
    ::= { isupSpecificExtensions 1208 }

missingCGUA OBJECT-IDENTITY
    STATUS      current
    DESCRIPTION 
        "ProbableCause.  This object identity is used with probableCause 
         in the ss7OnOccEvent or communicationsAlarm notification.  
         Probable Cause = 1209 (missingCGUA) which represents 
         measurement Q.752/12.9.
         
         When an acknolwegdement does not exist for a circuit in a CGUA 
         message that was requested in a CGU message, an alarm with this 
         probable cause is generated.  The alarm is not cleared."
    REFERENCE   
        "ITU-T Rec. Q.752 (1997) : Table 12, 12.9,
         ANSI T1.116.1 (2000D) : Table 12, 12.9"
    ::= { isupSpecificExtensions 1209 }

abnormalCGBA OBJECT-IDENTITY
    STATUS      current
    DESCRIPTION 
        "ProbableCause.  This object identity is used with probableCause 
         in the ss7OnOccEvent or communicationsAlarm notification.  
         Probable Cause = 1210 (abnormalCGBA) which represents 
         measurement Q.752/12.10.
         
         When an acknowledgement exists for a circuit in a CGBA message 
         that was not requested by a CGB message or which does not exist 
         for the circuit group, an alarm with this probable cause is 
         generated.  The alarm is not cleared."
    REFERENCE   
        "ITU-T Rec. Q.752 (1997) : Table 12, 12.10,
         ANSI T1.116.1 (2000D) : Table 12, 12.10"
    ::= { isupSpecificExtensions 1210 }

abnormalCGUA OBJECT-IDENTITY
    STATUS      current
    DESCRIPTION 
        "ProbableCause.  This object identity is used with probableCause 
         in the ss7OnOccEvent or communicationsAlarm notification.  
         Probable Cause = 1211 (abnormalCGUA) which represents 
         measurement Q.752/12.11.
         
         When an acknolwedgement exsits for a circuit in a CGUA message 
         that was not requested by a CGU message or which does not exist 
         for the circuit group, an alarm with this probable cause is 
         generated.  The alarm is not cleared."
    REFERENCE   
        "ITU-T Rec. Q.752 (1997) : Table 12, 12.11,
         ANSI T1.116.1 (2000D) : Table 12, 12.11"
    ::= { isupSpecificExtensions 1211 }

unexpectedCGBA OBJECT-IDENTITY
    STATUS      current
    DESCRIPTION 
        "ProbableCause.  This object identity is used with probableCause 
         in the ss7OnOccEvent or communicationsAlarm notification.  
         Probable Cause = 1212 (unexpectedCGBA) which represents 
         measurement Q.752/12.12.
         
         When a CGBA message is received for a circuit group for which 
         no CGB message is outstanding, an alarm with this probable 
         cause is generated.  The alarm is not cleared."
    REFERENCE   
        "ITU-T Rec. Q.752 (1997) : Table 12, 12.12,
         ANSI T1.116.1 (2000D) : Table 12, 12.12"
    ::= { isupSpecificExtensions 1212 }

unexpectedCGUA OBJECT-IDENTITY
    STATUS      current
    DESCRIPTION 
        "ProbableCause.  This object identity is used with probableCause 
         in the ss7OnOccEvent or communicationsAlarm notification.  
         Probable Cause = 1213 (unexpectedCGUA) which represents 
         measurement Q.752/12.13.
         
         When a CGUA message is received for a circuit group for which 
         no CGU message is oustanding, an alarm with this probable cause 
         is generated.  The alarm is not cleared."
    REFERENCE   
        "ITU-T Rec. Q.752 (1997) : Table 12, 12.13,
         ANSI T1.116.1 (2000D) : Table 12, 12.13"
    ::= { isupSpecificExtensions 1213 }

unexpectedBLA OBJECT-IDENTITY
    STATUS      current
    DESCRIPTION 
        "ProbableCause.  This object identity is used with probableCause 
         in the ss7OnOccEvent or communicationsAlarm notification.  
         Probable Cause = 1214 (unexpectedBLA) which represents 
         measurement Q.752/12.14.
         
         When a blocking acknowledge message is received for a circuit 
         for which no blocking request message was sent, an alarm with 
         this probable cause is generated.  The alarm is not cleared."
    REFERENCE   
        "ITU-T Rec. Q.752 (1997) : Table 12, 12.14,
         ANSI T1.116.1 (2000D) : Table 12, 12.14"
    ::= { isupSpecificExtensions 1214 }

unexpectedUBA OBJECT-IDENTITY
    STATUS      current
    DESCRIPTION 
        "ProbableCause.  This object identity is used with probableCause 
         in the ss7OnOccEvent or communicationsAlarm notification.  
         Probable Cause = 1215 (unexpectedUBA) which represents 
         measurement Q.752/12.15.
         
         When an unblocking acknowledge message is received for a 
         circuit for which no unblocking request message was sent, an 
         alarm with this probable cause is generated.  The alarm is not 
         cleared."
    REFERENCE   
        "ITU-T Rec. Q.752 (1997) : Table 12, 12.15,
         ANSI T1.116.1 (2000D) : Table 12, 12.15"
    ::= { isupSpecificExtensions 1215 }

t13Timeout OBJECT-IDENTITY
    STATUS      current
    DESCRIPTION 
        "ProbableCause.  This object identity is used with probableCause 
         in the ss7OnOccEvent or communicationsAlarm notification.  
         Probable Cause = 1216 (t13Timeout) which represents measurement 
         Q.752/12.16.
         
         Timer T13 is started when the first BLO message is sent.  When 
         T13 expires before a BLA message is received for the circuit, 
         an alarm with this probable cause is generated.  The alarm is 
         cleared when a BLA message has been received for the circuit, 
         or the blocking procedure is abandonned or cancelled."
    REFERENCE   
        "ITU-T Rec. Q.752 (1997) : Table 12, 12.16,
         ANSI T1.116.1 (2000D) : Table 12, 12.16"
    ::= { isupSpecificExtensions 1216 }

t15Timeout OBJECT-IDENTITY
    STATUS      current
    DESCRIPTION 
        "ProbableCause.  This object identity is used with probableCause 
         in the ss7OnOccEvent or communicationsAlarm notification.  
         Probable Cause = 1217 (t15Timeout) which represents measurement 
         Q.752/12.17.
         
         Timer T15 is started when the first UBL message is sent.  When 
         T15 expires before a UBA message is received for the circuit, 
         an alarm with this probable cause is generated.  The alarm is 
         cleared when a UBA message has been received for the circuit, 
         or the unblocking procedure is abandonned or cancelled."
    REFERENCE   
        "ITU-T Rec. Q.752 (1997) : Table 12, 12.17,
         ANSI T1.116.1 (2000D) : Table 12, 12.17"
    ::= { isupSpecificExtensions 1217 }

t19Timeout OBJECT-IDENTITY
    STATUS      current
    DESCRIPTION 
        "ProbableCause.  This object identity is used with probableCause 
         in the ss7OnOccEvent or communicationsAlarm notification.  
         Probable Cause = 1218 (t19Timeout) which represents measurement 
         Q.752/12.18.
         
         Timer T19 is started when the first CGB message is sent for a 
         circuit group.  When T19 expires before a CGBA message is 
         received for the circuit gorup, an alarm with this probable 
         cause is generated.  The alarm is cleared when a CGBA message 
         has been properly received for the circuit group, or the 
         circuit group blocking procedure is abandonned or cancelled."
    REFERENCE   
        "ITU-T Rec. Q.752 (1997) : Table 12, 12.18,
         ANSI T1.116.1 (2000D) : Table 12, 12.18"
    ::= { isupSpecificExtensions 1218 }

t21Timeout OBJECT-IDENTITY
    STATUS      current
    DESCRIPTION 
        "ProbableCause.  This object identity is used with probableCause 
         in the ss7OnOccEvent or communicationsAlarm notification.  
         Probable Cause = 1219 (t21Timeout) which represents measurement 
         Q.752/12.19.
         
         Timer T21 is started when the first CGU message is sent for a 
         circuit group.  When T21 expires before a CGUA message is 
         received for the circuit group, an alarm with this probable 
         cause is generated.  The alarm is cleared when a CGUA message 
         has been properly received for the circuit group, or the 
         circuit group unblocking procedure is abandonned or cancelled."
    REFERENCE   
        "ITU-T Rec. Q.752 (1997) : Table 12, 12.19,
         ANSI T1.116.1 (2000D) : Table 12, 12.19"
    ::= { isupSpecificExtensions 1219 }

messageFormatError OBJECT-IDENTITY
    STATUS      current
    DESCRIPTION 
        "ProbableCause.  This object identity is used with probableCause 
         in the ss7OnOccEvent or communicationsAlarm notification.  
         Probable Cause = 1220 (messageFormatError) which represents 
         measurement Q.752/12.20."
    REFERENCE   
        "ITU-T Rec. Q.752 (1997) : Table 12, 12.20,
         ANSI T1.116.1 (2000D) : Table 12, 12.20"
    ::= { isupSpecificExtensions 1220 }

unexpectedMessage OBJECT-IDENTITY
    STATUS      current
    DESCRIPTION 
        "ProbableCause.  This object identity is used with probableCause 
         in the ss7OnOccEvent or communicationsAlarm notification.  
         Probable Cause = 1221 (unexpectedMessage) which represents 
         measurement Q.752/12.21.
         
         When an unexpected message is received, an alarm with this 
         probable cause is generated.  This alarm is not cleared."
    REFERENCE   
        "ITU-T Rec. Q.752 (1997) : Table 12, 12.21,
         ANSI T1.116.1 (2000D) : Table 12, 12.21"
    ::= { isupSpecificExtensions 1221 }

unrecInfoRelease OBJECT-IDENTITY
    STATUS      current
    DESCRIPTION 
        "ProbableCause.  This object identity is used with probableCause 
         in the ss7OnOccEvent or communicationsAlarm notification.  
         Probable Cause = 1222 (unrecInfoRelease) which represents 
         measurement Q.752/12.22."
    REFERENCE   
        "ITU-T Rec. Q.752 (1997) : Table 12, 12.22,
         ANSI T1.116.1 (2000D) : Table 12, 12.22"
    ::= { isupSpecificExtensions 1222 }

unableToRelease OBJECT-IDENTITY
    STATUS      current
    DESCRIPTION 
        "ProbableCause.  This object identity is used with probableCause 
         in the ss7OnOccEvent or communicationsAlarm notification.  
         Probable Cause = 1223 (unableToRelease) which represents 
         measurement Q.752/12.23.
         
         When a REL message is received for a circuit that cannot be 
         released (e.g. there is no call control associated with the 
         circuit), an alarm with this probable cause is generated.  This 
         alarm is not cleared."
    REFERENCE   
        "ITU-T Rec. Q.752 (1997) : Table 12, 12.23,
         ANSI T1.116.1 (2000D) : Table 12, 12.23"
    ::= { isupSpecificExtensions 1223 }

isupProbableCauses2 OBJECT IDENTIFIER
    ::= { isupOids 5 }

isupConformance OBJECT IDENTIFIER
    ::= { isupMIB 2 }

isupCompliances OBJECT IDENTIFIER
    ::= { isupConformance 1 }

isupGroups OBJECT IDENTIFIER
    ::= { isupConformance 2 }

isupObjectGroup OBJECT-GROUP
    OBJECTS     { isupMsName, isupMsAlarmStatus, isupMsOperationalState, 
                  isupMsUsageState, isupMsVendorName, isupMsUserLabel, 
                  isupMsVersion, isupMsLocationName, 
                  isupMsPrimaryTimingSource, isupMsPrimaryTimingObject, 
                  isupMsSecondaryTimingSource, 
                  isupMsSecondaryTimingObject, isupMsAsaProfilePointer, 
                  isupMsManagedElementType, isupMsModelCode, 
                  isupMsNetworkElementAliases, isupMsRowStatus, 
                  isupPgOperState, isupPgAvailStatus, isupPgType, 
                  isupPgRevertive, isupPgSupportedByObjectList, 
                  isupPgWaitToRestoreTime, isupPgSettingWindowTime, 
                  isupPgReleasingWindowTime, isupPgHitsCount, 
                  isupPgSwitchType, isupPgProtectedUnits, 
                  isupPgProtectingUnits, isupPgInvokeProtection, 
                  isupPgReleaseProtection, isupPgRowStatus, 
                  isupPuProtecting, isupPuReliableResourcePointer, 
                  isupPuUnreliableResourcePointer, 
                  isupPuProtectionStatus, isupPuSwitchStatus, 
                  isupPuFromProtectionUnitNumber, 
                  isupPuToProtectionUnitNumber, isupPuAutoSwitchReason, 
                  isupPuLockoutReleaseFailed, isupPuPriority, 
                  isupPuRowStatus, isupLgOperationalState, 
                  isupLgAdministrativeState, isupLgSnServiceProvider, 
                  isupLgSnSap, isupLgOperationalProtocols, 
                  isupLgOperationalSubsets, isupLgRowStatus, 
                  isupMtpAddress, isupMtpUserPart, isupMtpUserPartStatus, 
                  isupMtpUserEntityNames, isupMtpProviderEntityNames, 
                  isupMtpUsageState, isupMtpAsaProfilePointer, 
                  isupMtpName, isupMtpLongMessageSupported, 
                  isupMtpRowStatus, isupNaProtocolVariant, 
                  isupNaProtocolYear, isupNaProtocolOptions, 
                  isupNaPointCodeFormat, isupNaSlsLength, 
                  isupNaSpDefault, isupNaName, isupNaRowStatus, 
                  isupSpPointCode, isupSpType, isupSpProceduralStatus, 
                  isupSpAvailabilityStatus, isupSpVersion, isupSpName, 
                  isupSpNaPointer, isupSpOptions, isupSpAlarmStatus, 
                  isupSpOperationalState, isupSpTotalRemoteSAPs, 
                  isupSpAdministrativeState, isupSpSupportedProtocols, 
                  isupSpOperationalSystemType, isupSpActivate, 
                  isupSpDeactivate, isupSpRowStatus, isupSrDest, 
                  isupSrOptions, isupSrSlsAssignment, isupSrAdminState, 
                  isupSrOpState, isupSrAsaProfilePointer, 
                  isupSrCongestedState, isupSrCongestionLevel, 
                  isupSrLoadsharingInformation, isupSrLoadsharingObject, 
                  isupSrRemoteExchangeLabel, isupSrName, isupSrProfile, 
                  isupSrAlarmStatus, isupSrRowStatus, 
                  isupRtTrunkGroupList, isupRtUsedAlgorithm, 
                  isupRtSelection, isupRtProportionList, 
                  isupRtPossibilitiesInList, isupRtUserLabel, 
                  isupRtProcStatus, isupRtControlStatus, 
                  isupRtAdminState, isupRtOperState, isupRtUsageState, 
                  isupRtRowStatus, isupRtTgSelectionOrdinal, 
                  isupRtTgSelectionProportion, isupRtTgSelectionList, 
                  isupRtTgSelectionRowStatus, isupTgNumberOfCircuits, 
                  isupTgLabelOfFarEndExchange, 
                  isupTgSignallingCapabilities, 
                  isupTgInformationTransferCapabilities, 
                  isupTgCircuitDirectionality, 
                  isupTgTransmissionCharacteristics, isupTgUserLabel, 
                  isupTgAdminState, isupTgAssocSignRouteSetNePart, 
                  isupTgBoundaryCrossing, isupTgSearchMethod, 
                  isupTgPrefTrafficRedirect, isupTgSuppressOwnCac, 
                  isupTgCarrierType, isupTgDoubleSeizureControl, 
                  isupTgAlarmCarrier, isupTgContCheck, 
                  isupTgContCheckRatio, isupTgPg, isupTgStandbyStatus, 
                  isupTgAlarmStatus, isupTgRowStatus, isupCgCIC, 
                  isupCgOperationalState, isupCgAlarmStatus, 
                  isupCgRangeType, isupCgRangeAndStatus, 
                  isupCgCarrierType, isupCgAlarmCarrier, isupCgContCheck, 
                  isupCgContCheckRatio, isupCgPg, isupCgStandbyStatus, 
                  isupCgRowStatus, isupCtCg, isupCtTg, isupCtAdminState, 
                  isupCtUsageState, isupCtCtpbInstance, 
                  isupCtCircuitNumber, isupCtOfficeEquip, isupCtCIC, 
                  isupCtRowStatus }
    STATUS      current
    DESCRIPTION 
        "Provides the full set of conformance objects."
    ::= { isupGroups 1 }

isupFullCompliance MODULE-COMPLIANCE
    STATUS      current
    DESCRIPTION 
        "Provides a compliance profile that provides full compliance to 
         this mib."

    MODULE      -- this module

        MANDATORY-GROUPS        { isupObjectGroup }

    ::= { isupCompliances 1 }

END -- end of module OPENSS7-ISUP-MIB.
