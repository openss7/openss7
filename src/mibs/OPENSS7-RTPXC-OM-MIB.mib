-- vim: ft=mib comments=\f\b\:\"ITU\-T,\f\b\:ITU\-T,\f\:\",\b\:\-\-,\:\-\-,\f\b\:\-,\f\b\:\· fo+=tcqlornw12 tw=64 ai nocin nosi sts=4 sw=4 et
-- =============================================================================
-- 
-- @(#) src/mibs/OPENSS7-RTPXC-OM-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-RTPXC-OM-MIB DEFINITIONS ::= BEGIN

IMPORTS
    HCPerfIntervalCount, HCPerfValidIntervals
        FROM HC-PerfHist-TC-MIB
    rtpswIfAddrId, rtpswInterfaceId, rtpswCallId
        FROM OPENSS7-RTPSW-MIB
    openss7Modules
        FROM OPENSS7-SMI
    MODULE-COMPLIANCE, OBJECT-GROUP
        FROM SNMPv2-CONF
    Counter64, Integer32, MODULE-IDENTITY, OBJECT-TYPE
        FROM SNMPv2-SMI;

rtpxcOmMIB MODULE-IDENTITY
    LAST-UPDATED "201107012131Z"
    ORGANIZATION 
        "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         E-mail: bidulock@openss7.org"
    DESCRIPTION 
        "
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION "201107012131Z"
    DESCRIPTION 
        "Initial version of this MIB."
    ::= { openss7Modules 505 }

rtpxcOmNotifications OBJECT IDENTIFIER
    ::= { rtpxcOmMIB 0 }

rtpxcOmNotifs OBJECT IDENTIFIER
    ::= { rtpxcOmMIB 1 }

rtpxcOmScalars OBJECT IDENTIFIER
    ::= { rtpxcOmMIB 2 }

rtpxcOmCurrent OBJECT IDENTIFIER
    ::= { rtpxcOmScalars 1 }

rtpxcForwCurrent OBJECT IDENTIFIER
    ::= { rtpxcOmScalars 2 }

rtpxcOmTables OBJECT IDENTIFIER
    ::= { rtpxcOmMIB 3 }

rtpxcOm5MinHistory OBJECT IDENTIFIER
    ::= { rtpxcOmTables 1 }

rtpxcOm15MinHistory OBJECT IDENTIFIER
    ::= { rtpxcOmTables 2 }

rtpxcInterfaceCurrent OBJECT IDENTIFIER
    ::= { rtpxcOmTables 3 }

rtpxcInterface5MinHistory OBJECT IDENTIFIER
    ::= { rtpxcOmTables 4 }

rtpxcInterface15MinHistory OBJECT IDENTIFIER
    ::= { rtpxcOmTables 5 }

rtpxcIfAddrCurrent OBJECT IDENTIFIER
    ::= { rtpxcOmTables 6 }

rtpxcIfAddr5MinHistory OBJECT IDENTIFIER
    ::= { rtpxcOmTables 7 }

rtpxcIfAddr15MinHistory OBJECT IDENTIFIER
    ::= { rtpxcOmTables 8 }

rtpxcForw5MinHistory OBJECT IDENTIFIER
    ::= { rtpxcOmTables 9 }

rtpxcForw15MinHistory OBJECT IDENTIFIER
    ::= { rtpxcOmTables 10 }

rtpxcOmTermPointCurrent OBJECT IDENTIFIER
    ::= { rtpxcOmTables 11 }

rtpxcOmCallCurrent OBJECT IDENTIFIER
    ::= { rtpxcOmTables 12 }

rtpxcOmCallHistory OBJECT IDENTIFIER
    ::= { rtpxcOmTables 12 }

rtpxcOmOids OBJECT IDENTIFIER
    ::= { rtpxcOmMIB 4 }

rtpxcOmGroups OBJECT IDENTIFIER
    ::= { rtpxcOmMIB 5 }

rtpxcOmCompliance OBJECT IDENTIFIER
    ::= { rtpxcOmMIB 6 }


END -- end of module OPENSS7-RTPXC-OM-MIB.
