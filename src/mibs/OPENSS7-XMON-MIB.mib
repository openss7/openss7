-- vim: ft=mib comments=\f\:\",\b\:\-\-,\:\-\-,\f\b\:- fo+=tcqlornw tw=72 nocin nosi sts=4 sw=4 et
-- =============================================================================
-- 
-- @(#) src/mibs/OPENSS7-XMON-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-XMON-MIB DEFINITIONS ::= BEGIN

IMPORTS
    HCPerfCurrentCount, HCPerfIntervalCount, HCPerfTimeElapsed, 
    HCPerfTotalCount, HCPerfValidIntervals
        FROM HC-PerfHist-TC-MIB
    openss7Modules
        FROM OPENSS7-SMI
    AdministrativeState, AvailabilityStatus, FullAction, IntervalsOfDay, 
    LogCapacityAlarmThreshold, OperationalState, ProceduralStatus, 
    SimpleNameType, UsageState, WeekMask
        FROM OPENSS7-SMI-MIB
    MilliSeconds
        FROM OPENSS7-TC
    PerfCurrentCount
        FROM PerfHist-TC-MIB
    IfIndex
        FROM SIP-MIB
    SnmpAdminString
        FROM SNMP-FRAMEWORK-MIB
    MODULE-COMPLIANCE, OBJECT-GROUP
        FROM SNMPv2-CONF
    Counter64, Integer32, MODULE-IDENTITY, OBJECT-IDENTITY, OBJECT-TYPE, 
    Unsigned32
        FROM SNMPv2-SMI
    DisplayString, PhysAddress, RowStatus, StorageType, 
    TEXTUAL-CONVENTION, TimeInterval, TimeStamp, TruthValue
        FROM SNMPv2-TC
    TransportAddress, TransportAddressType
        FROM TRANSPORT-ADDRESS-MIB;

xmonMIB MODULE-IDENTITY
    LAST-UPDATED "201212062146Z"
    ORGANIZATION 
        "The OpenSS7 Project"
    CONTACT-INFO 
        "Brian Bidulock
         OpenSS7 Corporation
         1469 Jefferys Crescent
         Edmonton AB  T6L 6T1
         CANADA
         Tel: +1 780 490 1141
         Fax: +1 780 490 1241
         Mob: +1 780 953 0557
         E-Mail: bidulock@openss7.org"
    DESCRIPTION 
        "Extended remote monitoring MIB module for monitoring SS7, 
         SIGTRAN and other communications protocols.
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201212062146Z"
    DESCRIPTION 
        "First release of this module."
    ::= { openss7Modules 83 }

-- 
-- This mib describes the necessary information for the host to perform 
-- capture and live feeds of data for monitored interfaces.  It is 
-- intended to provide monitoring for SS7 and SIGTRAN for the near term 
-- and SIP, H.323, BICC, H.248 in the longer term.
--

-- ====================================================================
-- TEXTUAL CONVENTIONS
-- ====================================================================

TimesOfDay ::= TEXTUAL-CONVENTION
    DISPLAY-HINT "1d:1d,"
    STATUS      current
    DESCRIPTION 
        "This textual convention specifies times of day by hour and 
         minute and replaces the following ASN.1 syntax:
         
         TimesOfDay ::= SET OF Time24
         
         It consists of an octet string that is an integral multiple of 
         2 octets.  Each 2 octet grouping is coded as a Time24 textual 
         convention representing one time of day.  Each two-octet 
         grouping represents as separate time of day."
    REFERENCE   
        "ITU-T Rec. X.721 (1992) | ISO/IEC 10165-2 : 1992, 
               Attribute-ASN1Module.IntervalsOfDay"
    SYNTAX      OCTET STRING

TimesOfWeek ::= TEXTUAL-CONVENTION
    DISPLAY-HINT "1x"
    STATUS      current
    DESCRIPTION 
        "This textual convention specifies intervals in the day for days 
         of the week and replaces the following ASN.1 syntax:
         
         WeekMask ::= SET OF SEQUENCE {
            daysOfWeek BIT STRING {
                sunday(0),
                monday(1),
                tuesday(2),
                wednesday(3),
                thursday(4),
                friday(5),
                saturday(6) }(SIZE(7)),
            timesOfDay TimesOfDay }
         
         The first octet of the octet string is a day of seek indicator 
         that can have bit values: sunday(0), monday(1), tuesday(2), 
         wednesday(3), thursday(4), friday(5) and saturday(6), with bit 
         position 7 unused and set to zero.  The second octet of the 
         string is an interval count indicating the number, 'n', of 
         times of day (multiples of 2 octets) to follow.  The next nx2 
         octets represent the times of day following the TimesOfDay 
         textual convention.  The pattern is repeated again beginning 
         with the week octet."
    REFERENCE   
        "ITU-T Rec. X.721 (1992) | ISO/IEC 10165-2 : 1992, 
               Attribute-ASN1Module.WeekMask"
    SYNTAX      OCTET STRING

DataLinkType ::= TEXTUAL-CONVENTION
    STATUS      current
    DESCRIPTION 
        "This textual convention specifies the data link type of a 
         capture file or interface in a capture file using the 
         convention of the PCAP and PCAP-NG file formats."
    REFERENCE   
        "PCAP/PCAPNG file formst."
    SYNTAX      INTEGER { null(0), ethernet(1), expether(2), ax25(3), 
                    pronet(4), chaos(5), tokenring(6), arcnet(7), 
                    slip(8), ppp(9), fddi(10), ppphdlc(50), pppether(51), 
                    symantec(99), rfc1483(100), rawip(101), bsdslip(102), 
                    bsdppp(103), ciscohdlc(104), ieee80211(105), 
                    atmclip(106), frelay(107), loop(108), enc(109), 
                    lane8023(110), hippi(111), hdlc(112), linuxsll(113), 
                    ltalk(114), econet(115), ipfilter(116), pflog(117), 
                    prism(119), aironet(120), hhdlc(121), rfc2825(122), 
                    sunatm(123), rio(124), pcie(125), aurora(126), 
                    ieee80211radio(127), tzsp(128), arcnetlinux(129), 
                    ipieee1394(138), mtp2ph(139), mtp2(140), mtp3(141), 
                    sccp(142), docsis(143), irda(144) }

EuiAddr ::= TEXTUAL-CONVENTION
    DISPLAY-HINT "1x:"
    STATUS      current
    DESCRIPTION 
        "This textual convention represents an EUI-64 address 
         represented in the order of transmission."
    SYNTAX      OCTET STRING (SIZE(8))

Uuid ::= TEXTUAL-CONVENTION
    DISPLAY-HINT "4x-2x-2x-2x-6x"
    STATUS      current
    DESCRIPTION 
        "This textual convention specifies a 128-bit unique user 
         identifier (UUID)."
    SYNTAX      OCTET STRING (SIZE(16))

FilterType ::= TEXTUAL-CONVENTION
    STATUS      current
    DESCRIPTION 
        "This textual convention specifies the filter types that are to 
         be applied to a monitoring source to limit the number of 
         packets collected."
    SYNTAX      BITS { arp(0), rarp(1), lldp(2), dns(3), mdns(4), 
                    m2pa(5), m2ua(6), m3ua(7), sua(8), iua(9), bicc(10), 
                    sip(11), h323(12), h248(13), q931(14), custom(15) }

CaptureInterfaces ::= TEXTUAL-CONVENTION
    DISPLAY-HINT "1d,"
    STATUS      current
    DESCRIPTION 
        "Provides a list of capture interface numbers, where each octet 
         in the OCTET STRING represents a separate capture interface.  
         Each capture interface number also represents an index into the 
         probeInterfaceTable for the same value of probeInterfaceIndex.  
         Only 256 interfaces can be represented."
    SYNTAX      OCTET STRING (SIZE(1..256))

ConnectionState ::= TEXTUAL-CONVENTION
    STATUS      current
    DESCRIPTION 
        "Provides the communications state of a transport connection:
         
         - idle(0), there is no transport connection; this host is 
           neither initiating nor responding to a connection request; 
           the operational state is disabled(0), the usage state is 
           idle(0) and the procedural status contains notInitialized(1);
           
         - ogConn(1), this host is in the process of initiating an 
           outgoing transport connection; the operational state is 
           disabled(0), the usage state is idle(0) and the procedural 
           status contains initializing(2);
           
         - icConn(2), this host is responding to an incoming transport 
           connection; the operational state is disabled(0), the usage 
           state is idle(0) and the procedural status contains 
           initializing(2);
           
         - established(3), the transport connection is established; the 
           operational state is enabled(1) or disabled(0);
           
         - shuttingDown(4), the transport connection is being shut down 
           by the local or remote end; the operational state is 
           disabled(0) and the procedural status contains 
           terminating(4).
           
         These values reflect the state of the transport connection.  
         For connectionless transports, the connection state may move 
         between idle(0) to established(3) without entering the other 
         states."
    SYNTAX      INTEGER { idle(0), ogConn(1), icConn(2), established(3), 
                    shuttingDown(4) }

ConnectionRole ::= TEXTUAL-CONVENTION
    STATUS      current
    DESCRIPTION 
        "Provides for the role of an endpoint in a transport connection:
         
         - initiator(1), this host initiates the connection;
         - responder(2), this host responds to connection requests;
         - both(3), this hostt will both attempt to initiate the 
           transport connection as well as respond to connection 
           requests.
         
         The agent may autonomously create rows with the responder(2) 
         role; whereas initiator(1) or both(3) role rows will be created 
         by management stations."
    SYNTAX      INTEGER { initiator(1), responder(2) }

SubstitutionString ::= TEXTUAL-CONVENTION
    DISPLAY-HINT "1a"
    STATUS      current
    DESCRIPTION 
        "Provides an administrative string with substitutions.  The 
         following substitutions (escape sequences) are available:

         - %I, the interface;
         - %Y, the 4-digit year;
         - %M, the 2-digit month of the year;
         - %D, the 2-digit day of the month;
         - %W, the 2-digit week of the year;
         - %h, the 2-digit hour of the day;
         - %m, the 2-digit minute of the hour;
         - %s, the 2-digit second of the minute;
         - %P, the UUID of this probe;
         - %U, the UUID of the remote probe;
         - %N, the name of the probe;
         - %F, the original file name.

         Escape sequences will be substituted on a per-file or per-use 
         basis."
    SYNTAX      OCTET STRING (SIZE(0..127))

-- ====================================================================
-- NOTIFICATIONS
-- ====================================================================

xmonNotifications OBJECT IDENTIFIER
    ::= { xmonMIB 1 }

-- ====================================================================
-- OBJECTS
-- ====================================================================

xmonObjects OBJECT IDENTIFIER
    ::= { xmonMIB 2 }

-- =====================================================================
-- xmonProbe group
-- =====================================================================

xmonProbe OBJECT-IDENTITY
    STATUS      current
    DESCRIPTION 
        "The xmonProbe group is responsible for managing a probe 
         implementation."
    ::= { xmonObjects 1 }

xmonProbeName OBJECT-TYPE
    SYNTAX      SnmpAdminString
    MAX-ACCESS  read-write
    STATUS      current
    DESCRIPTION 
        "Provides the name of the probe.  The name of the probe can be 
         changed by writing to this object.  Note that changes will not 
         be effective effective in capture files or feeds until 
         rotation.  The default value is the value of sysName."
    ::= { xmonProbe 1 }

xmonProbeUuid OBJECT-TYPE
    SYNTAX      Uuid
    MAX-ACCESS  read-write
    STATUS      current
    DESCRIPTION 
        "Provides the randomly generated unique user identifier (UUID) 
         associated with the probe.  When a UUID has not been assigned 
         to a probe, the agent must generate one and return it when this 
         object is read.  Management stations may write a new UUID.  
         This value persists across agent reboots."
    ::= { xmonProbe 2 }

xmonProbeHardware OBJECT-TYPE
    SYNTAX      SnmpAdminString
    MAX-ACCESS  read-write
    STATUS      current
    DESCRIPTION 
        "Provides a general, human-readable description of the hardware 
         of the probe.  This information will go verbatim into the 
         shb_hardware option field of a PCAP-NG file format section 
         header for files and feeds captured from this probe.  The 
         default value is the value of sysDescr or other suitable 
         hardware description string."
    ::= { xmonProbe 3 }

xmonProbeOs OBJECT-TYPE
    SYNTAX      SnmpAdminString
    MAX-ACCESS  read-write
    STATUS      current
    DESCRIPTION 
        "Provides a general, human-readable description of the operating 
         system of the probe.  This information will go verbtaim into 
         the shb_os option field of a PCAP-NG file format section header 
         for files and feeds captured from this probe.  The default 
         value is the value of sysDescr or other suitable operating 
         system description string (e.g. uname -a)."
    ::= { xmonProbe 4 }

xmonProbeUserAppl OBJECT-TYPE
    SYNTAX      SnmpAdminString
    MAX-ACCESS  read-only
    STATUS      current
    DESCRIPTION 
        "Provides the name of the application and version running on the 
         probe.  This information will go verbatim into the shb_userappl 
         option field of a PCAP-NG file format section header for files 
         and feeds captured from this probe."
    DEFVAL      { "ss7mon 1.1.2" }
    ::= { xmonProbe 5 }

-- =====================================================================
-- xmonSource group
-- =====================================================================

xmonSource OBJECT-IDENTITY
    STATUS      current
    DESCRIPTION 
        "The xmonSource group is responsible for managing sources of 
         packet capture."
    ::= { xmonObjects 2 }

xmonSourceTable OBJECT-TYPE
    SYNTAX      SEQUENCE OF XmonSourceEntry
    MAX-ACCESS  not-accessible
    STATUS      current
    DESCRIPTION 
        "Provides a table of sources available for monitoring and 
         capture on this probe or remote probes."
    ::= { xmonSource 1 }

xmonSourceEntry OBJECT-TYPE
    SYNTAX      XmonSourceEntry
    MAX-ACCESS  not-accessible
    STATUS      current
    DESCRIPTION 
        "Each row in this table provides for management of a single 
         monitoring source.  Note that a row does not exist in this 
         table unless a row for the same index exists also in the 
         xmonInterfaceTable or xmonRmonTable.  Creation and deletion of 
         rows in this table tracks the creation and deletion of rows in 
         the other tables.  A row with the same index cannot exist both 
         in the xmonInterfaceTable and xmonRmonTable simultaneously."
    INDEX       { xmonSourceIndex }
    ::= { xmonSourceTable 1 }

XmonSourceEntry ::= SEQUENCE {
    xmonSourceIndex         Integer32,
    xmonSourceType          INTEGER,
    xmonSourceName          SnmpAdminString,
    xmonSourceIfIndex       IfIndex,
    xmonSourceAdminState    AdministrativeState,
    xmonSourceOpState     OperationalState,
    xmonSourceAvailStatus   AvailabilityStatus,
    xmonSourceProcStatus    ProceduralStatus,
    xmonSourceUsageState    UsageState
}

xmonSourceIndex OBJECT-TYPE
    SYNTAX      Integer32 (0..65535)
    MAX-ACCESS  not-accessible
    STATUS      current
    DESCRIPTION 
        "Provides a zero-based oridinal index into the XMON interface 
         table.  This index corresponds to the interface identifier that 
         will be used in a PCAP-NG format capture file or feed."
    ::= { xmonSourceEntry 1 }

xmonSourceType OBJECT-TYPE
    SYNTAX      INTEGER { interface(1), rmon(2) }
    MAX-ACCESS  read-only
    STATUS      current
    DESCRIPTION 
        "Indicates whether this source is an interface or rmon source:
         
         - interface(1), a row with the same value of xmonSourceIndex 
           exists in the xmonInterfaceTable;
           
         - rmon(2), a row with the same value of xmonSourceIndex exists 
           in the xmonRmonTable.
           
         Rows with the same value of xmonSourceIndex cannot 
         simultaneously exist in the xmonInterfaceTable and 
         xmonRmonTable.  Any value of xmonSourceIndex that exists in 
         either of those tables also exists in this table."
    ::= { xmonSourceEntry 2 }

xmonSourceName OBJECT-TYPE
    SYNTAX      SnmpAdminString
    MAX-ACCESS  read-write
    STATUS      current
    DESCRIPTION 
        "Provides the name of the interface.  This is the same as the 
         corresponding ifName value from the ifXTable when the ifIndex 
         is specified in the xmonSourceIfIndex column.  The agent uses 
         SIOCGIFCONF or pcap_findalldevs(3pcap) to obtain a list of 
         interface names for local sources."
    ::= { xmonSourceEntry 3 }

xmonSourceIfIndex OBJECT-TYPE
    SYNTAX      IfIndex
    MAX-ACCESS  read-only
    STATUS      current
    DESCRIPTION 
        "Provides the corresponding value of the index into the ifTable 
         corresponding to the interface.  If the ifIndex value is 
         unknown or not applicable to the interface, the special value 
         zero (0) will appear in this column.  Note that thie ifIndex 
         depends on whether the source is an xmonInterface entry or a 
         xmonRmon entry.  When an interface, the ifIndex is that of the 
         local host; when an rmon channel, the ifIndex is that of the 
         remote host."
    ::= { xmonSourceEntry 4 }

xmonSourceAdminState OBJECT-TYPE
    SYNTAX      AdministrativeState
    MAX-ACCESS  read-write
    STATUS      current
    DESCRIPTION 
        "Provides the administrative state of monitoring from the 
         source:
         
         - locked(0), monitoring of packets from this source is 
           administratively prohibited;
           
         - unlocked(1), monitoring of packets from this source is 
           administratively permitted; capture of packtes from the 
           source will proceed, depending on the values of other state 
           and status attributes;
           
         - shuttingDown(2), monitoring of the source is shutting down: 
           once it ceases generating packets it will move to the 
           locked(0) state.
           
         The value shuttingDown(2) is only valid when read and not valid 
         when written.  This object is used primarily to enable or 
         disable monitoring of packets from the source."
    REFERENCE   
        "OPENSS7-SMI-MIB, AdministrativeState.
         ITU-T Rec. X.735 (1992) | ISO/IEC 10164-6 : 1993, 
               Section 8.1.1.1.3."
    DEFVAL      { unlocked }
    ::= { xmonSourceEntry 5 }

xmonSourceOpState OBJECT-TYPE
    SYNTAX      OperationalState
    MAX-ACCESS  read-only
    STATUS      current
    DESCRIPTION 
        "Provides the operational state of the source:
         
         - enabled(0), the source is enabled;
         - disabled(1), the source is disabled.
           
         When enabled(0), packets generated by the source can be 
         monitored; when disabled(1), they cannot.  The operational 
         state is determined by the source itself rather than any 
         actions taken within this MIB."
    REFERENCE   
        "OPENSS7-SMI-MIB, OperationalState.
         ITU-T Rec. X.735 (1992) | ISO/IEC 10164-6 : 1993, 
               Section 8.1.1.1.4."
    DEFVAL      { enabled }
    ::= { xmonSourceEntry 6 }

xmonSourceAvailStatus OBJECT-TYPE
    SYNTAX      AvailabilityStatus
    MAX-ACCESS  read-only
    STATUS      current
    DESCRIPTION 
        "Provides the availability status of the source; it may contain:
         
         - inTest(0), the source is in test; administrative state is 
           locked(0), operational state is disabled(1);
         - failed(1), the source has an internal fault that prevents it 
           from operating; operational state disabled(1);
         - powerOff(2), the source is not powered on;
         - offLine(3), the source requires a routing operation;
         - offDuty(4),the source is off duty per schedule;
         - dependency(5), the source cannot operate due to a dependency;
         - degraded(6), the source is operating with degraded 
           performance;
         - notInstalled(7), the source is not installed.
         - logFull(8), not used.
           
         The availability status reflects the availability of the source 
         rather than its availability for use as a monitoring source."
    REFERENCE   
        "OPENSS7-SMI-MIB, AvailabilityStatus.
         ITU-T Rec. X.735 (1992) | ISO/IEC 10164-6 : 1993, 
               Section 8.1.1.1.6.
         ITU-T Rec. X.735 (1992) | ISO/IEC 10164-6 : 1993, 
               Section 8.1.1.4.1."
    DEFVAL      { {} }
    ::= { xmonSourceEntry 7 }

xmonSourceProcStatus OBJECT-TYPE
    SYNTAX      ProceduralStatus
    MAX-ACCESS  read-only
    STATUS      current
    DESCRIPTION 
        "Provides the procedural status of the source:
         
         - intializationRequired(0), hardware or firmware associated 
           with the source requires initialization and that 
           initialization has not yet been performed; a manual or 
           automatic action is required to initialize the source;
           
         - notInitialized(1), hardware or firmware associated with the 
           source requires initialization and that initialization has 
           not completed yet;
           
         - initializing(2), hardware or firmware associated with the 
           source requires initialization and that initialization is 
           proceeding but has not yet completed;
           
         - reporting(3), the source is reporting its results;
           
         - terminating(4), the source is terminating.
           
         The procedural status for sources result from actions taken by 
         the underlying device or device driver and not by actions taken 
         within this MIB."
    REFERENCE   
        "OPENSS7-SMI-MIB, ProceduralStatus.
         ITU-T Rec. X.721 | ISO/IEC 10165-2, proceduralStatus."
    DEFVAL      { {} }
    ::= { xmonSourceEntry 8 }

xmonSourceUsageState OBJECT-TYPE
    SYNTAX      UsageState
    MAX-ACCESS  read-only
    STATUS      current
    DESCRIPTION 
        "Provides the usage state of the source:
         
         - idle(0), the source is not currently in use;
           
         - active(1), the source is in use and has sufficient operating 
           capacity to provide for additional users simultaneously;
           
         - busy(2), the source is in use and has no spare capacity.
           
         This usage state determines the use of the source as a monitor 
         and not any use of the source in active communication.  For 
         example, an ethernet source could be idle(0) for monitoring, 
         and busy(2) in active communication."
    REFERENCE   
        "OPENSS7-SMI-MIB, UsageState.
         ITU-T Rec. X.721 | ISO/IEC 10165-2, usageState."
    DEFVAL      { idle }
    ::= { xmonSourceEntry 9 }

xmonSourceStatsTable OBJECT-TYPE
    SYNTAX      SEQUENCE OF XmonSourceStatsEntry
    MAX-ACCESS  not-accessible
    STATUS      current
    DESCRIPTION 
        "Provides a table of current statistics for sources available 
         for monitoring on this probe."
    ::= { xmonSource 2 }

xmonSourceStatsEntry OBJECT-TYPE
    SYNTAX      XmonSourceStatsEntry
    MAX-ACCESS  not-accessible
    STATUS      current
    DESCRIPTION 
        "Each row in the table provides current collection statistics 
         asociated with one source that has been monitored.  Note that 
         when current counts are not valid for a given source, a 
         corresponding row does not exist in this table."
    INDEX       { xmonSourceIndex }
    ::= { xmonSourceStatsTable 1 }

XmonSourceStatsEntry ::= SEQUENCE {
    xmonSourceStatsTimeElapsed      HCPerfTimeElapsed,
    xmonSourceStatsTimeStamp        TimeStamp,
    xmonSourceStatsStartTime        TimeStamp,
    xmonSourceStatsEndTime          TimeStamp,
    xmonSourceStatsIfRecv           HCPerfCurrentCount,
    xmonSourceStatsIfDrop           HCPerfCurrentCount,
    xmonSourceStatsFilterAccept     HCPerfCurrentCount,
    xmonSourceStatsOsDrop           HCPerfCurrentCount,
    xmonSourceStatsUserDeliv        HCPerfCurrentCount
}

xmonSourceStatsTimeElapsed OBJECT-TYPE
    SYNTAX      HCPerfTimeElapsed (0..899)
    UNITS       "seconds"
    MAX-ACCESS  read-only
    STATUS      current
    DESCRIPTION 
        "Indicates the elasped time in the current statistics collection 
         interval."
    ::= { xmonSourceStatsEntry 1 }

xmonSourceStatsTimeStamp OBJECT-TYPE
    SYNTAX      TimeStamp
    MAX-ACCESS  read-only
    STATUS      current
    DESCRIPTION 
        "Indicates the time at which the current statistics report is 
         valid.  A value of zero (0) indicates that the time of the 
         report is unknown."
    ::= { xmonSourceStatsEntry 2 }

xmonSourceStatsStartTime OBJECT-TYPE
    SYNTAX      TimeStamp
    MAX-ACCESS  read-only
    STATUS      current
    DESCRIPTION 
        "Indicates the monitoring start time for this current statistics 
         report.  A value of zero (0) indicates that the start time is 
         unknown."
    ::= { xmonSourceStatsEntry 3 }

xmonSourceStatsEndTime OBJECT-TYPE
    SYNTAX      TimeStamp
    MAX-ACCESS  read-only
    STATUS      current
    DESCRIPTION 
        "Indicates the monitoring end time for this current statistics 
         report.  A value of zero (0) indicates that the end time is 
         unknown."
    ::= { xmonSourceStatsEntry 4 }

xmonSourceStatsIfRecv OBJECT-TYPE
    SYNTAX      HCPerfCurrentCount
    MAX-ACCESS  read-only
    STATUS      current
    DESCRIPTION 
        "A count of the number of packets received from the physical 
         source since the beginning of the current monitoring period.  
         This is the number of packets received by the physical source 
         regardless of monitoring.  It is obtained directly from the 
         device driver.  This count deos not include frames dropped due 
         to framing errors or invalid frame check sequences, but only 
         those packets successfully received by the physical source."
    REFERENCE   
        "PCAP-NG file format: isb_ifrecv."
    ::= { xmonSourceStatsEntry 5 }

xmonSourceStatsIfDrop OBJECT-TYPE
    SYNTAX      HCPerfCurrentCount
    MAX-ACCESS  read-only
    STATUS      current
    DESCRIPTION 
        "A count of the number of packets dropped by the source due to 
         lack of resources since the beginning of the monitoring period.  
         This is the number of packets dropped by the source regardless 
         of monitoring.  It is obtained directly from the device driver.  
         This count does not include frames dropped due to framing 
         errors or invalid frame check sequences, but only those that 
         were not delivered to any upper layer due to a lack of 
         resources in the physical source or device driver.
          
         The difference between xmonSourceStatsIfRecv and this column 
         should be the number of packets that were eligible for capture 
         (i.e. presented to the filter)."
    REFERENCE   
        "PCAP-NG file format: isb_drop."
    ::= { xmonSourceStatsEntry 6 }

xmonSourceStatsFilterAccept OBJECT-TYPE
    SYNTAX      HCPerfCurrentCount
    MAX-ACCESS  read-only
    STATUS      current
    DESCRIPTION 
        "A count of the number of packets accepted by the filter since 
         the beginning of the current monitoring period.  This is the 
         bs_capt field of the BIOCGSTATS structure and the 
         isb_filteraccept option field in the PCAP-NG format.
         
         The value xmonSourceStatsIfRecv minus the sum of 
         xmonSourceStatsIfDrop and this column should yeild the number 
         of packets dropped by the filter."
    REFERENCE   
        "bpf(4) manual page: bs_capt.
         PCAP-NG file format: isb_filteraccept."
    ::= { xmonSourceStatsEntry 7 }

xmonSourceStatsOsDrop OBJECT-TYPE
    SYNTAX      HCPerfCurrentCount
    MAX-ACCESS  read-only
    STATUS      current
    DESCRIPTION 
        "A count of the number of packets dropped by the operating 
         system since the beginning of the monitoring period.  This is 
         the bs_drop field of the BIOCGSTATS structure and the 
         isb_osdrop option field in the PCAP-NG format.
         
         The BPF driver drops packets in this way when the user-space 
         application that is retrieving captured packets from the 
         operating system does not read the file descritor at a 
         sufficient rate to avoid buffer overflow in the BPF driver.  
         Packets that are discarded in this way (due to limited buffer 
         capacity between the kernel and user-space) are reflected in 
         this count.
         
         The value xmonSourceStatsFilterAccept minus this column should 
         yield the number of packets that were eligible to be captured 
         by the monitoring application."
    REFERENCE   
        "bpf(4) manual page: bs_drop.
         PCAP-NG file format: isb_osdrop."
    ::= { xmonSourceStatsEntry 8 }

xmonSourceStatsUserDeliv OBJECT-TYPE
    SYNTAX      HCPerfCurrentCount
    MAX-ACCESS  read-only
    STATUS      current
    DESCRIPTION 
        "A count of the number of packets delivered to the monitoring 
         application since the beginning of the monitoring period.  This 
         value can be different than the value provided by the 
         difference between probeStatsFilterAccept and probeStatsOsDrop 
         because some packets could still lay in the OS buffers at the 
         time that the counts were read.  This is related to the bs_recv 
         field of the BIOCGSTATS stsructure except that it is the actual 
         number of packets read by the user-space application, whereas 
         bs_recv is the number of packets bufferred by the bpf(4) driver 
         and available to be read.  It is the isb_usrdeliv option field 
         in the PCAP-NG format."
    REFERENCE   
        "bpf(4) manual page: bs_recv.
         PCAP-NG file format: isb_usrdeliv."
    ::= { xmonSourceStatsEntry 9 }

xmonSourceHistTable OBJECT-TYPE
    SYNTAX      SEQUENCE OF XmonSourceHistEntry
    MAX-ACCESS  not-accessible
    STATUS      current
    DESCRIPTION 
        "Provides a table of historical statistics for sources available 
         for monitoring on this probe."
    ::= { xmonSource 3 }

xmonSourceHistEntry OBJECT-TYPE
    SYNTAX      XmonSourceHistEntry
    MAX-ACCESS  not-accessible
    STATUS      current
    DESCRIPTION 
        "Each row in the table provides historical collection statistics 
         associated with one collection interval for one source that has 
         been monitored."
    INDEX       { xmonSourceIndex, xmonSourceHistInterval }
    ::= { xmonSourceHistTable 1 }

XmonSourceHistEntry ::= SEQUENCE {
    xmonSourceHistInterval      Unsigned32,
    xmonSourceHistIfRecv        HCPerfIntervalCount,
    xmonSourceHistIfDrop        HCPerfIntervalCount,
    xmonSourceHistFilterAccept  HCPerfIntervalCount,
    xmonSourceHistOsDrop        HCPerfIntervalCount,
    xmonSourceHistUserDeliv     HCPerfIntervalCount
}

xmonSourceHistInterval OBJECT-TYPE
    SYNTAX      Unsigned32 (0..95)
    MAX-ACCESS  not-accessible
    STATUS      current
    DESCRIPTION 
        "Provides an index of the historical interval.  This is a number 
         between 0 and 95, where 0 is the most recent historical 
         interval and 95 is the least recevent interval.  Each interval 
         represents a 15-minute historical statistics collectino 
         interval."
    ::= { xmonSourceHistEntry 1 }

xmonSourceHistIfRecv OBJECT-TYPE
    SYNTAX      HCPerfIntervalCount
    MAX-ACCESS  read-only
    STATUS      current
    DESCRIPTION 
        "A count of the number of packets received from the physical 
         source during the collection period.  This is the number of 
         packets received by the physical source regardless of 
         monitoring.  It is obtained directly from the device driver.  
         This count does not include frames dropped due to framing 
         errors or invalid frame check sequences, but only those packets 
         successfully received by the physical source."
    REFERENCE   
        "PCAP-NG file format: isb_ifrecv."
    ::= { xmonSourceHistEntry 2 }

xmonSourceHistIfDrop OBJECT-TYPE
    SYNTAX      HCPerfIntervalCount
    MAX-ACCESS  read-only
    STATUS      current
    DESCRIPTION 
        "A count of the number of packets dropped by the source due to 
         lack of resources during the collection period.  This is the 
         number of packets dropped by the source regardless of 
         monitoring.  It is obtained directly from the device driver.  
         This count does not include frames dropped due to framing 
         errors or invalid frame check sequences, but only thos that 
         were not delivered to any upper layer doe to a lack of 
         resources in the physical source or device driver.
         
         The difference between xmonSourceHistIfRecv and this column 
         should be the number of packets that were eligible for capture 
         (i.e. presented to the filter)."
    REFERENCE   
        "PCAP-NG file format: isb_drop."
    ::= { xmonSourceHistEntry 3 }

xmonSourceHistFilterAccept OBJECT-TYPE
    SYNTAX      HCPerfIntervalCount
    MAX-ACCESS  read-only
    STATUS      current
    DESCRIPTION 
        "A count of the number of packets accepted by the filter over 
         the historical collection interval.  This is the bs_capt field 
         of the BIOCGSTATS structure and the isb_filteraccept option 
         field in the PCAP-NG format.
         
         The value xmonSourceHistIfRecv minus the sum of 
         xmonSourceHistIfDrop and this column should yeild the number of 
         packets dropped by the filter during the interval."
    REFERENCE   
        "bpf(4) manual page: bs_capt.
         PCAP-NG file format: isb_filteraccept."
    ::= { xmonSourceHistEntry 4 }

xmonSourceHistOsDrop OBJECT-TYPE
    SYNTAX      HCPerfIntervalCount
    MAX-ACCESS  read-only
    STATUS      current
    DESCRIPTION 
        "A count of the number of packets dropped by the operating 
         system during the historical collection interval.  This is the 
         bs_drop field of the BIOCGSTATS structure and the isb_osdrop 
         option field in the PCAP-NG format.
         
         The BPF driver drops packets in this way when the user-space 
         application that is retrieving captured packets from the 
         operating system does not read the file descritor at a 
         sufficient rate to avoid buffer overflow in the BPF driver.  
         Packets that are discarded in this way (due to limited buffer 
         capacity between the kernel and user-space) are reflected in 
         this count.
         
         The xmonSourceHistFilterAccept column minus this column should 
         yield the number of packets that were eligible to be captured 
         by the monitoring application."
    REFERENCE   
        "bpf(4) manual page: bs_drop.
         PCAP-NG file format: isb_osdrop."
    ::= { xmonSourceHistEntry 5 }

xmonSourceHistUserDeliv OBJECT-TYPE
    SYNTAX      HCPerfIntervalCount
    MAX-ACCESS  read-only
    STATUS      current
    DESCRIPTION 
        "A count of the number of packets delivered to the monitoring 
         application during the historical collection interval.  This 
         value can be different than the value provided by the 
         difference between probeStatsFilterAccept and probeStatsOsDrop 
         because some packets could still lay in the OS buffers at the 
         time that the counts were read.  This is related to the bs_recv 
         field of the BIOCGSTATS stsructure except that it is the actual 
         number of packets read by the user-space application, whereas 
         bs_recv is the number of packets bufferred by the bpf(4) driver 
         and available to be read.  It is the isb_usrdeliv option field 
         in the PCAP-NG format."
    REFERENCE   
        "bpf(4) manual page: bs_recv.
         PCAP-NG file format: isb_usrdeliv."
    ::= { xmonSourceHistEntry 6 }

xmonSourceTotalTable OBJECT-TYPE
    SYNTAX      SEQUENCE OF XmonSourceTotalEntry
    MAX-ACCESS  not-accessible
    STATUS      current
    DESCRIPTION 
        "Provides a table of totals of historical statistics for sources 
         available for monitoring on this probe."
    ::= { xmonSource 4 }

xmonSourceTotalEntry OBJECT-TYPE
    SYNTAX      XmonSourceTotalEntry
    MAX-ACCESS  not-accessible
    STATUS      current
    DESCRIPTION 
        "Each row in the table provides a total of historical collection 
         statistics associated with one source that has been monitored."
    INDEX       { xmonSourceIndex }
    ::= { xmonSourceTotalTable 1 }

XmonSourceTotalEntry ::= SEQUENCE {
    xmonSourceTotalValidIntervals   HCPerfValidIntervals,
    xmonSourceTotalIfRecv           HCPerfTotalCount,
    xmonSourceTotalIfDrop           HCPerfTotalCount,
    xmonSourceTotalFilterAccept     HCPerfTotalCount,
    xmonSourceTotalOsDrop           HCPerfTotalCount,
    xmonSourceTotalUserDeliv        HCPerfTotalCount
}

xmonSourceTotalValidIntervals OBJECT-TYPE
    SYNTAX      HCPerfValidIntervals
    MAX-ACCESS  read-only
    STATUS      current
    DESCRIPTION 
        "A count (between 0 and 96 inclusive) of the number of valid 
         historical collection intervals.  Valid collection intervals 
         are invtervals for which there is complete and valid 
         information."
    ::= { xmonSourceTotalEntry 1 }

xmonSourceTotalIfRecv OBJECT-TYPE
    SYNTAX      HCPerfTotalCount
    MAX-ACCESS  read-only
    STATUS      current
    DESCRIPTION 
        "A count of the total number of packets received from the 
         physical source during valid historical collection intervals.  
         This is the number of packets received by the physical source 
         regardless of monitoring.  It is obtained directly from the 
         device driver.  This count does not include frames dropped due 
         to framing errors or invalid frame check sequences, but only 
         those packets successfully received by the physical source."
    REFERENCE   
        "PCAP-NG file format: isb_ifrecv."
    ::= { xmonSourceTotalEntry 3 }

xmonSourceTotalIfDrop OBJECT-TYPE
    SYNTAX      HCPerfTotalCount
    MAX-ACCESS  read-only
    STATUS      current
    DESCRIPTION 
        "A count of the total number of packets dropped by the source 
         due to lack of resources during valid historical collection 
         intervals.  This is the number of packets dropped by the source 
         regardless of monitoring.  It is obtained directly from the 
         device driver.  This count does not include frames dropped due 
         to framing errors or invalid frame check sequences, but only 
         thos that were not delivered to any upper layer doe to a lack 
         of resources in the physical source or device driver.
         
         The difference between xmonSourceHistIfRecv and this column 
         should be the number of packets that were eligible for capture 
         (i.e. presented to the filter)."
    REFERENCE   
        "PCAP-NG file format: isb_drop."
    ::= { xmonSourceTotalEntry 4 }

xmonSourceTotalFilterAccept OBJECT-TYPE
    SYNTAX      HCPerfTotalCount
    MAX-ACCESS  read-only
    STATUS      current
    DESCRIPTION 
        "A count of the total number of packets accepted by the filter 
         over valid historical collection intervals.  This is the 
         bs_capt field of the BIOCGSTATS structure and the 
         isb_filteraccept option field in the PCAP-NG format.
         
         The value xmonSourceHistIfRecv minus the sum of 
         xmonSourceHistIfDrop and this column should yeild the number of 
         packets dropped by the filter during the interval."
    REFERENCE   
        "bpf(4) manual page: bs_capt.
         PCAP-NG file format: isb_filteraccept."
    ::= { xmonSourceTotalEntry 5 }

xmonSourceTotalOsDrop OBJECT-TYPE
    SYNTAX      HCPerfTotalCount
    MAX-ACCESS  read-only
    STATUS      current
    DESCRIPTION 
        "A count of the total number of packets dropped by the operating 
         system over valid historical collection intervals.  This is the 
         bs_drop field of the BIOCGSTATS structure and the isb_osdrop 
         option field in the PCAP-NG format.
         
         The BPF driver drops packets in this way when the user-space 
         application that is retrieving captured packets from the 
         operating system does not read the file descritor at a 
         sufficient rate to avoid buffer overflow in the BPF driver.  
         Packets that are discarded in this way (due to limited buffer 
         capacity between the kernel and user-space) are reflected in 
         this count.
         
         The xmonSourceHistFilterAccept column minus this column should 
         yield the number of packets that were eligible to be captured 
         by the monitoring application."
    REFERENCE   
        "bpf(4) manual page: bs_drop.
         PCAP-NG file format: isb_osdrop."
    ::= { xmonSourceTotalEntry 6 }

xmonSourceTotalUserDeliv OBJECT-TYPE
    SYNTAX      HCPerfTotalCount
    MAX-ACCESS  read-only
    STATUS      current
    DESCRIPTION 
        "A count of the total number of packets delivered to the 
         monitoring application over valid historical collection 
         intervals.  This value can be different than the value provided 
         by the difference between probeStatsFilterAccept and 
         probeStatsOsDrop because some packets could still lay in the OS 
         buffers at the time that the counts were read.  This is related 
         to the bs_recv field of the BIOCGSTATS stsructure except that 
         it is the actual number of packets read by the user-space 
         application, whereas bs_recv is the number of packets bufferred 
         by the bpf(4) driver and available to be read.  It is the 
         isb_usrdeliv option field in the PCAP-NG format."
    REFERENCE   
        "bpf(4) manual page: bs_recv.
         PCAP-NG file format: isb_usrdeliv."
    ::= { xmonSourceTotalEntry 7 }


-- =====================================================================
-- xmonInterface group
-- =====================================================================

xmonInterface OBJECT-IDENTITY
    STATUS      current
    DESCRIPTION 
        "The xmonInterface group is responsible for managing sources of 
         packet capture."
    ::= { xmonObjects 3 }

xmonInterfaceTable OBJECT-TYPE
    SYNTAX      SEQUENCE OF XmonInterfaceEntry
    MAX-ACCESS  not-accessible
    STATUS      current
    DESCRIPTION 
        "Provides a table of sources (interfaces) available for 
         monitoring and capture on this probe."
    ::= { xmonInterface 1 }

xmonInterfaceEntry OBJECT-TYPE
    SYNTAX      XmonInterfaceEntry
    MAX-ACCESS  not-accessible
    STATUS      current
    DESCRIPTION 
        "Each row provides a description of the characteristics of one 
         interface on this probe that can be monitored."
    INDEX       { xmonSourceIndex }
    ::= { xmonInterfaceTable 1 }

XmonInterfaceEntry ::= SEQUENCE {
    xmonInterfaceLinkType       DataLinkType,
    xmonInterfaceSnapLen        Unsigned32,
    xmonInterfacePromiscuous    TruthValue,
    xmonInterfaceMonitor        TruthValue,
    xmonInterfaceDirection      INTEGER,
    xmonInterfaceDescription    SnmpAdminString,
    xmonInterfacePhysAddr       PhysAddress,
    xmonInterfaceSpeed          Counter64,
    xmonInterfaceTsRes          INTEGER,
    xmonInterfaceTzone          Integer32,
    xmonInterfaceFilterType     FilterType,
    xmonInterfaceFilter         SnmpAdminString,
    xmonInterfaceFilterBpf      OCTET STRING,
    xmonInterfaceFilterStatus   INTEGER,
    xmonInterfaceOs             SnmpAdminString,
    xmonInterfaceFcsLen         Unsigned32,
    xmonInterfaceTsOffset       Counter64,
    xmonInterfaceStorageType    StorageType,
    xmonInterfaceRowStatus      RowStatus
}

xmonInterfaceLinkType OBJECT-TYPE
    SYNTAX      DataLinkType
    MAX-ACCESS  read-create
    STATUS      current
    DESCRIPTION 
        "Provides the data link type of the interface.  The data link 
         type has the same value as the data link type field of a PCAP 
         or PCAP-NG formatted file or feed.  Where multiple data link 
         types are supported by an interface, the agent will populate 
         this object by default with the data link type that preserves 
         the most data.  Only the data types that are compatible with 
         the interface may be written."
    REFERENCE   
        "bpfdrv(4) manual page, BIOCGDLT and BIOCSDLT ioctls."
    ::= { xmonInterfaceEntry 1 }

xmonInterfaceSnapLen OBJECT-TYPE
    SYNTAX      Unsigned32
    MAX-ACCESS  read-create
    STATUS      current
    DESCRIPTION 
        "Provides the snap length associated with the capture performed 
         on the interface.  The special value zero (0) specifies that 
         the snap length is unlimited.  The snap length is the maximum 
         number of octets that will be captured per packet, counting 
         from the beginning of the packet.  The default value is zero 
         (0) meaning the snap length is unlimited."
    REFERENCE   
        "pcap_set_snaplen(3pcap) manual page."
    DEFVAL      { 0 }
    ::= { xmonInterfaceEntry 2 }

xmonInterfacePromiscuous OBJECT-TYPE
    SYNTAX      TruthValue
    MAX-ACCESS  read-create
    STATUS      current
    DESCRIPTION 
        "Specifies whether to capture in promiscuous mode.  When 
         true(1), promiscuous capture is performed. When false(2), 
         non-promisuous capture is performed."
    REFERENCE   
        "pcap_set_promisc(3pcap) manual page."
    DEFVAL      { true }
    ::= { xmonInterfaceEntry 3 }

xmonInterfaceMonitor OBJECT-TYPE
    SYNTAX      TruthValue
    MAX-ACCESS  read-create
    STATUS      current
    DESCRIPTION 
        "Specifies whether to capture in monitor mode.  When true(1), 
         monitor mode capture is performed; when false(2), monitor mode 
         is not set for capture."
    REFERENCE   
        "pcap_set_rfmon(3pcap) manual page."
    DEFVAL      { false }
    ::= { xmonInterfaceEntry 4 }

xmonInterfaceDirection OBJECT-TYPE
    SYNTAX      INTEGER { any(0), in(1), out(2), inout(3) }
    MAX-ACCESS  read-create
    STATUS      current
    DESCRIPTION 
        "Specifies the directions of packets to capture as follows:
         
         - any(0), any packet seen by the interface regardless of 
           direction;
         - in(1), only packets received by the interface;
         - out(2), only packets send by the interface;
         - inout(3), packets received or sent by the interface.
           
         Not all directions are supported for all interfaces.  The value 
         any(0) represents the default and is supported by all 
         interfaces."
    REFERENCE   
        "pcap_setdirection(3pcap) manual page."
    DEFVAL      { any }
    ::= { xmonInterfaceEntry 5 }

xmonInterfaceDescription OBJECT-TYPE
    SYNTAX      SnmpAdminString
    MAX-ACCESS  read-only
    STATUS      current
    DESCRIPTION 
        "Provides a textual description of the interface.  This is the 
         same as the corresponding ifDesc value from the ifTable when 
         the ifIndex is specified in the xmonInterfaceIfIndex column.
         
         Note that net-snmp does not set this value correctly, but sets 
         it instead to the same values as the ifName value in the 
         ifXTtable (i.e. the name of the interface rather than its 
         description)."
    ::= { xmonInterfaceEntry 6 }

xmonInterfacePhysAddr OBJECT-TYPE
    SYNTAX      PhysAddress
    MAX-ACCESS  read-only
    STATUS      current
    DESCRIPTION 
        "Provides the physical address of the interface.  When no 
         physical address is associated with the interface, this value 
         will be a null octet string.  This is the same as the 
         corresponding ifPhysAddress value from the ifTable when the 
         ifIndex is specified in the xmonInterfaceIfIndex column.  When 
         the physical address is a 6 octet MAC-48 or EUI-48 address, 
         this value will go verbatim in the if_MACaddr option field of a 
         PCAP-NG format interface header for files and feeds captured 
         from this probe; when it is an 8-octet EUI-64 address, it will 
         go in the if_EUIaddr option field."
    DEFVAL      { "" }
    ::= { xmonInterfaceEntry 7 }

xmonInterfaceSpeed OBJECT-TYPE
    SYNTAX      Counter64
    MAX-ACCESS  read-only
    STATUS      current
    DESCRIPTION 
        "Provides the speed of the interface in bits per second.  The 
         value zero (0) is special and is used to indicate that the 
         speed of the interface is unknown or not applicable (e.g. 
         variable).  This is the same as the corresponding ifSpeed value 
         from the ifTable or converted ifHighSpeed value from the 
         ifXTable when the ifIndex is specified in the 
         xmonInterfaceTable column."
    ::= { xmonInterfaceEntry 8 }

xmonInterfaceTsRes OBJECT-TYPE
    SYNTAX      INTEGER { unknown(0), milli(3), micro(6), nano(9), 
                    bink(10), binM(20), binG(30), binary(32) }
    MAX-ACCESS  read-create
    STATUS      current
    DESCRIPTION 
        "Specifies the time resolution of timestamps.  The time 
         resolution if the minimum time granularity of the values used 
         to timestamp collected packets.  This object is single-valued 
         as follows:
         
         - unknown(0), unknown or unpsecified, it is assumed that time 
           stamps are in units of microseconds;
         - milli(3), decimal resolution to the millisecond;
         - micro(6), decimal resolution to the microsecond;
         - nano(9),  decimal resolution to the nanosecond;
         - bink(10), binary resolution to 2^-10 seconds;
         - binM(20), binary resolution to 2^-20 seconds;
         - binG(30),  binary resolution to 2^-30 seconds; 
         - binary(32), binary resolution to 2^-32 seconds.
           
         The agents should always support micro(6) resolution.  When set 
         to unknown(0), a time resolution of micro(6) is assumed.  This 
         value may be set by management stations.  The agent is not 
         required to support all settings.  If a management station 
         attempts to set an unsupported value, the previous supported 
         value will be retained.
         
         This value will be reflected into the if_tsresl option of the 
         interface header block in the PCAP-NG format file or feed for 
         this interface.  It is not reflected into the PCAP file format 
         because, although there is a place for it in the file header, 
         the PCAP file format does not make use of it and it is always 
         coded unknown(0)."
    DEFVAL      { micro }
    ::= { xmonInterfaceEntry 9 }

xmonInterfaceTzone OBJECT-TYPE
    SYNTAX      Integer32
    MAX-ACCESS  read-create
    STATUS      current
    DESCRIPTION 
        "Provides the time zone for packets collected from the interface 
         as the number of seconds of time offset from GMT.
         
         This value will be reflected into the if_tzone option of the 
         interface header block in the PCAP-NG format file or feed for 
         this interface.  It is not reflected into the PCAP file format 
         because, although there is a place fot it in the file header, 
         the PCAP file format does not make use of it and it is always 
         coded zero (0)."
    DEFVAL      { 0 }
    ::= { xmonInterfaceEntry 10 }

xmonInterfaceFilterType OBJECT-TYPE
    SYNTAX      FilterType
    MAX-ACCESS  read-create
    STATUS      current
    DESCRIPTION 
        "Provides the interface filter type used to filter packets from 
         the interface.  The filter type is set-valued as follows:
         
         - arp(0), capture ARP packets;
         - rarp(1), capture RARP packets;
         - lldp(2), capture LLDP packets;
         - dns(3), capture DNS packets;
         - mdns(4), capture mDNS packets;
         - m2pa(5), capture M2PA packets;
         - m2ua(6), capture M2UA packets;
         - m3ua(7), capture M3UA packets;
         - sua(8), capture SUA packets;
         - iua(9), capture IUA packets;
         - bicc(10), capture BICC packets;
         - sip(11), capture SIP packets;
         - h323(12), capture H.323 packets;
         - h248(13), capture H.248 packets;
         - q931(14), capture Q.931+ packets;
         - custom(15), apply a custom filter.
           
         When custom(15) is set, the other settings are ignored and the 
         filter is taken from the xmonInterfaceFilter and 
         xmonInterfaceFilterBpf columns.
         
         When other values are set, a filter string is generated that 
         filters the appropriate packets and it is placed by the agent 
         into xmonInterfaceFilter, and the compiled BPF bytecode program 
         is placed into xmonInterfaceFilterBfp.
         
         Protocols that use a transport address are filtered solely by 
         protocol type and well-known port number."
    DEFVAL      { {arp, rarp, lldp, dns, mdns, m2pa, m2ua, m3ua, sua} }
    ::= { xmonInterfaceEntry 11 }

xmonInterfaceFilter OBJECT-TYPE
    SYNTAX      SnmpAdminString
    MAX-ACCESS  read-create
    STATUS      current
    DESCRIPTION 
        "Provides the interface filter as a tcpdump (pcap) formatted 
         filter expression.  When the xmonInterfaceFilterType includes 
         custom(15), the agent generates the appropriate filter 
         expression and returns it for this object.  Any previously 
         written filter expression is remembered and returned should 
         custom(15) be added to the xmonInterfaceFilterType once again.
         
         When written, the agent will add custom(15) to the filter type 
         set and compiles the filter expression, setting the filter 
         status and BPF bytecode (when compilation is successful)."
    DEFVAL      { "" }
    ::= { xmonInterfaceEntry 12 }

xmonInterfaceFilterBpf OBJECT-TYPE
    SYNTAX      OCTET STRING
    MAX-ACCESS  read-create
    STATUS      current
    DESCRIPTION 
        "Provides the interface filter as a BPF format (native-endian) 
         bytecode filter program.  When the xmonInterfaceFilterType 
         includes custom(15), the agent generates and compiles the 
         appropriate filter expression and returns the BPF bytecode for 
         this object.  Any previously written BFP program is remembered 
         and returned should custom(15) be added to the 
         xmonInterfaceFilterType once again.
         
         When written, the agent will add custom(15) to the filter type, 
         nulls the filter expression, and sets the filter status."
    DEFVAL      { "" }
    ::= { xmonInterfaceEntry 13 }

xmonInterfaceFilterStatus OBJECT-TYPE
    SYNTAX      INTEGER { vacant(0), uninit(1), compiled(2), failed(3) }
    MAX-ACCESS  read-only
    STATUS      current
    DESCRIPTION 
        "Provides the status of the filter.  This object is 
         single-valued as follows:
         
         - vacant(0), there is no filter specified (even by type);
           
         - uninit(1), there is a filter expression specified; however, 
           it has yet to be compiled and verified;
           
         - compiled(2), there is a filter expression or program 
           specified and it has been compiled and verified;
           
         - failed(3), there is a filter expression or program but it 
           failed during compilation or verification.
           
         When a filter is uninit(1), it should proceed to the 
         compiled(2) or failed(3) within a short period of time.  When a 
         filter is failed(3) no filter will be applied to captured 
         packets."
    DEFVAL      { compiled }
    ::= { xmonInterfaceEntry 14 }

xmonInterfaceOs OBJECT-TYPE
    SYNTAX      SnmpAdminString
    MAX-ACCESS  read-create
    STATUS      current
    DESCRIPTION 
        "Specifies the name of the operating system of the machine in 
         which this interface is installed.  This information will go 
         verbatim into the if_os option field of a PCAP-NG file format 
         interface header for files and feeds captured from this probe.  
         The default value is the value of sysDescr or other suitable 
         operating system description string (e.g. uname -a).  Note that 
         in a PCAP-NG format file or feed, this value may be different 
         from the shb_os option field in the section header block when 
         the capture is performed by a different host."
    ::= { xmonInterfaceEntry 15 }

xmonInterfaceFcsLen OBJECT-TYPE
    SYNTAX      Unsigned32
    MAX-ACCESS  read-create
    STATUS      current
    DESCRIPTION 
        "Provides an integer value that specifies the length of the 
         frame check sequence (in bits) for this interface.  For link 
         layers whose FCS length can change during time, the special 
         value zero (0) is used.  This information will go verbatim into 
         the if_fcslen option of the interface header block in a PCAP-NG 
         format file or feed."
    ::= { xmonInterfaceEntry 16 }

xmonInterfaceTsOffset OBJECT-TYPE
    SYNTAX      Counter64
    UNITS       "seconds"
    MAX-ACCESS  read-only
    STATUS      current
    DESCRIPTION 
        "Specifies the time offset.  This field is not used and always 
         returnes zero (0)."
    DEFVAL      { 0 }
    ::= { xmonInterfaceEntry 17 }

xmonInterfaceStorageType OBJECT-TYPE
    SYNTAX      StorageType
    MAX-ACCESS  read-create
    STATUS      current
    DESCRIPTION 
        "Specifies the storage type for this conceptual row.  On write, 
         only storage types volatile(2) and nonVolatile(3) are 
         applicable.  volatile(2) rows do not persist across an agent 
         reboot."
    DEFVAL      { nonVolatile }
    ::= { xmonInterfaceEntry 18 }

xmonInterfaceRowStatus OBJECT-TYPE
    SYNTAX      RowStatus
    MAX-ACCESS  read-create
    STATUS      current
    DESCRIPTION 
        "Provides a mechanism whereby management stations may create and 
         destroy rows in this table.  The agent may autonomously create 
         and destroy entries in this table.  Creation of a row in this 
         table will fail if a row with the same value of xmonSourceIndex 
         exists in the xmonRmonTable.  Rows created in this table also 
         appear in the xmonSourceTable.  Rows deleted from this table 
         are also deleted from the xmonSourceTable."
    ::= { xmonInterfaceEntry 19 }

-- =====================================================================
-- xmonRmon group
-- =====================================================================

xmonRmon OBJECT-IDENTITY
    STATUS      current
    DESCRIPTION 
        "The xmonRmon group is responsible for managing remote 
         monitoring probes that provide capture using mib-2 RMON-MIB 
         capture(8) capabilities."
    ::= { xmonObjects 4 }

xmonRmonTable OBJECT-TYPE
    SYNTAX      SEQUENCE OF XmonRmonEntry
    MAX-ACCESS  not-accessible
    STATUS      current
    DESCRIPTION 
        "The probe, collector and network management system are capable 
         of collecting captured packets from remote probes that 
         implement the RMON-MIB capture capabilities.  The table 
         provides a list of definitions of remote RMON capture instances 
         from which the collector will capture packets."
    ::= { xmonRmon 1 }

xmonRmonEntry OBJECT-TYPE
    SYNTAX      XmonRmonEntry
    MAX-ACCESS  not-accessible
    STATUS      current
    DESCRIPTION 
        "Each row in the table specifies the character of one remote 
         RMON probe capture instance for collection."
    INDEX       { xmonSourceIndex }
    ::= { xmonRmonTable 1 }

XmonRmonEntry ::= SEQUENCE {
    xmonRmonIndex           Unsigned32,
    xmonRmonAddrType        TransportAddressType,
    xmonRmonAddr            TransportAddress,
    xmonRmonSnmpVersion     INTEGER,
    xmonRmonCommunity       SnmpAdminString,
    xmonRmonUsername        SnmpAdminString,
    xmonRmonPassword        SnmpAdminString,
    xmonRmonBuffCtrlIndex   Integer32,
    xmonRmonBuffIndex       Integer32,
    xmonRmonStorageType     StorageType,
    xmonRmonRowStatus       RowStatus
}

xmonRmonIndex OBJECT-TYPE
    SYNTAX      Unsigned32
    MAX-ACCESS  not-accessible
    STATUS      current
    DESCRIPTION 
        "Provides a non-zero ordinal index into this table.  Aside from 
         its use as an index, this attribute has no other significance."
    ::= { xmonRmonEntry 1 }

xmonRmonAddrType OBJECT-TYPE
    SYNTAX      TransportAddressType
    MAX-ACCESS  read-create
    STATUS      current
    DESCRIPTION 
        "Specifies the transport address type.  The client supported 
         SNMP-supported transport address types: udpIpv4(1), 
         udpIpv4z(3), udpIpv6(2), udpIpv6z(4), and udpDns(14)."
    REFERENCE   
        "TRANSPORT-ADDRESS-MIB, TransportAddressType."
    ::= { xmonRmonEntry 2 }

xmonRmonAddr OBJECT-TYPE
    SYNTAX      TransportAddress
    MAX-ACCESS  read-create
    STATUS      current
    DESCRIPTION 
        "Specifies the transport address of the RMON probe from which to 
         collect capture packets.  The address is of type 
         xmonRmonAddrType."
    REFERENCE   
        "TRANSPORT-ADDRESS-MIB, TransportAddress."
    ::= { xmonRmonEntry 3 }

xmonRmonSnmpVersion OBJECT-TYPE
    SYNTAX      INTEGER { any(0), v1(1), v2c(2), v3(3) }
    MAX-ACCESS  read-create
    STATUS      current
    DESCRIPTION 
        "Specifies the version of SNMP to use when collecting captured 
         packets from the remote RMON host."
    ::= { xmonRmonEntry 4 }

xmonRmonCommunity OBJECT-TYPE
    SYNTAX      SnmpAdminString
    MAX-ACCESS  read-create
    STATUS      current
    DESCRIPTION 
        "Specifies the SNMP v2c community string to be used when 
         collecting captured packets from the remote RMON host."
    DEFVAL      { "public" }
    ::= { xmonRmonEntry 5 }

xmonRmonUsername OBJECT-TYPE
    SYNTAX      SnmpAdminString
    MAX-ACCESS  read-create
    STATUS      current
    DESCRIPTION 
        "Specifies the SNMP v3 username to be used when collecting 
         captured packets from the remote RMON host."
    DEFVAL      { "unexicon" }
    ::= { xmonRmonEntry 6 }

xmonRmonPassword OBJECT-TYPE
    SYNTAX      SnmpAdminString
    MAX-ACCESS  read-create
    STATUS      current
    DESCRIPTION 
        "Specifies the SNMP v3 password to be used when collecting 
         captured packets from the remote RMON host.  A read of this 
         object will only return the number of '*' characters equal to 
         the length of the password."
    DEFVAL      { "unexicon" }
    ::= { xmonRmonEntry 7 }

xmonRmonBuffCtrlIndex OBJECT-TYPE
    SYNTAX      Integer32 (1..65535)
    MAX-ACCESS  read-create
    STATUS      current
    DESCRIPTION 
        "Provides the value of the bufferControlIndex index into the 
         bufferControlTable in the RMON-MIB.  In combination with the 
         transport address, this uniquely defines the RMON-MIB capture 
         source."
    REFERENCE   
        "RMON-MIB, bufferControlIndex."
    ::= { xmonRmonEntry 8 }

xmonRmonBuffIndex OBJECT-TYPE
    SYNTAX      Integer32 (1..2147483647)
    MAX-ACCESS  read-only
    STATUS      current
    DESCRIPTION 
        "Provides the value of the captureBufferIndex index into the 
         captureBufferTable in the RMON-MIB.  In combination with the 
         other remote attributes, this uniquely defines the packet that 
         was last imported from this capture source."
    REFERENCE   
        "RMON-MIB, captureBufferIndex."
    DEFVAL      { 1 }
    ::= { xmonRmonEntry 9 }

xmonRmonStorageType OBJECT-TYPE
    SYNTAX      StorageType
    MAX-ACCESS  read-create
    STATUS      current
    DESCRIPTION 
        "Specifies the storage type for this conceptual row.  On write, 
         only storage types volatile(2) and nonVolatile(3) are 
         applicable.  volatile(2) rows do not persist across an agent 
         reboot."
    DEFVAL      { nonVolatile }
    ::= { xmonRmonEntry 10 }

xmonRmonRowStatus OBJECT-TYPE
    SYNTAX      RowStatus
    MAX-ACCESS  read-create
    STATUS      current
    DESCRIPTION 
        "Provides a mechanism whereby management stations may create and 
         destroy rows in this table.  The agent may autonomously create 
         and destroy entries in this table.  Creation of a row in this 
         table will fail if a row with the same value of xmonSourceIndex 
         exists in the xmonRmonTable.  Rows created in this table also 
         appear in the xmonSourceTable.  Rows deleted from this table 
         are also deleted from the xmonSourceTable."
    ::= { xmonRmonEntry 11 }

-- =====================================================================
-- xmonBuffer group
-- =====================================================================

xmonBuffer OBJECT-IDENTITY
    STATUS      current
    DESCRIPTION 
        "The xmonBuffer group is responsible for managing the buffer.  
         Live feeds can take their capture from the buffer."
    ::= { xmonObjects 5 }

xmonBufferAdminState OBJECT-TYPE
    SYNTAX      AdministrativeState
    MAX-ACCESS  read-write
    STATUS      current
    DESCRIPTION 
        "Represents the administrative capability of the buffer to 
         perform its function.  The following adminstrative states are 
         defined:
         
         - locked(0), use of the buffer has been prhobited by a managing 
           system; packets from the buffer may be retreived but new 
           packets shall not be added to the buffer; packets may 
           be removed;
           
         - unlocked(1), use of the buffer has been permitted by a 
           managing system; packets from the buffer may be retrieved 
           and, conditional on the values of other state and status 
           attributes, new packets may be added;
           
         - shuttingDown(2), use of the buffer has been prohibited by a 
           managing system; however, the managed system is in the 
           process of shutting down the buffer; once this procedure 
           completes, the buffer will move to the locked(0) state.
           
         The value of shuttingDown(2) can be read but not written."
    REFERENCE   
        "OPENSS7-SMI-MIB, AdministrativeState.
         ITU-T Rec. X.735 (1992) | ISO/IEC 10164-6 : 1993, 
               Section 8.1.1.1.3."
    ::= { xmonBuffer 1 }

xmonBufferOpState OBJECT-TYPE
    SYNTAX      OperationalState
    MAX-ACCESS  read-only
    STATUS      current
    DESCRIPTION 
        "Indicates the operational capability of the buffer to perform 
         its function.  The following operational states are defined:
         
         - enabled(0), the buffer is operational and ready for use; 
           information from bufferred packets may be retreived and, 
           conditional on the values of other state and status 
           attributes, new packets may be added;
           
         - disabled(1), the buffer is not available for use; new packets 
           cannot be added.
           
         A change in operational state shall generate a state changed 
         notification."
    REFERENCE   
        "OPENSS7-SMI-MIB, OperationalState.
         ITU-T Rec. X.735 (1992) | ISO/IEC 10164-6 : 1993, 
               Section 8.1.1.1.4."
    ::= { xmonBuffer 2 }

xmonBufferAvailStatus OBJECT-TYPE
    SYNTAX      AvailabilityStatus
    MAX-ACCESS  read-only
    STATUS      current
    DESCRIPTION 
        "Indicates the availability status of the buffer.  The attribute 
         can indicate a logFull(8) condition; indicating that bufferred 
         packets can be retreived but that no new packets can be 
         bufferred.  The following availabliity status members are 
         defined:
         
         - inTest(0), not used;
         - failed(1), not used;
         - powerOff(2), not used;
         - offLine(3), set when the administrative state is locked(0) or 
           the operational state is disabled(1), except when unavailable 
           in accordance with a predetermined schedule;
         - offDuty(4), set when buffer has been unavailable in 
           accordance with a predetermined schedule;
         - dependency(5), capture to the buffer depends on the 
           definition of a source from which to capture; this value is 
           set when no monitoring source is defined from which to 
           caputre;
         - degraded(6), not used;
         - notInstalled(7), not used;
         - logFull(8), set when the buffer can no longer store captured 
           packets because the buffer is full in accordanc with the 
           criteria specified by other attributes.
           
         No state chanige notification is generated when this object 
         changes value."
    REFERENCE   
        "OPENSS7-SMI-MIB, AvailabilityStatus.
         ITU-T Rec. X.735 (1992) | ISO/IEC 10164-6 : 1993, 
               Section 8.1.1.1.6.
         ITU-T Rec. X.735 (1992) | ISO/IEC 10164-6 : 1993, 
               Section 8.1.1.4.1."
    ::= { xmonBuffer 3 }

xmonBufferFullAction OBJECT-TYPE
    SYNTAX      FullAction
    MAX-ACCESS  read-write
    STATUS      current
    DESCRIPTION 
        "Specifies the action to be taken when the maximum size of the 
         buffer has been reached in accordance with sizing criteria and 
         attributes.  Values are:
         
         - wrap(0), the oldest packets in the buffer, as determined by 
           the bufferred packet time stamp (or other discard policy 
           determined by xmonBufferDiscardPolicy), will be deleted to 
           free resources for the addition of new packets;
           
         - halt(1), no more packets will be added to the buffer; 
           packets already present will be retained;
           
         Both options are supported by the agent.  The default full 
         action for the buffer is wrap(0)."
    REFERENCE   
        "OPENSS7-SMI-MIB, FullAction.
         ITU-T Rec. X.735 (1992) | ISO/IEC 10164-6 : 1993, 
               Section 8.1.1.1.5."
    DEFVAL      { wrap }
    ::= { xmonBuffer 4 }

xmonBufferMaxSize OBJECT-TYPE
    SYNTAX      Unsigned32
    UNITS       "kbytes"
    MAX-ACCESS  read-write
    STATUS      current
    DESCRIPTION 
        "Specifies the size of the buffer, measured in number of 
         1024-byte blocks.  A buffer may have an indeterminate size.  A 
         maximum buffer size of zero (0) specifies that the buffer has 
         no predefined limit based on octets although other attributes 
         may contribute to a 'log-full' criteria.
         
         Note: since the buffer size is specified in kbytes, the actual 
         amount of information that is contained in a buffer will be 
         determined by the data representation in the buffer.  This data 
         representation is not subject to standardization.  The maximum 
         buffer size does not include the system overhead involved in 
         establishing the buffer.  Thus, immediately after creation, the 
         buffer size should read zero."
    REFERENCE   
        "ITU-T Rec. X.735 (1992) | ISO/IEC 10164-6 : 1993, 
               Section 8.1.1.2.1."
    DEFVAL      { 0 }
    ::= { xmonBuffer 5 }

xmonBufferMaxPackets OBJECT-TYPE
    SYNTAX      Unsigned32
    UNITS       "packets"
    MAX-ACCESS  read-write
    STATUS      current
    DESCRIPTION 
        "Specifies the maximum number of packets that will be stored in 
         the buffer before wrapping or halting occurs.  The value zero 
         (0) specifies that the buffer has no predefined limit based on 
         number of messages although other attributes may contribute to 
         a 'log-full' criteria.  Unfortunately, a maximum number of 
         packets of over 4G cannot be specified."
    ::= { xmonBuffer 6 }

xmonBufferMaxTime OBJECT-TYPE
    SYNTAX      TimeInterval
    UNITS       "seconds"
    MAX-ACCESS  read-write
    STATUS      current
    DESCRIPTION 
        "Specifies the maximum time interval for which messages will be 
         sotre in the buffer before wrapping or halting occurs.  The 
         value zero (0) specifies that the buffer has no predefined 
         limit based on duration of time although other attributes may 
         contribute to a 'log-full' criteria."
    ::= { xmonBuffer 7 }

xmonBufferCurrentSize OBJECT-TYPE
    SYNTAX      HCPerfCurrentCount
    UNITS       "kbytes"
    MAX-ACCESS  read-only
    STATUS      current
    DESCRIPTION 
        "Indicates the current size of the buffer measured in 1024-byte 
         blocks.
         
         Note: since the buffer size is specified in kbytes, the actual 
         amount of information that is contained in a buffer will be 
         determined by the data representation in the buffer.  This data 
         representation is not subject to standardization.  THe maximum 
         buffer size does not includes the system overhead involved in 
         establishing the buffer.  Thus immediately after creation, the 
         buffer size should read zero."
    REFERENCE   
        "ITU-T Rec. X.735 (1992) | ISO/IEC 10164-6 : 1993, 
               Section 8.1.1.2.2."
    ::= { xmonBuffer 8 }

xmonBufferNumberOfPackets OBJECT-TYPE
    SYNTAX      Counter64
    UNITS       "packets"
    MAX-ACCESS  read-only
    STATUS      current
    DESCRIPTION 
        "Indicates the current number of packets in the buffer."
    REFERENCE   
        "ITU-T Rec. X.735 (1992) | ISO/IEC 10164-6 : 1993, 
               Section 8.1.1.2.3."
    ::= { xmonBuffer 9 }

xmonBufferCurrentInterval OBJECT-TYPE
    SYNTAX      TimeInterval
    UNITS       "seconds"
    MAX-ACCESS  read-only
    STATUS      current
    DESCRIPTION 
        "Indicates the current time interval (in seconds) over which 
         messages are contained in the buffer.  This is the time 
         interval (in seconds) since the buffer was created."
    ::= { xmonBuffer 10 }

xmonBufferAlarmThreshold OBJECT-TYPE
    SYNTAX      LogCapacityAlarmThreshold
    UNITS       "%"
    MAX-ACCESS  read-write
    STATUS      current
    DESCRIPTION 
        "Specifies the threshold above which transmission of alarms will 
         occur.  This threshold is only applicable if a finite and fixed 
         criteria (from xmonBufferMaxSize, xmonBufferMaxPackets, and 
         xmonBufferMaxTime) exists and the corresponding current value 
         has approached the specified percentage of that limit.
         
         The value specifies as a percentage of the final limiting 
         criteria (e.g. buffer size) at which an event will be generated 
         to indicate that a 'log-full' or 'log-wrap' condition is 
         approaching.  This attribute is set-valued.  Support of this 
         attribute is mandatory for the halt(1) behaviour (see 
         xmonBufferFullAction).  When a buffer is created with the 
         wrap(0) condition, the capacity threshold events are triggered 
         as if coupled to a gauge that counts from zero to the highest 
         capacity threshold value defined and then resets to zero."
    REFERENCE   
        "ITU-T Rec. X.735 (1992) | ISO/IEC 10164-6 : 1993, 
               Section 8.1.1.3."
    DEFVAL      { "\x64" }
    ::= { xmonBuffer 11 }

xmonBufferOctetHiWaterMark OBJECT-TYPE
    SYNTAX      Counter64
    UNITS       "octets"
    MAX-ACCESS  read-only
    STATUS      current
    DESCRIPTION 
        "Provides the high water mark of the number of packet payload 
         octets in the buffer since the low water mark was last set or 
         since the last reset.  xmonBufferReset can be used to reset 
         this gauge to zero.  This value can be used to properly size 
         the buffer so that it is unlikely to wrap or 
         halt."
    ::= { xmonBuffer 12 }

xmonBufferOctetLoWaterMark OBJECT-TYPE
    SYNTAX      Counter64
    UNITS       "octets"
    MAX-ACCESS  read-only
    STATUS      current
    DESCRIPTION 
        "Provides the low water mark of the number of packet payload 
         octets in the buffer since the high water mark was last set or 
         since the last reset.  xmonBufferReset can be used to reset 
         this gauge to zero.  This value can be used to properly size 
         the buffer so that it is unlikely to wrap or halt."
    ::= { xmonBuffer 13 }

xmonBufferPktsHiWaterMark OBJECT-TYPE
    SYNTAX      Counter64
    UNITS       "packets"
    MAX-ACCESS  read-only
    STATUS      current
    DESCRIPTION 
        "Provides the high water mark of the number of packets in the 
         buffer since the low water mark was last set or since the last 
         reset.  xmonBufferReset may be used to reset this gauge to 
         zero.  This value can be used to properly size the buffer so 
         that it is unlikely to wrap or halt."
    ::= { xmonBuffer 14 }

xmonBufferPktsLoWaterMark OBJECT-TYPE
    SYNTAX      Counter64
    UNITS       "packets"
    MAX-ACCESS  read-only
    STATUS      current
    DESCRIPTION 
        "Provides the low water mark of the number of packets in the 
         buffer since the high water mark was last set or since the last 
         reset.  xmonBufferReset can be used to reset this gauge to 
         zero.  This value can be used to properly size the buffer so 
         that it is unlikely to wrap or halt."
    ::= { xmonBuffer 15 }

xmonBufferTimeHiWaterMark OBJECT-TYPE
    SYNTAX      TimeInterval
    MAX-ACCESS  read-only
    STATUS      current
    DESCRIPTION 
        "Provides the high water mark of the duration of time for buffer 
         since the low water mark was last set or since the last reset.  
         xmonBufferReset may be used to reset this gauge to zero.  This 
         value can be used to properly size the buffer so that it is 
         unlikely to wrap or halt."
    ::= { xmonBuffer 16 }

xmonBufferTimeLoWaterMark OBJECT-TYPE
    SYNTAX      TimeInterval
    MAX-ACCESS  read-only
    STATUS      current
    DESCRIPTION 
        "Provides the low water mark of the duration of time for buffer 
         since the high water mark was last set or since the last reset.  
         xmonBufferReset may be used to reset this gauge to zero.  This 
         value can be used to properly size the buffer so that it is 
         unlikely to wrap or halt."
    ::= { xmonBuffer 17 }

xmonBufferDrops OBJECT-TYPE
    SYNTAX      PerfCurrentCount
    UNITS       "packets"
    MAX-ACCESS  read-only
    STATUS      current
    DESCRIPTION 
        "Indicates the number of packets dropped as a result of buffer 
         wrap or buffer halt.  When the buffer is set for wrap(0), this 
         is the number of messages dropped from the front of the buffer.  
         When the buffer is set to halt(1), this is the number of 
         messages dropped from the end of the buffer.  This number is 
         reset by reading the first or last message in the buffer 
         (respectively).  It may also be reset using xmonBufferReset."
    DEFVAL      { 0 }
    ::= { xmonBuffer 18 }

xmonBufferReset OBJECT-TYPE
    SYNTAX      INTEGER { reset(0) }
    MAX-ACCESS  read-write
    STATUS      current
    DESCRIPTION 
        "When written, resets the buffer high and low watermarks to 
         zero.  Also, reset the number of message buffer drops."
    DEFVAL      { reset }
    ::= { xmonBuffer 19 }

xmonBufferTimeElapsed OBJECT-TYPE
    SYNTAX      TimeInterval
    MAX-ACCESS  read-only
    STATUS      current
    DESCRIPTION 
        "Indicates the time interval covered by the buffer.  This may be 
         different than the difference between timestamps of the first 
         message and the last message captured, because there may have 
         been a period of time after capture began for which no messages 
         were yet captured.  The interval should equal the difference 
         between the xmonBufferEndTime and the xmonBufferBegTime."
    ::= { xmonBuffer 20 }

xmonBufferBegTime OBJECT-TYPE
    SYNTAX      TimeStamp
    MAX-ACCESS  read-only
    STATUS      current
    DESCRIPTION 
        "Indicates the time (using the TimeStamp textual convention) 
         that the capture buffer was opened (capture of messages to the 
         buffer began), reset or cleared."
    ::= { xmonBuffer 21 }

xmonBufferEndTime OBJECT-TYPE
    SYNTAX      TimeStamp
    MAX-ACCESS  read-only
    STATUS      current
    DESCRIPTION 
        "Indicates the time (using the TimeStamp textual convention) 
         that the capture buffer was closed (capture of messages to the 
         buffer ended) or the time stamp of the last packet in the 
         buffer."
    ::= { xmonBuffer 22 }

xmonBufferIfRecv OBJECT-TYPE
    SYNTAX      HCPerfCurrentCount
    UNITS       "packets"
    MAX-ACCESS  read-only
    STATUS      current
    DESCRIPTION 
        "Indicates the total number of packets received from the 
         interface contained in the buffer during its capture period and 
         since the last reset or clear.
         
         This is the number of packets received by the physical 
         interface regardless of monitoring.  It is obtained directly 
         from the device driver."
    REFERENCE   
        "PCAP-NG file format: isb_ifrecv."
    ::= { xmonBuffer 23 }

xmonBufferIfDrop OBJECT-TYPE
    SYNTAX      HCPerfCurrentCount
    UNITS       "packets"
    MAX-ACCESS  read-only
    STATUS      current
    DESCRIPTION 
        "Indicates the total number of packets that were dropped by any 
         interface contained in the buffer due to resource shortage 
         during its capture period and since the last reset or clear.
         
         This is the number of packets dropped by the interface 
         regardless of monitoring.  It is obtained directly from the 
         device driver."
    REFERENCE   
        "PCAP-NG file format: isb_drop."
    ::= { xmonBuffer 24 }

xmonBufferFilterAccept OBJECT-TYPE
    SYNTAX      HCPerfCurrentCount
    UNITS       "packets"
    MAX-ACCESS  read-only
    STATUS      current
    DESCRIPTION 
        "Indicates the total number of packets accepted by the filter on 
         any interface contained in the buffer during its capture period 
         and since the last reset or clear.
         
         This is the bs_capt field of the BIOCGSTATS structure and the 
         isb_filteraccept option in the PCAP-NG format."
    REFERENCE   
        "bpf(4) manual page: bs_capt.
         PCAP-NG file format: isb_filteraccept."
    ::= { xmonBuffer 25 }

xmonBufferOsDrop OBJECT-TYPE
    SYNTAX      HCPerfCurrentCount
    UNITS       "packets"
    MAX-ACCESS  read-only
    STATUS      current
    DESCRIPTION 
        "Indicates the total number of packets that were dropped by the 
         operating system (i.e. the device driver) for any interface 
         contained in the buffer during its capture period and since the 
         last reset or clear.
         
         This is the bs_drop field of the BIOCGSTATS structure and the 
         isb_osdrop option in the PCAP-NG format."
    REFERENCE   
        "bpf(4) manual page: bs_drop.
         PCAP-NG file format: isb_osdrop."
    ::= { xmonBuffer 26 }

xmonBufferUserDeliv OBJECT-TYPE
    SYNTAX      HCPerfCurrentCount
    UNITS       "packets"
    MAX-ACCESS  read-only
    STATUS      current
    DESCRIPTION 
        "Indicates the total number of packets that were delivered to 
         the user-space capture application for any interface contained 
         in the buffer during its capture period and since the last 
         reset or clear.
         
         This is related to the bs_recv field of the BIOCGSTATS 
         structure except that it is that actual number of packets read 
         by the user-space application, whereas bs_recv is the number of 
         packets bufferred by the bpf(4) driver and available to be 
         read.  It is the isb_usrdeliv option in the PCAP-NG format."
    REFERENCE   
        "bpf(4) manual page: bs_recv.
         PCAP-NG file format: isb_usrdeliv."
    ::= { xmonBuffer 27 }

xmonBufferIfCompress OBJECT-TYPE
    SYNTAX      HCPerfCurrentCount
    UNITS       "packets"
    MAX-ACCESS  read-only
    STATUS      current
    DESCRIPTION 
        "Indicates the total number of packets (frames) that were 
         compressed for any interface contained in the buffer during its 
         capture period and since the last reset or clear."
    ::= { xmonBuffer 28 }

xmonBufferUserOctets OBJECT-TYPE
    SYNTAX      HCPerfCurrentCount
    UNITS       "octets"
    MAX-ACCESS  read-only
    STATUS      current
    DESCRIPTION 
        "Indicates the total number of packet payload octets that were 
         captured for any interface contained in the buffer during its 
         capture period."
    ::= { xmonBuffer 29 }

xmonBufferActionResult OBJECT-TYPE
    SYNTAX      INTEGER { success(0), failure(1), clear(2) }
    MAX-ACCESS  read-write
    STATUS      current
    DESCRIPTION 
        "Provides actions and their results.  The action-result is 
         single-valued and can assume one of the following values:
         
         - success(0), the last action was successful;
         - failure(1), the last action failed;
         - clear(2), clear the capture buffer.
           
         When written, only the value clear(2) is valid and represents 
         the action to be performed.  When read, only the values 
         success(0) or failure(1) will be returned and represent the 
         result of the previous action."
    ::= { xmonBuffer 30 }

-- =====================================================================
-- xmonCapture group
-- =====================================================================

xmonCapture OBJECT-IDENTITY
    STATUS      current
    DESCRIPTION 
        "The xmonCapture group is responsible for managing the naming, 
         rotation, spooling of capture files."
    ::= { xmonObjects 6 }

xmonCapturePath OBJECT-TYPE
    SYNTAX      SubstitutionString
    MAX-ACCESS  read-write
    STATUS      current
    DESCRIPTION 
        "Specifies the file system path to the directory where files are 
         spooled as they are being captured.  All substitutions are 
         supported except %I.  The default if not specified is 
         '/var/local/openss7/xmon/spool/%P'.
         
         In general this value should not be changed from its default 
         because external programs might rely on files being present at 
         the default path."
    DEFVAL      { "/var/local/openss7/xmon/spool/%P" }
    ::= { xmonCapture 1 }

xmonCaptureFilename OBJECT-TYPE
    SYNTAX      SubstitutionString
    MAX-ACCESS  read-write
    STATUS      current
    DESCRIPTION 
        "Specifies the file name (without extension) for capture files, 
         both spooled and rotated.  All substitutions are supported.  
         The appropriate file extension is always added to this name.  
         The default if not specified is 'xmon-%I-%Y-%M-%D-%h:%m:%s'."
    DEFVAL      { "xmon-%I-%Y-%M-%D-%h:%m:%s" }
    ::= { xmonCapture 2 }

xmonCaptureAdminState OBJECT-TYPE
    SYNTAX      AdministrativeState
    MAX-ACCESS  read-write
    STATUS      current
    DESCRIPTION 
        "Represents the administrative capability of capture to perform 
         its function.  The following administrative states are defined:
         
         - locked(0), use of the capture has been prohibited by a 
           managing system; information from subordinate spool files may 
           be retreived but new files shall not be created; files may be 
           deleted;
           
         - unlocked(1), use of the capture has been permitted by a 
           managing system; information from subordinate spool files may 
           by retrieved and, conditional on the values of other state 
           and status attributes, new files may be created;
           
         - shuttingDown(2), use of the capture has been prohibited by a 
           managing system; however, the managed system is in the 
           process of shutting down ongoing capture; once this procedure 
           completes, the capture will move to the locked(0) state.
           
         The value of shuttingDown(2) can be read but not written."
    REFERENCE   
        "OPENSS7-SMI-MIB, AdministrativeState.
         ITU-T Rec. X.735 (1992) | ISO/IEC 10164-6 : 1993, 
               Section 8.1.1.1.3."
    ::= { xmonCapture 3 }

xmonCaptureOpState OBJECT-TYPE
    SYNTAX      OperationalState
    MAX-ACCESS  read-only
    STATUS      current
    DESCRIPTION 
        "Indicates the operational capability of the capture to perform 
         its function.  The following operational states are defined:
         
         - enabled(0), the capture is operational and ready for use; 
           information from subordinate spool files may be retreived 
           and, conditional on the values of other state and status 
           attributes, new files may be created;
           
         - disabled(1), the capture is not available for use; new spool 
           files cannot be created.
           
         A change in operational state shall generate a state changed 
         notification."
    REFERENCE   
        "OPENSS7-SMI-MIB, OperationalState.
         ITU-T Rec. X.735 (1992) | ISO/IEC 10164-6 : 1993, 
               Section 8.1.1.1.4."
    ::= { xmonCapture 4 }

xmonCaptureAvailStatus OBJECT-TYPE
    SYNTAX      AvailabilityStatus
    MAX-ACCESS  read-only
    STATUS      current
    DESCRIPTION 
        "Indicates the availability status of the capture.  The 
         attribute can indicate a 'log-full' condition; indicating that 
         spool files can be retrieved but that no new spool files can be 
         added.  The following availabiltiy status members are defined:
         
         - inTest(0), not used;
         - failed(1), not used;
         - powerOff(2), not used;
         - offLine(3), set when the administrative state is locked(0) or 
           the operational state is disabled(1);
         - offDuty(4), set when capture has been unavailable in 
           accordance with a predetermined time schedule;
         - dependency(5), capture depends on the definition of a 
           monitoring source from which to capture; this value is set 
           when no monitoring source is defined from which to capture;
         - degraded(6), not used;
         - notInstalled(7), not used;
         - logFull(8), set when capture can no longer buffer or spool 
           captured packets because the capture is full in accordance 
           with the criteria specified by other attributes.
           
         No state change notification is generated when this object 
         changes value."
    REFERENCE   
        "OPENSS7-SMI-MIB, AvailabilityStatus.
         ITU-T Rec. X.735 (1992) | ISO/IEC 10164-6 : 1993, 
               Section 8.1.1.1.6.
         ITU-T Rec. X.735 (1992) | ISO/IEC 10164-6 : 1993, 
               Section 8.1.1.4.1."
    ::= { xmonCapture 5 }

xmonCaptureFullAction OBJECT-TYPE
    SYNTAX      FullAction
    MAX-ACCESS  read-write
    STATUS      current
    DESCRIPTION 
        "Specifies the action to be taken when the maximum size of the 
         capture has been reached in accordance with sizing criteria and 
         attributes.  Values are:
         
         - wrap(0), the oldest spool files in the capture, as determined 
           by the spool file time stamp (or other discard policy 
           determined by xmonCaptureDiscardPolicy), will be deleted to 
           free resources for the creation of new spool files;
           
         - halt(1), no more spool files will be generated; files 
           already spooled will be retained;
           
         Both options are supported by the agent.  The default full 
         action for capture is wrap(0)."
    REFERENCE   
        "OPENSS7-SMI-MIB, FullAction.
         ITU-T Rec. X.735 (1992) | ISO/IEC 10164-6 : 1993, 
               Section 8.1.1.1.5."
    DEFVAL      { wrap }
    ::= { xmonCapture 6 }

xmonCaptureMaxSize OBJECT-TYPE
    SYNTAX      Unsigned32
    UNITS       "kbytes"
    MAX-ACCESS  read-write
    STATUS      current
    DESCRIPTION 
        "Specifies the size of the capture, measured in number of 
         1024-byte blocks.  A capture may have an indeterminate size.  A 
         maximum capture size of zero (0) specifies that the capture has 
         no predefined limit based on octets although other attributes 
         may contribute to a 'log-full' criteria.
         
         Note: since the capture size is specified in octets, the actual 
         amount of information that is contained in a capture will be 
         determined by the data representation in the capture.  This 
         data representation is not subject to standardization.  The 
         maximum capture size does not include the system overhead 
         involved in establishing the capture.  Thus, immediately after 
         creation, the capture size should read zero."
    REFERENCE   
        "ITU-T Rec. X.735 (1992) | ISO/IEC 10164-6 : 1993, 
               Section 8.1.1.2.1."
    DEFVAL      { 0 }
    ::= { xmonCapture 7 }

xmonCaptureMaxPackets OBJECT-TYPE
    SYNTAX      Unsigned32
    UNITS       "packets"
    MAX-ACCESS  read-write
    STATUS      current
    DESCRIPTION 
        "Specifies the maximum number of packets that will be stored in 
         the capture before wrapping or halting occurs.  The value zero 
         (0) specifies that the capture has no predefined limit based on 
         number of messages although other attributes may contribute to 
         a 'log-full' criteria.  Unfortunately, a maximum number of 
         packets of over 4G cannot be specified."
    ::= { xmonCapture 8 }

xmonCaptureMaxTime OBJECT-TYPE
    SYNTAX      TimeInterval
    UNITS       "seconds"
    MAX-ACCESS  read-write
    STATUS      current
    DESCRIPTION 
        "Specifies the maximum time interval for which messages will be 
         sotre in the capture before wrapping or halting occurs.  The 
         value zero (0) specifies that the capture has no predefined 
         limit based on duration of time although other attributes may 
         contribute to a 'log-full' criteria."
    ::= { xmonCapture 9 }

xmonCaptureCurrentSize OBJECT-TYPE
    SYNTAX      Counter64
    UNITS       "octets"
    MAX-ACCESS  read-only
    STATUS      current
    DESCRIPTION 
        "Indicates the current size of the capture measured in 1024-byte 
         blocks.
         
         Note: since the capture size is specified in kbytes, the actual 
         amount of information that is contained in a capture will be 
         determined by the data representation in the capture.  This 
         data representation is not subject to standardization.  THe 
         maximum capture size does not includes the system overhead 
         involved in establishing the capture.  Thus immediately after 
         creation, the capture size should read zero."
    REFERENCE   
        "ITU-T Rec. X.735 (1992) | ISO/IEC 10164-6 : 1993, 
               Section 8.1.1.2.2."
    ::= { xmonCapture 10 }

xmonCaptureNumberOfPackets OBJECT-TYPE
    SYNTAX      Counter64
    UNITS       "packets"
    MAX-ACCESS  read-only
    STATUS      current
    DESCRIPTION 
        "Indicates the current number of packets in the capture."
    REFERENCE   
        "ITU-T Rec. X.735 (1992) | ISO/IEC 10164-6 : 1993, 
               Section 8.1.1.2.3."
    ::= { xmonCapture 11 }

xmonCaptureCurrentInterval OBJECT-TYPE
    SYNTAX      TimeInterval
    UNITS       "seconds"
    MAX-ACCESS  read-only
    STATUS      current
    DESCRIPTION 
        "Indicates the current time interval (in seconds) over which 
         messages are contained in the capture.  This is the time 
         interval (in seconds) since the capture was created."
    ::= { xmonCapture 12 }

xmonCaptureAlarmThreshold OBJECT-TYPE
    SYNTAX      LogCapacityAlarmThreshold
    UNITS       "%"
    MAX-ACCESS  read-write
    STATUS      current
    DESCRIPTION 
        "Specifies the threshold above which transmission of alarms will 
         occur.  This threshold is only applicable if a finite and fixed 
         criteria (from xmonCaptureMaxSize, xmonCaptureMaxPackets, and 
         xmonCaptureMaxTime) exists and the corresponding current value 
         has approached the specified percentage of that limit.
         
         The value specifies as a percentage of the final limiting 
         criteria (e.g. capture size) at which an event will be 
         generated to indicate that a 'log-full' or 'log-wrap' condition 
         is approaching.  This attribute is set-valued.  Support of this 
         attribute is mandatory for the halt(1) behaviour (see 
         xmonCaptureFullAction).  When a capture is created with the 
         wrap(0) condition, the capacity threshold events are triggered 
         as if coupled to a gauge that counts from zero to the highest 
         capacity threshold value defined and then resets to zero."
    REFERENCE   
        "ITU-T Rec. X.735 (1992) | ISO/IEC 10164-6 : 1993, 
               Section 8.1.1.3."
    DEFVAL      { "\x64" }
    ::= { xmonCapture 13 }

xmonCaptureOctetHiWaterMark OBJECT-TYPE
    SYNTAX      Counter64
    UNITS       "octets"
    MAX-ACCESS  read-only
    STATUS      current
    DESCRIPTION 
        "Provides the high water mark of the number of packet payload 
         octets captured.  This is the maximum number of packet payload 
         octets that were in the capture since the low water mark was 
         last set or since the last reset.  xmonCaptureReset can be used 
         to reset this gauge to zero.  This value can be used to 
         properly size the capture so that it is unlikely to wrap or 
         halt."
    ::= { xmonCapture 14 }

xmonCaptureOctetLoWaterMark OBJECT-TYPE
    SYNTAX      Counter64
    UNITS       "octets"
    MAX-ACCESS  read-only
    STATUS      current
    DESCRIPTION 
        "Provides the low water mark of the number of packet payload 
         octets captured in the capture since the high water mark was 
         last set or since the last reset.  xmonCaptureReset can be used 
         to reset this gauge to zero.  This value can be used to 
         properly size the capture so that it is unlikely to wrap or 
         halt."
    ::= { xmonCapture 15 }

xmonCapturePktsHiWaterMark OBJECT-TYPE
    SYNTAX      Counter64
    UNITS       "packets"
    MAX-ACCESS  read-only
    STATUS      current
    DESCRIPTION 
        "Provides the high water mark of the number of packets in the 
         capture since the low water mark was last set or since the last 
         reset.  xmonCaptureReset may be used to reset this gauge to 
         zero.  This value can be used to properly size the capture so 
         that it is unlikely to wrap or halt."
    ::= { xmonCapture 16 }

xmonCapturePktsLoWaterMark OBJECT-TYPE
    SYNTAX      Counter64
    UNITS       "packets"
    MAX-ACCESS  read-only
    STATUS      current
    DESCRIPTION 
        "Provides the low water mark of the number of packets in the 
         capture since the high water mark was last set or since the 
         last reset.  xmonCaptureReset can be used to reset this gauge 
         to zero.  This value can be used to properly size the capture 
         so that it is unlikely to wrap or halt."
    ::= { xmonCapture 17 }

xmonCaptureTimeHiWaterMark OBJECT-TYPE
    SYNTAX      TimeInterval
    MAX-ACCESS  read-only
    STATUS      current
    DESCRIPTION 
        "Provides the high water mark of the duration of time for 
         capture since the low water mark was last set or since the last 
         reset.  xmonCaptureReset may be used to reset this gauge to 
         zero.  This value can be used to properly size the capture so 
         that it is unlikely to wrap or halt."
    ::= { xmonCapture 18 }

xmonCaptureTimeLoWaterMark OBJECT-TYPE
    SYNTAX      TimeInterval
    MAX-ACCESS  read-only
    STATUS      current
    DESCRIPTION 
        "Provides the low water mark of the duration of time for capture 
         since the high water mark was last set or since the last reset.  
         xmonCaptureReset may be used to reset this gauge to zero.  This 
         value can be used to properly size the capture so that it is 
         unlikely to wrap or halt."
    ::= { xmonCapture 19 }

-- =====================================================================
-- xmonArchive group
-- =====================================================================

xmonArchive OBJECT-IDENTITY
    STATUS      current
    DESCRIPTION 
        "The xmonArchive group is responsible for managing the archiving 
         of capture files."
    ::= { xmonObjects 7 }

xmonArchivePath OBJECT-TYPE
    SYNTAX      SubstitutionString
    MAX-ACCESS  read-write
    STATUS      current
    DESCRIPTION 
        "Specifies the file system path to the directory where spooled 
         capture files are to be archived.  All substitutions except %I 
         are supported.  The default if not specified is 
         '/var/local/openss7/xmon/archive/%P'.
         
         In general this value should not be changed from its default 
         because external programs might rely on files being present at 
         the default path."
    DEFVAL      { "/var/local/openss7/xmon/spool/%P" }
    ::= { xmonArchive 1 }

xmonArchiveTable OBJECT-TYPE
    SYNTAX      SEQUENCE OF XmonArchiveEntry
    MAX-ACCESS  not-accessible
    STATUS      current
    DESCRIPTION 
        "Provides a table of spooled and archived capture files."
    ::= { xmonArchive 2 }

xmonArchiveEntry OBJECT-TYPE
    SYNTAX      XmonArchiveEntry
    MAX-ACCESS  not-accessible
    STATUS      current
    DESCRIPTION 
        "Each row in the xmonArchiveTable provides information 
         concerning a single capture file and provides some actions that 
         can be performed on the file."
    INDEX       { xmonArchiveIndex }
    ::= { xmonArchiveTable 1 }

XmonArchiveEntry ::= SEQUENCE {
    xmonArchiveIndex            Unsigned32,
    xmonArchiveName             SnmpAdminString,
    xmonArchiveFileFormat       INTEGER,
    xmonArchiveCompressed       INTEGER,
    xmonArchiveState            INTEGER,
    xmonArchiveSize             Counter64,
    xmonArchiveCompSize         Counter64,
    xmonArchiveTimeElapsed      TimeInterval,
    xmonArchiveBegTime          TimeStamp,
    xmonArchiveEndTime          TimeStamp,
    xmonArchiveIfRecv           Counter64,
    xmonArchiveIfDrop           Counter64,
    xmonArchiveFilterAccept     Counter64,
    xmonArchiveOsDrop           Counter64,
    xmonArchiveUserDeliv        Counter64,
    xmonArchiveIfCompress       Counter64,
    xmonArchiveUserOctets       Counter64,
    xmonArchiveActionResult     INTEGER
}

xmonArchiveIndex OBJECT-TYPE
    SYNTAX      Unsigned32
    MAX-ACCESS  not-accessible
    STATUS      current
    DESCRIPTION 
        "Provides a non-zero ordinal index into the capture file table 
         that uniquely identifies the capture file.  Files do not obtain 
         a new index as they are rotated.  Indices are not small integer 
         numbers, and are reverse assigned (subsequent indices are 
         smaller in value than previously assigned indices).  Indices 
         are oridinal and monotonically decreasing.  The current capture 
         file will, therefore, always be the smallest index and appear 
         first when the table is walked.  Aside from this, the precise 
         value of the ordinal index is of no significance and is 
         assigned by the agent."
    ::= { xmonArchiveEntry 1 }

xmonArchiveName OBJECT-TYPE
    SYNTAX      SnmpAdminString
    MAX-ACCESS  read-write
    STATUS      current
    DESCRIPTION 
        "Provides the base name (without file system path or extensions) 
         of the capture file.  The file name may be changed by writing 
         to this object.  Note that files in the current(0) state cannot 
         be renamed.  Also, an attempt to name a file to the same name 
         as another existing file will fail."
    ::= { xmonArchiveEntry 2 }

xmonArchiveFileFormat OBJECT-TYPE
    SYNTAX      INTEGER { unknown(0), pcap(1), pcapng(2) }
    MAX-ACCESS  read-only
    STATUS      current
    DESCRIPTION 
        "Provides the format of the file.  The format can be one of the 
         following:
         
         - pcap(1), the file is formated in the tcpdump PCAP format;
         - pcapng(2), the file is formatted in the PCAP-NG format.
           
         The value zero(0) can be used to indicate that the format of 
         the file is unknown, unspecified or unapplicable."
    DEFVAL      { pcapng }
    ::= { xmonArchiveEntry 3 }

xmonArchiveCompressed OBJECT-TYPE
    SYNTAX      INTEGER { none(0), gz(1), bz2(2), xz(3), zip(4) }
    MAX-ACCESS  read-write
    STATUS      current
    DESCRIPTION 
        "Provides the compression applied to the file on the file 
         system.  Compression is single-valued and can assume one of the 
         following values:
         
         - none(0), the file is not compressed;
         - gz(1), the file is gzip compressed;
         - bz2(2), the file is bzip2 compressed;
         - xz(3), the file is xz compressed;
         - zip(4), the file is zip compressed.
           
         The file can be decompressed or recompressed by writing to this 
         object.  Note that files in the current(0) or deleted(3) state 
         cannot be compressed."
    ::= { xmonArchiveEntry 4 }

xmonArchiveState OBJECT-TYPE
    SYNTAX      INTEGER { current(0), spooled(1), archived(2), 
                    deleted(3) }
    MAX-ACCESS  read-only
    STATUS      current
    DESCRIPTION 
        "Indicates the state of the file.  File state is single-valued 
         and can be one of the following:
         
         - current(0), the file is a current capture file that is 
           actively accumulating captured frames; current files cannot 
           be compressed or renamed;
           
         - spooled(1), the file has been rotated and is no longer 
           capturing frames; however, it is awaiting upload or download;
           
         - archived(2), the file has been rotated and also uploaded or 
           downloaded and is archived; archived files are subject to 
           deletion;
           
         - deleted(3), the file has been removed form the archive; 
           deleted files cannot be recompressed or decompressed.
           
         Management stations can change the state of the file using the 
         probeArchiveActionResult object."
    ::= { xmonArchiveEntry 5 }

xmonArchiveSize OBJECT-TYPE
    SYNTAX      Counter64
    MAX-ACCESS  read-only
    STATUS      current
    DESCRIPTION 
        "Indicates the size of the uncompressed file in bytes.  When no 
         compression is applied to the file, this value will be the same 
         as the probeArchiveCompSize."
    ::= { xmonArchiveEntry 6 }

xmonArchiveCompSize OBJECT-TYPE
    SYNTAX      Counter64
    MAX-ACCESS  read-only
    STATUS      current
    DESCRIPTION 
        "Indicates the size of the compressed file in bytes.  When no 
         compression is applied to the file, this value will be the same 
         as the probeArchiveSize."
    ::= { xmonArchiveEntry 7 }

xmonArchiveTimeElapsed OBJECT-TYPE
    SYNTAX      TimeInterval
    MAX-ACCESS  read-only
    STATUS      current
    DESCRIPTION 
        "Indicates the interfaces that are represented in the capture 
         file.  For pcap(1) formatted files, there is only one interface 
         per file; for pcapng(2) formatted files, there can be multiple 
         interfaces per file.  Interfaces indicated in this list will 
         also exist as an entry in the probeCaptureIfTable."
    ::= { xmonArchiveEntry 8 }

xmonArchiveBegTime OBJECT-TYPE
    SYNTAX      TimeStamp
    MAX-ACCESS  read-only
    STATUS      current
    DESCRIPTION 
        "Indicates the time interval covered by the file.  This may be 
         different than the difference between the timestamps of the 
         first message captured and the last message captured, because 
         there may have been a period of time after capture began for 
         which no messages were yet captured.  The interval should equal 
         the difference between the probeArchiveEndTime and the 
         probeArchiveBegTime."
    ::= { xmonArchiveEntry 9 }

xmonArchiveEndTime OBJECT-TYPE
    SYNTAX      TimeStamp
    MAX-ACCESS  read-only
    STATUS      current
    DESCRIPTION 
        "Indicates the time (using the TimeStamp textual convention) 
         that the capture file was opened (capture of message to the 
         file began)."
    ::= { xmonArchiveEntry 10 }

xmonArchiveIfRecv OBJECT-TYPE
    SYNTAX      Counter64
    MAX-ACCESS  read-only
    STATUS      current
    DESCRIPTION 
        "Indicates the total number of frames that were received by 
         any interface contained in the file during its capture period.
         
         This is the number of packets received by the physical 
         interface regardless of monitoring.  It is obtained directly 
         from the device driver."
    REFERENCE   
        "PCAP-NG file format: isb_ifrecv."
    ::= { xmonArchiveEntry 11 }

xmonArchiveIfDrop OBJECT-TYPE
    SYNTAX      Counter64
    MAX-ACCESS  read-only
    STATUS      current
    DESCRIPTION 
        "Indicates the total number of frames that were dropped by any 
         interface contained in the file due to resource shortage during 
         its capture period.
         
         This is the number of packets dropped by the interface 
         regardless of monitoring.  It is obtained directly from the 
         device driver."
    REFERENCE   
        "PCAP-NG file format: isb_drop."
    ::= { xmonArchiveEntry 12 }

xmonArchiveFilterAccept OBJECT-TYPE
    SYNTAX      Counter64
    MAX-ACCESS  read-only
    STATUS      current
    DESCRIPTION 
        "Indicates the total number of frames that were accepted by the 
         filter associated with any interface contained in the file 
         during its capture period.
         
         This is the bs_capt field of the BIOCGSTATS structure and the 
         isb_filteraccept option in the PCAP-NG format."
    REFERENCE   
        "bpf(4) manual page: bs_capt.
         PCAP-NG file format: isb_filteraccept."
    ::= { xmonArchiveEntry 13 }

xmonArchiveOsDrop OBJECT-TYPE
    SYNTAX      Counter64
    MAX-ACCESS  read-only
    STATUS      current
    DESCRIPTION 
        "Indicates the total number of frames that were dropped by the 
         operating system (i.e. the device driver) for any interface 
         contained in the file during its capture period.
         
         This is the bs_drop field of the BIOCGSTATS structure and the 
         isb_osdrop option in the PCAP-NG format."
    REFERENCE   
        "bpf(4) manual page: bs_drop.
         PCAP-NG file format: isb_osdrop."
    ::= { xmonArchiveEntry 14 }

xmonArchiveUserDeliv OBJECT-TYPE
    SYNTAX      Counter64
    MAX-ACCESS  read-only
    STATUS      current
    DESCRIPTION 
        "Indicates the total number of frames that were delivered to the 
         user-space capture application for any interface contained in 
         the file during its capture period.
         
         This is related to the bs_recv field of the BIOCGSTATS 
         structure except that it is that actual number of packets read 
         by the user-space application, whereas bs_recv is the number of 
         packets bufferred by the bpf(4) driver and available to be 
         read.  It is the isb_usrdeliv option in the PCAP-NG format."
    REFERENCE   
        "bpf(4) manual page: bs_recv.
         PCAP-NG file format: isb_usrdeliv."
    ::= { xmonArchiveEntry 15 }

xmonArchiveIfCompress OBJECT-TYPE
    SYNTAX      Counter64
    MAX-ACCESS  read-only
    STATUS      current
    DESCRIPTION 
        "Indicates the total number of frames that were compressed for 
         any interface contained in the file during its capture period."
    ::= { xmonArchiveEntry 16 }

xmonArchiveUserOctets OBJECT-TYPE
    SYNTAX      Counter64
    MAX-ACCESS  read-only
    STATUS      current
    DESCRIPTION 
        "Indicates the total number of frame octets that were captured 
         for any interface contained in the file during its capture 
         period."
    ::= { xmonArchiveEntry 17 }

xmonArchiveActionResult OBJECT-TYPE
    SYNTAX      INTEGER { success(0), failure(1), spool(2), archive(3), 
                    delete(4), upload(5) }
    MAX-ACCESS  read-write
    STATUS      current
    DESCRIPTION 
        "Provides actions and their results.  The action-result is 
         single-valued and can assume one of the following values:
         
         - success(0), the last action was successful;
         - failure(1), the last action failed;
         - spool(2), changes the state of a file in the current or 
           archived states to spooled; when successfully applied to a 
           current capture file, the capture file is rotated; when to an 
           archived file, the file is respooled;
         - archive(3), change the state of a spooled file to archived; 
           this action unspools and archives a spooled file;
         - delete(4), delete the capture file; this action can only be 
           applied to archived files;
         - upload(5), initiate an upload of the file; this action can 
           only be applied to spooled files; once upload is complete, 
           the file will be archived.
           
         When written, only values spool(2), archive(3), delete(4) and 
         upload(5) are valid and represent the action to be performed.  
         When read, only values success(0) or failure(1) will be 
         returned and represent the result of the previous action."
    ::= { xmonArchiveEntry 18 }

-- =====================================================================
-- xmonFeed group
-- =====================================================================

xmonFeed OBJECT-IDENTITY
    STATUS      current
    DESCRIPTION 
        "The xmonFeed group is responsible for managing the feeding of 
         captured packet streams from a probe a collector.  These 
         definitions are maintained at a probe."
    ::= { xmonObjects 8 }

xmonFeedTypes OBJECT-TYPE
    SYNTAX      BITS { udp(0), tcp(1), sctp(2) }
    MAX-ACCESS  read-write
    STATUS      current
    DESCRIPTION 
        "Specifies the transport protocols over which the host will 
         listen for incoming live feed connections (whether for 
         probe-initiated feeds or collector-initiated feeds)."
    DEFVAL      { {udp, tcp} }
    ::= { xmonFeed 1 }

xmonFeedPort OBJECT-TYPE
    SYNTAX      Integer32 (0..65535)
    MAX-ACCESS  read-write
    STATUS      current
    DESCRIPTION 
        "Specifies the port on which the probe will listen for remote 
         feed requests from netowrk management systems."
    DEFVAL      { 5572 }
    ::= { xmonFeed 2 }

xmonFeedListenTable OBJECT-TYPE
    SYNTAX      SEQUENCE OF XmonFeedListenEntry
    MAX-ACCESS  not-accessible
    STATUS      current
    DESCRIPTION 
        "Provides a table of transport addresses upon which the 
         host will listen for live feed connections."
    ::= { xmonFeed 3 }

xmonFeedListenEntry OBJECT-TYPE
    SYNTAX      XmonFeedListenEntry
    MAX-ACCESS  not-accessible
    STATUS      current
    DESCRIPTION 
        "Each row in the table describes one transport address on which 
         the host will listen for remote feed requests from network 
         management stations."
    INDEX       { xmonFeedListenIndex }
    ::= { xmonFeedListenTable 1 }

XmonFeedListenEntry ::= SEQUENCE {
    xmonFeedListenIndex         Unsigned32,
    xmonFeedListenAddrType      TransportAddressType,
    xmonFeedListenAddr          TransportAddress,
    xmonFeedListenRowStatus     RowStatus
}

xmonFeedListenIndex OBJECT-TYPE
    SYNTAX      Unsigned32
    MAX-ACCESS  not-accessible
    STATUS      current
    DESCRIPTION 
        "Provides a non-zero ordinal index into this table."
    ::= { xmonFeedListenEntry 1 }

xmonFeedListenAddrType OBJECT-TYPE
    SYNTAX      TransportAddressType
    MAX-ACCESS  read-create
    STATUS      current
    DESCRIPTION 
        "Specifies the transport address type for this address.  
         Transport address types are restricted to UDP, TCP and SCTP 
         transport domains."
    ::= { xmonFeedListenEntry 2 }

xmonFeedListenAddr OBJECT-TYPE
    SYNTAX      TransportAddress
    MAX-ACCESS  read-create
    STATUS      current
    DESCRIPTION 
        "Specifies the transport address (IP address, port and possibly 
         zone id, or domain name) upon which the probe will listen for 
         remote feed requests from network management stations."
    ::= { xmonFeedListenEntry 3 }

xmonFeedListenRowStatus OBJECT-TYPE
    SYNTAX      RowStatus
    MAX-ACCESS  read-create
    STATUS      current
    DESCRIPTION 
        "Provides a mechanism whereby management stations may create and 
         destroy rows in this table.  When there are no transport 
         addresses specified in this table, the agent will populate the 
         table autonomously with all transport addresses upon which it 
         is listening using the xmonFeedPort value as the port number.  
         Rows in this table that are specified by management stations 
         will persist across agent reboots.  Rows populated autonomously 
         by the agent will not."
    ::= { xmonFeedListenEntry 4 }

xmonFeedTable OBJECT-TYPE
    SYNTAX      SEQUENCE OF XmonFeedEntry
    MAX-ACCESS  not-accessible
    STATUS      current
    DESCRIPTION 
        "The probe is capable of feeding packets captured on local 
         monitoring sources to remote network management systems.  In 
         doing so, either the probe or the network management system can 
         establish the necessary transport connection.  This table 
         contains the transport addresses of the network management 
         systems to which the probe will feed (or is feeding) captured 
         packets.  This table contains connections that are initiated by 
         the probe or network management system.  Only connections 
         initiated by the probe are persistent across an agent reboot.  
         This table contains definitions that are maintained at a probe.  
         The network managements station must contain its own 
         definintions in its application outside of the scope of this 
         MIB."
    ::= { xmonFeed 5 }

xmonFeedEntry OBJECT-TYPE
    SYNTAX      XmonFeedEntry
    MAX-ACCESS  not-accessible
    STATUS      current
    DESCRIPTION 
        "Each row in this table describes one network management stystem 
         to which this probe will feed captured packets from the probe's 
         monitor sources.  Rows established by a management station 
         initiate transport connections.  Rows established autonomously 
         by the agent have responded to a transport connection."
    INDEX       { xmonFeedIndex }
    ::= { xmonFeedTable 1 }

XmonFeedEntry ::= SEQUENCE {
    xmonFeedIndex           Unsigned32,
    xmonFeedRole            ConnectionRole,
    xmonFeedName            DisplayString,
    xmonFeedAddrType        TransportAddressType,
    xmonFeedAddr            TransportAddress,
    xmonFeedConnInterval    TimeInterval,
    xmonFeedConnAttempts    Unsigned32,
    xmonFeedProfile         SimpleNameType,
    xmonFeedAdminState      AdministrativeState,
    xmonFeedOpState         OperationalState,
    xmonFeedProcStatus      ProceduralStatus,
    xmonFeedUsageState      UsageState,
    xmonFeedConnState       ConnectionState,
    xmonFeedStorageType     StorageType,
    xmonFeedRowStatus       RowStatus
}

xmonFeedIndex OBJECT-TYPE
    SYNTAX      Unsigned32
    MAX-ACCESS  not-accessible
    STATUS      current
    DESCRIPTION 
        "Provides a non-zero ordinal index into this table.  Aside from 
         its use as an index, this attribute has no significance."
    ::= { xmonFeedEntry 1 }

xmonFeedRole OBJECT-TYPE
    SYNTAX      ConnectionRole
    MAX-ACCESS  read-only
    STATUS      current
    DESCRIPTION 
        "Indicates the role of the current host in the feed:
         
         - intiator(1), this host initiates the connection;
         - responder(2), this host responds to the connection;
         - both(3), this host will both initiate and respond to the 
           connection.
           
         The agent may autonomously create reponder(2) rows."
    DEFVAL      { initiator }
    ::= { xmonFeedEntry 2 }

xmonFeedName OBJECT-TYPE
    SYNTAX      DisplayString
    MAX-ACCESS  read-create
    STATUS      current
    DESCRIPTION 
        "Provides the specification of the the name of one transport 
         endpoint to which to feed captured packets expressed typically 
         as a hostname and port address sepcification; however, this 
         hostname is not used for establishing connections.  To specify 
         a hostname as a transport address, use the udpDns(14), 
         tcpDns(15) or sctpDns(16) transport address type in the 
         xmonFeedAddrType column."
    ::= { xmonFeedEntry 3 }

xmonFeedAddrType OBJECT-TYPE
    SYNTAX      TransportAddressType
    MAX-ACCESS  read-create
    STATUS      current
    DESCRIPTION 
        "Specifies the transport address type.  The client supports most 
         transport address types provided in the TRANSPORT-ADDRESS-MIB.
         
         Note well that a transport address in the UDP transport domain 
         should only be used when tunnelled in a reliable transport; 
         otherwise, captured packet loss may occur."
    REFERENCE   
        "TRANSPORT-ADDRESS-MIB, TransportAddressType."
    ::= { xmonFeedEntry 4 }

xmonFeedAddr OBJECT-TYPE
    SYNTAX      TransportAddress
    MAX-ACCESS  read-create
    STATUS      current
    DESCRIPTION 
        "Specifies the transport address of the network management 
         system to which to transfer captured packets.  The address is 
         of type xmonFeedAddrType."
    REFERENCE   
        "TRANSPORT-ADDRESS-MIB, TransportAddress."
    ::= { xmonFeedEntry 5 }

xmonFeedConnInterval OBJECT-TYPE
    SYNTAX      TimeInterval
    MAX-ACCESS  read-create
    STATUS      current
    DESCRIPTION 
        "Specifies the interval at which the probe will attempt to 
         reinitiate a failed connection attempt on this connection.  
         When a connection attempt fails, the probe will wait for this 
         interval of time before attempting to reconnect."
    DEFVAL      { 500 }
    ::= { xmonFeedEntry 6 }

xmonFeedConnAttempts OBJECT-TYPE
    SYNTAX      Unsigned32
    MAX-ACCESS  read-create
    STATUS      current
    DESCRIPTION 
        "Specifies the maximum number of reattempts that a probe will 
         initiate before the transport connectivity it ceases initiation 
         attempts and considers the transport connection to be 
         permanently failed.  The special value zero (0) means that the 
         transport connection will never be considered permanently 
         failed."
    DEFVAL      { 0 }
    ::= { xmonFeedEntry 7 }

xmonFeedProfile OBJECT-TYPE
    SYNTAX      SimpleNameType
    MAX-ACCESS  read-create
    STATUS      current
    DESCRIPTION 
        "Specifies the transport protocol parameters profile that is to 
         be used to supply protocol parameters, timers, and options for 
         the connection.  The values of this object must be the same as 
         the name of a row in the xmonSctpProfileTable.  Protocol 
         profiles are only applicable to transport addresses in the SCTP 
         transport domain."
    DEFVAL      { "" }
    ::= { xmonFeedEntry 8 }

xmonFeedAdminState OBJECT-TYPE
    SYNTAX      AdministrativeState
    MAX-ACCESS  read-create
    STATUS      current
    DESCRIPTION 
        "Provides the administrative state of the feed.  This attribute 
         is single-valued and can assume one of the following:
         
         - locked(0), the feed is administratively prohibited;
           
         - unlocked(1), the feed is administratively permitted;
           
         - shuttingDown(2), the transport connection is shutting down: 
           once the connection is released, the feed will move to the 
           locked(0) state.
           
         The value shuttingDown(2) is only valid when read and not valid 
         when written.  This object is used primarily to enable or 
         disable feeds to the collector."
    REFERENCE   
        "OPENSS7-SMI-MIB, AdministrativeState.
         ITU-T Rec. X.735 (1992) | ISO/IEC 10164-6 : 1993, 
               Section 8.1.1.1.3."
    DEFVAL      { unlocked }
    ::= { xmonFeedEntry 9 }

xmonFeedOpState OBJECT-TYPE
    SYNTAX      OperationalState
    MAX-ACCESS  read-only
    STATUS      current
    DESCRIPTION 
        "Represents the operational capability of the transport 
         connection to perform its function.  The following states are 
         defined:
         
         - enabled(0), the transport connection is operational and ready 
           for use, captured packets will be transferred;
           
         - disabled(1), the transport connection is not available for 
           use; captured packets will be bufferred but cannot be 
           transferred.
           
         A change in operational state shall generate a state changed 
         notification for persistent rows."
    REFERENCE   
        "OPENSS7-SMI-MIB, OperationalState.
         ITU-T Rec. X.735 (1992) | ISO/IEC 10164-6 : 1993, 
               Section 8.1.1.1.4."
    ::= { xmonFeedEntry 10 }

xmonFeedProcStatus OBJECT-TYPE
    SYNTAX      ProceduralStatus
    MAX-ACCESS  read-only
    STATUS      current
    DESCRIPTION 
        "Provides the procedural status of the feed:
         
         - initializationRequired(0), the feed requires initialization 
           and that initialization has not yet been performed; a manual 
           or automatic action is required to initialize the feed;
           
         - notInitialized(1), the feed requires initialization and that 
           initialization has not completed yet;
           
         - initializing(2), the feed requires initialization and that 
           initialization is proceeding but has not yet completed;
           
         - reporting(3), the feed is reporting its results;
           
         - terminating(4), the feed is terminating.
           
         The procedural status for feeds result from actions taken by 
         the agent and not by actions taken within this MIB."
    REFERENCE   
        "OPENSS7-SMI-MIB, ProceduralStatus.
         ITU-T Rec. X.721 | ISO/IEC 10165-2, proceduralStatus."
    ::= { xmonFeedEntry 11 }

xmonFeedUsageState OBJECT-TYPE
    SYNTAX      UsageState
    MAX-ACCESS  read-only
    STATUS      current
    DESCRIPTION 
        "Provides the usage state of the feed:
         
         - idle(0), the feed is not currently in use;
           
         - active(1), the feed is in use and has sufficient operating 
           capacity to provide for additional transfer of captured 
           packets;
           
         - busy(2), the feed is in use and has no spare capacity to 
           transfer additional captured packets.
           
         This usage state determines the use of the feed in transferring 
         captured packets and not any other use of the transport 
         connection."
    REFERENCE   
        "OPENSS7-SMI-MIB, UsageState.
         ITU-T Rec. X.721 | ISO/IEC 10165-2, usageState."
    ::= { xmonFeedEntry 12 }

xmonFeedConnState OBJECT-TYPE
    SYNTAX      ConnectionState
    MAX-ACCESS  read-only
    STATUS      current
    DESCRIPTION 
        "Provides the communications state of the transport connection:
         
         - idle(0), there is no transport connection; the probe is 
           neither initiating nor responding to a connection request for 
           this collector; the operational state is disabled(0), the 
           usage state is idle(0) and the procedural status contains 
           notInitialized(1);
           
         - ogConn(1), the probe is in the process of initiating an 
           outgoing transport connection; the operational state is 
           disabled(0), the usage state is idle(0) and the procedural 
           status contains initializing(2);
           
         - icConn(2), the probe is responding to an incoming transport 
           connection from the collector; the operational state is 
           disabled(0), the usage state is idle(0) and the procedural 
           status contains initializing(2);
           
         - established(3), the transport connection is established; the 
           operational state is enabled(1) or disabled(0);
           
         - shuttingDown(4), the transport connection is being shut down 
           by the local or remote end; the operational state is 
           disabled(0) and the procedural status contains 
           terminating(4).
           
         These values reflect the state of the transport connection.  
         For connectionless transports, the connection state may move 
         between idle(0) to established(3) without entering the other 
         states."
    ::= { xmonFeedEntry 13 }

xmonFeedStorageType OBJECT-TYPE
    SYNTAX      StorageType
    MAX-ACCESS  read-create
    STATUS      current
    DESCRIPTION 
        "Specifies the storage type for this conceptual row.  On write, 
         only storage types volatile(2) and nonVolatile(3) are 
         applicable.  volatile(2) rows do not persist across an agent 
         reboot."
    DEFVAL      { nonVolatile }
    ::= { xmonFeedEntry 14 }

xmonFeedRowStatus OBJECT-TYPE
    SYNTAX      RowStatus
    MAX-ACCESS  read-create
    STATUS      current
    DESCRIPTION 
        "Provides a mechanism whereby management stations may create and 
         destroy rows in this table.
         
         The agent may autonomously create and destroy entries in this 
         table.  The agent may permit collectors to establish feeds from 
         this probe without a corresponding row in this table being 
         present when a feed is established.  Once accepted, the agent 
         should autonomously populate a corresponding entry in this 
         table."
    ::= { xmonFeedEntry 15 }

xmonFeedStatsTable OBJECT-TYPE
    SYNTAX      SEQUENCE OF XmonFeedStatsEntry
    MAX-ACCESS  not-accessible
    STATUS      current
    DESCRIPTION 
        "For feed connections that have been established at some point 
         in time, this table contains the transfer statistics for the 
         connection."
    ::= { xmonFeed 6 }

xmonFeedStatsEntry OBJECT-TYPE
    SYNTAX      XmonFeedStatsEntry
    MAX-ACCESS  not-accessible
    STATUS      current
    DESCRIPTION 
        "Each row in the xmonFeedStatsTable corresponds to a collector 
         to which this probe will feed captured packets.  Each row 
         contains the transfer statistics for the current or most recent 
         connections.
         
         Note that this information is not persistent across agent 
         reboots."
    INDEX       { xmonFeedIndex, xmonFeedConnIndex }
    ::= { xmonFeedStatsTable 1 }

XmonFeedStatsEntry ::= SEQUENCE {
    xmonFeedConnIndex       Unsigned32,
    xmonFeedTimeElapsed     TimeInterval,
    xmonFeedBegTime         TimeStamp,
    xmonFeedEndTime         TimeStamp,
    xmonFeedIfRecv          Counter64,
    xmonFeedIfDrop          Counter64,
    xmonFeedFilterAccept    Counter64,
    xmonFeedOsDrop          Counter64,
    xmonFeedUserDeliv       Counter64,
    xmonFeedIfCompress      Counter64,
    xmonFeedUserOctets      Counter64
}

xmonFeedConnIndex OBJECT-TYPE
    SYNTAX      Unsigned32
    MAX-ACCESS  not-accessible
    STATUS      current
    DESCRIPTION 
        "Provides a non-zero ordinal index into this table in 
         conjunction with the xmonFeedIndex that identifies the 
         collector.  This sub-index is used to identify the specific 
         instance of transport connection.  Historical information will 
         be retained; however, this table is not persistent and any 
         information contained in it may be lost across and agent 
         reboot."
    ::= { xmonFeedStatsEntry 1 }

xmonFeedTimeElapsed OBJECT-TYPE
    SYNTAX      TimeInterval
    MAX-ACCESS  read-only
    STATUS      current
    DESCRIPTION 
        "Indicates the time interval covered by the feed of captured 
         packets.  This may be different that the difference between the 
         time stamps of the first and last packet fed, because there may 
         have been a period of time after the feed start for which no 
         packets were captured.  The interval should equal the 
         difference between xmonFeedEndTime and xmonFeedBegTime."
    ::= { xmonFeedStatsEntry 2 }

xmonFeedBegTime OBJECT-TYPE
    SYNTAX      TimeStamp
    MAX-ACCESS  read-only
    STATUS      current
    DESCRIPTION 
        "Indicates the time (using the TimeStamp textual convention) 
         that the transport connection was opened (transfer of captured 
         packets across the transport connection began)."
    ::= { xmonFeedStatsEntry 3 }

xmonFeedEndTime OBJECT-TYPE
    SYNTAX      TimeStamp
    MAX-ACCESS  read-only
    STATUS      current
    DESCRIPTION 
        "Indicates the time (using the TimeStamp textual convention) 
         that the transport connection was closed (transfer of captured 
         packets across the transport connection ended)."
    ::= { xmonFeedStatsEntry 4 }

xmonFeedIfRecv OBJECT-TYPE
    SYNTAX      Counter64
    MAX-ACCESS  read-only
    STATUS      current
    DESCRIPTION 
        "Indicates the total number of packets that were received from 
         any physical interface since the beginning of the transfer 
         period.  This is the number of packets received by any physical 
         interface regardless of monitoring.  It is obtained directly 
         from the device driver."
    REFERENCE   
        "PCAP-NG file format: isb_ifrecv."
    ::= { xmonFeedStatsEntry 5 }

xmonFeedIfDrop OBJECT-TYPE
    SYNTAX      Counter64
    MAX-ACCESS  read-only
    STATUS      current
    DESCRIPTION 
        "Indicates the total number of packets dropped by any interface 
         due to lack of resources since the beginning of the transfer 
         period.  This is the number of packets dropped by any interface 
         regardless of monitoring.  It is obtained directly from the 
         device driver."
    REFERENCE   
        "PCAP-NG file format: isb_drop."
    ::= { xmonFeedStatsEntry 6 }

xmonFeedFilterAccept OBJECT-TYPE
    SYNTAX      Counter64
    MAX-ACCESS  read-only
    STATUS      current
    DESCRIPTION 
        "Indicates the total number of packets accepted by any interface 
         filter since the beginning of the transfer period.  This is the 
         bs_capt field of the BIOCGSTATS structure and the 
         isb_filteraccept option in the PCAP-NG format."
    REFERENCE   
        "bpf(4) manual page: bs_capt.
         PCAP-NG file format: isb_filteraccept."
    ::= { xmonFeedStatsEntry 7 }

xmonFeedOsDrop OBJECT-TYPE
    SYNTAX      Counter64
    MAX-ACCESS  read-only
    STATUS      current
    DESCRIPTION 
        "Indicates the total number of packets dropped by the operating 
         system for any interface since the beginning of the transfer 
         period.  These packets were dropped because the capture 
         application did not keep up with the rate at which the 
         oeprating system was feeding captured packets.  This is the 
         bs_drop field of the BIOCGSTATS structure and the isb_drop 
         option in the PCAP-NG format."
    REFERENCE   
        "bpf(4) manual page: bs_drop
         PCAP-NG file format: isb_osdrop."
    ::= { xmonFeedStatsEntry 8 }

xmonFeedUserDeliv OBJECT-TYPE
    SYNTAX      Counter64
    MAX-ACCESS  read-only
    STATUS      current
    DESCRIPTION 
        "Indicates the total number of packets delivered to the 
         monitoring application for any interface since the beginning of 
         the transfer period.  This value can be different from the 
         value provided by xmonFeedFilterAccept minus xmonXferOsDrop 
         because some packets could still lay in the OS buffers at the 
         transfer period end time.  This count is established by the 
         application reading packets from the operating system.  This is 
         the isb_usrdeliv option in the PCAP-NG format."
    REFERENCE   
        "PCAP-NG file format: isb_usrdeliv."
    ::= { xmonFeedStatsEntry 9 }

xmonFeedIfCompress OBJECT-TYPE
    SYNTAX      Counter64
    MAX-ACCESS  read-only
    STATUS      current
    DESCRIPTION 
        "Indicates the total number of packets that were compressed for 
         any interface since the beginning of the transfer period.  This 
         statistic is primarily for SS7 monitoring in that it tracks 
         FISU and LSSU compression."
    ::= { xmonFeedStatsEntry 10 }

xmonFeedUserOctets OBJECT-TYPE
    SYNTAX      Counter64
    MAX-ACCESS  read-only
    STATUS      current
    DESCRIPTION 
        "Indicates the total number of packet payload octets that were 
         transferred during the transfer period."
    ::= { xmonFeedStatsEntry 11 }

-- =====================================================================
-- xmonPush group
-- =====================================================================

xmonPush OBJECT-IDENTITY
    STATUS      current
    DESCRIPTION 
        "The xmonPush group is responsible for managing the pushing of 
         captured packet streams from a probe to a collector.  These 
         definitions are maintained at a probe."
    ::= { xmonObjects 9 }

xmonPushPort OBJECT-TYPE
    SYNTAX      Integer32 (0..65535)
    MAX-ACCESS  read-write
    STATUS      current
    DESCRIPTION 
        "Specifies the port on which the collector will listen for remote 
         push requests from probes."
    DEFVAL      { 5573 }
    ::= { xmonPush 1 }

xmonPushListenTable OBJECT-TYPE
    SYNTAX      SEQUENCE OF XmonPushListenEntry
    MAX-ACCESS  not-accessible
    STATUS      current
    DESCRIPTION 
        "Provides a table of transport addresses upon which the 
         collector will listen for remote push requests from probes."
    ::= { xmonPush 2 }

xmonPushListenEntry OBJECT-TYPE
    SYNTAX      XmonPushListenEntry
    MAX-ACCESS  not-accessible
    STATUS      current
    DESCRIPTION 
        "Each row in the table represents a single transport address on 
         which the probe will listen for remote push requests from 
         probes."
    INDEX       { xmonPushListenIndex }
    ::= { xmonPushListenTable 1 }

XmonPushListenEntry ::= SEQUENCE {
    xmonPushListenIndex         Unsigned32,
    xmonPushListenAddrType      TransportAddressType,
    xmonPushListenAddr          TransportAddress,
    xmonPushListenRowStatus     RowStatus
}

xmonPushListenIndex OBJECT-TYPE
    SYNTAX      Unsigned32
    MAX-ACCESS  not-accessible
    STATUS      current
    DESCRIPTION 
        "Provides a non-zero ordinal index into this table."
    ::= { xmonPushListenEntry 1 }

xmonPushListenAddrType OBJECT-TYPE
    SYNTAX      TransportAddressType
    MAX-ACCESS  read-create
    STATUS      current
    DESCRIPTION 
        "Specifies the transport address type for this address.  
         Transport address types are restricted to UDP, TCP and SCTP 
         transport domains."
    ::= { xmonPushListenEntry 2 }

xmonPushListenAddr OBJECT-TYPE
    SYNTAX      TransportAddress
    MAX-ACCESS  read-create
    STATUS      current
    DESCRIPTION 
        "Specifies the transport address (IP address, port and possibly 
         zone id, or domain name) upon which the probe will listen for 
         remote push requests from probes."
    ::= { xmonPushListenEntry 3 }

xmonPushListenRowStatus OBJECT-TYPE
    SYNTAX      RowStatus
    MAX-ACCESS  read-create
    STATUS      current
    DESCRIPTION 
        "Provides a mechanism whereby management stations may create and 
         destroy rows in this table.  When there are no transport 
         addresses specified in this table, the agent will populate the 
         table autonomously with all transport addresses upon which it 
         is listening using the xmonPushPort value as the port number.  
         Rows in this table that are specified by management stations 
         will persist across agent reboots.  Rows populated autonomously 
         by the agent will not."
    ::= { xmonPushListenEntry 4 }

xmonPushTable OBJECT-TYPE
    SYNTAX      SEQUENCE OF XmonPushEntry
    MAX-ACCESS  not-accessible
    STATUS      current
    DESCRIPTION 
        "The probe is capable of pushing packets captured on local 
         monitoring sources to remote collectors.  In doing so, either 
         the probe or the collector can establish the necessary 
         transport connection.  This table contains the transport 
         addresses of the collectors to which the probe will push (or is 
         pushing) captured packets.  The table contains connections that 
         are initiated by the probe or by the collector.  Only 
         connections initiated by the probe are persistent across an 
         agent reboot.  This table contains definitions that are 
         maintained at a probe.  The xmonPullTable contains definitions 
         that are maintained at a collector."
    ::= { xmonPush 3 }

xmonPushEntry OBJECT-TYPE
    SYNTAX      XmonPushEntry
    MAX-ACCESS  not-accessible
    STATUS      current
    DESCRIPTION 
        "Each row in this table describes one collector to which this 
         probe will push captured packets from the probe's monitor 
         sources.  Rows established by a management station initiate 
         transport connections.  Rows established autonomously by the 
         agent have responded to a transport connection."
    INDEX       { xmonPushIndex }
    ::= { xmonPushTable 1 }

XmonPushEntry ::= SEQUENCE {
    xmonPushIndex           Unsigned32,
    xmonPushRole            ConnectionRole,
    xmonPushName            DisplayString,
    xmonPushAddrType        TransportAddressType,
    xmonPushAddr            TransportAddress,
    xmonPushConnInterval    TimeInterval,
    xmonPushConnAttempts    Unsigned32,
    xmonPushProfile         SimpleNameType,
    xmonPushAdminState      AdministrativeState,
    xmonPushOpState       OperationalState,
    xmonPushProcStatus      ProceduralStatus,
    xmonPushUsageState      UsageState,
    xmonPushConnState       ConnectionState,
    xmonPushStorageType     StorageType,
    xmonPushRowStatus       RowStatus
}

xmonPushIndex OBJECT-TYPE
    SYNTAX      Unsigned32
    MAX-ACCESS  not-accessible
    STATUS      current
    DESCRIPTION 
        "Provides a non-zero ordinal index into this table.  Aside from 
         its use as an index, this attribute has no significance."
    ::= { xmonPushEntry 1 }

xmonPushRole OBJECT-TYPE
    SYNTAX      ConnectionRole
    MAX-ACCESS  read-only
    STATUS      current
    DESCRIPTION 
        "Indicates the role in which this host participates in the 
         transport connection:
         
         - initiator(1), this host initiates the connection;
         - responder(2), this host responds to the connection;
         - both(3), this host will both initiate and respond to the 
           connection.
           
         The agent may autonomously create responder(2) roles."
    DEFVAL      { initiator }
    ::= { xmonPushEntry 2 }

xmonPushName OBJECT-TYPE
    SYNTAX      DisplayString
    MAX-ACCESS  read-create
    STATUS      current
    DESCRIPTION 
        "Provides the specification of the name of one transport 
         endpoint to which to push monitor sources expressed typically 
         as a hostname and port address specification; however, this 
         hostname is not used for establishing connections.  To specify 
         a hostname as a transport address, use the udpDns(14), 
         tcpDns(15) or sctpDns(16) transport address type in the 
         xmonPushAddrType column."
    ::= { xmonPushEntry 3 }

xmonPushAddrType OBJECT-TYPE
    SYNTAX      TransportAddressType
    MAX-ACCESS  read-create
    STATUS      current
    DESCRIPTION 
        "Specifies the transport address type.  For sctpipv4(9), the 
         transport address is an IPv4 address and port number; for 
         sctpipv6(10), it is an IPv6 address and port number."
    REFERENCE   
        "TRANSPORT-ADDRESS-MIB, TransportAddressType"
    DEFVAL      { sctpIpv4 }
    ::= { xmonPushEntry 4 }

xmonPushAddr OBJECT-TYPE
    SYNTAX      TransportAddress
    MAX-ACCESS  read-create
    STATUS      current
    DESCRIPTION 
        "Specifies the transport address of the remote host to which to 
         push monitor sources.  The address is of type 
         xmonPushAddrType."
    REFERENCE   
        "TRANSPORT-ADDRESS-MIB, TransportAddressType"
    ::= { xmonPushEntry 5 }

xmonPushConnInterval OBJECT-TYPE
    SYNTAX      TimeInterval
    MAX-ACCESS  read-create
    STATUS      current
    DESCRIPTION 
        "Specifies the interval at which the probe will attempt to 
         reinitiate a failed connection attempt on this connection.  
         When a connection attempt fails, the probe will wait for this 
         interval of time before attempting to reconnect."
    DEFVAL      { 500 }
    ::= { xmonPushEntry 6 }

xmonPushConnAttempts OBJECT-TYPE
    SYNTAX      Unsigned32
    MAX-ACCESS  read-create
    STATUS      current
    DESCRIPTION 
        "Specifies the maximum number of reattempts that a probe will 
         initiate before the transport connectivity it ceases initiation 
         attempts and considers the transport connection to be 
         permanently failed.  The special value zero (0) means that the 
         transport connection will never be considered permanently 
         failed."
    DEFVAL      { 0 }
    ::= { xmonPushEntry 7 }

xmonPushProfile OBJECT-TYPE
    SYNTAX      SimpleNameType
    MAX-ACCESS  read-create
    STATUS      current
    DESCRIPTION 
        "Specifies the transport protocol parameters profile that is to 
         be used to supply protocol parameters, timers, and options for 
         the connection.  The values of this object must be the same as 
         the name of a row in the xmonSctpProfileTable.  Protocol 
         profiles are only applicable to transport addresses in the SCTP 
         transport domain."
    DEFVAL      { "" }
    ::= { xmonPushEntry 8 }

xmonPushAdminState OBJECT-TYPE
    SYNTAX      AdministrativeState
    MAX-ACCESS  read-create
    STATUS      current
    DESCRIPTION 
        "Provides the administrative state of the feed.  This attribute 
         is single-valued and can assume one of the following:
         
         - locked(0), the feed is administratively prohibited;
           
         - unlocked(1), the feed is administratively permitted;
           
         - shuttingDown(2), the transport connection is shutting down: 
           once the connection is released, the feed will move to the 
           locked(0) state.
           
         The value shuttingDown(2) is only valid when read and not valid 
         when written.  This object is used primarily to enable or 
         disable feeds to the collector."
    REFERENCE   
        "OPENSS7-SMI-MIB, AdministrativeState.
         ITU-T Rec. X.735 (1992) | ISO/IEC 10164-6 : 1993, 
               Section 8.1.1.1.3."
    DEFVAL      { unlocked }
    ::= { xmonPushEntry 9 }

xmonPushOpState OBJECT-TYPE
    SYNTAX      OperationalState
    MAX-ACCESS  read-only
    STATUS      current
    DESCRIPTION 
        "Represents the operational capability of the transport 
         connection to perform its function.  The following states are 
         defined:
         
         - enabled(0), the transport connection is operational and ready 
           for use, captured packets will be transferred;
           
         - disabled(1), the transport connection is not available for 
           use; captured packets will be bufferred but cannot be 
           transferred.
           
         A change in operational state shall generate a state changed 
         notification for persistent rows."
    REFERENCE   
        "OPENSS7-SMI-MIB, OperationalState.
         ITU-T Rec. X.735 (1992) | ISO/IEC 10164-6 : 1993, 
               Section 8.1.1.1.4."
    ::= { xmonPushEntry 10 }

xmonPushProcStatus OBJECT-TYPE
    SYNTAX      ProceduralStatus
    MAX-ACCESS  read-only
    STATUS      current
    DESCRIPTION 
        "Provides the procedural status of the feed:
         
         - initializationRequired(0), the feed requires initialization 
           and that initialization has not yet been performed; a manual 
           or automatic action is required to initialize the feed;
           
         - notInitialized(1), the feed requires initialization and that 
           initialization has not completed yet;
           
         - initializing(2), the feed requires initialization and that 
           initialization is proceeding but has not yet completed;
           
         - reporting(3), the feed is reporting its results;
           
         - terminating(4), the feed is terminating.
           
         The procedural status for feeds result from actions taken by 
         the agent and not by actions taken within this MIB."
    REFERENCE   
        "OPENSS7-SMI-MIB, ProceduralStatus.
         ITU-T Rec. X.721 | ISO/IEC 10165-2, proceduralStatus."
    ::= { xmonPushEntry 11 }

xmonPushUsageState OBJECT-TYPE
    SYNTAX      UsageState
    MAX-ACCESS  read-only
    STATUS      current
    DESCRIPTION 
        "Provides the usage state of the feed:
         
         - idle(0), the feed is not currently in use;
           
         - active(1), the feed is in use and has sufficient operating 
           capacity to provide for additional transfer of captured 
           packets;
           
         - busy(2), the feed is in use and has no spare capacity to 
           transfer additional captured packets.
           
         This usage state determines the use of the feed in transferring 
         captured packets and not any other use of the transport 
         connection."
    REFERENCE   
        "OPENSS7-SMI-MIB, UsageState.
         ITU-T Rec. X.721 | ISO/IEC 10165-2, usageState."
    ::= { xmonPushEntry 12 }

xmonPushConnState OBJECT-TYPE
    SYNTAX      ConnectionState
    MAX-ACCESS  read-only
    STATUS      current
    DESCRIPTION 
        "Provides the state of the SCTP association use to export 
         monitor sources from the remote probe corresponding to this 
         row.  The state can be:
         
         - idle(0), no SCTP association formed;
         - ogConn(1), connecting outgoing, SCTP association being 
           established by this host;
         - icConn(2), connecting incoming, SCTP association being 
           established by remote host;
         - established(3), SCTP association is established and active;
         - shuttinDown(4), the SCTP associat is shutting down.
           
         Only SCTP associations that are in the established(3) state can 
         capture packets or have filters applied."
    ::= { xmonPushEntry 13 }

xmonPushStorageType OBJECT-TYPE
    SYNTAX      StorageType
    MAX-ACCESS  read-create
    STATUS      current
    DESCRIPTION 
        "Specifies the storage type for this conceptual row.  On write, 
         only storage types volatile(2) and nonVolatile(3) are 
         applicable.  volatile(2) rows do not persist across an agent 
         reboot."
    DEFVAL      { nonVolatile }
    ::= { xmonPushEntry 14 }

xmonPushRowStatus OBJECT-TYPE
    SYNTAX      RowStatus
    MAX-ACCESS  read-create
    STATUS      current
    DESCRIPTION 
        "Provides a mechanism whereby mangaement stations may create and 
         destroy rows in this table."
    ::= { xmonPushEntry 15 }

-- =====================================================================
-- xmonPull group
-- =====================================================================

xmonPull OBJECT-IDENTITY
    STATUS      current
    DESCRIPTION 
        "The xmonPull group is responsible for managing the pulling of 
         captured packet stream from a probe at a collector.  These 
         definitions are maintained at a collector."
    ::= { xmonObjects 10 }

xmonPullPort OBJECT-TYPE
    SYNTAX      Integer32 (0..65535)
    MAX-ACCESS  read-write
    STATUS      current
    DESCRIPTION 
        "Specifies the port on which the probe will listen for remote 
         pull requests from collectors."
    ::= { xmonPull 1 }

xmonPullListenTable OBJECT-TYPE
    SYNTAX      SEQUENCE OF XmonPullListenEntry
    MAX-ACCESS  not-accessible
    STATUS      current
    DESCRIPTION 
        "Provides a table of transport addresses upon which the probe 
         will listen for remote pull requests from collectors."
    ::= { xmonPull 2 }

xmonPullListenEntry OBJECT-TYPE
    SYNTAX      XmonPullListenEntry
    MAX-ACCESS  not-accessible
    STATUS      current
    DESCRIPTION 
        "Each row in the table represents a single transport address 
         on which the probe will listen for remote pull requests from 
         collectors."
    INDEX       { xmonPullListenIndex }
    ::= { xmonPullListenTable 1 }

XmonPullListenEntry ::= SEQUENCE {
    xmonPullListenIndex         Unsigned32,
    xmonPullListenAddrType      TransportAddressType,
    xmonPullListenAddr          TransportAddress,
    xmonPullListenRowStatus     RowStatus
}

xmonPullListenIndex OBJECT-TYPE
    SYNTAX      Unsigned32
    MAX-ACCESS  not-accessible
    STATUS      current
    DESCRIPTION 
        "Provides a non-zero ordinal index into this table."
    ::= { xmonPullListenEntry 1 }

xmonPullListenAddrType OBJECT-TYPE
    SYNTAX      TransportAddressType
    MAX-ACCESS  read-create
    STATUS      current
    DESCRIPTION 
        "Specifies the transport address type for this address.  
         Transport address types are restricted to UDP, TCP and SCTP 
         transport domains."
    ::= { xmonPullListenEntry 2 }

xmonPullListenAddr OBJECT-TYPE
    SYNTAX      TransportAddress
    MAX-ACCESS  read-create
    STATUS      current
    DESCRIPTION 
        "Specifies the transport address (IP address, port and possibly 
         zone id, or domain name) upon which the probe will listen for 
         remote pull requests from collectors."
    ::= { xmonPullListenEntry 3 }

xmonPullListenRowStatus OBJECT-TYPE
    SYNTAX      RowStatus
    MAX-ACCESS  read-create
    STATUS      current
    DESCRIPTION 
        "Provides a mechanism whereby management stations may create and 
         destroy rows in this table.  When there are no transport 
         addresses specified in this table, the agent will populate the 
         table autonomously with all transport addresses upon which it 
         is listening using the xmonPullPort value as the port number.  
         Rows in this table that are specified by management stations 
         will persist across agent reboots.  Rows populated autonomously 
         by the agent will not."
    ::= { xmonPullListenEntry 4 }

xmonPullSpoolPath OBJECT-TYPE
    SYNTAX      SubstitutionString
    MAX-ACCESS  read-write
    STATUS      current
    DESCRIPTION 
        "Specifies the file system path to the directory where files are 
         spooled while they are being pulled.  All susbstitutions are 
         supported.  The default if not specified is 
         '/var/local/openss7/xmon/spool/%U'.
         
         In general this value should not be changed from its default 
         because external programs might rely on files being present at 
         the default path."
    DEFVAL      { "/var/local/openss7/xmon/spool/%U" }
    ::= { xmonPull 3 }

xmonPullArchivePath OBJECT-TYPE
    SYNTAX      SubstitutionString
    MAX-ACCESS  read-write
    STATUS      current
    DESCRIPTION 
        "Specifies the file system path to the directory where files are 
         archived once they have been pulled.  All substitutions are 
         supported.  The default if not sepcified is 
         '/var/local/openss7/xmon/archive/%U'.
         
         In general this value should not be changed from its default 
         because external programs might rely on files being present at 
         the default path."
    DEFVAL      { "/var/local/openss7/xmon/archive/%U" }
    ::= { xmonPull 4 }


xmonPullTable OBJECT-TYPE
    SYNTAX      SEQUENCE OF XmonPullEntry
    MAX-ACCESS  not-accessible
    STATUS      current
    DESCRIPTION 
        "The collector is capable of pulling packets captured on remote 
         monitoring sources from remote probes.  In doing so, either the 
         collector or the probe can establish the necessary transport 
         connection.  This table contains the transport addresses of the 
         probes from which the collector will pull (or is pulling) 
         captured packets.  The table contains connections that are 
         initiated by the collector or by the probe.  Only connections 
         initiated by the collector are persistent across an agent 
         reboot.  This table contains definitions that are maintained at 
         a collector.  The xmonPushTable contains definitions that are 
         maintained at a probe."
    ::= { xmonPull 5 }

xmonPullEntry OBJECT-TYPE
    SYNTAX      XmonPullEntry
    MAX-ACCESS  not-accessible
    STATUS      current
    DESCRIPTION 
        "Each row in this table describes one probe from which this 
         collector will pull captured packets from the probe's monitor 
         sources.  Rows established by a management station initiate 
         transport connections.  Rows established autonomously by the 
         agent have responded to a transport connection."
    INDEX       { xmonPullIndex }
    ::= { xmonPullTable 1 }

XmonPullEntry ::= SEQUENCE {
    xmonPullIndex           Unsigned32,
    xmonPullRole            ConnectionRole,
    xmonPullName            DisplayString,
    xmonPullAddrType        TransportAddressType,
    xmonPullAddr            TransportAddress,
    xmonPullConnInterval    TimeInterval,
    xmonPullConnAttempts    Unsigned32,
    xmonPullProfile         SimpleNameType,
    xmonPullAdminState      AdministrativeState,
    xmonPullOpState       OperationalState,
    xmonPullProcStatus      ProceduralStatus,
    xmonPullUsageState      UsageState,
    xmonPullConnState       ConnectionState,
    xmonPullStorageType     StorageType,
    xmonPullRowStatus       RowStatus
}

xmonPullIndex OBJECT-TYPE
    SYNTAX      Unsigned32
    MAX-ACCESS  not-accessible
    STATUS      current
    DESCRIPTION 
        "Provides a non-zero ordinal row index into this table.  Aside 
         from its use as an index, this attribute has no significance."
    ::= { xmonPullEntry 1 }

xmonPullRole OBJECT-TYPE
    SYNTAX      ConnectionRole
    MAX-ACCESS  read-only
    STATUS      current
    DESCRIPTION 
        "Indicates the role in which this host participates in the 
         transport connection:
         
         - initiator(1), this host initiates the connection;
         - responder(2), this host responds to the connection;
         - both(3), this host will both initiate and respond to the 
           connection.
           
         The agent may autonomously create responder(2) roles."
    DEFVAL      { initiator }
    ::= { xmonPullEntry 2 }

xmonPullName OBJECT-TYPE
    SYNTAX      DisplayString
    MAX-ACCESS  read-create
    STATUS      current
    DESCRIPTION 
        "Providse the specification of the name of one transport 
         endpoint from which to pull monitor sources expressed typically 
         as a hostname and port address specification; however, this 
         hostname will not be used for establishing connections.  To 
         specify a hostname as a transport address, used the udpDns(14), 
         tcpDns(15) or sctpDns(16) transport address type in the 
         xmonPullAddrType column."
    ::= { xmonPullEntry 3 }

xmonPullAddrType OBJECT-TYPE
    SYNTAX      TransportAddressType
    MAX-ACCESS  read-create
    STATUS      current
    DESCRIPTION 
        "Specifies the transport address type.  For sctpIpv4(9), the 
         transport address is an IPv4 address and port number; for 
         sctpIpv6(10), it is an IPv6 address and port number."
    REFERENCE   
        "TRANSPORT-ADDRESS-MIB, TransportAddressType"
    ::= { xmonPullEntry 4 }

xmonPullAddr OBJECT-TYPE
    SYNTAX      TransportAddress
    MAX-ACCESS  read-create
    STATUS      current
    DESCRIPTION 
        "Specifies the trasnport address of the remote host from which 
         to pull monitor sources.  The address is of type 
         xmonPullAddrType."
    REFERENCE   
        "TRANSPORT-ADDRESS-MIB, TransportAddressType"
    ::= { xmonPullEntry 5 }

xmonPullConnInterval OBJECT-TYPE
    SYNTAX      TimeInterval
    MAX-ACCESS  read-create
    STATUS      current
    DESCRIPTION 
        "Specifies the interval at which the probe will attempt to 
         reinitiate a failed connection attempt on this connection.  
         When a connection attempt fails, the probe will wait for this 
         interval of time before attempting to reconnect."
    DEFVAL      { 500 }
    ::= { xmonPullEntry 6 }

xmonPullConnAttempts OBJECT-TYPE
    SYNTAX      Unsigned32
    MAX-ACCESS  read-create
    STATUS      current
    DESCRIPTION 
        "Specifies the maximum number of reattempts that a probe will 
         initiate before the transport connectivity it ceases initiation 
         attempts and considers the transport connection to be 
         permanently failed.  The special value zero (0) means that the 
         transport connection will never be considered permanently 
         failed."
    DEFVAL      { 0 }
    ::= { xmonPullEntry 7 }

xmonPullProfile OBJECT-TYPE
    SYNTAX      SimpleNameType
    MAX-ACCESS  read-create
    STATUS      current
    DESCRIPTION 
        "Specifies the transport protocol parameters profile that is to 
         be used to supply protocol parameters, timers, and options for 
         the connection.  The values of this object must be the same as 
         the name of a row in the xmonSctpProfileTable.  Protocol 
         profiles are only applicable to transport addresses in the SCTP 
         transport domain."
    DEFVAL      { "" }
    ::= { xmonPullEntry 8 }

xmonPullAdminState OBJECT-TYPE
    SYNTAX      AdministrativeState
    MAX-ACCESS  read-create
    STATUS      current
    DESCRIPTION 
        "Provides the administrative state of the feed.  This attribute 
         is single-valued and can assume one of the following:
         
         - locked(0), the feed is administratively prohibited;
           
         - unlocked(1), the feed is administratively permitted;
           
         - shuttingDown(2), the transport connection is shutting down: 
           once the connection is released, the feed will move to the 
           locked(0) state.
           
         The value shuttingDown(2) is only valid when read and not valid 
         when written.  This object is used primarily to enable or 
         disable feeds to the collector."
    REFERENCE   
        "OPENSS7-SMI-MIB, AdministrativeState.
         ITU-T Rec. X.735 (1992) | ISO/IEC 10164-6 : 1993, 
               Section 8.1.1.1.3."
    DEFVAL      { unlocked }
    ::= { xmonPullEntry 9 }

xmonPullOpState OBJECT-TYPE
    SYNTAX      OperationalState
    MAX-ACCESS  read-only
    STATUS      current
    DESCRIPTION 
        "Represents the operational capability of the transport 
         connection to perform its function.  The following states are 
         defined:
         
         - enabled(0), the transport connection is operational and ready 
           for use, captured packets will be transferred;
           
         - disabled(1), the transport connection is not available for 
           use; captured packets will be bufferred but cannot be 
           transferred.
           
         A change in operational state shall generate a state changed 
         notification for persistent rows."
    REFERENCE   
        "OPENSS7-SMI-MIB, OperationalState.
         ITU-T Rec. X.735 (1992) | ISO/IEC 10164-6 : 1993, 
               Section 8.1.1.1.4."
    ::= { xmonPullEntry 10 }

xmonPullProcStatus OBJECT-TYPE
    SYNTAX      ProceduralStatus
    MAX-ACCESS  read-only
    STATUS      current
    DESCRIPTION 
        "Provides the procedural status of the feed:
         
         - initializationRequired(0), the feed requires initialization 
           and that initialization has not yet been performed; a manual 
           or automatic action is required to initialize the feed;
           
         - notInitialized(1), the feed requires initialization and that 
           initialization has not completed yet;
           
         - initializing(2), the feed requires initialization and that 
           initialization is proceeding but has not yet completed;
           
         - reporting(3), the feed is reporting its results;
           
         - terminating(4), the feed is terminating.
           
         The procedural status for feeds result from actions taken by 
         the agent and not by actions taken within this MIB."
    REFERENCE   
        "OPENSS7-SMI-MIB, ProceduralStatus.
         ITU-T Rec. X.721 | ISO/IEC 10165-2, proceduralStatus."
    ::= { xmonPullEntry 11 }

xmonPullUsageState OBJECT-TYPE
    SYNTAX      UsageState
    MAX-ACCESS  read-only
    STATUS      current
    DESCRIPTION 
        "Provides the usage state of the feed:
         
         - idle(0), the feed is not currently in use;
           
         - active(1), the feed is in use and has sufficient operating 
           capacity to provide for additional transfer of captured 
           packets;
           
         - busy(2), the feed is in use and has no spare capacity to 
           transfer additional captured packets.
           
         This usage state determines the use of the feed in transferring 
         captured packets and not any other use of the transport 
         connection."
    REFERENCE   
        "OPENSS7-SMI-MIB, UsageState.
         ITU-T Rec. X.721 | ISO/IEC 10165-2, usageState."
    ::= { xmonPullEntry 12 }

xmonPullConnState OBJECT-TYPE
    SYNTAX      ConnectionState
    MAX-ACCESS  read-only
    STATUS      current
    DESCRIPTION 
        "Provides the state of the SCTP association use to import 
         monitor sources from the remote probe corresponding to this 
         row.  The state can be:
         
         - idle(0), no SCTP association formed;
         - ogConn(1), connecting outgoing, SCTP association being 
           established by this host;
         - icConn(2), connecting incoming, SCTP association being 
           established by remote host;
         - established(3), SCTP association is established and active;
         - shuttinDown(4), the SCTP associat is shutting down.
           
         Only SCTP associations that are in the established(3) state can 
         capture packets or have filters applied."
    ::= { xmonPullEntry 13 }

xmonPullStorageType OBJECT-TYPE
    SYNTAX      StorageType
    MAX-ACCESS  read-create
    STATUS      current
    DESCRIPTION 
        "Specifies the storage type for this conceptual row.  On write, 
         only storage types volatile(2) and nonVolatile(3) are 
         applicable.  volatile(2) rows do not persist across an agent 
         reboot."
    DEFVAL      { nonVolatile }
    ::= { xmonPullEntry 14 }

xmonPullRowStatus OBJECT-TYPE
    SYNTAX      RowStatus
    MAX-ACCESS  read-create
    STATUS      current
    DESCRIPTION 
        "Provides a mechanism whereby management stations may create and 
         destroy rows in this table."
    ::= { xmonPullEntry 15 }

-- =====================================================================
-- xmonCollector group
-- =====================================================================

xmonCollector OBJECT-IDENTITY
    STATUS      current
    DESCRIPTION 
        "The xmonCollector group is responsible for managing this host 
         as a collector."
    ::= { xmonObjects 11 }

xmonCollectorExtensions OBJECT-TYPE
    SYNTAX      BITS { any(0), pcap(1), pcapng(2) }
    MAX-ACCESS  read-write
    STATUS      current
    DESCRIPTION 
        "Specifies the filename extensions to be downloaded.  This 
         object is set-valued and can contain the following:
         
         - any(0), download files with any extension;
           
         - pcap(1), download files with the .pcap extension;
           
         - pcapng(2), download files with the .pcapng extension.
           
         Only the extensions specified will be downloaded."
    ::= { xmonCollector 1 }

xmonCollectorAdminState OBJECT-TYPE
    SYNTAX      AdministrativeState
    MAX-ACCESS  read-write
    STATUS      current
    DESCRIPTION 
        "Represents the administrative capability of the collector to 
         perform its function as follows:
         
         - locked(0), downloading and archiving of capture files to the 
           repository has been prohibited by a managing system; all 
           download activities cease;
           
         - unlocked(1), downloading and archiving of capture files to 
           the repository has been permitted by a managing system; the 
           downloading and archiving of capture files continues based on 
           the values of other state and status attributes;
           
         - shuttingDown(2), downloading and archiving of capture files 
           to the repository has been prohibited by a managing system; 
           however, a download is in progress and must complete before 
           the state moves to the locked(0) state.
           
         The value shuttingDown(2) is only valid on read and is invalid 
         on write."
    REFERENCE   
        "OPENSS7-SMI-MIB, AdministrativeState.
         ITU-T Rec. X.735 (1992) | ISO/IEC 10164-6 : 1993, 
               Section 8.1.1.1.3."
    DEFVAL      { unlocked }
    ::= { xmonCollector 2 }

xmonCollectorOpState OBJECT-TYPE
    SYNTAX      OperationalState
    MAX-ACCESS  read-only
    STATUS      current
    DESCRIPTION 
        "Indicates the operational capability of the collector to 
         perform its function as follows:
         
         - enabled(0), the repository is operational and ready for use;
           
         - disabled(1), the repository is not available for use; new 
           downloads will not be initiated.
           
         A changed in operational state shall generate a state changed 
         notification."
    REFERENCE   
        "OPENSS7-SMI-MIB, OperationalState.
         ITU-T Rec. X.735 (1992) | ISO/IEC 10164-6 : 1993, 
               Section 8.1.1.1.4."
    DEFVAL      { enabled }
    ::= { xmonCollector 3 }

xmonCollectorAvailStatus OBJECT-TYPE
    SYNTAX      AvailabilityStatus
    MAX-ACCESS  read-only
    STATUS      current
    DESCRIPTION 
        "Indicates the availability status of the collector.  The 
         attribute may indicate a 'log-full' condition; indicating that 
         capture files can be retrieved but that no new capture files 
         can be added.  When the resource has been made unavailable in 
         accordance with a predetermined time schedule its value will be 
         'Off-Duty'."
    REFERENCE   
        "ITU-T Rec. X.735 (1992) | ISO/IEC 10164-6 : 1993, 
               Section 8.1.1.1.6.
         ITU-T Rec. X.735 (1992) | ISO/IEC 10164-6 : 1993, 
               Section 8.1.1.4.1."
    DEFVAL      { {} }
    ::= { xmonCollector 4 }

xmonCollectorFullAction OBJECT-TYPE
    SYNTAX      FullAction
    MAX-ACCESS  read-write
    STATUS      current
    DESCRIPTION 
        "Provides a specification of the action to be taken when the 
         maximum size of the archive has been reached.  Options are:
         
         - wrap(0), the oldest files in the archive, as determined by 
           the file time stamp, will be deleted to free resources for 
           the addition of newly downloaded files; but see also 
           xmonCollectorDiscardPolicy;
           
         - halt(1), no more files will be added to the archive; files 
           already in the archive will be retained.
           
         Both options are supported by the collector archive."
    ::= { xmonCollector 5 }

xmonCollectorAlarmThreshold OBJECT-TYPE
    SYNTAX      LogCapacityAlarmThreshold
    MAX-ACCESS  read-write
    STATUS      current
    DESCRIPTION 
        "The log alarm package provides for transmission of alarms when 
         a buffer full condition approaches.  This package shall be 
         present whenever a buffer is of finite size and halts buffering 
         when the 'log-full' availability status occurs.
         
         This attribute specifies, as a percentage of maximum buffer 
         size, the points at which an event will be generated to 
         indicate that a 'log-full' or 'log-wrap' condition is 
         approaching.  This attribute is set-valued.  Support of this 
         attribute is mandatory for the halt behaviour.  When a buffer 
         is created with the wrap option, the capacity threshold events 
         are triggered as if couple to a gauge that counts from zero to 
         the highest capacity threshold value defined and then resets to 
         zero."
    REFERENCE   
        "ITU-T Rec. X.735 (1992) | ISO/IEC 10164-6 : 1993, 
               Section 8.1.1.3."
    DEFVAL      { "\x64" }
    ::= { xmonCollector 6 }

xmonCollectorCachePath OBJECT-TYPE
    SYNTAX      SubstitutionString
    MAX-ACCESS  read-write
    STATUS      current
    DESCRIPTION 
        "Specifies the file system path to the directory where files are 
         cached while they are being downloaded.  All substitutions are 
         supported except %I.  The default if not specified is 
         '/var/local/openss7/xmon/cache/%U'.
         
         In general this value should not be changed from its default 
         because external programs might rely on files being present at 
         the default path."
    DEFVAL      { "/var/local/openss7/xmon/cache/%U" }
    ::= { xmonCollector 7 }

xmonCollectorSpoolPath OBJECT-TYPE
    SYNTAX      SubstitutionString
    MAX-ACCESS  read-write
    STATUS      current
    DESCRIPTION 
        "Specifies the file system path to the directory where files are 
         spooled once they have been downloaded.  All substitutions are 
         supported except %I.  The default if not specified is 
         '/var/local/openss7/xmon/spool/%U'.
         
         In general this value should not be changed from its default 
         because external programs might rely on files being present at 
         the default path."
    DEFVAL      { "/var/local/openss7/xmon/spool/%U" }
    ::= { xmonCollector 8 }

xmonCollectorArchivePath OBJECT-TYPE
    SYNTAX      SubstitutionString
    MAX-ACCESS  read-write
    STATUS      current
    DESCRIPTION 
        "Specifies the file system path to the directory where files are 
         archived once they have been uploaded.  All substitutions are 
         supported except %I.  The default if not specified is 
         '/var/local/openss7/xmon/archive/%U'.
         
         In general this value should not be changed from its default 
         because external programs might rely on files being present at 
         the default path."
    DEFVAL      { "/var/local/openss7/xmon/spool/%U" }
    ::= { xmonCollector 9 }

xmonCollectorArchiveSubdirs OBJECT-TYPE
    SYNTAX      BITS { daily(0), weekly(1), monthly(2), yearly(3) }
    MAX-ACCESS  read-write
    STATUS      current
    DESCRIPTION 
        "Specifies the subdirectories that will be used within the 
         archive file system directory to organize archived files by 
         date.  This object is set and can contain zero or more of the 
         following values:
         
         - daily(0), collect files by day of download within a daily 
           subdirectory whose name is the date (YYYY-MM-DD);
           
         - weekly(1), collect files and daily subdirectories (if any) 
           within a weekly subdirectory whose name is the date of the 
           beginning of the week (YYYY-MM-DD);
           
         - monthly(2), collect files, daily and weekly subdirectories 
           (if any) within a monthly subdirectory whose name is the year 
           and month (YYYY-MM);
           
         - yearly(3), collect files, daily, weekly and mothly 
           subdirectories (if any) within a yearly subdirectory whose 
           name is the year (YYYY).
           
         The default value on row creation when not specified is 
         daily(0) and monthly(2)."
    DEFVAL      { {daily, monthly} }
    ::= { xmonCollector 10 }

xmonCollectorCompression OBJECT-TYPE
    SYNTAX      INTEGER { none(0), gz(1), bz2(2), xz(3), zip(4) }
    MAX-ACCESS  read-write
    STATUS      current
    DESCRIPTION 
        "When a capture file is downloaded and spooled it is compressed.  
         Compression is maintained on the file when it is archived.  
         This object specifies what compression to use.  This object is 
         single-valued as follows:
         
         - none(0), no compression, maintain whatever compression of the 
           file was performed by the probe;
           
         - gz(1), gzip compression, .gz file extension;
           
         - bz2(2), bzip2 compression, .bz2 file extension;
           
         - xz(3), xz compression, .xz filename extension;
           
         - zip(4), zip archive, .zip filename extension.
           
         When a compression of other than none(0) is specified, the 
         corresponding file extension will be added to the file name.  
         The file will be decompressed and recompressed in the new 
         format if the downloaded format does not match that specified 
         by this object.  Zip archives contain a single original file.  
         The default value if unspecified is xz(3) compression."
    DEFVAL      { xz }
    ::= { xmonCollector 11 }

xmonCollectorFileSystemAlloc OBJECT-TYPE
    SYNTAX      Unsigned32 (0..100)
    UNITS       "percent"
    MAX-ACCESS  read-write
    STATUS      current
    DESCRIPTION 
        "Specifies the percentage of the file system in which the 
         xmonCollectorArchivePath exists that is allocated to archival 
         capture files.  The total amount of space occupied by archival 
         capture files will not exceed this limit.
         
         The default value is 90%."
    DEFVAL      { 90 }
    ::= { xmonCollector 12 }

xmonCollectorMaxDiskUsage OBJECT-TYPE
    SYNTAX      Unsigned32 (0..100)
    UNITS       "percent"
    MAX-ACCESS  read-write
    STATUS      current
    DESCRIPTION 
        "Specifies the percentage of the allocation portion of the file 
         system in which the xmonCollectorArchivePath exists that is 
         usable for archival capture files.  The total amount of space 
         occupied by archival capture files will not exceed this limit.
         
         The default value is 80%."
    DEFVAL      { 80 }
    ::= { xmonCollector 13 }

xmonCollectorDiscardPolicy OBJECT-TYPE
    SYNTAX      INTEGER { ignore(0), oldest(1), largest(2) }
    MAX-ACCESS  read-write
    STATUS      current
    DESCRIPTION 
        "Specifies the discard policy for archival capture files when 
         file system allocation and disk usage limits are exceeded and 
         the xmonDownloadFullAction is set to halt(1).  This object is 
         single-valued as follows:
         
         - ignore(0), ignores file system and disk usage limits;
           
         - oldest(1), the oldest archival capture files are discarded;
           
         - largest(2), the largest archival capture files are discared.
           
         The default value is ignore(0)."
    DEFVAL      { ignore }
    ::= { xmonCollector 14 }

-- =====================================================================
-- xmonUpload group
-- =====================================================================

xmonUpload OBJECT-IDENTITY
    STATUS      current
    DESCRIPTION 
        "The xmonUpload group is responsible for managing the uploading 
         of spooled capture files from a probe to a collector or central 
         repository."
    ::= { xmonObjects 12 }

xmonUploadTable OBJECT-TYPE
    SYNTAX      SEQUENCE OF XmonUploadEntry
    MAX-ACCESS  not-accessible
    STATUS      current
    DESCRIPTION 
        "Provides a table of collectors to which the probe is to upload 
         capture files on a regular schedule."
    ::= { xmonUpload 1 }

xmonUploadEntry OBJECT-TYPE
    SYNTAX      XmonUploadEntry
    MAX-ACCESS  not-accessible
    STATUS      current
    DESCRIPTION 
        "Each row in the table specifies a single collector to which to 
         upload capture files on a regular schedule."
    INDEX       { xmonUploadIndex }
    ::= { xmonUploadTable 1 }

XmonUploadEntry ::= SEQUENCE {
    xmonUploadIndex             Unsigned32,
    xmonUploadSpec              SubstitutionString,
    xmonUploadUsername          SnmpAdminString,
    xmonUploadPassword          SnmpAdminString,
    xmonUploadPeriod            TimeInterval,
    xmonUploadStartTime         TimeStamp,
    xmonUploadStopTime          TimeStamp,
    xmonUploadIntervalsOfDay    IntervalsOfDay,
    xmonUploadWeekMask          WeekMask,
    xmonUploadOnRotation        TruthValue,
    xmonUploadSelection         INTEGER,
    xmonUploadAdminState        AdministrativeState,
    xmonUploadUsageState        UsageState,
    xmonUploadProcStatus        ProceduralStatus,
    xmonUploadStorageType       StorageType,
    xmonUploadRowStatus         RowStatus
}

xmonUploadIndex OBJECT-TYPE
    SYNTAX      Unsigned32
    MAX-ACCESS  not-accessible
    STATUS      current
    DESCRIPTION 
        "Provides a non-zero ordinal index into the xmonUploadTable.  
         Aside from being an index, this object has no other 
         significance."
    ::= { xmonUploadEntry 1 }

xmonUploadSpec OBJECT-TYPE
    SYNTAX      SubstitutionString
    MAX-ACCESS  read-create
    STATUS      current
    DESCRIPTION 
        "Specifies the method and path to which to upload files on the 
         collector.  This string consists of the URL of a directory to 
         which files will be uploaded.  Supported protocols are all 
         protocols supported by curl(1).  All substitutions are 
         supported.  Escape sequences will be substituted on a per-file 
         basis as files are uploaded."
    REFERENCE   
        "curl(1) manual page."
    ::= { xmonUploadEntry 2 }

xmonUploadUsername OBJECT-TYPE
    SYNTAX      SnmpAdminString
    MAX-ACCESS  read-create
    STATUS      current
    DESCRIPTION 
        "Provides the username for use with the upload string when 
         required.  A username will not be provided unless demanded by 
         the remote server."
    DEFVAL      { "openss7" }
    ::= { xmonUploadEntry 3 }

xmonUploadPassword OBJECT-TYPE
    SYNTAX      SnmpAdminString
    MAX-ACCESS  read-create
    STATUS      current
    DESCRIPTION 
        "Provides a password for use with the upload string when 
         required.  A password will not be provided unless demanded by 
         the remote server.  A read of this object will only return the 
         number of '*' characters equal to the length of the password."
    DEFVAL      { "openss7" }
    ::= { xmonUploadEntry 4 }

xmonUploadPeriod OBJECT-TYPE
    SYNTAX      TimeInterval
    UNITS       "seconds"
    MAX-ACCESS  read-create
    STATUS      current
    DESCRIPTION 
        "Provides the ability to automatically control the frequency at 
         which uploading occurs.  This attribute defines the amount of 
         time that the probe will wait since the last upload before 
         another is attempted.  The special value zero (0) specifies 
         that uploading is not to be attempted periodically but based on 
         the other scheduling parameters in this row.
         
         This object can be used to attempt near-real-time uploads; 
         however, uploading files on a frequent basis (e.g. every 5 
         minutes) could place a high load on the probe for some 
         protocols.  For rsync this is likely not a problem.  The 
         default is every 15 minutes."
    DEFVAL      { 90000 }
    ::= { xmonUploadEntry 5 }

xmonUploadStartTime OBJECT-TYPE
    SYNTAX      TimeStamp
    MAX-ACCESS  read-create
    STATUS      current
    DESCRIPTION 
        "Provides the ability to automatically control the time that 
         uploading starts.  This attribute defines the date and time at 
         which an unlocked(0) and enabled(1) upload starts functioning.  
         If the value of the start time is not specified in the create 
         request, it value defaults to the time of creation of the row 
         causing it to function immediately."
    REFERENCE   
        "ITU-T Rec. X.735 (1992) | ISO/IEC 10164-6 : 1993, 
               Section 8.1.1.4.2."
    DEFVAL      { 0 }
    ::= { xmonUploadEntry 6 }

xmonUploadStopTime OBJECT-TYPE
    SYNTAX      TimeStamp
    MAX-ACCESS  read-create
    STATUS      current
    DESCRIPTION 
        "Provides the ability to automatically control the time that 
         uploading stops.  This attribute defines the data and time at 
         which an upload stops functioning.  If the value of the stop 
         time is not specified in the create request, its value defaults 
         to 'continuous operation'.  Continuous operation is represented 
         by a null value for the stop time."
    REFERENCE   
        "ITU-T Rec. X.735 (1992) | ISO/IEC 10164-6 : 1993, 
               Section 8.1.1.4.2."
    DEFVAL      { 0 }
    ::= { xmonUploadEntry 7 }

xmonUploadIntervalsOfDay OBJECT-TYPE
    SYNTAX      IntervalsOfDay
    MAX-ACCESS  read-create
    STATUS      current
    DESCRIPTION 
        "Provides the capability of scheduling uploads on a daily 
         schedule (scheduling with a periodicity of 24 hours).  This 
         attribute defines the list of time intervals (interval-start 
         and interval-end times of day) during which the uploads will 
         occur.  During excluded intervals uploads will not occur. If 
         not specified in the create request, the value of this object 
         defaults to a single interval encompassing the entire 24-hour 
         period of a day."
    REFERENCE   
        "ITU-T Rec. X.735 (1992) | ISO/IEC 10164-6 : 1993, 
               Section 8.1.1.4.3."
    DEFVAL      { "\x00\x00\x17\x3B" }
    ::= { xmonUploadEntry 8 }

xmonUploadWeekMask OBJECT-TYPE
    SYNTAX      WeekMask
    MAX-ACCESS  read-create
    STATUS      current
    DESCRIPTION 
        "Provides the capablity of scheduling uploads on a weekly 
         schedule (scheduling with a periodicity of one week).  This 
         attribute defines a set of mask components, each specifying a 
         set of time intervals on a 24-hour time-of-day clock, 
         pertaining to selected days of the week.  The week mask 
         attribute defaults to a scheduling criteria of 'always-on' at 
         row creation.
         
         The days of week component defines the days of the week on which 
         uploads may occur.  This component, if not present during row 
         creation, will default to all seven days of the week.
         
         The intervals of day component defines the list of time 
         intervals (interval-start and interval-end times of day) during 
         which uploads may occur when the current day is one of the days 
         that is selected within the corresponding days of week 
         component.  During excluded intervals uploads will not occur.  
         If not specified during row creation, the value of this 
         component defaults to a single interval encompassing the entire 
         24 hour period of a day."
    REFERENCE   
        "ITU-T Rec. X.735 (1992) | ISO/IEC 10164-6 : 1993, 
               Section 8.1.1.4.4."
    DEFVAL      { "\x7F\x01\x00\x00\x17\x3B" }
    ::= { xmonUploadEntry 9 }

xmonUploadOnRotation OBJECT-TYPE
    SYNTAX      TruthValue
    MAX-ACCESS  read-create
    STATUS      current
    DESCRIPTION 
        "Specifies whether to schedule uploads at packet capture archive 
         file rotation events:
         
         - true(1), upload of a newly archived capture file will be 
           initiated immediately upon rotation;
           
         - false(2), upload of a newly archived capture file will be 
           initiated only in accordance with other scheduling 
           attributes.
           
         When set to true(1), the agent will ignore all other upload 
         scheduling parameters for uploading newly archived capture 
         files."
    ::= { xmonUploadEntry 10 }

xmonUploadSelection OBJECT-TYPE
    SYNTAX      INTEGER { new(1), rotated(2), sync(3), all(4) }
    MAX-ACCESS  read-create
    STATUS      current
    DESCRIPTION 
        "Specifies which files are to be uploaded during an upload 
         cycle:
         
         - new(1), only files that have not previously been uploaded to 
           this collector will be uploaded;
           
         - rotated(2), only rotated files that have not previously been 
           uploaded to this collector will be uploaded;
           
         - sync(3), upload any files present on the probe that are not 
           present on the collector;
           
         - all(4), upload all files present on the probe during each 
           cycle.
           
         Only upload protocols that support synchronization will 
         effect the sync(3) setting; those that do not will revert to 
         new(1) behavior."
    ::= { xmonUploadEntry 11 }

xmonUploadAdminState OBJECT-TYPE
    SYNTAX      AdministrativeState
    MAX-ACCESS  read-create
    STATUS      current
    DESCRIPTION 
        "Provides the administrative state of uploads to the remote 
         collector:
         
         - locked(0), the probe is prohibited from uploading files to 
           the remote collector;
           
         - unlocked(1), the probe is permitted to upload files to the 
           remote server according to the upload schedule;
           
         - shuttingDown(2), the probe is actively uploading files to the 
           remote server and will move to the locked(0) state once the 
           upload completes (whether successful or not).
           
         This is used to control the state of uploads.  Set to locked(0) 
         to suppress uploading for a period of time.  Set to unlocked(1) 
         to enable uploading."
    DEFVAL      { unlocked }
    ::= { xmonUploadEntry 12 }

xmonUploadUsageState OBJECT-TYPE
    SYNTAX      UsageState
    MAX-ACCESS  read-only
    STATUS      current
    DESCRIPTION 
        "Provides the usage state of upload cycles:
         
         - idle(0), uploads are idle; no upload is in progress;
           
         - active(1), uploads are active and in progress; additional 
           uploads may be initiated;
           
         - busy(2), uploads are active and in progress; no additional 
           uploads may be initiated.
           
         This usage state determines the use of uploading by the agent 
         and not as a result of any action performed within this MIB."
    ::= { xmonUploadEntry 13 }

xmonUploadProcStatus OBJECT-TYPE
    SYNTAX      ProceduralStatus
    MAX-ACCESS  read-only
    STATUS      current
    DESCRIPTION 
        "Provides the procedural status of uploads to the remote 
         collector:
         
         - intializationRequired(0), not used;
         - notInitialized(1), not used;
         - initializing(2), an upload cycle requires initialization and 
           that initialization is proceeding but has not yet completed;
         - reporting(3), the upload cycle is reporting its results;
         - terminating(4), the upload cycle is terminating.
           
         The procedural status for upload cycles result from scheduling 
         and operation of the upload cycle and not by actions taken 
         within this MIB."
    REFERENCE   
        "OPENSS7-SMI-MIB, ProceduralStatus.
         ITU-T Rec. X.721 | ISO/IEC 10165-2, proceduralStatus."
    ::= { xmonUploadEntry 14 }

xmonUploadStorageType OBJECT-TYPE
    SYNTAX      StorageType
    MAX-ACCESS  read-create
    STATUS      current
    DESCRIPTION 
        "Specifies the storage type for this conceptual row.  On write, 
         only storage types volatile(2) and nonVolatile(3) are 
         applicable.  volatile(2) rows do not persist across an agent 
         reboot."
    DEFVAL      { nonVolatile }
    ::= { xmonUploadEntry 15 }

xmonUploadRowStatus OBJECT-TYPE
    SYNTAX      RowStatus
    MAX-ACCESS  read-create
    STATUS      current
    DESCRIPTION 
        "Provides a mechanism whereby management stations may create and 
         destroy rows in this table."
    ::= { xmonUploadEntry 16 }

-- =====================================================================
-- xmonDownload group
-- =====================================================================

xmonDownload OBJECT-IDENTITY
    STATUS      current
    DESCRIPTION 
        "The xmonDownload group is responsible for managing the 
         downloading of spooled capture files from a probe at a 
         collector or central repository."
    ::= { xmonObjects 13 }

xmonDownloadTable OBJECT-TYPE
    SYNTAX      SEQUENCE OF XmonDownloadEntry
    MAX-ACCESS  not-accessible
    STATUS      current
    DESCRIPTION 
        "Provides a table of probes from which the collector is to 
         download capture files on a regular schedule."
    ::= { xmonDownload 1 }

xmonDownloadEntry OBJECT-TYPE
    SYNTAX      XmonDownloadEntry
    MAX-ACCESS  not-accessible
    STATUS      current
    DESCRIPTION 
        "Each row in the table specifies a single probe from which to 
         download capture files on a regular schedule."
    INDEX       { xmonDownloadIndex }
    ::= { xmonDownloadTable 1 }

XmonDownloadEntry ::= SEQUENCE {
    xmonDownloadIndex           Unsigned32,
    xmonDownloadSpec            SubstitutionString,
    xmonDownloadUsername        SnmpAdminString,
    xmonDownloadPassword        SnmpAdminString,
    xmonDownloadPeriod          TimeInterval,
    xmonDownloadStartTime       TimeStamp,
    xmonDownloadStopTime        TimeStamp,
    xmonDownloadIntervalsOfDay  IntervalsOfDay,
    xmonDownloadWeekMask        WeekMask,
    xmonDownloadOnRotation      TruthValue,
    xmonDownloadSelection       INTEGER,
    xmonDownloadAdminState      AdministrativeState,
    xmonDownloadUsageState      UsageState,
    xmonDownloadProcStatus      ProceduralStatus,
    xmonDownloadStorageType     StorageType,
    xmonDownloadRowStatus       RowStatus
}

xmonDownloadIndex OBJECT-TYPE
    SYNTAX      Unsigned32
    MAX-ACCESS  not-accessible
    STATUS      current
    DESCRIPTION 
        "Provides a non-zero ordinal index of the rows in this table."
    ::= { xmonDownloadEntry 1 }

xmonDownloadSpec OBJECT-TYPE
    SYNTAX      SubstitutionString
    MAX-ACCESS  read-create
    STATUS      current
    DESCRIPTION 
        "Specifies the method and path from which to download files on 
         the probe.  This string consists of the URL of a directory from 
         which files will be downloaded.  Supported protocols are all 
         protocols supported by curl(1).  A substitutions are supported.  
         Escape sequences will be substituted on a per-file basis as 
         files are uploaded."
    REFERENCE   
        "curl(1) manual page."
    ::= { xmonDownloadEntry 2 }

xmonDownloadUsername OBJECT-TYPE
    SYNTAX      SnmpAdminString
    MAX-ACCESS  read-create
    STATUS      current
    DESCRIPTION 
        "Provides the username for use with the download string when 
         required.  A username will not be provided unless demanded by 
         the remote server.  Note that the username may also be included 
         in the URL in the xmonDownloadSpec."
    DEFVAL      { "unexicon" }
    ::= { xmonDownloadEntry 3 }

xmonDownloadPassword OBJECT-TYPE
    SYNTAX      SnmpAdminString
    MAX-ACCESS  read-create
    STATUS      current
    DESCRIPTION 
        "Provides a password for use with the download string when 
         required.  A password will not be provided unless demanded by 
         the remote server.  A read of this object will only return the 
         number of '*' characters equal to the length of the password.  
         Note that the password may also be included in the URL in the 
         xmonDownloadSpec; however, it is much more secure to include it 
         here."
    DEFVAL      { "unexicon" }
    ::= { xmonDownloadEntry 4 }

xmonDownloadPeriod OBJECT-TYPE
    SYNTAX      TimeInterval
    UNITS       "seconds"
    MAX-ACCESS  read-create
    STATUS      current
    DESCRIPTION 
        "Provides the ability to automatically control the frequency at 
         which downloading occurs.  This attribute defines the amount of 
         time that the collector will wait since the last download 
         before another is attempted.  The special value zero (0) 
         specifies that downloading is not to be attempted periodically 
         but based on the other scheduling parameters in this row.
         
         This object can be used to attempt near-real-time downloads; 
         however, downloading files on a frequent basis (e.g. every 5 
         minutes) could place a high load on the probe for some 
         protocols.  For rsync this is likely not a problem.  The 
         default is every 15 minutes."
    DEFVAL      { 90000 }
    ::= { xmonDownloadEntry 5 }

xmonDownloadStartTime OBJECT-TYPE
    SYNTAX      TimeStamp
    MAX-ACCESS  read-create
    STATUS      current
    DESCRIPTION 
        "Provides the ability to automatically control the time that 
         downloading starts.  This attribute defines the date and time 
         at which an unlocked(0) and enabled(1) download starts 
         functioning.  If the value of the start time is not specified 
         in the create request, its value defaults to zero (0) causing 
         it to function immediately."
    REFERENCE   
        "ITU-T Rec. X.735 (1992) | ISO/IEC 10164-6 : 1993, 
               Section 8.1.1.4.2."
    DEFVAL      { 0 }
    ::= { xmonDownloadEntry 6 }

xmonDownloadStopTime OBJECT-TYPE
    SYNTAX      TimeStamp
    MAX-ACCESS  read-create
    STATUS      current
    DESCRIPTION 
        "Provides the ablity to automatically control the time that 
         downloading stops.  This attribte defines the date and time 
         at which downloading stops functioning.  If the value of the 
         stop time is not specified in the create request, its value 
         defaults to 'continuous operation'.  Continuous operation is 
         represented by a zero (0) value for the stop time."
    REFERENCE   
        "ITU-T Rec. X.735 (1992) | ISO/IEC 10164-6 : 1993, 
               Section 8.1.1.4.2."
    DEFVAL      { 0 }
    ::= { xmonDownloadEntry 7 }

xmonDownloadIntervalsOfDay OBJECT-TYPE
    SYNTAX      IntervalsOfDay
    MAX-ACCESS  read-create
    STATUS      current
    DESCRIPTION 
        "Provides the capability of scheduling uploads on a daily 
         schedule (scheduling with a periodicity of 24 hours).  This 
         attribute defines the list of time intervals (interval-start 
         and interval-end times of day) during which the downloads will 
         occur.  During excluded intervals downloads will not occur. If 
         not specified in the create request, the value of this object 
         defaults to a single interval encompassing the entire 24-hour 
         period of a day."
    REFERENCE   
        "ITU-T Rec. X.735 (1992) | ISO/IEC 10164-6 : 1993, 
               Section 8.1.1.4.3."
    DEFVAL      { "\x00\x00\x17\x3B" }
    ::= { xmonDownloadEntry 8 }

xmonDownloadWeekMask OBJECT-TYPE
    SYNTAX      WeekMask
    MAX-ACCESS  read-create
    STATUS      current
    DESCRIPTION 
        "Provides the capablity of scheduling downloads on a weekly 
         schedule (scheduling with a periodicity of one week).  This 
         attribute defines a set of mask components, each specifying a 
         set of time intervals on a 24-hour time-of-day clock, 
         pertaining to selected days of the week.  The week mask 
         attribute defaults to a scheduling criteria of 'always-on' at 
         row creation.
         
         The days of week component defines the days of the week on 
         which downloads may occur.  This component, if not present 
         during row creation, will default to all seven days of the 
         week.
         
         The intervals of day component defines the list of time 
         intervals (interval-start and interval-end times of day) during 
         which downloads may occur when the current day is one of the 
         days that is selected within the corresponding days of week 
         component.  During excluded intervals downloads will not occur.  
         If not specified during row creation, the value of this 
         component defaults to a single interval encompassing the entire 
         24 hour period of a day."
    REFERENCE   
        "ITU-T Rec. X.735 (1992) | ISO/IEC 10164-6 : 1993, 
               Section 8.1.1.4.4."
    DEFVAL      { "\x7F\x01\x00\x00\x17\x3B" }
    ::= { xmonDownloadEntry 9 }

xmonDownloadOnRotation OBJECT-TYPE
    SYNTAX      TruthValue
    MAX-ACCESS  read-create
    STATUS      current
    DESCRIPTION 
        "Specifies whether to schedule downloads at packet capture 
         archive file rotation events:
         
         - true(1), download of a newly archived capture file will be 
           initiated immediately upon rotation;
           
         - false(2), download of a newly archived capture file will be 
           initiated only in accordance with other scheduling 
           attributes.
           
         When set to true(1), the agent will ignore all other download 
         scheduling parameters for downloading newly archived capture 
         files."
    ::= { xmonDownloadEntry 10 }

xmonDownloadSelection OBJECT-TYPE
    SYNTAX      INTEGER { new(1), rotated(2), sync(3), all(4) }
    MAX-ACCESS  read-create
    STATUS      current
    DESCRIPTION 
        "Specifies which files are to be downloaded during an download 
         cycle:
         
         - new(1), only files that have not previously been downloaded 
           to this collector will be downloaded;
           
         - rotated(2), only rotated files that have not previously been 
           downloaded to this collector will be downloaded;
           
         - sync(3), download any files present on the probe that are not 
           present on the collector;
           
         - all(4), download all files present on the probe during each 
           cycle.
           
         Only download protocols that support synchronization will 
         effect the sync(3) setting; those that do not will revert to 
         new(1) behavior."
    ::= { xmonDownloadEntry 11 }

xmonDownloadAdminState OBJECT-TYPE
    SYNTAX      AdministrativeState
    MAX-ACCESS  read-create
    STATUS      current
    DESCRIPTION 
        "Provides the administrative state of downloads from the remote 
         probe:
         
         - locked(0), the probe is prohibited from downloading files 
           from the remote probe;
           
         - unlocked(1), the probe is permitted to download files from 
           the remote server according to the download schedule;
           
         - shuttingDown(2), the collector is actively downloading files 
           from the remote server and will move to the locked(0) state 
           once the download completes (whether successful or not).
           
         This is used to control the state of downloads.  Set to 
         locked(0) to suppress downloading for a period of time.  Set to 
         unlocked(1) to enable downloading."
    DEFVAL      { unlocked }
    ::= { xmonDownloadEntry 12 }

xmonDownloadUsageState OBJECT-TYPE
    SYNTAX      UsageState
    MAX-ACCESS  read-only
    STATUS      current
    DESCRIPTION 
        "Provides the usage state of download cycles:
         
         - idle(0), downloads are idle; no download is in progress;
           
         - active(1), downloads are active and in progress; additional 
           downloads may be initiated;
           
         - busy(2), downloads are active and in progress; no additional 
           downloads may be initiated.
           
         This usage state determines the use of downloading by the agent 
         and not as a result of any action performed within this MIB."
    ::= { xmonDownloadEntry 13 }

xmonDownloadProcStatus OBJECT-TYPE
    SYNTAX      ProceduralStatus
    MAX-ACCESS  read-only
    STATUS      current
    DESCRIPTION 
        "Provides the procedural status of downloads to the remote 
         collector:
         
         - intializationRequired(0), not used;
         - notInitialized(1), not used;
         - initializing(2), a download cycle requires initialization and 
           that initialization is proceeding but has not yet completed;
         - reporting(3), the download cycle is reporting its results;
         - terminating(4), the download cycle is terminating.
           
         The procedural status for download cycles result from 
         scheduling and operation of the download cycle and not by 
         actions taken within this MIB."
    REFERENCE   
        "OPENSS7-SMI-MIB, ProceduralStatus.
         ITU-T Rec. X.721 | ISO/IEC 10165-2, proceduralStatus."
    ::= { xmonDownloadEntry 14 }

xmonDownloadStorageType OBJECT-TYPE
    SYNTAX      StorageType
    MAX-ACCESS  read-create
    STATUS      current
    DESCRIPTION 
        "Specifies the storage type for this conceptual row.  On write, 
         only storage types volatile(2) and nonVolatile(3) are 
         applicable.  volatile(2) rows do not persist across an agent 
         reboot."
    DEFVAL      { nonVolatile }
    ::= { xmonDownloadEntry 15 }

xmonDownloadRowStatus OBJECT-TYPE
    SYNTAX      RowStatus
    MAX-ACCESS  read-create
    STATUS      current
    DESCRIPTION 
        "Provides a mechanism whereby management stations may create and 
         destroy rows in this table."
    ::= { xmonDownloadEntry 16 }

-- =====================================================================
-- xmonProfile group
-- =====================================================================

xmonProfile OBJECT-IDENTITY
    STATUS      current
    DESCRIPTION 
        "The xmonProfile group is responsible for providing SCTP 
         protocol parameters and defaults for use with the creation and 
         operation of SCTP associations."
    ::= { xmonObjects 14 }

xmonSctpDefaultNoDelay OBJECT-TYPE
    SYNTAX      TruthValue
    MAX-ACCESS  read-write
    STATUS      current
    DESCRIPTION 
        "Provides the default value to be used in the xmonSctpNoDelay 
         column when rows are created in the xmonSctpTable and no value is 
         specified."
    DEFVAL      { false }
    ::= { xmonProfile 1 }

xmonSctpDefaultMaxseg OBJECT-TYPE
    SYNTAX      Unsigned32
    MAX-ACCESS  read-write
    STATUS      current
    DESCRIPTION 
        "Provides the default value to be used in the xmonSctpMaxseg 
         column when rows are created in the xmonSctpTable and no value is 
         specified."
    DEFVAL      { 536 }
    ::= { xmonProfile 2 }

xmonSctpDefaultHeartbeatItvl OBJECT-TYPE
    SYNTAX      MilliSeconds
    UNITS       "seconds"
    MAX-ACCESS  read-write
    STATUS      current
    DESCRIPTION 
        "Provides the default value to be used in the 
         xmonSctpHeartbeatItvl column when rows are created in the 
         xmonSctpTable and no value is specified."
    DEFVAL      { 60000 }
    ::= { xmonProfile 3 }

xmonSctpDefaultHeartbeat OBJECT-TYPE
    SYNTAX      TruthValue
    MAX-ACCESS  read-write
    STATUS      current
    DESCRIPTION 
        "Provides the default value to be used in the xmonSctpHeartbeat 
         column when rows are created in the xmonSctpTable and no value is 
         specified."
    DEFVAL      { true }
    ::= { xmonProfile 4 }

xmonSctpDefaultRtoInitial OBJECT-TYPE
    SYNTAX      MilliSeconds
    UNITS       "seconds"
    MAX-ACCESS  read-write
    STATUS      current
    DESCRIPTION 
        "Provides the default value to be used in the xmonSctpRtoInitial 
         column when rows are created in the xmonSctpTable and no value is 
         specified."
    DEFVAL      { 3000 }
    ::= { xmonProfile 5 }

xmonSctpDefaultRtoMin OBJECT-TYPE
    SYNTAX      MilliSeconds
    UNITS       "seconds"
    MAX-ACCESS  read-write
    STATUS      current
    DESCRIPTION 
        "Provides the default value to be used in the xmonSctpRtoMin 
         column when rows are created in the xmonSctpTable and no value is 
         specified."
    DEFVAL      { 1000 }
    ::= { xmonProfile 6 }

xmonSctpDefaultRtoMax OBJECT-TYPE
    SYNTAX      MilliSeconds
    UNITS       "seconds"
    MAX-ACCESS  read-write
    STATUS      current
    DESCRIPTION 
        "Provides the default value to be used in the xmonSctpRtoMax 
         column when rows are created in the xmonSctpTable and no value is 
         specified."
    DEFVAL      { 60000 }
    ::= { xmonProfile 7 }

xmonSctpDefaultPathMaxRetrans OBJECT-TYPE
    SYNTAX      Unsigned32
    MAX-ACCESS  read-write
    STATUS      current
    DESCRIPTION 
        "Provides the default value to be used in the 
         xmonSctpPathMaxRetrans column when rows are created in the 
         xmonSctpTable and no value is specified."
    DEFVAL      { 5 }
    ::= { xmonProfile 8 }

xmonSctpDefaultCookieLife OBJECT-TYPE
    SYNTAX      MilliSeconds
    UNITS       "seconds"
    MAX-ACCESS  read-write
    STATUS      current
    DESCRIPTION 
        "Provides the default value to be used in the xmonSctpCookieLife 
         column when rows are created in the xmonSctpTable and no value is 
         specified."
    DEFVAL      { 0 }
    ::= { xmonProfile 9 }

xmonSctpDefaultCookieInc OBJECT-TYPE
    SYNTAX      MilliSeconds
    UNITS       "seconds"
    MAX-ACCESS  read-write
    STATUS      current
    DESCRIPTION 
        "Provides the default value to be used in the xmonSctpCookieInc 
         column when rows are created in the xmonSctpTable and no value is 
         specified."
    DEFVAL      { 5000 }
    ::= { xmonProfile 10 }

xmonSctpDefaultMaxInitRetries OBJECT-TYPE
    SYNTAX      Unsigned32
    MAX-ACCESS  read-write
    STATUS      current
    DESCRIPTION 
        "Provides the default value to be used in the 
         xmonSctpMaxInitRetries column when rows are created in the 
         xmonSctpTable and no value is specified."
    DEFVAL      { 8 }
    ::= { xmonProfile 11 }

xmonSctpDefaultMaxBurst OBJECT-TYPE
    SYNTAX      Unsigned32
    MAX-ACCESS  read-write
    STATUS      current
    DESCRIPTION 
        "Provides the default value to be used in the xmonSctpMaxBurst 
         column when rows are created in the xmonSctpTable and no value is 
         specified."
    DEFVAL      { 3 }
    ::= { xmonProfile 12 }

xmonSctpDefaultAssocMaxRetrans OBJECT-TYPE
    SYNTAX      Unsigned32
    MAX-ACCESS  read-write
    STATUS      current
    DESCRIPTION 
        "Provides the default value to be used in the 
         xmonSctpAssocMaxRetrans column when rows are created in the 
         xmonSctpTable and no value is specified."
    DEFVAL      { 10 }
    ::= { xmonProfile 13 }

xmonSctpDefaultSackDelay OBJECT-TYPE
    SYNTAX      MilliSeconds
    UNITS       "seconds"
    MAX-ACCESS  read-write
    STATUS      current
    DESCRIPTION 
        "Provides the default value to be used in the xmonSctpSackDelay 
         column when rows are created in the xmonSctpTable and no value is 
         specified."
    DEFVAL      { 200 }
    ::= { xmonProfile 14 }

xmonSctpDefaultLifetime OBJECT-TYPE
    SYNTAX      MilliSeconds
    UNITS       "seconds"
    MAX-ACCESS  read-write
    STATUS      current
    DESCRIPTION 
        "Provides the default value to be used in the xmonSctpLifetime 
         column when rows are created in the xmonSctpTable and no value is 
         specified."
    DEFVAL      { 0 }
    ::= { xmonProfile 15 }

xmonSctpTable OBJECT-TYPE
    SYNTAX      SEQUENCE OF XmonSctpEntry
    MAX-ACCESS  not-accessible
    STATUS      current
    DESCRIPTION 
        "The xmonSctpTable provides a table of SCTP protocol parameters 
         where each row provides one SCTP protocol parameter profile for 
         use in establishing and accepting SCTP associations."
    ::= { xmonProfile 16 }

xmonSctpEntry OBJECT-TYPE
    SYNTAX      XmonSctpEntry
    MAX-ACCESS  not-accessible
    STATUS      current
    DESCRIPTION 
        "Each row in this table consists of a single SCTP prptocol 
         parameter profile indexed by its name."
    INDEX       { xmonSctpProfileName }
    ::= { xmonSctpTable 1 }

XmonSctpEntry ::= SEQUENCE {
    xmonSctpProfileName         SimpleNameType,
    xmonSctpNoDelay             TruthValue,
    xmonSctpMaxseg              Unsigned32,
    xmonSctpHeartbeatItvl       MilliSeconds,
    xmonSctpHeartbeat           TruthValue,
    xmonSctpRtoInitial          MilliSeconds,
    xmonSctpRtoMin              MilliSeconds,
    xmonSctpRtoMax              MilliSeconds,
    xmonSctpPathMaxRetrans      Unsigned32,
    xmonSctpCookieLife          MilliSeconds,
    xmonSctpCookieInc           MilliSeconds,
    xmonSctpMaxInitRetries      Unsigned32,
    xmonSctpMaxBurst            Unsigned32,
    xmonSctpAssocMaxRetrans     Unsigned32,
    xmonSctpSackDelay           MilliSeconds,
    xmonSctpLifetime            MilliSeconds,
    xmonSctpRowStatus           RowStatus
}

xmonSctpProfileName OBJECT-TYPE
    SYNTAX      SimpleNameType
    MAX-ACCESS  not-accessible
    STATUS      current
    DESCRIPTION 
        "Provides the non-null name index of each row in the xmonSctpTable."
    ::= { xmonSctpEntry 1 }

xmonSctpNoDelay OBJECT-TYPE
    SYNTAX      TruthValue
    MAX-ACCESS  read-create
    STATUS      current
    DESCRIPTION 
        "This column defined, under this SCTP profile, whether the Nagle 
         algorithm should be applied to SCTP associations.  The Nagle 
         algorithm increases the size of the packets placed on the 
         network at the expense of delaying the transmission of some 
         data during congestion episodes.  When set to true(1), the 
         Nagle algorithm is suppressed; otherwise, set to false(2), the 
         Nagle algorithm is in effect.
         
         The default value for newly created profiles is determined by 
         the setting of xmonSctpDefaultNoDelay."
    ::= { xmonSctpEntry 2 }

xmonSctpMaxseg OBJECT-TYPE
    SYNTAX      Unsigned32
    MAX-ACCESS  read-create
    STATUS      current
    DESCRIPTION 
        "This column defines the maximum SCTP payload size for outgoing 
         packets.  Values greater than the association MTU are ignored 
         and have no effect.  The value determines the maximum size (in 
         octets) above which SCTP will fragment larget DATA chunks into 
         smaller DATA chunks, and beneath which SCTP will bundle DATA 
         chunks into single packets or combine smaller DATA chunks into 
         larger DATA chunks.  Normally this value is the association MTU 
         value minus the size of the current IP and SCTP headers, minus 
         the size of one DATA chunk header.  When set to a lower value, 
         the lower value will be used.
         
         The default value for newly created profiles is determined by 
         the setting of xmonSctpDefaultMaxseg."
    ::= { xmonSctpEntry 3 }

xmonSctpHeartbeatItvl OBJECT-TYPE
    SYNTAX      MilliSeconds
    UNITS       "seconds"
    MAX-ACCESS  read-create
    STATUS      current
    DESCRIPTION 
        "This column defines the time interval (in milliseconds) between 
         successive HEARTBEAT messages used to probe destination 
         transport addresses for RTT calculation and activity.  Valid 
         values are zero (0) - do not heartbeat, or a value of 1 
         millisecond or greater.
         
         The default value for newly create profiles is determined by 
         the setting of xmonSctpDefaultHeartbeatItvl."
    ::= { xmonSctpEntry 4 }

xmonSctpHeartbeat OBJECT-TYPE
    SYNTAX      TruthValue
    MAX-ACCESS  read-create
    STATUS      current
    DESCRIPTION 
        "This column determines whether HEARTBEAT messages used to probe 
         destination transport addresses for RTT calculation and 
         activity will be sent periodically.  The default value from RFC 
         4960 is true(1).
         
         Disabling heartbeats reduces the protocol's responsiveness in 
         detection of failures and redirection of traffic away from 
         failed paths and interfaces.  This column should normally be 
         left at its default value.
         
         The default value for newly created profiles is determined by 
         the setting of slM2paDefaultSctpHeartbeat."
    ::= { xmonSctpEntry 5 }

xmonSctpRtoInitial OBJECT-TYPE
    SYNTAX      MilliSeconds
    UNITS       "seconds"
    MAX-ACCESS  read-create
    STATUS      current
    DESCRIPTION 
        "This column defines the initial time interval (in milliseconds) 
         that will be used as an initial RTO (retransmission timeout) 
         value when sending packets to a destination for the first time.  
         Valid values are zero or greater but must be within the range 
         xmonSctpRtoMin to xmonSctpRtoMax.  The default value is the value 
         recommended by RFC 2960 and RFC 4960 (1000 milliseconds, or 1 
         second).
         
         Note that, in general, the RTO initial should not be less than 
         the peer's maximum SACK delay, otherwise, excessive 
         retransmission migh occur while the peer is delaying 
         acknowledgements.
         
         The default value for newly created profiles is determined by 
         the setting of xmonSctpDefaultRtoInitial."
    ::= { xmonSctpEntry 6 }

xmonSctpRtoMin OBJECT-TYPE
    SYNTAX      MilliSeconds
    UNITS       "seconds"
    MAX-ACCESS  read-create
    STATUS      current
    DESCRIPTION 
        "This column defines the minimum timer interval (in 
         milliseconds) that will be used as an RTO (retransmission 
         timeout) value when sending packets to a destination transport 
         address and expecting acknowledgements.  Valid values are zero 
         or greater and must be less than or equal to xmonSctpRtoInitial 
         and strictly less than and xmonSctpRtoMax.  The default value is 
         the value recommended by RFC 2960 and RFC 4960 (1000 
         milliseconds, or 1 second).
         
         Note that, in general, the RTO minimum should not be less than 
         the peer's maximum SACK delay, otherwise, excessive 
         retransmission might occur while the peer is delaying 
         acknowledgements.
         
         The default value for newly created profiles is determined by 
         the setting of xmonSctpDefaultRtoMin."
    ::= { xmonSctpEntry 7 }

xmonSctpRtoMax OBJECT-TYPE
    SYNTAX      MilliSeconds
    UNITS       "seconds"
    MAX-ACCESS  read-create
    STATUS      current
    DESCRIPTION 
        "This column defines the maximum time interval (in milliseconds) 
         that will be used as an RTO (retransmission timeout) value when 
         sending packets to a destination transport address and 
         expecting acknowledgements.  Valid values are zero or greater 
         but must be greater than or equal to xmonSctpRtoInitial and 
         strictly greater than xmonSctpRtoMin.  The default value is the 
         value recommended by RFC 2960 and RFC 4960 (60000 milliseconds, 
         or 60 seconds).
         
         Note that, in general, the RTO maximum should not be less than 
         the peer's maximum SACK delay, otherwise, excessive 
         retransmission might occur while the peer is delaying 
         acknowledgements.
         
         The default value for newly created profiles is determined by 
         the setting of xmonSctpDefaultRtoMax."
    ::= { xmonSctpEntry 8 }

xmonSctpPathMaxRetrans OBJECT-TYPE
    SYNTAX      Unsigned32
    MAX-ACCESS  read-create
    STATUS      current
    DESCRIPTION 
        "This column defines the number of times that SCTP will attempt 
         retransmitting a packet to a given destination transport 
         address before it considers that destination transport address 
         inactive.  Valid values are zero or greater.  The default value 
         is the value recommended in RFC 2960 (5 retransmissions).
         
         Adjusting this value has an effect on th period of time taken 
         to fail-over between destinations for multi-homed connections.  
         Lower values (including zero) will yield faster fail-over 
         response times.  Lower values, however, may cause thrashing 
         between destinations contributing to congestion in the network.  
         Default values are applicable to Internet applications.
         
         The default value for newly created profiles is determined by 
         the setting of xmonSctpDefaultPathMaxRetrans."
    ::= { xmonSctpEntry 9 }

xmonSctpCookieLife OBJECT-TYPE
    SYNTAX      MilliSeconds
    UNITS       "seconds"
    MAX-ACCESS  read-create
    STATUS      current
    DESCRIPTION 
        "This column defines the time interval (in milliseconds) in 
         conjunction with xmonSctpCookieInc beyond which a COOKIE-ECHO 
         received with a cookie sent in an INIT-ACK will no longer be 
         accepted.  For SCTP, this also limits the maximum time interval 
         for which the HMAC secret key for the cookie will be valid.  
         Valid values are zero or greater.  Values of zero will  be 
         converted to a system clock tick.  The default value is the 
         value recommended by RFC 2960 (60,000 milliseconds, or 60 
         seconds).
         
         Reducing this value will increase the probability that passive 
         connection attempts will fail due to expired cookies.  
         Increasing the value will reduce the overall security of the 
         system by permitting attackers an increased interval within 
         which to crack HMACs and guess verification tags.  This value 
         may be adjusted in conjunction with xmonSctpCookieInc to meet 
         most objectives for successful passive connection attempts with 
         the best security afforded by smaller values of 
         xmonSctpCookieLife.
         
         Unfortunately, the xmonSctpCookieLife and xmonSctpCookieInc must be 
         adjusted to accommodate the slowest peer on the slowest 
         connection.  The default setting is adequate for Internet 
         applications.
         
         The default value for newly created profiles is determined by 
         the setting of xmonSctpDefaultCookieLife."
    ::= { xmonSctpEntry 10 }

xmonSctpCookieInc OBJECT-TYPE
    SYNTAX      MilliSeconds
    UNITS       "seconds"
    MAX-ACCESS  read-create
    STATUS      current
    DESCRIPTION 
        "This column defines the time increment (in milliseconds) that 
         will be added to the lifespan of the cookie in an INIT-ACK if 
         the received INIT requests cookie preservative to lengthen the 
         lifespan of the cookie.  Valid values are zero or greater.  The 
         default value is the value recommended in RFC 2960 5.2.6 (1000 
         milliseconds, or 1 second).
         
         This value can be adjusted in conjunction with xmonSctpCookieLife 
         to meet objectives of successful passive connection attempts 
         and security.  The default setting is adequate for Internet 
         applications.
         
         The default value for newly created profiles is determined by 
         the setting of xmonSctpDefaultCookieInc."
    ::= { xmonSctpEntry 11 }

xmonSctpMaxInitRetries OBJECT-TYPE
    SYNTAX      Unsigned32
    MAX-ACCESS  read-create
    STATUS      current
    DESCRIPTION 
        "This column defines the number of times that an INIT or 
         COOKIE-ECHO will be resent to a given destination before 
         abandoning an active open attempt.  Value values are zero or 
         greater.  The default value is the value recommended by RFC 
         2960 (8 retries).
         
         The default value for newly created profiles is determined by 
         the setting of xmonSctpDefaultMaxInitRetries."
    ::= { xmonSctpEntry 12 }

xmonSctpMaxBurst OBJECT-TYPE
    SYNTAX      Unsigned32
    MAX-ACCESS  read-create
    STATUS      current
    DESCRIPTION 
        "This column defines the maximum number of MTUs of new data 
         chunks that will be sent in a burst in accordance with SCTP 
         Specification Errata and Issues, RFC 4460 and RFC 4960.  The 
         default value is the value recommended in RFC 4960 (4 MTUs).
         
         The default value for newly create profiles is determined by 
         the setting of xmonSctpDefaultMaxBurst."
    ::= { xmonSctpEntry 13 }

xmonSctpAssocMaxRetrans OBJECT-TYPE
    SYNTAX      Unsigned32
    MAX-ACCESS  read-create
    STATUS      current
    DESCRIPTION 
        "This column defines the number of times that the sending 
         endpoint will attempt retransmitting a packet on any active 
         destination transport address before it aborts the association.  
         Value values are zero or greater.  The default value is the 
         value recommended in RFC 2960 (10 retransmissions).
         
         This value should be larger than sum of the path maximum number 
         of retransmission values of each of the destinations.
         
         Setting this value to less than the sum of the path maximum 
         retransmission values for all of the destinations has the 
         interesting effect of permitting a connection to persist even 
         when all destinations have been deemed inactive.
         
         The default value for newly created profiles is determined by 
         the setting of xmonSctpDefaultAssocMaxRetrans."
    DEFVAL      { 20 }
    ::= { xmonSctpEntry 14 }

xmonSctpSackDelay OBJECT-TYPE
    SYNTAX      MilliSeconds
    UNITS       "seconds"
    MAX-ACCESS  read-create
    STATUS      current
    DESCRIPTION 
        "This column defines the interval of time (in milliseconds) that 
         will be used as an RTO (retransmission timeout) value when 
         sending packets to a destination transport address.  Valid 
         values are zero or to 500 milliseconds (RFC 2960 forbids 
         setting this value larger than 500 milliseconds).  The default 
         value is the value recommended in RFC 2960 (200 milliseconds).
         
         The default value for newly created profiles is determined by 
         the setting of xmonSctpDefaultSackDelay."
    DEFVAL      { 20 }
    ::= { xmonSctpEntry 15 }

xmonSctpLifetime OBJECT-TYPE
    SYNTAX      MilliSeconds
    UNITS       "seconds"
    MAX-ACCESS  read-create
    STATUS      current
    DESCRIPTION 
        "The default value for newly created rows is determined by the 
         setting of xmonSctpDefaultLifetime."
    ::= { xmonSctpEntry 16 }

xmonSctpRowStatus OBJECT-TYPE
    SYNTAX      RowStatus
    MAX-ACCESS  read-create
    STATUS      current
    DESCRIPTION 
        "Provides a mechanism whereby management stations, following the 
         RowStatus textual convention from the SNMPv2-TC module, may 
         create or destroy conceptual rows in this table.  Profiles that 
         are referenced by another table cannot be deleted until the 
         reference is removed."
    REFERENCE   
        "STD 58, SNMPv2-TC RowStatus."
    ::= { xmonSctpEntry 17 }

-- ====================================================================
-- GROUPS
-- ====================================================================

xmonGroups OBJECT IDENTIFIER
    ::= { xmonMIB 3 }

xmonCompliances OBJECT IDENTIFIER
    ::= { xmonMIB 4 }

xmonProbeGroup OBJECT-GROUP
    OBJECTS     { xmonProbeName, xmonProbeUuid, xmonProbeHardware, 
                  xmonProbeOs, xmonProbeUserAppl }
    STATUS      current
    DESCRIPTION 
        "A collection of objects providing management of the probe."
    ::= { xmonGroups 1 }

xmonSourceGroup OBJECT-GROUP
    OBJECTS     { xmonSourceType, xmonSourceName, xmonSourceIfIndex, 
                  xmonSourceAdminState, xmonSourceOpState, 
                  xmonSourceAvailStatus, xmonSourceProcStatus, 
                  xmonSourceUsageState }
    STATUS      current
    DESCRIPTION 
        "A collection of objects providing management of monitoring 
         sources for a probe."
    ::= { xmonGroups 2 }

xmonInterfaceGroup OBJECT-GROUP
    OBJECTS     { xmonInterfaceLinkType, xmonInterfaceSnapLen, 
                  xmonInterfacePromiscuous, xmonInterfaceMonitor, 
                  xmonInterfaceDirection, xmonInterfaceDescription, 
                  xmonInterfacePhysAddr, xmonInterfaceSpeed, 
                  xmonInterfaceTsRes, xmonInterfaceTzone, 
                  xmonInterfaceFilterType, xmonInterfaceFilter, 
                  xmonInterfaceFilterBpf, xmonInterfaceFilterStatus, 
                  xmonInterfaceOs, xmonInterfaceFcsLen, 
                  xmonInterfaceTsOffset, xmonInterfaceStorageType, 
                  xmonInterfaceRowStatus }
    STATUS      current
    DESCRIPTION 
        "A collection of objects providing management of monitoring 
         interfaces for a probe."
    ::= { xmonGroups 3 }

xmonRmonGroup OBJECT-GROUP
    OBJECTS     { xmonRmonAddrType, xmonRmonAddr, xmonRmonSnmpVersion, 
                  xmonRmonCommunity, xmonRmonUsername, xmonRmonPassword, 
                  xmonRmonBuffCtrlIndex, xmonRmonBuffIndex, 
                  xmonRmonStorageType, xmonRmonRowStatus }
    STATUS      current
    DESCRIPTION 
        "A collection of objects providing management for initiating 
         capture of packets from a remote probe utilizing the RMON 
         capture(8) group."
    ::= { xmonGroups 4 }

xmonBufferGroup OBJECT-GROUP
    OBJECTS     { xmonBufferAdminState, xmonBufferOpState, 
                  xmonBufferAvailStatus, xmonBufferFullAction, 
                  xmonBufferMaxSize, xmonBufferMaxPackets, 
                  xmonBufferMaxTime, xmonBufferAlarmThreshold, 
                  xmonBufferActionResult }
    STATUS      current
    DESCRIPTION 
        "A collection of objects providing management of the capture 
         buffer for a probe."
    ::= { xmonGroups 5 }

xmonCaptureGroup OBJECT-GROUP
    OBJECTS     { xmonCapturePath, xmonCaptureFilename, 
                  xmonCaptureAdminState, xmonCaptureOpState, 
                  xmonCaptureAvailStatus, xmonCaptureFullAction, 
                  xmonCaptureMaxSize, xmonCaptureMaxPackets, 
                  xmonCaptureMaxTime, xmonCaptureAlarmThreshold }
    STATUS      current
    DESCRIPTION 
        "A collection of objects providing managment of capture for a 
         probe."
    ::= { xmonGroups 6 }

xmonArchiveGroup OBJECT-GROUP
    OBJECTS     { xmonArchivePath, xmonArchiveName, 
                  xmonArchiveFileFormat, xmonArchiveCompressed, 
                  xmonArchiveState, xmonArchiveActionResult }
    STATUS      current
    DESCRIPTION 
        "A collection of objects providing management of the capture 
         archive for a probe or collector."
    ::= { xmonGroups 7 }

xmonFeedGroup OBJECT-GROUP
    OBJECTS     { xmonFeedTypes, xmonFeedPort, xmonFeedListenAddrType, 
                  xmonFeedListenAddr, xmonFeedListenRowStatus, 
                  xmonFeedRole, xmonFeedName, xmonFeedAddrType, 
                  xmonFeedAddr, xmonFeedConnInterval, 
                  xmonFeedConnAttempts, xmonFeedProfile, 
                  xmonFeedAdminState, xmonFeedOpState, 
                  xmonFeedProcStatus, xmonFeedUsageState, 
                  xmonFeedConnState, xmonFeedStorageType, 
                  xmonFeedRowStatus }
    STATUS      current
    DESCRIPTION 
        "A collection of objects providing managment of nms- and 
         probe-initiated live feeds between probe and network management 
         system."
    ::= { xmonGroups 8 }

xmonPushGroup OBJECT-GROUP
    OBJECTS     { xmonPushRole, xmonPushName, xmonPushAddrType, 
                  xmonPushAddr, xmonPushConnInterval, 
                  xmonPushConnAttempts, xmonPushProfile, 
                  xmonPushAdminState, xmonPushOpState, 
                  xmonPushProcStatus, xmonPushUsageState, 
                  xmonPushConnState, xmonPushStorageType, 
                  xmonPushRowStatus, xmonPullPort, 
                  xmonPullListenAddrType, xmonPullListenAddr, 
                  xmonPullListenRowStatus }
    STATUS      current
    DESCRIPTION 
        "A collection of objects providing management of probe initiated 
         dynamic feeds of captured packets between probes and 
         collectors."
    ::= { xmonGroups 9 }

xmonPullGroup OBJECT-GROUP
    OBJECTS     { xmonPullSpoolPath, xmonPullArchivePath, xmonPullRole, 
                  xmonPullName, xmonPullAddrType, xmonPullAddr, 
                  xmonPullConnInterval, xmonPullConnAttempts, 
                  xmonPullProfile, xmonPullAdminState, xmonPullOpState, 
                  xmonPullProcStatus, xmonPullUsageState, 
                  xmonPullConnState, xmonPullStorageType, 
                  xmonPullRowStatus, xmonPushPort, 
                  xmonPushListenAddrType, xmonPushListenAddr, 
                  xmonPushListenRowStatus }
    STATUS      current
    DESCRIPTION 
        "A collection of objects providing management of collector 
         initiated dynamic feeds of captured packets between probes and 
         collectors."
    ::= { xmonGroups 10 }

xmonCollectorGroup OBJECT-GROUP
    OBJECTS     { xmonCollectorExtensions, xmonCollectorAdminState, 
                  xmonCollectorOpState, xmonCollectorAvailStatus, 
                  xmonCollectorFullAction, xmonCollectorAlarmThreshold, 
                  xmonCollectorCachePath, xmonCollectorSpoolPath, 
                  xmonCollectorArchivePath, xmonCollectorArchiveSubdirs, 
                  xmonCollectorCompression, xmonCollectorFileSystemAlloc, 
                  xmonCollectorMaxDiskUsage, xmonCollectorDiscardPolicy }
    STATUS      current
    DESCRIPTION 
        "A collection of objects provinding management of a collector."
    ::= { xmonGroups 11 }

xmonProfileGroup OBJECT-GROUP
    OBJECTS     { xmonSctpDefaultNoDelay, xmonSctpDefaultMaxseg, 
                  xmonSctpDefaultHeartbeatItvl, xmonSctpDefaultHeartbeat, 
                  xmonSctpDefaultRtoInitial, xmonSctpDefaultRtoMin, 
                  xmonSctpDefaultRtoMax, xmonSctpDefaultPathMaxRetrans, 
                  xmonSctpDefaultCookieLife, xmonSctpDefaultCookieInc, 
                  xmonSctpDefaultMaxInitRetries, xmonSctpDefaultMaxBurst, 
                  xmonSctpDefaultAssocMaxRetrans, 
                  xmonSctpDefaultSackDelay, xmonSctpDefaultLifetime, 
                  xmonSctpNoDelay, xmonSctpMaxseg, xmonSctpHeartbeatItvl, 
                  xmonSctpHeartbeat, xmonSctpRtoInitial, xmonSctpRtoMin, 
                  xmonSctpRtoMax, xmonSctpPathMaxRetrans, 
                  xmonSctpCookieLife, xmonSctpCookieInc, 
                  xmonSctpMaxInitRetries, xmonSctpMaxBurst, 
                  xmonSctpAssocMaxRetrans, xmonSctpSackDelay, 
                  xmonSctpLifetime, xmonSctpRowStatus }
    STATUS      current
    DESCRIPTION 
        "A collection of objects providing management of protocol 
         options profiles."
    ::= { xmonGroups 12 }

xmonUploadGroup OBJECT-GROUP
    OBJECTS     { xmonUploadSpec, xmonUploadUsername, xmonUploadPassword, 
                  xmonUploadPeriod, xmonUploadStartTime, 
                  xmonUploadStopTime, xmonUploadIntervalsOfDay, 
                  xmonUploadWeekMask, xmonUploadOnRotation, 
                  xmonUploadSelection, xmonUploadAdminState, 
                  xmonUploadUsageState, xmonUploadProcStatus, 
                  xmonUploadStorageType, xmonUploadRowStatus }
    STATUS      current
    DESCRIPTION 
        "A collection of objects providing management of probe-initiated 
         transfer of archival capture files from a collector to a 
         repository."
    ::= { xmonGroups 13 }

xmonDownloadGroup OBJECT-GROUP
    OBJECTS     { xmonDownloadSpec, xmonDownloadUsername, 
                  xmonDownloadPassword, xmonDownloadPeriod, 
                  xmonDownloadStartTime, xmonDownloadStopTime, 
                  xmonDownloadIntervalsOfDay, xmonDownloadWeekMask, 
                  xmonDownloadOnRotation, xmonDownloadSelection, 
                  xmonDownloadAdminState, xmonDownloadUsageState, 
                  xmonDownloadProcStatus, xmonDownloadStorageType, 
                  xmonDownloadRowStatus }
    STATUS      current
    DESCRIPTION 
        "A collection of objects provinding management of 
         collector-initiated transfer of archival capture files from a 
         collector to a repository."
    ::= { xmonGroups 14 }

-- xmonProbeStatsGroup OBJECT-GROUP
--     OBJECTS     { xmonProbe }
--     STATUS      current
--     DESCRIPTION 
--         "A collection of objects providing current monitoring statistics 
--          for a probe."
--     ::= { xmonGroups 15 }

xmonSourceStatsGroup OBJECT-GROUP
    OBJECTS     { xmonSourceStatsTimeElapsed, xmonSourceStatsTimeStamp, 
                  xmonSourceStatsStartTime, xmonSourceStatsEndTime, 
                  xmonSourceStatsIfRecv, xmonSourceStatsIfDrop, 
                  xmonSourceStatsFilterAccept, xmonSourceStatsOsDrop, 
                  xmonSourceStatsUserDeliv }
    STATUS      current
    DESCRIPTION 
        "A collection of objects providing current monitoring source 
         statistics for a probe."
    ::= { xmonGroups 16 }

xmonBufferStatsGroup OBJECT-GROUP
    OBJECTS     { xmonBufferCurrentSize, xmonBufferNumberOfPackets, 
                  xmonBufferCurrentInterval, xmonBufferOctetHiWaterMark, 
                  xmonBufferOctetLoWaterMark, xmonBufferPktsHiWaterMark, 
                  xmonBufferPktsLoWaterMark, xmonBufferTimeHiWaterMark, 
                  xmonBufferTimeLoWaterMark, xmonBufferTimeElapsed, 
                  xmonBufferBegTime, xmonBufferEndTime, xmonBufferIfRecv, 
                  xmonBufferIfDrop, xmonBufferFilterAccept, 
                  xmonBufferOsDrop, xmonBufferUserDeliv, 
                  xmonBufferIfCompress, xmonBufferUserOctets, 
                  xmonBufferDrops, xmonBufferReset }
    STATUS      current
    DESCRIPTION 
        "A collection of objects providing current capture buffer 
         statistics for a probe."
    ::= { xmonGroups 17 }

xmonCaptureStatsGroup OBJECT-GROUP
    OBJECTS     { xmonCaptureCurrentSize, xmonCaptureNumberOfPackets, 
                  xmonCaptureCurrentInterval, 
                  xmonCaptureOctetHiWaterMark, 
                  xmonCaptureOctetLoWaterMark, 
                  xmonCapturePktsHiWaterMark, xmonCapturePktsLoWaterMark, 
                  xmonCaptureTimeHiWaterMark, xmonCaptureTimeLoWaterMark }
    STATUS      current
    DESCRIPTION 
        "A collection of objects providing current capture statistics 
         for a probe."
    ::= { xmonGroups 18 }

xmonArchiveStatsGroup OBJECT-GROUP
    OBJECTS     { xmonArchiveSize, xmonArchiveCompSize, 
                  xmonArchiveTimeElapsed, xmonArchiveBegTime, 
                  xmonArchiveEndTime, xmonArchiveIfRecv, 
                  xmonArchiveIfDrop, xmonArchiveFilterAccept, 
                  xmonArchiveOsDrop, xmonArchiveUserDeliv, 
                  xmonArchiveIfCompress, xmonArchiveUserOctets }
    STATUS      current
    DESCRIPTION 
        "A collection of objects providing current capture archive 
         statistics for a probe or collector."
    ::= { xmonGroups 19 }

xmonFeedStatsGroup OBJECT-GROUP
    OBJECTS     { xmonFeedTimeElapsed, xmonFeedBegTime, xmonFeedEndTime, 
                  xmonFeedIfRecv, xmonFeedIfDrop, xmonFeedFilterAccept, 
                  xmonFeedOsDrop, xmonFeedUserDeliv, xmonFeedIfCompress, 
                  xmonFeedUserOctets }
    STATUS      current
    DESCRIPTION 
        "A collection of objects providing live feed statistics for a 
         probe."
    ::= { xmonGroups 20 }

-- xmonProbeHistGroup OBJECT-GROUP
--     OBJECTS     { xmonProbe }
--     STATUS      current
--     DESCRIPTION 
--         "A collection of objects providing historical monitoring 
--          statistics for a probe."
--     ::= { xmonGroups 21 }

xmonSourceHistGroup OBJECT-GROUP
    OBJECTS     { xmonSourceHistIfRecv, xmonSourceHistIfDrop, 
                  xmonSourceHistFilterAccept, xmonSourceHistOsDrop, 
                  xmonSourceHistUserDeliv, xmonSourceTotalValidIntervals, 
                  xmonSourceTotalIfRecv, xmonSourceTotalIfDrop, 
                  xmonSourceTotalFilterAccept, xmonSourceTotalOsDrop, 
                  xmonSourceTotalUserDeliv }
    STATUS      current
    DESCRIPTION 
        "A collection of objects providing historical monitoring source 
         statistics for a probe."
    ::= { xmonGroups 22 }

-- xmonBufferHistGroup OBJECT-GROUP
--     OBJECTS     { xmonBuffer }
--     STATUS      current
--     DESCRIPTION 
--         "A collection of objects providing historical capture buffer 
--          statistics for a probe."
--     ::= { xmonGroups 23 }

-- xmonCaptureHistGroup OBJECT-GROUP
--     OBJECTS     { xmonCapture }
--     STATUS      current
--     DESCRIPTION 
--         "A collection of objects providing historical capture statistics 
--          for a probe."
--     ::= { xmonGroups 24 }

-- ====================================================================
-- COMPLIANCE
-- ====================================================================

xmonBasicCompliance MODULE-COMPLIANCE
    STATUS      current
    DESCRIPTION 
        "Provides the module compliance requirements for the extended 
         remote monitoring MIB."

    MODULE      -- this module

        MANDATORY-GROUPS        { xmonProbeGroup }

        GROUP   xmonInterfaceGroup
        DESCRIPTION   
              "Conditional items when local monitoring sources are 
               implemented."

        GROUP   xmonRmonGroup
        DESCRIPTION   
              "Conditional items when rmote RMON monitoring sources are 
               implemented."

        GROUP   xmonSourceGroup
        DESCRIPTION   
              "Conditional items when monitoring sources are 
               implemented."

        GROUP   xmonSourceStatsGroup
        DESCRIPTION   
              "Conditional items when current capture source statistics 
               are implemented."

        GROUP   xmonSourceHistGroup
        DESCRIPTION   
              "Conditional items when historical capture source 
               statistics are implemented."

        GROUP   xmonBufferGroup
        DESCRIPTION   
              "Conditional items when a probe is implemented."

        GROUP   xmonBufferStatsGroup
        DESCRIPTION   
              "Conditional items when buffer statistics are 
               implemented."

    ::= { xmonCompliances 1 }

xmonProbeCompliance MODULE-COMPLIANCE
    STATUS      current
    DESCRIPTION 
        "Provides the module compliance requirements for the extended 
         remote monitoring MIB when the implementation is a probe only.  
         A probe is a network element that captures messages and 
         archives then in files that are uploaded to a collector or 
         repository according to a schedule.
         
         The probe may also provide its monitoring sources as live feeds 
         to network management systems or to collectors that will 
         capture their own files form the live feed."

    MODULE      -- this module

        MANDATORY-GROUPS        { xmonProbeGroup, xmonInterfaceGroup, 
                  xmonSourceGroup, xmonBufferGroup, xmonCaptureGroup, 
                  xmonArchiveGroup }

        GROUP   xmonSourceStatsGroup
        DESCRIPTION   
              "Conditional items when current capture source statistics 
               are implemented."

        GROUP   xmonSourceHistGroup
        DESCRIPTION   
              "Conditional items when historical capture source 
               statistics are implemented."

        GROUP   xmonBufferStatsGroup
        DESCRIPTION   
              "Conditional items when buffer statistics are 
               implemented."

        GROUP   xmonCaptureStatsGroup
        DESCRIPTION   
              "Conditional items when capture statistics are 
               implemented."

        GROUP   xmonArchiveStatsGroup
        DESCRIPTION   
              "Conditional items when archive file statistics are 
               implemented."

        GROUP   xmonFeedGroup
        DESCRIPTION   
              "Conditional items to provide live capture feeds to 
               network management systems."

        GROUP   xmonFeedStatsGroup
        DESCRIPTION   
              "Conditional items when live feed statistics are 
               implemented."

        GROUP   xmonPushGroup
        DESCRIPTION   
              "Conditional items to provide live capture feeds to 
               collectors."

        GROUP   xmonProfileGroup
        DESCRIPTION   
              "Conditional items to provide SCTP transport protocol 
               profile support for live feeds."

        GROUP   xmonUploadGroup
        DESCRIPTION   
              "Conditional items when probe-initiated uploads of capture 
               archive files is implemented."

    ::= { xmonCompliances 2 }

xmonCollectorCompliance MODULE-COMPLIANCE
    STATUS      current
    DESCRIPTION 
        "Provides the module compliance requirements for the XMON MIB 
         when the implementation is a collector only."

    MODULE      -- this module

        MANDATORY-GROUPS        { xmonCollectorGroup, xmonArchiveGroup, 
                  xmonPullGroup, xmonDownloadGroup }

        GROUP   xmonArchiveStatsGroup
        DESCRIPTION   
              "Conditional items when archive file statistics are 
               implemented."

        GROUP   xmonSourceGroup
        DESCRIPTION   
              "Conditional items when the collector implements 
               collection of captured packets from a RMON remote probe."

        GROUP   xmonRmonGroup
        DESCRIPTION   
              "Conditional items when the collector implements 
               collection of captured packets from a RMON remote probe."

        OBJECT  xmonRmonAddrType
        SYNTAX  TransportAddressType { udpIpv4(1), udpIpv6(2), 
                    udpIpv4z(3), udpIpv6z(4), udpDns(14) }
        DESCRIPTION   
              "This object has a restricted range of values in its 
               syntax.  Only UDP transport types are supported SNMP RMON 
               capture."

    ::= { xmonCompliances 3 }

xmonRepositoryCompliance MODULE-COMPLIANCE
    STATUS      current
    DESCRIPTION 
        "Provides the module compliance requirements for the XMON MIB 
         when the implementation is a central archive repository.  
         Central archive repositories are responsible for downloading 
         archive capture files from probes and collectors and placing 
         them into a central archive repository."

    MODULE      -- this module

        MANDATORY-GROUPS        { xmonArchiveGroup, xmonDownloadGroup }

        GROUP   xmonArchiveStatsGroup
        DESCRIPTION   
              "Conditional items when archive file statistics are 
               implemented."

        GROUP   xmonCollectorGroup
        DESCRIPTION   
              "Conditional items when the repository also acts as a 
               collector."

        GROUP   xmonPullGroup
        DESCRIPTION   
              "Conditional items when the repository also acts as a 
               collector and initiates live feeds for accepting captured 
               packets from probes."

        GROUP   xmonSourceGroup
        DESCRIPTION   
              "Conditional items when the respository also acts as a 
               collector and collects captured packets from a remote 
               RMON probe."

        GROUP   xmonRmonGroup
        DESCRIPTION   
              "Conditional items when the repository also acts as a 
               collector and collects captured packets from a remote 
               RMON probe."

        OBJECT  xmonRmonAddrType
        SYNTAX  TransportAddressType { udpIpv4(1), udpIpv6(2), 
                    udpIpv4z(3), udpIpv6z(4), udpDns(14) }
        DESCRIPTION   
              "This object has a restricted range of values in its 
               syntax.  Only UDP transport types are supported SNMP RMON 
               capture."

    ::= { xmonCompliances 4 }

xmonNmsCompliance MODULE-COMPLIANCE
    STATUS      current
    DESCRIPTION 
        "Provides the module compliance requirements for the XMON MIB 
         when the implementation is a network management system.  
         Network management systems are responsible for initiating or 
         accepting capture feeds from probes and collectors.  They may 
         also responsible for maintaining their own archive."

    MODULE      -- this module

        MANDATORY-GROUPS        { xmonCaptureGroup }

        GROUP   xmonCaptureStatsGroup
        DESCRIPTION   
              "Conditional items when capture statistics are 
               implemented."

        GROUP   xmonPullGroup
        DESCRIPTION   
              "Conditional items if the network management system also 
               acts as a collector."

        GROUP   xmonSourceGroup
        DESCRIPTION   
              "Conditional items if the network management system also 
               acts as a collector."

        GROUP   xmonRmonGroup
        DESCRIPTION   
              "Conditional items if the network management system also 
               acts as a collector."

        GROUP   xmonArchiveGroup
        DESCRIPTION   
              "Conditional items if the network management system also 
               acts as a repository."

        GROUP   xmonArchiveStatsGroup
        DESCRIPTION   
              "Conditional items when archive file statistics are 
               implemented."

        GROUP   xmonDownloadGroup
        DESCRIPTION   
              "Conditional items if the network management system also 
               acts as a repository."

        OBJECT  xmonRmonAddrType
        SYNTAX  TransportAddressType { udpIpv4(1), udpIpv6(2), 
                    udpIpv4z(3), udpIpv6z(4), udpDns(14) }
        DESCRIPTION   
              "This object has a restricted range of values in its 
               syntax.  Only UDP transport types are supported SNMP RMON 
               capture."

    ::= { xmonCompliances 5 }

xmonFullCompliance MODULE-COMPLIANCE
    STATUS      current
    DESCRIPTION 
        "Provides the module compliacne requirements for the XMON MIB 
         when the implementation acts in all roles: it acts as a probe 
         for local monitoring sources, acts as a collector from remote 
         probes, acts as a network management system for local and 
         remote probes, and acts as a central archive repository for its 
         own purposes."

    MODULE      -- this module

        MANDATORY-GROUPS        { xmonProbeGroup, xmonInterfaceGroup, 
                  xmonSourceGroup, xmonBufferGroup, xmonCaptureGroup, 
                  xmonArchiveGroup, xmonCollectorGroup, xmonPullGroup, 
                  xmonDownloadGroup }

        GROUP   xmonSourceStatsGroup
        DESCRIPTION   
              "Conditional items when current capture source statistics 
               are implemented."

        GROUP   xmonSourceHistGroup
        DESCRIPTION   
              "Conditional items when historical capture source 
               statistics are implemented."

        GROUP   xmonBufferStatsGroup
        DESCRIPTION   
              "Conditional items when buffer statistics are 
               implemented."

        GROUP   xmonCaptureStatsGroup
        DESCRIPTION   
              "Conditional items when capture statistics are 
               implemented."

        GROUP   xmonArchiveStatsGroup
        DESCRIPTION   
              "Conditional items when archive file statistics are 
               implemented."

        GROUP   xmonFeedGroup
        DESCRIPTION   
              "Conditional items to provide live capture feeds to 
               network management systems."

        GROUP   xmonFeedStatsGroup
        DESCRIPTION   
              "Conditional items when live feed statistics are 
               implemented."

        GROUP   xmonPushGroup
        DESCRIPTION   
              "Conditional items to provide live capture feeds to 
               collectors."

        GROUP   xmonProfileGroup
        DESCRIPTION   
              "Conditional items to provide SCTP transport protocol 
               profile support for live feeds."

        GROUP   xmonUploadGroup
        DESCRIPTION   
              "Conditional items when probe-initiated uploads of capture 
               archive files is implemented."

    ::= { xmonCompliances 6 }

END -- end of module OPENSS7-XMON-MIB.

-- vim: ft=mib comments=\f\:\",\b\:\-\-,\:\-\-,\f\b\:- fo+=tcqlornw tw=72 nocin nosi sts=4 sw=4 et
