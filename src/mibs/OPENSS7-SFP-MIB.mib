-- vim: ft=mib comments=\f\:\",\b\:\-\-,\:\-\-,\f\b\:- fo+=tcqlornw tw=72 nocin nosi sts=4 sw=4 et
-- =============================================================================
-- 
-- @(#) src/mibs/OPENSS7-SFP-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-SFP-MIB DEFINITIONS ::= BEGIN

IMPORTS
    openss7G774
        FROM OPENSS7-SMI
    AdministrativeState, AlarmStatus, AvailabilityStatus, 
    OperationalState, ProceduralStatus, StandbyStatus, 
    smiConditionalNotificationsGroup
        FROM OPENSS7-SMI-MIB
    SnmpAdminString
        FROM SNMP-FRAMEWORK-MIB
    MODULE-COMPLIANCE, OBJECT-GROUP
        FROM SNMPv2-CONF
    Integer32, MODULE-IDENTITY, OBJECT-IDENTITY, OBJECT-TYPE, Unsigned32
        FROM SNMPv2-SMI
    DateAndTime, RowPointer, TEXTUAL-CONVENTION
        FROM SNMPv2-TC;

sfpMIB MODULE-IDENTITY
    LAST-UPDATED "201004080744Z"
    ORGANIZATION 
        "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         E-mail: bidulock@openss7.org"
    DESCRIPTION 
        "This is a MIB providing access to the management information 
         associated with SFP Modules.
         
         SFF-8053, Gigabit Interface Converter (GBIC).
         INF-8074i, SFP (Small Formfactor Pluggable) Transceiver.
         SFF-8079, SFP Rate and Application Selection.
         SFF-8089, Rate and Application Codes.
         SFF-8431, Enhanced Small Form Factor Pluggable Module SFP+.
         SFF-8472, Diagnostic Monitoring Interface for Optical 
             Transceivers.
         ITU-T Recommendation G.774, Synchronous Digital Hierarchy 
             (SDH), Management Information Model for the Network Element 
            View, 02/2001.
         ITU-T Recommendation G.774.1, Synchronous Digital Hierarchy 
             (SDH), Bidirectional Performance Monitoring for the Network 
             Element View, 02/2001.
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201004080744Z"
    DESCRIPTION 
        "First release of this module."
    ::= { openss7G774 11 }


SfpAlarms ::= TEXTUAL-CONVENTION
    STATUS      current
    DESCRIPTION 
        "This textual convention provides information as to which 
         warning or alarm thresholds have been crossed by which 
         monitored values.  Monitored values include temperature, supply 
         voltage, transmitter bias current, transmitted power, and 
         received power.  An object that uses this textual convention in 
         its SYNTAX clause is set-valued and may contain zero or more of 
         the following:
         
         - tempHi(0), the temperature has exceeded the high threshold;
         - tempLo(1), the temperature was beneath the low threshold;
         - vccHi(2), the supply voltage has exceeded the high threshold;
         - vccLo(3), the supply voltage was beneath the low threshold;
         - txBiasHi(4), the Tx bias has exceeded the high threshold;
         - txBiasLo(5), the Tx bias was beneath the low threshold;
         - txPowerHi(6), the Tx power has exceeded the high threshold;
         - txPowerLo(7), the Tx power was beneath the low threshold;
         - rxPowerHi(8), the Rx power has exceeded the high threshold; 
         - rxPowerLo(9), the Rx power was beneath the low threshold.
         
         An object with this textual convention in its SYNTAX clause 
         will have a MAX-ACCESS of read-only."
    REFERENCE   
        "SFF-8472 Rev 10.4, Table 16"
    SYNTAX      BITS { tempHi(0), tempLo(1), vccHi(2), vccLo(3), 
                    txBiasHi(4), txBiasLo(5), txPowerHi(6), txPowerLo(7), 
                    rxPowerHi(8), rxPowerLo(9) }

SfpApplication ::= TEXTUAL-CONVENTION
    STATUS      current
    DESCRIPTION 
        "This textual convention provides a specification of the 
         application for an SFP/SFP+ transceiver module.  The list is 
         too long to describe here, see SFF-8089 Rev 1.3 Table 4-1 for a 
         complete listing of these values and their meanings."
    REFERENCE   
        "SFF-8089 Rev 1.3, Table 4-1"
    SYNTAX      INTEGER { fc100MxSNI(256), fc100SMLCL(257), 
                    fc100SMLLV(258), fc100SEELS(259), fc100DFELS(260), 
                    fc200MxSNI(266), fc200SMLCL(267), fc200SMLLV(268), 
                    fc200SEELS(269), fc200DFELS(270), fc400MxSNS(276), 
                    fc400SMLCL(277), fc400DFELS(278), fc400SEELS(279), 
                    fcMMF625(280), fcMMF50(281), fc800MxSNI(306), 
                    fc800SMLLL(307), fc1200MxSNI(346), fc1200SMLLL(347), 
                    fc1200SMLCL(348), e100baseFX(512), e100baseLX10(513), 
                    e100baseBX10(514), e1000baseSX(517), 
                    e1000baseLX(518), e1000baseBX10(519), 
                    e1000baseLX10(520), e1000basePX10(521), 
                    e1000baseLX20(522), e1000baseCX(523), 
                    e1000baseT(524), e10GbaseSW(532), e10GbaseLW(533), 
                    e10GbaseLR(534), e10GbaseEW(535), e10GbaseER(536), 
                    e10GbaseT(537), oc3I1(768), oc3S11(769), oc3S12(770), 
                    oc3L11(771), oc3L12(772), oc3L13(773), oc3SR1(774), 
                    oc3IR1(775), oc3IR2(776), oc3LR1(777), oc3LR2(778), 
                    oc3LR3(779), oc12I4(798), oc12S41(799), oc12S42(800), 
                    oc12L41(801), oc12L42(802), oc12L43(803), 
                    oc12V41(804), oc12V42(805), oc12V43(806), 
                    oc12U42(807), oc12U43(808), oc12SR1(809), 
                    oc12IR1(810), oc12IR2(811), oc12LR1(812), 
                    oc12LR2(813), oc12LR3(814), oc48I16(815), 
                    oc48S161(816), oc48S162(817), oc48L161(818), 
                    oc48L162(819), oc48L163(820), oc48V162(821), 
                    oc48V163(822), oc48U162(823), oc48U163(824), 
                    oc48SR1(825), oc48IR1(826), oc48IR2(827), 
                    oc48LR1(828), oc48LR2(829), oc48LR3(830), 
                    oc192VSR6002M1(858), oc192VSR6002M2(859), 
                    oc192VSR6002M5(860), oc192I641r(861), oc192I641(862), 
                    oc192I642r(863), oc192I642(864), oc192I643(865), 
                    oc192I645(866), oc192S641(867), oc192S642a(868), 
                    oc192S642b(869), oc192S643a(870), oc192S643b(871), 
                    oc192S645a(872), oc192S645b(873), oc192L641(874), 
                    oc192L642a(875), oc192L642b(876), oc192L642c(877), 
                    oc192L643(878), oc192V642a(879), oc192V642b(880), 
                    oc192V643(881), oc192SR1(882), oc192SR2(883), 
                    oc192IR1(884), oc192IR2(885), oc192IR3(886), 
                    oc192LR1(887), oc192LR2a(888), oc192LR2b(889), 
                    oc192LR2c(890), oc192LR3(891), oc192VR1(892), 
                    oc192VR2a(893), oc192VR3(894), ib1xSX(1024), 
                    ib1xLX(1025), ib1xCA(1026), ib1xCP(1027), 
                    sbconMMF(1280), sbconSMF(1281), cu100d05(1536), 
                    cu100d1(1537), cu100d15(1538), cu100d2(1539), 
                    cu100d25(1540), cu100d3(1541), cu100d35(1542), 
                    cu100d4(1543), cu100d45(1544), cu100d5(1545), 
                    cu100d55(1546), cu100d6(1547), cu100d65(1548), 
                    cu100d7(1549), cu100d75(1550), cu200d0(1556), 
                    cu200d075(1557), cu200d15(1558), cu200d225(1559), 
                    cu200d3(1560), cu200d375(1561), cu200d45(1562), 
                    cu200d525(1563), cu200d6(1564), cu200d675(1565), 
                    cu200d75(1566), cu200d825(1567), cu200d9(1568), 
                    cu200d975(1569), cu200d105(1570), cu200d1125(1571), 
                    cu400d1(1577), cu400d2(1578), cu400d3(1579), 
                    cu400d4(1580), cu400d5(1581), cu400d6(1582), 
                    cu400d7(1583), cu400d8(1584), cu400d9(1585), 
                    cu400d10(1586), cu400d11(1587), cu400d12(1588), 
                    cu400d13(1589), cu400d14(1590), cu400d15(1591) }

SfpMonitor ::= TEXTUAL-CONVENTION
    STATUS      current
    DESCRIPTION 
        "This textual convention provides information as to the 
         monitored value of the settings of various pins on the SFP 
         module.  An object that uses this textual convention in its 
         SYNTAX clause is single-valued and may contain one of the 
         following:
         
         - unknown(0), the setting of the pin is unknown because the 
           module corresponding to this object does not implement the 
           feature;
         
         - asserted(1), the pin is asserted (regardless of whether the 
           pin is active high or active low); or,
         
         - deasserted(2), the pin is deasserted (again, regardless of 
           whether the pin is active high or active low).
         
         An object with this textual convention in its SYNTAX clause 
         will have a MAX-ACCESS of read-only."
    REFERENCE   
        "SFF-8472 Rev 10.4, Table 3.17"
    SYNTAX      INTEGER { unknown(0), asserted(1), deasserted(2) }

sfpNotifications OBJECT IDENTIFIER
    ::= { sfpMIB 0 }

sfpObjects OBJECT IDENTIFIER
    ::= { sfpMIB 1 }

sfpTables OBJECT IDENTIFIER
    ::= { sfpObjects 1 }

sfpModule OBJECT IDENTIFIER
    ::= { sfpTables 1 }

sfpModuleTable OBJECT-TYPE
    SYNTAX      SEQUENCE OF SfpModuleEntry
    MAX-ACCESS  not-accessible
    STATUS      current
    DESCRIPTION 
        "This table provides access to the information associated with 
         each SFP module as specified in INF-8074."
    REFERENCE   
        "INF-8074"
    ::= { sfpModule 1 }

sfpModuleEntry OBJECT-TYPE
    SYNTAX      SfpModuleEntry
    MAX-ACCESS  not-accessible
    STATUS      current
    DESCRIPTION 
        "Each conceptual row in this table corresponds to an SFP 
         module in the system.  Conceptual rows may neither be added nor 
         removed from this table my management stations but are 
         autonomously added or removed by the managed system from within."
    INDEX       { sfpModuleId }
    ::= { sfpModuleTable 1 }

SfpModuleEntry ::= SEQUENCE {
    sfpModuleId                         Unsigned32,
    sfpModuleType                       INTEGER,
    sfpModuleExtendedType               INTEGER,
    sfpModuleConnectorType              INTEGER,
    sfpModuleTransceiver                BITS,
    sfpModuleCompliance                 INTEGER,
    sfpModuleEncoding                   INTEGER,
    sfpModuleNormalBitRate              Unsigned32,
    sfpModuleRateIdentifier             INTEGER,
    sfpModuleLinkLength9125k            Integer32,
    sfpModuleLinkLength9125m            Integer32,
    sfpModuleLinkLength50125m           Integer32,
    sfpModuleLinkLength625125m          Integer32,
    sfpModuleLinkLengthCopper           Unsigned32,
    sfpModuleVendorName                 SnmpAdminString,
    sfpModuleVendorOUI                  OCTET STRING,
    sfpModulePartNumber                 SnmpAdminString,
    sfpModuleRevisionLevel              SnmpAdminString,
    sfpModuleLaserWavelength            Unsigned32,
    sfpModulePassiveCableCompliance     BITS,
    sfpModuleActiveCableCompliance      BITS,
    sfpModuleOptions                    BITS,
    sfpModuleUpperBitRate               Unsigned32,
    sfpModuleLowerBitRate               Unsigned32,
    sfpModuleVendorSerialNo             SnmpAdminString,
    sfpModuleManufactureDate            DateAndTime
}

sfpModuleId OBJECT-TYPE
    SYNTAX      Unsigned32
    MAX-ACCESS  not-accessible
    STATUS      current
    DESCRIPTION 
        "Provides a non-zero, ordinal index that identifies the specific 
         SFP/SFP+ module."
    ::= { sfpModuleEntry 1 }

sfpModuleType OBJECT-TYPE
    SYNTAX      INTEGER { unknown(0), gbic(1), fixed(2), sfp(3) }
    MAX-ACCESS  read-only
    STATUS      current
    DESCRIPTION 
        "Indicates the type of SFP/SFP+ module.  This column can adopt 
         one of the following values:
         
         - unknown(0), the type of the module is unknown, unspecified or 
           vendor specific;
         - gbic(1), the module is a GBIC module;
         - fixed(2), the module is soldered to the motherboard; or,
         - sfp(3), the module is an SFP transceiver.
           
         Modules providing this MIB are typically sfp(3) modules."
    REFERENCE   
        "SFF-8472, Diagnostic Monitoring Interface for Optical 
             Transceivers."
    ::= { sfpModuleEntry 2 }

sfpModuleExtendedType OBJECT-TYPE
    SYNTAX      INTEGER { serialId(4) }
    MAX-ACCESS  read-only
    STATUS      current
    DESCRIPTION 
        "
         - serialId(4), the module definition is a serial ID module 
           definition."
    REFERENCE   
        "SFF-8472, Diagnostic Monitoring Interface for Optical 
             Transceivers."
    ::= { sfpModuleEntry 3 }

sfpModuleConnectorType OBJECT-TYPE
    SYNTAX      INTEGER { unknown(0), sc(1), fc1(2), fc2(3), bnc(4), 
                    fc(5), fj(6), lc(7), mtrj(8), mu(9), sg(10), op(11), 
                    hssdc2(32), cp(33), rj45(34), other(128) }
    MAX-ACCESS  read-only
    STATUS      current
    DESCRIPTION 
        "Indicates the connector type associated with the SFP/SFP+ 
         module.  THis column can adopt one of the following values:
         
         - unknown(0), unknown or unspecified;
         - sc(1), SC connector;
         - fc1(2), Fibre Channel Style 1 copper connector;
         - fc2(3), Fibre Channel Style 2 copper connector;
         - bnc(4), BNC/TNC;
         - fc(5), Fiber Channel coaxial headers;
         - fj(6), FiberJack;
         - lc(7), LC;
         - mtrj(8), MT-RJ;
         - mu(9), MU;
         - sg(10), SG;
         - op(11), optical pigtail;
         - hssdc2(32), HSSDC II;
         - cp(33), copper pigtail;
         - rj45(34), RJ45; or,
         - other(128), vendor specific.
           
         Modules providing this MIB typically support sc(1), lc(7), 
         mtrj(8), op(110, or rj45(34) connectors."
    REFERENCE   
        "SFF-8472, Diagnostic Monitoring Interface for Optical 
             Transceivers."
    ::= { sfpModuleEntry 4 }

sfpModuleTransceiver OBJECT-TYPE
    SYNTAX      BITS { ibCP(0), ibCA(1), ibLX(2), ibSX(3), e10GbaseSR(4), 
                    e10GbaseLR(5), e10GbaseLRM(6), e10GbaseER(7), 
                    oc48sr(8), oc48ir(9), oc48lr(10), oc192sr(13), 
                    oc3sr(16), oc3ir(17), oc3lr(18), oc12sr(20), 
                    oc12ir(21), oc12lr(22), e1000baseSX(24), 
                    e1000baseLX(25), e1000baseCX(26), e1000baseT(27), 
                    e100baseLX(28), e100baseFX(29), ebaseBX(30), 
                    ebasePX(31), fcInterEL(32), fcLC(33), fcSA(34), 
                    fcM(35), fcL(36), fcI(37), fcS(38), fcV(39), 
                    sfpPC(42), sfpAC(43), fcLL(44), fcSL(45), fcSN(46), 
                    fcIntraEL(47), sM(48), m5(50), m6(51), tV(52), 
                    mI(53), tP(54), tW(55) }
                    -- fcSDR(48), fcDDR(50), fcQDR(52), fc1600(53), fc800(54), fc1200(55)
    MAX-ACCESS  read-only
    STATUS      current
    DESCRIPTION 
        "
         - oc48sr(0), OC-48 short reach;
         - oc48ir(1), OC-48 intermediate reach;
         - oc48lr(2), OC-48 long reach;
         - oc12sr(4), OC-12 short reach;
         - oc12ir(5), OC-12 intermediate reach;
         - oc12lr(6), OC-12 long reach;
         - oc3sr(8), OC-3 short reach;
         - oc3ir(9), OC-3 intermediate reach;
         - oc3lr(10), OC-3 long reach;
         - e1000baseSX(16), 1000BASE-SX support;
         - e1000baseLX(17), 1000BASE-LX support;
         - e1000baseCX(18), 1000BASE-CX support;
         - e1000baseT(19),  1000BASE-T support;
         - fcL(28), Fibre Channel long distance (L);
         - fcI(29), Fibre Channel intermediate distance (I);
         - fcS(30), Fibre Channel short distance (S);
         - fcV(31), Fibre Channel very long distance (V);
         - fcLL(36), Fibre Channel longwave laser (LL);
         - fcSL(37), Fibre Channel shortwave laser w/ OFC (SL);
         - fcSN(38), Fibre Channel shortwave laser w/o OFC (SN);
         - fcIntraEL(39), Fibre Channel electrical intra enclosure (EL);
         - fcInterEL(24), Fibre Channel electrical inter enclosure (EL);
         - fcLC(25), longwave laser (LC);
         - sM(40), single mode (SM);
         - m5(42), multi-mode 50um (M5);
         - m6(43), multi-mode 62.5um (M6);
         - tV(44), video coax (TV);
         - mI(45), miniature coax (MI);
         - tP(46), sheilded twisted pair (TP);
         - tW(47), twin axial pair (TW);
         - fcSDR(48), 100 MBytes/sec;
         - fcDDR(50), 200 MBytes/sec;
         - fcQDR(52), 400 MBytes/sec;
         - fc1600(53), 1600 MBytes/sec;
         - fc800(54), 800 MBytes/sec;
         - fc1200(55), 1200 MByes/sec.
           "
    REFERENCE   
        "ITU-T Rec. G.774 (02/2001) : characteristicInfo ATTRIBUTE."
    ::= { sfpModuleEntry 5 }

sfpModuleCompliance OBJECT-TYPE
    SYNTAX      INTEGER { var0(0), var1(1), var2(2), var3(3) }
    MAX-ACCESS  read-only
    STATUS      current
    DESCRIPTION 
        "
         - var(0),
         - var(1),
         - var(2),
         - var(3),"
    REFERENCE   
        "SFF-8472, Diagnostic Monitoring Interface for Optical 
             Transceivers."
    ::= { sfpModuleEntry 6 }

sfpModuleEncoding OBJECT-TYPE
    SYNTAX      INTEGER { unspecified(0), enc8B10B(1), enc4B5B(2), 
                    encNRZ(3), encManchester(4), encSONET(5), 
                    enc64B66B(6) }
    MAX-ACCESS  read-only
    STATUS      current
    DESCRIPTION 
        "Indicates the line encoding used.  It may be one of the 
         following:
         
         - unspecified(0), unspecified;
         - enc8B10B(1), 8B/10B;
         - enc4B5B(2), 4B/5B;
         - encNRZ(3), NRZ;
         - encManchester(4), Manchester;
         - encSONET(5), SONET Scrambled; or,
         - enc64B66B(6), 64B/65B.
         
         For SONET/SDH SFP/SFP+ optical transceivers, this value should 
         typically be encSONET(5) for SONET/SDH scrambled data.
         
         Note that older SONET/SDH INF-8074i modules not supporting 
         SFF-8472 might report a module encoding of unspecified(0) 
         because the codepoint for encSONET(5) was not yet defined in 
         INF-8074i."
    REFERENCE   
        "ITU-T Rec. G.774 (02/2001) : characteristicInfo ATTRIBUTE."
    ::= { sfpModuleEntry 7 }

sfpModuleNormalBitRate OBJECT-TYPE
    SYNTAX      Unsigned32
    UNITS       "Mbps"
    MAX-ACCESS  read-only
    STATUS      current
    DESCRIPTION 
        "The normal bit rate specified in units of Megabits per second, 
         rounded off to the nearest 100 Megabits per second.  The bit 
         rate includes those bits necessary to encode and delimit the 
         signal as well as those bits carrying data information.  A 
         valud of zero (0) indicates that the bit rate is not specified 
         and must be determined from the transceiver technology 
         (sfpModuleTransceiver).  The actual information transfer rate 
         will depend on the encoding of the data, as defined by the 
         encoding value."
    REFERENCE   
        "ITU-T Rec. G.774 (02/2001) : characteristicInfo ATTRIBUTE."
    ::= { sfpModuleEntry 8 }

sfpModuleRateIdentifier OBJECT-TYPE
    SYNTAX      INTEGER { unspec(0), sff8079(1), sff8431rx(2), 
                    sff8431tx(4), sff8431rxtx(6) }
    MAX-ACCESS  read-only
    STATUS      current
    DESCRIPTION 
        "Indicates the way that the SFP/SFP+ optical transceiver module 
         performs rate selection:
         
         - unspec(0), unspecified, or SFF-8079 (Rate_Select only);
         - sff8079(1), SFF-8079 (4/2/1G Rate_Select & AS0/AS1);
         - sff8431rx(2), SFF-8431 (8/4/2G Rx Rate_Select only);
         - sff8431tx(4), SFF-8431 (8/4/2G Tx Rate_Select only);
         - sff8431rxtx(6), SFF-8431 (8/4/2G Independent Rx & Tx 
           Rate_Select);"
    REFERENCE   
        "SFF-8079 Rev 1.7, SFP Rate and Application Selection
         SFF-8431 Rev 4.1, Enhanced 10 Gbps Pluggable Module (SFP+)
         SFF-8472 Rev 10.4, Table 3.6a"
    ::= { sfpModuleEntry 9 }

sfpModuleLinkLength9125k OBJECT-TYPE
    SYNTAX      Integer32 (0..255)
    UNITS       "kilometers"
    MAX-ACCESS  read-only
    STATUS      current
    DESCRIPTION 
        "This value specifies the link length that is supported by the 
         SFP transceiver while operating in compliance with the 
         applicable standards using single mode fiber (9/125).  The 
         value is in units of kilometers.  A value of 255 means that the 
         transceiver supports a link length greater than 254 kilometers.  
         A value of zero means that the transceiver does not support 
         single mode fiber or that the length information must be 
         determined from the transceiver technology 
         (sfpModuleTransceiver)."
    REFERENCE   
        "SFF-8472 Rev 10.4.
         ITU-T Rec. G.774 (02/2001) : opticalReach ATTRIBUTE."
    ::= { sfpModuleEntry 10 }

sfpModuleLinkLength9125m OBJECT-TYPE
    SYNTAX      Integer32 (0..255)
    UNITS       "100 meters"
    MAX-ACCESS  read-only
    STATUS      current
    DESCRIPTION 
        "This value sepcifies the link length that is supported by the 
         SFP transceiver while operating in compliance with the 
         applicable standards using single mode fibre (9/125).  The 
         value is in units of 100 meters.  A value of 255 means that the 
         SFP transceiver supports a link length greather than 25.4 km.  
         A value of zero means that the SFP transceiver does not support 
         single mode fiber or that the length information must be 
         determined from the transceiver technology 
         (sfpModuleTransceiver)."
    REFERENCE   
        "SFF-8472 Rev 10.4.
         ITU-T Rec. G.774 (02/2001) : opticalReach ATTRIBUTE."
    ::= { sfpModuleEntry 11 }

sfpModuleLinkLength50125m OBJECT-TYPE
    SYNTAX      Integer32 (0..255)
    UNITS       "10 meters"
    MAX-ACCESS  read-only
    STATUS      current
    DESCRIPTION 
        "This value specifies the link length that is supported by the 
         SFP transceiver while operating in compliance with the 
         applicable standards using 50 micron multi-mode fiber (50/125).  
         The value is in units of 10 meters.  A value of 255 means that 
         the SFP transceiver supports a link length greater than 2.54 
         km.  A value of zero (0) means that the transceiver does not 
         support 50 micron multi-mode fiber or that the length 
         information must be determined from the transceiver technology 
         (sfpModuleTransceiver)."
    REFERENCE   
        "SFF-8472 Rev 10.4.
         ITU-T Rec. G.774 (02/2001) : opticalReach ATTRIBUTE."
    ::= { sfpModuleEntry 12 }

sfpModuleLinkLength625125m OBJECT-TYPE
    SYNTAX      Integer32 (0..255)
    UNITS       "10 meters"
    MAX-ACCESS  read-only
    STATUS      current
    DESCRIPTION 
        "This value specifies the link length that is supported by the 
         SFP transceiver while operating in compliance with the 
         applicable standards using 62.5 micron multi-mode fiber 
         (62.5/125).  The value is in units of 10 meters.  A value of 
         255 means that the SFP transceiver supports a link length 
         greater than 2.54 km.  A value of zero (0) means that the 
         transceiver does not support 62.5 micron multi-mode fiber or 
         that the length information must be determined from the 
         transceiver technology (sfpModuleTransceiver)."
    REFERENCE   
        "SFF-8472 Rev 10.4.
         ITU-T Rec. G.774 (02/2001) : opticalReach ATTRIBUTE."
    ::= { sfpModuleEntry 13 }

sfpModuleLinkLengthCopper OBJECT-TYPE
    SYNTAX      Unsigned32
    UNITS       "meters"
    MAX-ACCESS  read-only
    STATUS      current
    DESCRIPTION 
        "This value specifies the minimum link length that is supported 
         by the SFP transceiver while operating in compliance with the 
         applicable standards using copper cable.  The value is in units 
         of 1 meter.  A value of 255 means that the SFP transceiver 
         supports a link length greater than 254 meters.  A value of 
         zero means that the SFP transceiver does not support copper 
         cables or that the length information must be determined from 
         the transceiver technology (sfpModuleTransceiver).  Further 
         information about the cable design, equalization, an connectors 
         is usually required to guarantee meeting a particular length 
         requirement."
    REFERENCE   
        "SFF-8472 Rev 10.4.
         ITU-T Rec. G.774 (02/2001) : opticalReach ATTRIBUTE."
    ::= { sfpModuleEntry 14 }

sfpModuleVendorName OBJECT-TYPE
    SYNTAX      SnmpAdminString
    MAX-ACCESS  read-only
    STATUS      current
    DESCRIPTION 
        "The vendor name is the full name of the corporation, a commonly 
         accepted abbreviation of the name of the corporation, the SCSI 
         company code for the corporation, or the stock exchange code 
         for the corporation.  At least one of the vendor name or the 
         vendor OUI fields shall contain valid serial data."
    REFERENCE   
        "SFF-8472 Rev 10.4."
    ::= { sfpModuleEntry 15 }

sfpModuleVendorOUI OBJECT-TYPE
    SYNTAX      OCTET STRING (SIZE(3))
    MAX-ACCESS  read-only
    STATUS      current
    DESCRIPTION 
        "The vendor organizationally unique identifier field (vendor 
         OUI) is a 3-byte field that contains the IEEE Company 
         Identifier for the vendor.  A value of all zeros in the 3-byte 
         field indicates that the Vendor OUI is unspecified."
    REFERENCE   
        "SFF-8472 Rev 10.4."
    ::= { sfpModuleEntry 16 }

sfpModulePartNumber OBJECT-TYPE
    SYNTAX      SnmpAdminString
    MAX-ACCESS  read-only
    STATUS      current
    DESCRIPTION 
        "The vendor part number is a 16 character string defining the 
         vendor part number or product name."
    REFERENCE   
        "SFF-8472 Rev 10.4."
    ::= { sfpModuleEntry 17 }

sfpModuleRevisionLevel OBJECT-TYPE
    SYNTAX      SnmpAdminString
    MAX-ACCESS  read-only
    STATUS      current
    DESCRIPTION 
        "The vendor revision number is a 4 character string defining the 
         vendor's product revision number."
    REFERENCE   
        "SFF-8472 Rev 10.4."
    ::= { sfpModuleEntry 18 }

sfpModuleLaserWavelength OBJECT-TYPE
    SYNTAX      Unsigned32
    UNITS       "nanometers"
    MAX-ACCESS  read-only
    STATUS      current
    DESCRIPTION 
        "Specifies the wavelength of the laser in nanometers.  When zero 
         (0), the wavelength of the laser is not specified and must be 
         inferred from the transceiver technology 
         (sfpModuleTransceiver)."
    REFERENCE   
        "SFF-8472 Rev 10.4.
         ITU-T Rec. G.774 (02/2001) : opticalWavelength ATTRIBUTE."
    ::= { sfpModuleEntry 19 }

sfpModulePassiveCableCompliance OBJECT-TYPE
    SYNTAX      BITS { sff8431appE(0), fCPI4appH(1) }
    MAX-ACCESS  read-only
    STATUS      current
    DESCRIPTION 
        "
         - sff8431appE(0), compliant to SFF-8431 Appendix E; and,
         - fCPI4appH(1), compliant to FC-PI-4 Appendix H."
    REFERENCE   
        "SFF-8431, Enhanced Small Form Factor Pluggable Module SFP+,
            Appendix E;
         FC-PI-4 Appendix H."
    ::= { sfpModuleEntry 20 }

sfpModuleActiveCableCompliance OBJECT-TYPE
    SYNTAX      BITS { sff8431appE(0), fCPI4appH(1), sff8431lim(2), 
                    fCPI4lim(3) }
    MAX-ACCESS  read-only
    STATUS      current
    DESCRIPTION 
        "
         - sff8431appE(0), compliant to SFF-8431 Appendix E;
         - fCPI4appH(1), compliant to FC-PI-4 Appendix H;
         - sff8431lim(2), compliant to SFF-8431 Limiting; and,
         - fCPI4lim(3), compliant to FC-PI-4 Limiting."
    REFERENCE   
        "SFF-8431, Enhanced Small Form Factor Pluggable Module SFP+,
            Appendix E;
         FC-PI-4 Appendix H."
    ::= { sfpModuleEntry 21 }

sfpModuleOptions OBJECT-TYPE
    SYNTAX      BITS { undefined(0), lossOfSignal(1), 
                    lossOfSignalInverted(2), txFault(3), txDisable(4), 
                    rateSelect(5), lro(8), pld(9), ctd(10) }
    MAX-ACCESS  read-only
    STATUS      current
    DESCRIPTION 
        "
         - lossOfSignal(1), Loss of Signal is implemented;
         - lossOfSignalInverted(2), Loss of Signal is implemented, but 
           the signal is inverted from that of the SFP definition;
         - txFault(3), the TX_FAULT signal is implemented;
         - txDisable(4), TX_DISABLE is implemented and disables the 
           serial output; and,
         - rateSelect(5), RATE_SELECT is implemented (and required).
         - lro(8), Linear Receiver Output Implemented (see SFF-8431); 
           not present indentifies a conventional limiting (or 
           unspecified) receiver output; present indentifies a linear 
           receiver output;
         - pld(9), Power Level Declaration (see SFF-8431); not present 
           identifies Power Level 1 (or unspecified) requirements; 
           present identifies Power Level 2 requirement;
         - ctd(10), Cooled Transceiver Declaration (see SFF-8431); not 
           present identifies a conventional uncooled (or unspecified) 
           laser implementation; present identifies a cooled laser 
           transmitter implementation."
    REFERENCE   
        "INF-8074i, SFP (Small Formfactor Pluggable) Transceiver;
         SFF-8431, Enhanced Small Form Factor Pluggable Module SFP+;
         SFF-8472, Diagnostic Monitoring Interface for Optical 
             Transceivers."
    ::= { sfpModuleEntry 22 }

sfpModuleUpperBitRate OBJECT-TYPE
    SYNTAX      Unsigned32
    UNITS       "%"
    MAX-ACCESS  read-only
    STATUS      current
    DESCRIPTION 
        "The upper bit rate limit at which the SFP transceiver will 
         still meet its specificaitons specified in units of percent 
         above the normal bit rate.  A value of zero indicates that this 
         field is not specified."
    REFERENCE   
        "SFF-8472, Diagnostic Monitoring Interface for Optical 
             Transceivers."
    ::= { sfpModuleEntry 23 }

sfpModuleLowerBitRate OBJECT-TYPE
    SYNTAX      Unsigned32
    UNITS       "%"
    MAX-ACCESS  read-only
    STATUS      current
    DESCRIPTION 
        "The lower bit rate limit at which the SFP transceiver will 
         still meet its specifications specified in units of percent 
         below the normal bit rate.  A value of zero inidcates that this 
         field is not specified."
    REFERENCE   
        "INF-8074i, SFP (Small Formfactor Pluggable) Transceiver;
         SFF-8431, Enhanced Small Form Factor Pluggable Module SFP+;
         SFF-8472, Diagnostic Monitoring Interface for Optical 
             Transceivers."
    ::= { sfpModuleEntry 24 }

sfpModuleVendorSerialNo OBJECT-TYPE
    SYNTAX      SnmpAdminString
    MAX-ACCESS  read-only
    STATUS      current
    DESCRIPTION 
        "The vendor serial number as a 16 character string defining the 
         vendor's serial number for the SFP transceiver."
    REFERENCE   
        "INF-8074i, SFP (Small Formfactor Pluggable) Transceiver;
         SFF-8431, Enhanced Small Form Factor Pluggable Module SFP+;
         SFF-8472, Diagnostic Monitoring Interface for Optical 
             Transceivers."
    ::= { sfpModuleEntry 25 }

sfpModuleManufactureDate OBJECT-TYPE
    SYNTAX      DateAndTime
    MAX-ACCESS  read-only
    STATUS      current
    DESCRIPTION 
        "The date on which the SFP module was manufactured."
    REFERENCE   
        "INF-8074i, SFP (Small Formfactor Pluggable) Transceiver;
         SFF-8431, Enhanced Small Form Factor Pluggable Module SFP+;
         SFF-8472, Diagnostic Monitoring Interface for Optical 
             Transceivers."
    ::= { sfpModuleEntry 26 }

sfpAppl OBJECT IDENTIFIER
    ::= { sfpTables 2 }

sfpApplTable OBJECT-TYPE
    SYNTAX      SEQUENCE OF SfpApplEntry
    MAX-ACCESS  not-accessible
    STATUS      current
    DESCRIPTION 
        "This table provides information about the application selected 
         for each SFP/SFP+ transceiver when the SFP/SFP+ transceiver 
         supports the SFF rate and application mechanism specified in 
         SFF-8079 Rev. 1.7.  When a given SFP/SFP+ module supports 
         SFF-8079, an entry will appear in this table and corresponding 
         entries will appear in the sfpApplCodeTable; otherwise, there 
         will be no entry for the SFP/SFP+ module in this table, nor the 
         sfpApplCodeTable.
         
         Rate and application selection for SFP/SFP+ modules is complex 
         and there are a number of standards that have evolved, not all 
         compatible with each other.  An SFP/SFP+ module that requires  
         application selection but which has been configured for the 
         wrong application may exhibit suboptimal performance.  The 
         purpose of this table and the subtending sfpApplCodeTable is 
         to provide for diagnosis of misassigned application selections."
    REFERENCE   
        "SFF-8079 Rev 1.7"
    ::= { sfpAppl 1 }

sfpApplEntry OBJECT-TYPE
    SYNTAX      SfpApplEntry
    MAX-ACCESS  not-accessible
    STATUS      current
    DESCRIPTION 
        "Each entry in this table corresponds to an SFP/SFP+ module from 
         the sfpModuleTable with the same sfpModuleId index.  Each entry 
         that exists in this table is for an SFP/SFP+ module that 
         supports the rate and application selection methods of 
         SFF-8079.  For each entry in this table, there is also one or 
         more entries in the associated side-table, sfpApplCodeTable, 
         corresponding to the Application Selection Table of the 
         SFP/SFP+ module.  The Application Selection Table provides all 
         of the supported application codes."
    REFERENCE   
        "SFF-8079 Rev 1.7"
    INDEX       { sfpModuleId }
    ::= { sfpApplTable 1 }

SfpApplEntry ::= SEQUENCE {
    sfpApplControlMode  INTEGER,
    sfpApplTableLength  Integer32,
    sfpApplTableSelect  Integer32,
    sfpApplSelectValue  SfpApplication
}

sfpApplControlMode OBJECT-TYPE
    SYNTAX      INTEGER { emulation(0), hardware(1), software(2) }
    MAX-ACCESS  read-only
    STATUS      current
    DESCRIPTION 
        "Indicates the application select control mode.  This can be one 
         of the following values:
         
         - emulation(0), RateSelect or Extended RateSelect emulation 
           mode: In emulation mode, Rate_Select (pin 7) and A2h byte 
           110{3} control rate selection.  The AS(1) pin and table 
           select field are ignored.
         
         - hardware(1), HW Application Select mode: In hardware mode, 
           AS(0) and AS(1) pins select the application and both software 
           rate select and table select are ignored.
         
         - software(2), SW Application Select mode: In software mode, 
           all bits and fields are ignore except the table select field.
         
         See SFF-8079 for more information.  The interactions of rate 
         select, extended rate select, and application select, are 
         complex.  The primary purpose of this object is to provide an 
         indication of the supported and programmed modes on the 
         SFP/SFP+ module to aid software fault resolution.
         
         MSA compliant SFP/SFP+ modules should boot in emulation(0) 
         mode and only alter modes when subsequently programmed by the 
         host application."
    REFERENCE   
        "SFF-8079 Rev 1.7, Section 5.3.2.1 and Table 12."
    ::= { sfpApplEntry 1 }

sfpApplTableLength OBJECT-TYPE
    SYNTAX      Integer32 (1..63)
    MAX-ACCESS  read-only
    STATUS      current
    DESCRIPTION 
        "Indicates the length of the Application Select Table (the 
         maximum index for this SFP/SFP+ module in the sfpApplCodeTable 
         side-table).  When an entry exists in this table, at least one 
         (and no more than 63) entries exist for the corresponding 
         sfpModuleId in the sfpApplCodeTable side-table."
    REFERENCE   
        "SFF-8079 Rev 1.7 Section 5.2.1 and Table 6."
    ::= { sfpApplEntry 2 }

sfpApplTableSelect OBJECT-TYPE
    SYNTAX      Integer32 (0..63)
    MAX-ACCESS  read-write
    STATUS      current
    DESCRIPTION 
        "Specifies the index in the sfpApplCodeTable of the entry that 
         is currently specified for the SFP/SFP+ transceiver.  When 
         specified as zero (0), there is no valid value in the field.
         
         Note that SFF-8079 gives the range of the TS field as 0..63 
         where 63 is invalid, but this field is effectively TS+1, where 
         the value zero (0) is invalid."
    REFERENCE   
        "SFF-8079 Rev 1.7 Section 5.3.1 and Table 11."
    ::= { sfpApplEntry 3 }

sfpApplSelectValue OBJECT-TYPE
    SYNTAX      SfpApplication
    MAX-ACCESS  read-only
    STATUS      current
    DESCRIPTION 
        "Specifies the application code of the application which is 
         currently selected from the table, regardless of the setting of 
         control mode and the various other bits and hardware lines.  
         That is, this is the application that is currently in effect 
         for the SFP/SFP+ transceiver."
    REFERENCE   
        "SFF-8079 Rev 1.7 Section 5.3.1 and Table 11."
    ::= { sfpApplEntry 4 }

sfpApplCode OBJECT IDENTIFIER
    ::= { sfpTables 3 }

sfpApplCodeTable OBJECT-TYPE
    SYNTAX      SEQUENCE OF SfpApplCodeEntry
    MAX-ACCESS  not-accessible
    STATUS      current
    DESCRIPTION 
        "This table provides the ApplicationSelect Table (AST) for each 
         of the SFP/SFP+ modules that support the SFF-8079 rate and 
         application selection methods.  Each entry corresponds to one 
         of the entries in the AST for each of the SFP/SFP+ modules 
         supporting SFF-8079."
    REFERENCE   
        "SFF-8079 Rev 1.7, Section 5.2.1 and Table 6."
    ::= { sfpApplCode 1 }

sfpApplCodeEntry OBJECT-TYPE
    SYNTAX      SfpApplCodeEntry
    MAX-ACCESS  not-accessible
    STATUS      current
    DESCRIPTION 
        "Each entry in this table corresponds to a single supported 
         application selection for a given SFP/SFP+ module supporting 
         the SFF-8079 rate and application selection procedures.  The 
         sfpApplCodeIndex (1..63) identifies from one to 63 application 
         codes supported by the SFP/SFP+ module given by sfpModuleId."
    REFERENCE   
        "SFF-8079 Rev 1.7, Section 5.2.1 and Table 6."
    INDEX       { sfpModuleId, sfpApplCodeIndex }
    ::= { sfpApplCodeTable 1 }

SfpApplCodeEntry ::= SEQUENCE {
    sfpApplCodeIndex        Unsigned32,
    sfpApplCodeSelect       INTEGER,
    sfpApplCodeCategory     INTEGER,
    sfpApplCodeValue        SfpApplication
}

sfpApplCodeIndex OBJECT-TYPE
    SYNTAX      Unsigned32 (1..63)
    MAX-ACCESS  not-accessible
    STATUS      current
    DESCRIPTION 
        "Provides an ordinal index for this specific application code.  
         There can be between 1 and 63 application codes assigned to a 
         given SFP/SFP+ module (as specified by sfpModuleId).  When a 
         given entry `n' exists (`n' > 1), all indices from 1 to `n-1' 
         also exist.  For each entry in the sfpApplTable, at least one 
         entry will also exist in this table for the sfpModuleId.  The 
         highest index for a given sfpModuleId in this table is given by 
         the sfpApplTableLength field in the sfpApplTable."
    REFERENCE   
        "SFF-8079 Rev 1.7, Section 5.2.1 and Table 6."
    ::= { sfpApplCodeEntry 1 }

sfpApplCodeSelect OBJECT-TYPE
    SYNTAX      INTEGER { noSelect(0), code00(4), code01(5), code10(6), 
                    code11(7) }
    MAX-ACCESS  read-only
    STATUS      current
    DESCRIPTION 
        "
         - noSelect(0),
         - code00(4),
         - code01(5),
         - code10(6),
         - code11(7)"
    REFERENCE   
        "SFF-8079 Rev 1.7, Section 5.2.1 and Table 6."
    ::= { sfpApplCodeEntry 2 }

sfpApplCodeCategory OBJECT-TYPE
    SYNTAX      INTEGER { unspecified(0), fibreChannel(1), ethernet(2), 
                    sonet(3), infiniband(4), sbcon(5), copper(6), 
                    other(7) }
    MAX-ACCESS  read-only
    STATUS      current
    DESCRIPTION 
        "Provides the category supported by this application code entry 
         in the application select table.  This is for convenience: the 
         category is also part of the application code in the 
         sfpApplCodeValue column.  The category can be one of:
         
         - unspecified(0): unspecified (vendor specific) applications;
         - fibreChannel(1): Fibre Channel applications;
         - ethernet(2): Ethernet applications;
         - sonet(3): SONET or SDH applications;
         - infiniband(4): InfiniBand applications;
         - sbcon(5): SBCON applications;
         - copper(6): Copper applications; or,
         - other(7): other (unknown) applications."
    REFERENCE   
        "SFF-8079 Rev 1.7, Section 5.2.1 and Table 6,
         SFF-8089 Rev 1.3, Table 4-1."
    ::= { sfpApplCodeEntry 3 }

sfpApplCodeValue OBJECT-TYPE
    SYNTAX      SfpApplication
    MAX-ACCESS  read-only
    STATUS      current
    DESCRIPTION 
        "Provides the code value of the supported application in 
         accordance with the codes provided in SFF-8089."
    REFERENCE   
        "SFF-8079 Rev 1.7, Section 5.2.1 and Table 6,
         SFF-8089 Rev 1.3, Table 4-1."
    ::= { sfpApplCodeEntry 4 }

sfpDiag OBJECT IDENTIFIER
    ::= { sfpTables 4 }

sfpDiagTable OBJECT-TYPE
    SYNTAX      SEQUENCE OF SfpDiagEntry
    MAX-ACCESS  not-accessible
    STATUS      current
    DESCRIPTION 
        "This table, indexed off of the SFP transceiver module 
         identifier, provides ancilliary information concerning the 
         Diagnostic Monitoring Interface for Optical Transceivers as 
         specified in SFF-8472.  Only optical modules will have an entry 
         in this table.  Also, only optical modules implementing a 
         revision of SFF-8472 or a proprietary version of the DMI will 
         have an entry in this table."
    REFERENCE   
        "SFF-8472, Diagnostic Monitoring Interface for Optical 
         Transceivers."
    ::= { sfpDiag 1 }

sfpDiagEntry OBJECT-TYPE
    SYNTAX      SfpDiagEntry
    MAX-ACCESS  not-accessible
    STATUS      current
    DESCRIPTION 
        "Each entry (conceptual row in this table) corresponds to an SFP 
         optical module that implements the SFF-8472 Diagnostic 
         Monitoring Interface.  Each entry provides information on the 
         diagnostic type, diagnostic options, DMI compliance, and the 
         alarm and warning thresholds for temperature, supply voltage, 
         transmitter bias current, transmitter power, and receiver 
         power.
         
         Alarm thresholds identify the range outside of which the 
         optical transceiver would be operating outside its rated 
         operating range.  Passing these thresholds results in agent 
         equipment alarm notifications with perceived severity of major 
         or cleared.
         
         Warning thresholds identify the range outside of which the 
         optical transceiver would be operating outside its recommended 
         operating rane.  Passing these thresholds results in agent 
         equipment alarm notifications with perceived severity or minor 
         or cleared."
    REFERENCE   
        "SFF-8472, Diagnostic Monitoring Interface for Optical 
         Transceivers."
    INDEX       { sfpModuleId }
    ::= { sfpDiagTable 1 }

SfpDiagEntry ::= SEQUENCE {
    sfpDiagType                 BITS,
    sfpDiagOptions              BITS,
    sfpDiagDmiCompliance        BITS,
    sfpDiagTempHiAlarm          Unsigned32,
    sfpDiagTempLoAlarm          Unsigned32,
    sfpDiagTempHiWarning        Unsigned32,
    sfpDiagTempLoWarning        Unsigned32,
    sfpDiagVoltHiAlarm          Unsigned32,
    sfpDiagVoltLoAlarm          Unsigned32,
    sfpDiagVoltHiWarning        Unsigned32,
    sfpDiagVoltLoWarning        Unsigned32,
    sfpDiagBiasHiAlarm          Unsigned32,
    sfpDiagBiasLoAlarm          Unsigned32,
    sfpDiagBiasHiWarning        Unsigned32,
    sfpDiagBiasLoWarning        Unsigned32,
    sfpDiagTxPowerHiAlarm       Unsigned32,
    sfpDiagTxPowerLoAlarm       Unsigned32,
    sfpDiagTxPowerHiWarning     Unsigned32,
    sfpDiagTxPowerLoWarning     Unsigned32,
    sfpDiagRxPowerHiAlarm       Unsigned32,
    sfpDiagRxPowerLoAlarm       Unsigned32,
    sfpDiagRxPowerHiWarning     Unsigned32,
    sfpDiagRxPowerLoWarning     Unsigned32
}

sfpDiagType OBJECT-TYPE
    SYNTAX      BITS { undefined(0), reserved1(1), aCR(2), rPMT(3), 
                    extCal(4), intCal(5), dMI(6) }
    MAX-ACCESS  read-only
    STATUS      current
    DESCRIPTION 
        "Indicates the degree of support for the Diagnostic Monitoring 
         Interface (DMI) for optical modules specified in SFF-8472 and 
         the methods implemented.  This object is set-valued and may 
         contain zero or more of the following:
         
         - aCR(2), when present, indicates that address change is 
           required.  Address change is a method of accessing DMI 
           information on the 2-wire bus connected to the SFP module.
         
         - rPMT(3), received power measurement type: when present, 
           indicates that received power measurement is based on average 
           power, when absent that received power measurement is based 
           on OMA (Optical Modulation Amplitude).
         
         - extCal(4), externally calibrated; measurements are based on 
           direct ADC (Analog to Digital Conversion) values that must be 
           converted to absolute values in standard units.  When 
           present, an entry for this SFP module will also exist in the 
           sfpCalibTable.
         
         - intCal(5), internally calibrated; measurements are based on 
           absolute standard units.  When present, no entry for this SFP 
           will exist in the sfpCalibTable.
         
         - dMI(6), digital diagnostic monitoring implemented when 
           present.  For entries in this table, dMI(6) is always 
           present.  When the SFP module does not support DMI, there is 
           no entry in this table for the module."
    REFERENCE   
        "SFF-8472 Rev 10.4, Table 3.9"
    ::= { sfpDiagEntry 1 }

sfpDiagOptions OBJECT-TYPE
    SYNTAX      BITS { undefined(0), softRateSelect(1), applSelect(2), 
                    rateSelect(3), rxLOS(4), txFault(5), txDisable(6), 
                    alarms(7) }
    MAX-ACCESS  read-only
    STATUS      current
    DESCRIPTION 
        "Indicates the implementation of DMI soft selection and 
         monitoring features for the SFP module.  This object is 
         set-valued and can contain zero or more of the following:
         
         - softRateSelect(1), optional soft Rate Select control 
           implemented per SFF-8431;
         - applSelect(2), optional Application Select control 
           implemented per SFF-8079;
         - rateSelect(3), optional soft RATE_SELECT control and 
           monitoring implemented;
         - rxLOS(4), RX_LOS monitoring implemented;
         - txFault(5), TX_FAULT monitoring implemented;
         - txDisable(6), TX_DISABLE control and monitoring implemented;
         - alarms(7), optional alarm/warning flags implemented for all 
           monitored quantities.
         
         Typical SFP modules implement rxLOS(4), txFault(5), 
         txDisable(6) and alarms(7).  Most modules auto-detect the 
         rate and application and do not implement softRateSelect(1) nor 
         applSelect(2)."
    REFERENCE   
        "SFF-8472 Rev 10.4, Table 3.10"
    ::= { sfpDiagEntry 2 }

sfpDiagDmiCompliance OBJECT-TYPE
    SYNTAX      BITS { undefined(0), rev93(1), rev95(2), rev102(3), 
                    rev104(4) }
    MAX-ACCESS  read-only
    STATUS      current
    DESCRIPTION 
        "Indicates the level of compliance of the Diagnostic Monitoring 
         Interface provided by the transceiver.  This object is single 
         valued, and can assume one of the following values:
         
         - undefined(0), digial diagnostic functionality not included or 
           undefined;
         - rev93(1), includes functionality described in revision 9.3 of 
           SFF-8472;
         - rev95(2), includes functionality described in revision 9.3 of 
           SFF-8472;
         - rev102(3), includes functionality described in revision 10.2 
           of SFF-8472; and,
         - rev104(4), includes functionality described in revision 10.4 
           of SFF-8472.
         
         It is typical for SFP modules to support the most recent 
         version of the Diagnositic Monitoring Interface specification, 
         which currently is at revision 10.4."
    REFERENCE   
        "SFF-8472 Rev 10.4, Table 3.12"
    ::= { sfpDiagEntry 3 }

sfpDiagTempHiAlarm OBJECT-TYPE
    SYNTAX      Unsigned32
    MAX-ACCESS  read-only
    STATUS      current
    DESCRIPTION 
        "Indicates the setting of the high temperature alarm threshold.  
         This is the temperature beyond which the transceiver will be 
         operating outside its rated operating range.  This value is 
         factory set.  Most SFP transceivers will operate up to a 
         temperature of 85 degrees Celcius.
         
         When this threshold is crossed, the agent will generate an 
         equipment alarm notification with probable cause of temperature 
         unacceptable, perceived severity of major or cleared, and a 
         specific problem of high temperature."
    REFERENCE   
        "SFF-8472 Rev 10.4, Table 3.15"
    ::= { sfpDiagEntry 4 }

sfpDiagTempLoAlarm OBJECT-TYPE
    SYNTAX      Unsigned32
    MAX-ACCESS  read-only
    STATUS      current
    DESCRIPTION 
        "Indicates the setting of the low temperature alarm threshold.  
         This is the temperature beneath which the transciever will be 
         operating outside its rated operating range.  This value is 
         factory set.  Most SFP transceivers will operate down to a 
         temperature of 0 degrees Celcius; some as low as -40 or -50 
         degrees Celcius.
         
         When this threshold is crossed, the agent will generate an 
         equipment alarm notification with probable cause of temperature 
         unacceptable, perceived severity of major or cleared, and a 
         specific problem of low temperature."
    REFERENCE   
        "SFF-8472 Rev 10.4, Table 3.15"
    ::= { sfpDiagEntry 5 }

sfpDiagTempHiWarning OBJECT-TYPE
    SYNTAX      Unsigned32
    MAX-ACCESS  read-only
    STATUS      current
    DESCRIPTION 
        "Indicates the setting of the high temperature warning 
         threshold.  This is the temperature beyond which the 
         transceiver wll be operating outside its recommended operating 
         range.  This value is factory set.  Most SFP transceivers will 
         operate up to a temperature of 85 degrees Celcius.
         
         When this threshold is crossed, the agent will generate an 
         equipment alarm notification with probable cause of temperature 
         unacceptable, perceived severity of minor or cleared, and a 
         specific problem of high temperature."
    REFERENCE   
        "SFF-8472 Rev 10.4, Table 3.15"
    ::= { sfpDiagEntry 6 }

sfpDiagTempLoWarning OBJECT-TYPE
    SYNTAX      Unsigned32
    MAX-ACCESS  read-only
    STATUS      current
    DESCRIPTION 
        "Indicates the setting of the low temperature warning threshold.  
         This is the temperature beneath which the transceiver will be 
         operating outside its recommended operating range.  This value 
         factory set.  Most SFP transceivers will operate down to a 
         temperature of 0 degrees Celcius; some as low as -40 or -50 
         degrees Celcius.
         
         When this threshold is crossed, the agent will generate an 
         equipment alarm notification with probable cause of temperature 
         unacceptable, perceived severity of minor or cleared, and a 
         specific problem of low temperature."
    REFERENCE   
        "SFF-8472 Rev 10.4, Table 3.15"
    ::= { sfpDiagEntry 7 }

sfpDiagVoltHiAlarm OBJECT-TYPE
    SYNTAX      Unsigned32
    MAX-ACCESS  read-only
    STATUS      current
    DESCRIPTION 
        "Indicates the setting of the high supply voltage alarm 
         threshold.  This is the supply voltage above which the 
         transceiver will be operating outside its rated operating 
         range.  This value is factory set.  SFP transceivers that 
         conform to MSA will accept a high supply voltage of +3.465 VDC.
         
         When this threshold is crossed, the agent will generate an 
         equipmentAlarm notification with probable cause of power 
         problem, perceived severity major or cleared, and a specific 
         problem of high voltage."
    REFERENCE   
        "SFF-8472 Rev 10.4, Table 3.15"
    ::= { sfpDiagEntry 8 }

sfpDiagVoltLoAlarm OBJECT-TYPE
    SYNTAX      Unsigned32
    MAX-ACCESS  read-only
    STATUS      current
    DESCRIPTION 
        "Indicates the setting of the low supply voltage alarm 
         threshold.  This is the supply voltage beneath which the 
         transceiver will be operating outside its rated operating 
         range.  This value is factory set.  SFP transceivers that 
         conform to MSA will accept a low supply voltage of +3.135 VDC.
         
         When this threshold is crossed, the agent will generate an 
         equipment alarm notification with probable cause of power 
         problem, perceived severity major or cleared, and a specific 
         problem of low voltage."
    REFERENCE   
        "SFF-8472 Rev 10.4, Table 3.15"
    ::= { sfpDiagEntry 9 }

sfpDiagVoltHiWarning OBJECT-TYPE
    SYNTAX      Unsigned32
    MAX-ACCESS  read-only
    STATUS      current
    DESCRIPTION 
        "Indicates the setting of the high supply voltage warning 
         threshold.  This is the supply voltage above which the 
         transceiver will be operating outside its recommended operating 
         range.  This value is factory set.  SFP transceivers that 
         conform to MSA will accept a high supply voltage of +3.465 VDC.
         
         When this threshold is crossed, the agent will generate an 
         equipment alarm notification with probable cause of power 
         problem, perceived severity of minor or cleared, and a specific 
         problem of high voltage."
    REFERENCE   
        "SFF-8472 Rev 10.4, Table 3.15"
    ::= { sfpDiagEntry 10 }

sfpDiagVoltLoWarning OBJECT-TYPE
    SYNTAX      Unsigned32
    MAX-ACCESS  read-only
    STATUS      current
    DESCRIPTION 
        "Indicates the setting of the low supply voltage warning 
         threshold.  This is the supply voltage beneath which the 
         transciever will be operating outside its recommended operating 
         range.  This value is factory set.  SFP transceivers that 
         conform to MSA will accept a low supply voltage of +3.135 VDC.
         
         When this threshold is crossed, the agent will generate an 
         equipment alarm notification with probable cause of power 
         problem, perceived severity minor or cleared, and a specific 
         problem of low voltage."
    REFERENCE   
        "SFF-8472 Rev 10.4, Table 3.15"
    ::= { sfpDiagEntry 11 }

sfpDiagBiasHiAlarm OBJECT-TYPE
    SYNTAX      Unsigned32
    MAX-ACCESS  read-only
    STATUS      current
    DESCRIPTION 
        "Indicates the setting of the high transmitter bias current 
         alarm threshold.  This is the transmitter bias current beyond 
         which the transceiver will be operating outside its rated 
         operating range.  This value is factory set.
         
         When this threshold is crossed, the agent will generate an 
         equipment alarm notification with probable cause of threshold 
         crossed, perceived severity of major or cleared, and a specific 
         problem of high transmitter bias.
         
         When there is not a coincident problem with supply voltage, 
         this alarm indicates that there is a problem with the 
         transceiver's laser or transmit drivers."
    REFERENCE   
        "SFF-8472 Rev 10.4, Table 3.15"
    ::= { sfpDiagEntry 12 }

sfpDiagBiasLoAlarm OBJECT-TYPE
    SYNTAX      Unsigned32
    MAX-ACCESS  read-only
    STATUS      current
    DESCRIPTION 
        "Indicates the setting of the low transmitter bias current alarm 
         threshold.  This is the transmitter bias current beneath which 
         the trasceiver will be operating outside its rated operating 
         range.  This value is factory set.
         
         When this threshold is crossed the agent will generate an 
         equipment alarm notification with probable cause of threshold 
         crossed, perceived severity of major or cleared, and a specific 
         problem of low transmitter bias.
         
         When there is not a coincident problem with supply voltage, 
         this alarm indicates that there is a problem with the 
         transciever's laser or transmit drivers."
    REFERENCE   
        "SFF-8472 Rev 10.4, Table 3.15"
    ::= { sfpDiagEntry 13 }

sfpDiagBiasHiWarning OBJECT-TYPE
    SYNTAX      Unsigned32
    MAX-ACCESS  read-only
    STATUS      current
    DESCRIPTION 
        "Indicates the setting of the high transmitter bias current 
         warning threshold.  This is the transmitter bias current beyond 
         which the transceiver will be operating outside its recommended 
         operating range.  This value is factory set.
         
         When this threshold is crossed, the agent will generate an 
         equipment alarm notification with probable cuase of threshold 
         crossed, percieved severity of minor or cleared, and a specific 
         problem of high transmitter bias.
         
         When there is not a coincident problem with supply voltage, 
         this alarm indicates that there is a problem with the 
         transciever's laser or transmit drivers."
    REFERENCE   
        "SFF-8472 Rev 10.4, Table 3.15"
    ::= { sfpDiagEntry 14 }

sfpDiagBiasLoWarning OBJECT-TYPE
    SYNTAX      Unsigned32
    MAX-ACCESS  read-only
    STATUS      current
    DESCRIPTION 
        "Indicates the setting of the low transmitter bias current 
         warning threshold.  This is the transmitter bias current 
         beneath which the transceiver will be operating outside its 
         recommended operating range.  This value is factory set.
         
         When this threshold is crossed, the agent will generate an 
         equipment alarm notification with probable cuase of threshold 
         crossed, perceived severity of minor or cleared, and a specific 
         problem of low transmitter bias.
         
         When there is not a coincident problem with supply voltage, 
         this alarm indicates that there is a problem with the 
         transceiver's laser or transmit drivers."
    REFERENCE   
        "SFF-8472 Rev 10.4, Table 3.15"
    ::= { sfpDiagEntry 15 }

sfpDiagTxPowerHiAlarm OBJECT-TYPE
    SYNTAX      Unsigned32
    MAX-ACCESS  read-only
    STATUS      current
    DESCRIPTION 
        "Indicates the setting of the high transmitter power alarm 
         threshold.  This is the transmitter power beyond which the 
         transceiver will be operating outside its rated operating 
         range.  This value is factory set.
         
         When this threshold is crossed, the agent will generate an 
         equipment alarm notification with probable cause of transmit 
         failure, perceived severity of major or cleared, and a specific 
         problem of high transmit power."
    REFERENCE   
        "SFF-8472 Rev 10.4, Table 3.15"
    ::= { sfpDiagEntry 16 }

sfpDiagTxPowerLoAlarm OBJECT-TYPE
    SYNTAX      Unsigned32
    MAX-ACCESS  read-only
    STATUS      current
    DESCRIPTION 
        "Indicates the setting of the lower transmitter power alarm 
         threshold.  This is the transmitter power beneath which the 
         transceiver will be operating outside its rated operating 
         range.  This value is factory set.
         
         When this threshold is crossed, the agent will generate an 
         equipment alarm notification with probable cuase of transmit 
         failure, perceived severity of major or cleared, and a specific 
         problem of low transmit power."
    REFERENCE   
        "SFF-8472 Rev 10.4, Table 3.15"
    ::= { sfpDiagEntry 17 }

sfpDiagTxPowerHiWarning OBJECT-TYPE
    SYNTAX      Unsigned32
    MAX-ACCESS  read-only
    STATUS      current
    DESCRIPTION 
        "Indicates the setting of the high transmit power warning 
         threshold.  This is the transmitter power beyond which the 
         transceiver will be operating outside its recommended operating 
         range.  This value is factory set.
         
         When this threshold is crossed, the agent will generate an 
         equipment alarm notification with probable cause of transmit 
         failure, perceived severity of minor or cleared, and a specific 
         problem of high transmit power."
    REFERENCE   
        "SFF-8472 Rev 10.4, Table 3.15"
    ::= { sfpDiagEntry 18 }

sfpDiagTxPowerLoWarning OBJECT-TYPE
    SYNTAX      Unsigned32
    MAX-ACCESS  read-only
    STATUS      current
    DESCRIPTION 
        "Indicates the setting of the low transmit power warning 
         threshold.  This is the transmitter power beneath which the 
         transceiver will be operating outside its recommended operating 
         range.  This value is factory set.
         
         When this threshold is crossed, the agent will generate an 
         equipment alarm notification with probable cause of transmit 
         failure, perceived severity of minor or cleared, and a specific 
         problem of low transmit power."
    REFERENCE   
        "SFF-8472 Rev 10.4, Table 3.15"
    ::= { sfpDiagEntry 19 }

sfpDiagRxPowerHiAlarm OBJECT-TYPE
    SYNTAX      Unsigned32
    MAX-ACCESS  read-only
    STATUS      current
    DESCRIPTION 
        "Indicates the setting of the high receiver power alarm 
         threshold.  This is the receiver power beyond which the 
         transceiver will be operating outside its rated operating 
         range.  This value is factory set.
         
         When this threshold is crossed, the agent will generate an 
         equipment alarm notification with probable cause of receive 
         failure, perceived severity of major or cleared, and a specific 
         problem of high receive power."
    REFERENCE   
        "SFF-8472 Rev 10.4, Table 3.15"
    ::= { sfpDiagEntry 20 }

sfpDiagRxPowerLoAlarm OBJECT-TYPE
    SYNTAX      Unsigned32
    MAX-ACCESS  read-only
    STATUS      current
    DESCRIPTION 
        "Indicates the setting of the low receiver power alarm 
         threshold.  This is the receiver power beneath which the 
         transceiver will be operating outside its rated operating 
         range.  This value is factory set.
         
         When this threshold is crossed, the agent will generate an 
         equipment alarm notification with probable cause of receive 
         failure, perceived severity of major or cleared, and a specific 
         problem of low receive power."
    REFERENCE   
        "SFF-8472 Rev 10.4, Table 3.15"
    ::= { sfpDiagEntry 21 }

sfpDiagRxPowerHiWarning OBJECT-TYPE
    SYNTAX      Unsigned32
    MAX-ACCESS  read-only
    STATUS      current
    DESCRIPTION 
        "Indicates the setting of the high receiver power warning 
         threshold.  This is the receiver power beyond which the 
         transceiver will be operating outside its recommended operating 
         range.  This value is factory set.
         
         When this threshold is crossed, the agent will generate an 
         equipment alarm notification with probable cause of receive 
         failure, perceived severity of minor or cleared, and a specific 
         problem of high receive power."
    REFERENCE   
        "SFF-8472 Rev 10.4, Table 3.15"
    ::= { sfpDiagEntry 22 }

sfpDiagRxPowerLoWarning OBJECT-TYPE
    SYNTAX      Unsigned32
    MAX-ACCESS  read-only
    STATUS      current
    DESCRIPTION 
        "Indicates the setting of the low receiver power warning 
         threshold.  This is the receiver power beneath which the 
         transceiver will be operating outside its recommended operating 
         range.  This value is factory set.
         
         When this threshold is crossed, the agent will generate an 
         equipment alarm notification with probable cause of receive 
         failure, perceived severity of minor or cleared, and a specific 
         problem of low receive power."
    REFERENCE   
        "SFF-8472 Rev 10.4, Table 3.15"
    ::= { sfpDiagEntry 23 }

sfpCalib OBJECT IDENTIFIER
    ::= { sfpTables 5 }

sfpCalibTable OBJECT-TYPE
    SYNTAX      SEQUENCE OF SfpCalibEntry
    MAX-ACCESS  not-accessible
    STATUS      current
    DESCRIPTION 
        "This table contains external calibration constants for the SFP 
         module.  Entries only exist in this table for optical SFP 
         modules that comply with the Diagnostic Monitoring Interface 
         for Optical Modules specification (SFF-8472) and which also 
         require external calibration.  External calibration is where 
         the SFP module reports only raw ADC (Analog to Digital 
         Converter) measurements and require a conversion operation 
         before absolute values in standard units can be determined.  
         Internal calibration is where the optical SFP module reports 
         absolute values in standard units."
    REFERENCE   
        "SFF-8472 Rev 10.4, Table 3.16"
    ::= { sfpCalib 1 }

sfpCalibEntry OBJECT-TYPE
    SYNTAX      SfpCalibEntry
    MAX-ACCESS  not-accessible
    STATUS      current
    DESCRIPTION 
        "Each entry (conceptual row in this table) corresponds to the 
         external calibration constants for a specific optical SFP 
         module that complies with the Diagnostic Monitoring Interface 
         (DMI) for Optical Modules specifications (SFF-8472).  External 
         calibrartion constants are used to convert between raw ADC 
         measurements and absolute values when a transceiver is 
         externally calibrated.  When a transceiver is internally 
         calibrated, there will be no entry in this table for the SFP 
         module.  See sfpDiagType in the sfpDiagTable for the module.
         
         Each entry provides the external calibration constants for 
         received power, transmitter bias current, transmitter power, 
         temperature and supply voltage."
    REFERENCE   
        "SFF-8472 Rev 10.4, Table 3.16"
    INDEX       { sfpModuleId }
    ::= { sfpCalibTable 1 }

SfpCalibEntry ::= SEQUENCE {
    sfpCalibRxPwr0          Unsigned32,
    sfpCalibRxPwr1          Unsigned32,
    sfpCalibRxPwr2          Unsigned32,
    sfpCalibRxPwr3          Unsigned32,
    sfpCalibRxPwr4          Unsigned32,
    sfpCalibTxISlope        Unsigned32,
    sfpCalibTxIOffset       Integer32,
    sfpCalibTxPwrSlope      Unsigned32,
    sfpCalibTxPwrOffset     Integer32,
    sfpCalibTSlope          Unsigned32,
    sfpCalibTOffset         Integer32,
    sfpCalibVSlope          Unsigned32,
    sfpCalibVOffset         Integer32
}

sfpCalibRxPwr0 OBJECT-TYPE
    SYNTAX      Unsigned32
    MAX-ACCESS  read-only
    STATUS      current
    DESCRIPTION 
        "This is one of four values used to externally calibrate the 
         receiver power measurement."
    REFERENCE   
        "SFF-8472 Rev 10.4, Calibration Constants"
    ::= { sfpCalibEntry 1 }

sfpCalibRxPwr1 OBJECT-TYPE
    SYNTAX      Unsigned32
    MAX-ACCESS  read-only
    STATUS      current
    DESCRIPTION 
        "This is one of four values used to externally calibrate the 
         receiver power measurement."
    REFERENCE   
        "SFF-8472 Rev 10.4, Calibration Constants"
    ::= { sfpCalibEntry 2 }

sfpCalibRxPwr2 OBJECT-TYPE
    SYNTAX      Unsigned32
    MAX-ACCESS  read-only
    STATUS      current
    DESCRIPTION 
        "This is one of four values used to externally calibrate the 
         receiver power measurement."
    REFERENCE   
        "SFF-8472 Rev 10.4, Calibration Constants"
    ::= { sfpCalibEntry 3 }

sfpCalibRxPwr3 OBJECT-TYPE
    SYNTAX      Unsigned32
    MAX-ACCESS  read-only
    STATUS      current
    DESCRIPTION 
        "This is one of four values used to externally calibrate the 
         receiver power measurement."
    REFERENCE   
        "SFF-8472 Rev 10.4, Calibration Constants"
    ::= { sfpCalibEntry 4 }

sfpCalibRxPwr4 OBJECT-TYPE
    SYNTAX      Unsigned32
    MAX-ACCESS  read-only
    STATUS      current
    DESCRIPTION 
        "This is one of four values used to externally calibrate the 
         receiver power measurement."
    REFERENCE   
        "SFF-8472 Rev 10.4, Calibration Constants"
    ::= { sfpCalibEntry 5 }

sfpCalibTxISlope OBJECT-TYPE
    SYNTAX      Unsigned32
    MAX-ACCESS  read-only
    STATUS      current
    DESCRIPTION 
        "Indicates the value to be combined in a product with the 
         difference of the measured value and the transmitter bias 
         current calibration offset.  This is one of two values used to 
         externally calibrate the transmitter bias current measurement."
    REFERENCE   
        "SFF-8472 Rev 10.4, Calibration Constants"
    ::= { sfpCalibEntry 6 }

sfpCalibTxIOffset OBJECT-TYPE
    SYNTAX      Integer32
    MAX-ACCESS  read-only
    STATUS      current
    DESCRIPTION 
        "Indicates the value to be combined in a difference with the 
         measured transmitter bias current.  This is one of two values 
         used to externally calibrate the transmitter bias current 
         measurement."
    REFERENCE   
        "SFF-8472 Rev 10.4, Calibration Constants"
    ::= { sfpCalibEntry 7 }

sfpCalibTxPwrSlope OBJECT-TYPE
    SYNTAX      Unsigned32
    MAX-ACCESS  read-only
    STATUS      current
    DESCRIPTION 
        "Indicates the value to be combined in a product with the 
         difference of the measured value and the transmitter power 
         calibration offset.  This is one of two values used to 
         externally calibrate the transmitter power measurement."
    REFERENCE   
        "SFF-8472 Rev 10.4, Calibration Constants"
    ::= { sfpCalibEntry 8 }

sfpCalibTxPwrOffset OBJECT-TYPE
    SYNTAX      Integer32
    MAX-ACCESS  read-only
    STATUS      current
    DESCRIPTION 
        "Indicates the value to be combined in a difference with the 
         measured transmitter power.  This is one of two values used to 
         externally calibrate the transmitter power measurement."
    REFERENCE   
        "SFF-8472 Rev 10.4, Calibration Constants"
    ::= { sfpCalibEntry 9 }

sfpCalibTSlope OBJECT-TYPE
    SYNTAX      Unsigned32
    MAX-ACCESS  read-only
    STATUS      current
    DESCRIPTION 
        "Indicates the value to be combined in a product with the 
         difference of the measured value and the temperature 
         calibtation offset.  This is one of two values used to 
         externally calibrate the temperature measurement."
    REFERENCE   
        "SFF-8472 Rev 10.4, Calibration Constants"
    ::= { sfpCalibEntry 10 }

sfpCalibTOffset OBJECT-TYPE
    SYNTAX      Integer32
    MAX-ACCESS  read-only
    STATUS      current
    DESCRIPTION 
        "Indicates the value to be combined in a difference with the 
         measured temperature.  This is one of two values used to 
         externally calibrate the temperature measurement."
    REFERENCE   
        "SFF-8472 Rev 10.4, Calibration Constants"
    ::= { sfpCalibEntry 11 }

sfpCalibVSlope OBJECT-TYPE
    SYNTAX      Unsigned32
    MAX-ACCESS  read-only
    STATUS      current
    DESCRIPTION 
        "Indicates the value to be combined in a product with the 
         difference of the measured value and the supply voltage 
         calibration offset.  This is one of two values used to 
         externally calibrate the voltage measurement."
    REFERENCE   
        "SFF-8472 Rev 10.4, Calibration Constants"
    ::= { sfpCalibEntry 12 }

sfpCalibVOffset OBJECT-TYPE
    SYNTAX      Integer32
    MAX-ACCESS  read-only
    STATUS      current
    DESCRIPTION 
        "Indicates the value to be combined in a difference with the 
         measured supply voltage.  This is one of two values used to 
         externally calibrate the voltage measurement."
    REFERENCE   
        "SFF-8472 Rev 10.4, Calibration Constants"
    ::= { sfpCalibEntry 13 }

sfpMon OBJECT IDENTIFIER
    ::= { sfpTables 6 }

sfpMonTable OBJECT-TYPE
    SYNTAX      SEQUENCE OF SfpMonEntry
    MAX-ACCESS  not-accessible
    STATUS      current
    DESCRIPTION 
        "This table provides A/D values and status."
    REFERENCE   
        "SFF-8472 Rev 10.4, Table 3.17"
    ::= { sfpMon 1 }

sfpMonEntry OBJECT-TYPE
    SYNTAX      SfpMonEntry
    MAX-ACCESS  not-accessible
    STATUS      current
    DESCRIPTION 
        "Each entry in the sfpMonTable provides A/D values and status 
         for a single SFP/SFP+ modules as identified by the sfpModuleId 
         index value."
    REFERENCE   
        "SFF-8472 Rev 10.4, Table 3.17"
    INDEX       { sfpModuleId }
    ::= { sfpMonTable 1 }

SfpMonEntry ::= SEQUENCE {
    sfpMonTemp              Unsigned32,
    sfpMonVolt              Unsigned32,
    sfpMonBias              Unsigned32,
    sfpMonTxPower           Unsigned32,
    sfpMonRxPower           Unsigned32,
    sfpMonDataReadyBar      SfpMonitor,
    sfpMonRxLossOfSignal    SfpMonitor,
    sfpMonTxFaultState      SfpMonitor,
    sfpMonRateSelect        SfpMonitor,
    sfpMonApplSelect        SfpMonitor,
    sfpMonTxDisable         SfpMonitor,
    sfpMonPowerLevel        INTEGER,
    sfpMonSoftRateSelect    SfpMonitor,
    sfpMonSoftRateSelect1   SfpMonitor,
    sfpMonSoftPowerLevel    INTEGER,
    sfpMonSoftTxDisable     SfpMonitor
}

sfpMonTemp OBJECT-TYPE
    SYNTAX      Unsigned32
    MAX-ACCESS  read-only
    STATUS      current
    DESCRIPTION 
        "Internally measured module temperature.  When externally 
         calibrated, this value is adjusted by the agent to reflect the 
         absolute value."
    REFERENCE   
        "SFF-8472 Rev 10.4, Table 3.17"
    ::= { sfpMonEntry 1 }

sfpMonVolt OBJECT-TYPE
    SYNTAX      Unsigned32
    MAX-ACCESS  read-only
    STATUS      current
    DESCRIPTION 
        "Internally measured supply voltage in transceiver.  When 
         externally calibrated, this value is adjusted by the agent to 
         reflect the absolute value."
    REFERENCE   
        "SFF-8472 Rev 10.4, Table 3.17"
    ::= { sfpMonEntry 2 }

sfpMonBias OBJECT-TYPE
    SYNTAX      Unsigned32
    MAX-ACCESS  read-only
    STATUS      current
    DESCRIPTION 
        "Internally measured Tx Bias Current.  When externally 
         calibrated, this value is adjusted by the agent to reflect the 
         absolute value."
    REFERENCE   
        "SFF-8472 Rev 10.4, Table 3.17"
    ::= { sfpMonEntry 3 }

sfpMonTxPower OBJECT-TYPE
    SYNTAX      Unsigned32
    MAX-ACCESS  read-only
    STATUS      current
    DESCRIPTION 
        "Internally measured Tx output power.  When externally 
         calibrated, this value is adjusted by the agent to reflect the 
         absolute value."
    REFERENCE   
        "SFF-8472 Rev 10.4, Table 3.17"
    ::= { sfpMonEntry 4 }

sfpMonRxPower OBJECT-TYPE
    SYNTAX      Unsigned32
    MAX-ACCESS  read-only
    STATUS      current
    DESCRIPTION 
        "Internally measured Rx input power.  When externally 
         calibrated, this value is adjusted by the agent to reflect the 
         absolute value.
         
         Note that depending on the setting of sfpDiagType (in the 
         sfpDiagTable for the module), the receive power is either 
         average power (P) or optical modulation amplitude (OMA)."
    REFERENCE   
        "SFF-8472 Rev 10.4, Table 3.17"
    ::= { sfpMonEntry 5 }

sfpMonDataReadyBar OBJECT-TYPE
    SYNTAX      SfpMonitor
    MAX-ACCESS  read-only
    STATUS      current
    DESCRIPTION 
        "This object is single-valued and can have one of the following 
         values:
         
         - unknown(0), monitoring of data ready is not implemented and 
           the state of the module is unknown;
         - asserted(1), the transceiver has acheived power up and data 
           is ready;
         - deasserted(2), the transcevier has not acheived power up.
         
         A value of asserted(1) indicates that the transceiver has 
         acheived power up and data is ready."
    REFERENCE   
        "SFF-8472 Rev 10.4, Table 3.17"
    ::= { sfpMonEntry 6 }

sfpMonRxLossOfSignal OBJECT-TYPE
    SYNTAX      SfpMonitor
    MAX-ACCESS  read-only
    STATUS      current
    DESCRIPTION 
        "Reflects the state of the RX_LOS output pin.  A value of 
         asserted(1), indicates that the RX_LOS output pin is asserted 
         and a receive loss of signal condition exists.
         
         - unknown(0), the monitoring of the RX_LOS signal is not 
           implemented and the state of the signal is unknown;
         - asserted(1), the RX_LOS signal is asserted; or,
         - deasserted(2), the RX_LOS signal is deasserted.
         
         When this value is asserted or deasserted, the agent generates 
         an equipment alarm notification with perceived severity of 
         major or cleared, probable cause of loss of signal, and 
         specific problem of receiver loss of signal.
         
         The agent will typically inititate changeover or changeback in 
         a 1:1 Automatic Protection Switching arrangement on the basis 
         of this condition."
    REFERENCE   
        "SFF-8472 Rev 10.4, Table 3.17"
    ::= { sfpMonEntry 7 }

sfpMonTxFaultState OBJECT-TYPE
    SYNTAX      SfpMonitor
    MAX-ACCESS  read-only
    STATUS      current
    DESCRIPTION 
        "Reflects the state of the TX_FAULT output pin.  A value of 
         asserted(1) indicates that the TX_FAULT output pin is asserted 
         and a transmitter fault condition exists.
         
         - unknown(0), the monitoring of the TxFault signal is not 
           implemented and the state of the signal is unknown;
         - asserted(1), the TxFault signal is asserted; or,
         - deasserted(2), the TxFault signal is deasserted.
         
         When this value is asserted or deasserted, the agent generates 
         an equipment alarm notification with perceived severity of 
         major or cleared, probable cause of transmitter failure, and 
         specific problem of transmitter fault.
         
         The agent may typically initiate changeover or changeback in a 
         1:1 Automatic Protection Switching arrangement on the basis of 
         this condition.  Some implementations may wait for segment AIS 
         condition before responding to a transmitter fault condtion."
    REFERENCE   
        "SFF-8472 Rev 10.4, Table 3.17"
    ::= { sfpMonEntry 8 }

sfpMonRateSelect OBJECT-TYPE
    SYNTAX      SfpMonitor
    MAX-ACCESS  read-only
    STATUS      current
    DESCRIPTION 
        "Reflects the state of the Rate Select (or Application Select 
         [0]) input pin.  The object can have one of the following 
         values:
         
         - unknown(0), the soft rate select option is not supported by 
           the SFP module and the agent has no other way of knowing the 
           setting of the signal;
         - asserted(1), the rate select pin, RS(0), is asserted; or,
         - deasserted(2), the rate select pin, RS(0), is deasserted.
         
         Note that this indication is only valid (other than unknown(0)) 
         when the SFP module supports soft rate select as indicated by 
         the presence of the softRateSelect(1) bit in the sfpDiagOptions 
         object of the corresponding entry in the sfpDiagTable."
    REFERENCE   
        "SFF-8472 Rev 10.4, Table 3.17"
    ::= { sfpMonEntry 9 }

sfpMonApplSelect OBJECT-TYPE
    SYNTAX      SfpMonitor
    MAX-ACCESS  read-only
    STATUS      current
    DESCRIPTION 
        "Reflects the state of the Rate Select 1 (or Application Select 
         [1]), input pin.  The object can have one of the following 
         values:
         
         - unknown(0), the soft application select option is not 
           supported by the SFP module and the agent has no other way of 
           knowing the setting of the signal;
         - asserted(1), the application select pin, RS(1), is asserted; 
           or,
         - deasserted(2), the application select pin, RS(1), is 
           deasserted.
         
         Note that this indication is only valid (other than unknown(0)) 
         when the SFP module supports soft application select as 
         indicated by the presence of the applSelect(2) bit in the 
         sfpDiagOptions object of the corresponding entry in the 
         sfpDiagTable."
    REFERENCE   
        "SFF-8472 Rev 10.4, Table 3.17"
    ::= { sfpMonEntry 10 }

sfpMonTxDisable OBJECT-TYPE
    SYNTAX      SfpMonitor
    MAX-ACCESS  read-only
    STATUS      current
    DESCRIPTION 
        "Reflects the state of the TX_DISABLE input pin.  The object can 
         have one of the following values:
         
         - unknown(0), the monitoring of the TxDisable input pin is not 
           implemented and the state of the signal is unknown;
         - asserted(1), the TxDisable signal is asserted; or,
         - deasserted(2), the TxDisable signal is deasserted.
         
         When the value of the TxDisable pin is asserted, the 
         operational state of the module is disabled(0); when 
         deasserted, the operational state is enabled(1)."
    REFERENCE   
        "SFF-8472 Rev 10.4, Table 3.17"
    ::= { sfpMonEntry 11 }

sfpMonPowerLevel OBJECT-TYPE
    SYNTAX      INTEGER { powerLevel1(0), powerLevel2(1) }
    MAX-ACCESS  read-only
    STATUS      current
    DESCRIPTION 
        "Indicates the current SFF-8431 Power Level (maximum power 
         dissipation) operational state, and can be one of the 
         following values:
         
         - powerLevel1(0), INF-8074 (SFP) or SFF-8431 (SFP+) Power Level 
           1 operation (1.0 Watts maximum); or,
         - powerLevel2(1), SFF-8431 (SFP+) Power Level 2 operation (1.5 
           Watts maximum).
         
         This object reflects the current authorized maximum power 
         dissipation of the SFP/SFP+ module.  SFP+ high-power modules 
         are permitted to require high-power for proper operation.  Such 
         a module will have an AvailabilityStatus of 
         initializationRequired(0) and an OperationState of disabled(0) 
         until the module has been authorized for high-power power 
         consumption."
    REFERENCE   
        "INF-8074, Table 1, Note 8,
         SFF-8472 Rev 10.4, Table 3.18a"
    ::= { sfpMonEntry 12 }

sfpMonSoftRateSelect OBJECT-TYPE
    SYNTAX      SfpMonitor
    MAX-ACCESS  read-write
    STATUS      current
    DESCRIPTION 
        "Allows management stations to control rate selection.  This 
         object is single-valued.  When read, the object can have one of 
         the following values:
         
         - unknown(0), the module does not support the soft rate select 
           feature; writing to this object will have no effect;
         - asserted(1), soft rate select is asserted; or,
         - deasserted(2), soft rate select is deasserted.
         
         A value of asserted(1) selects full bandwidth operation.  This 
         setting is OR'ed with the Rate_Select, RS(0), hardware pin 
         value.  Default at power-up is deasserted(2).  If soft Rate 
         Select is not implemented, the transciever ignores the setting 
         of this object and always returns unknown(0).
         
         Implementations of this MIB do not require write support for 
         this object.  Mangement stations should set this value with 
         caution.  Writing this value has dubious diagnostic or testing 
         purposes."
    REFERENCE   
        "SFF-8472 Rev 10.4, Table 3.17"
    ::= { sfpMonEntry 13 }

sfpMonSoftRateSelect1 OBJECT-TYPE
    SYNTAX      SfpMonitor
    MAX-ACCESS  read-write
    STATUS      current
    DESCRIPTION 
        "Indicates software Tx rate control.  The object is 
         single-valued.  When read, the object can have one of the 
         following values:
         
         - unknown(0), the module does not support the soft rate select 
           feature; writing to this object will have no effect;
         - asserted(1), soft rate select 1 is asserted; or,
         - deasserted(2), soft rate select 1 is deasserted.
         
         A value of asserted(1), selects full speed Tx operation.  This 
         setting is OR'ed with the Rate_Select, RS(1), hardware pin 
         value.  Default at power-up is deasserted(2).  If soft Rate 
         Select 1 is not implemented, the transceiver ignores the 
         setting of this object and always returns unknown(0)."
    REFERENCE   
        "SFF-8472 Rev 10.4, Table 3.18a"
    ::= { sfpMonEntry 14 }

sfpMonSoftPowerLevel OBJECT-TYPE
    SYNTAX      INTEGER { powerLevel1(0), powerLevel2(1) }
    MAX-ACCESS  read-write
    STATUS      current
    DESCRIPTION 
        "Indicates the software selectable SFF-8431 Power Level (maximum 
         power dissipation) status, and can be one of the following 
         values:
         
         - powerLevel1(0), INF-8074 (SFP) or SFF-8431 (SFP+) Power Level 
           1 operation (1.0 Watts maximum); or,
         - powerLevel2(1), SFF-8431 (SFP+) Power Level 2 operation (1.5 
           Watts maximum).
         
         SFP+ modules are permitted to require and operate at Power 
         Level 2.  SFP modules are only permitted Power Level 1 
         operation.  SFP+ modules that require Power Level 2 to be 
         operable will not funtion until the agent sets this value to 
         powerLevel2(1) permitting high power operation.  When an 
         SFP+ module requiring high-power operation is configured only 
         for low-power operation; the availability status will contain 
         initializationRequired(0) and the operational state will be 
         disabled(0).
         
         Implementations of this MIB do not require write support for 
         this object.  Mangement stations should set this value with 
         caution.  Writing this value has dubious diagnostic or testing 
         purposes."
    REFERENCE   
        "INF-8074, Table 1, Note 8,
         SFF-8472 Rev 10.4, Table 3.18a"
    ::= { sfpMonEntry 15 }

sfpMonSoftTxDisable OBJECT-TYPE
    SYNTAX      SfpMonitor
    MAX-ACCESS  read-write
    STATUS      current
    DESCRIPTION 
        "Allows management stations to control disabling of the laser.  
         This object is single valued.  When read, the object can have 
         one of the following values:
         
         - unknown(0), the module does not support the soft TxDisable 
           feature; writing to this object will have no effect;
         - asserted(1), soft TxDisable is asserted; or,
         - deasserted(2), soft TxDisable is deasserted.
         
         Provided that the module supports the feature, a value of 
         asserted(1) disables the laser.  This setting is OR'ed with the 
         hardware TX_DISABLE pin value as reflected by sfpMonTxDisable.  
         When TX_DISABLE is asserted by hardware, this value has no 
         effect.
         
         Note: per SFP MSA the TX_DISABLE pin is default enabled unless 
         pulled low by hardware.  If Soft TX Disable is not implemented, 
         the transceiver ignores the value of this setting and always 
         reads unknown(0).  The default power up value when supported is 
         deasserted(2).
         
         Not all implementations of this MIB need support writing this 
         value.  When supported, mangement stations should set this 
         value cautiously.  Asserting Tx disable will power down the 
         laser on the module causing all traffic through the module to 
         be lost.
         
         Implementations of this MIB do not require write support for 
         this object.  Mangement stations should set this value with 
         caution.  Writing this value has dubious diagnostic or testing 
         purposes."
    REFERENCE   
        "SFF-8472 Rev 10.4, Table 3.17"
    ::= { sfpMonEntry 16 }

sfpStatus OBJECT IDENTIFIER
    ::= { sfpTables 7 }

sfpStatusTable OBJECT-TYPE
    SYNTAX      SEQUENCE OF SfpStatusEntry
    MAX-ACCESS  not-accessible
    STATUS      current
    DESCRIPTION 
        "This table provides the current system status of the SFP module."
    REFERENCE   
        "INF-8074"
    ::= { sfpStatus 1 }

sfpStatusEntry OBJECT-TYPE
    SYNTAX      SfpStatusEntry
    MAX-ACCESS  not-accessible
    STATUS      current
    DESCRIPTION 
        "Each conceptual row in this table corresponds to an SFP module 
         in the system.  Conceptual rows may neither be added nor 
         deleted from this table by management stations, but are 
         autonomously added or deleted by the managed system from 
         within."
    INDEX       { sfpModuleId }
    ::= { sfpStatusTable 1 }

SfpStatusEntry ::= SEQUENCE {
    sfpStatusEquipId                RowPointer,
    sfpStatusAdministrativeState    AdministrativeState,
    sfpStatusAvailabilityStatus     AvailabilityStatus,
    sfpStatusOperationalState       OperationalState,
    sfpStatusAlarmStatus            AlarmStatus,
    sfpStatusProceduralStatus       ProceduralStatus,
    sfpStandbyStatus                StandbyStatus,
    sfpStatusAlarms                 SfpAlarms,
    sfpStatusAlarmsHistory          SfpAlarms,
    sfpStatusWarnings               SfpAlarms,
    sfpStatusWarningsHistory        SfpAlarms
}

sfpStatusEquipId OBJECT-TYPE
    SYNTAX      RowPointer
    MAX-ACCESS  read-only
    STATUS      current
    DESCRIPTION 
        "Provides an equiment identifier following the RowPointer 
         textual convention.  The value of this column specifies the row 
         in the the SNMP table that represents the equipment associated 
         with the SFP/SFP+ module."
    REFERENCE   
        "SFF-8472, Diagnostic Monitoring Interface for Optical 
             Transceivers."
    ::= { sfpStatusEntry 1 }

sfpStatusAdministrativeState OBJECT-TYPE
    SYNTAX      AdministrativeState
    MAX-ACCESS  read-write
    STATUS      current
    DESCRIPTION 
        "Provides the administrative state of the SFP/SFP+ module in 
         accordance with ITU-T Rec. X.721 | ISO/IEC 10165-2 and the 
         AdministrativeState textual convention of the OPENSS7-SMI-MIB.
         This object controls the administrative state of the SFP/SFP+ 
         module and can have one of the following values:
         
         - locked(0), the SFP/SFP+ module is administratively prohibited 
           from providing service;
         
         - unlocked(1), the SFP/SFP+ module is administratively 
           permitted to provide service;
         
         - shuttingDown(2), the SFP/SFP+ module is gracefully 
           withdrawing form providing service.
         
         Setting this object to locked(0) results in the immediate 
         withdrawal from service of the SFP/SFP+ module.  This may 
         result in the abortive removal from service of the SFP/SFP+ 
         module.  Setting this object to shuttingDown(2) results in the 
         graceful withdrawal from service of the SFP/SFP+ module."
    REFERENCE   
        "ITU-T Rec. X.721 (1992) | ISO/IEC 10165-2 : 1992, 
               Attribute-ASN1Module.AdministrativeState.
         ITU-T Rec. X.731 (1992) | ISO/IEC 10164-2 : 1993, 
               Section 8.1.1.3."
    ::= { sfpStatusEntry 2 }

sfpStatusAvailabilityStatus OBJECT-TYPE
    SYNTAX      AvailabilityStatus
    MAX-ACCESS  read-only
    STATUS      current
    DESCRIPTION 
        "Indicates the availability status of the SFP/SFP+ module in 
         accordance with ITU-T Rec. X.721 | ISO/IEC 10165-2 and the 
         AvailabilityStatus textual convention of the OPENSS7-SMI-MIB.  
         The availability status is set-valued and the set-value may 
         contain any of the following:
         
         - inTest(0), the SFP/SFP+ module is undergoing a test 
           procedure;
         - failed(1), the SFP/SFP+ module has an internal fault that 
           prevents it from operating (the operational state is 
           disabled);
         - powerOff(2), the SFP/SFP+ module requires power to be applied 
           and is not powered on (the operational state is disabled);
         - offLine(3), the resource is off-line (the operational state 
           is disabled);
         - offDuty(4), the SFP/SFP+ module is off duty (the operational 
           state is enabled or disabled);
         - dependency(5), the SFP/SFP+ depends on another resource which 
           is not operational (the operational state is disabled);
         - degraded(6), the SFP/SFP+ module is degraded (the operational 
           state is enabled);
         - notInstalled(7), the SFP/SFP+ module is not installed (the 
           operational state is disabled);
         - logFull(8), not used."
    REFERENCE   
        "ITU-T Rec. X.721 (1992) | ISO/IEC 10165-2 : 1992, 
               Attribute-ASN1Module.AvailabilityStatus
         ITU-T Rec. X.731 (1992) | ISO/IEC 10164-2 : 1993, 
               Section 8.1.2.3."
    ::= { sfpStatusEntry 3 }

sfpStatusOperationalState OBJECT-TYPE
    SYNTAX      OperationalState
    MAX-ACCESS  read-only
    STATUS      current
    DESCRIPTION 
        "Indicates the operational state of the SFP/SFP+ module in 
         accordance with ITU-T Rec. X.721 | ISO/IEC 10165-2 and the 
         OperationalState textual convention of the OPENSS7-SMI-MIB.  
         The operational state can be one of the following:
         
         - disabled(0), the SFP/SFP+ module is totally inoperable and is 
           unable to provide service;
         - enabled(1), the SFP/SFP+ module is partially or fully 
           operable and available for use."
    REFERENCE   
        "ITU-T Rec. X.721 | ISO/IEC 10165-2, operationalState."
    ::= { sfpStatusEntry 4 }

sfpStatusAlarmStatus OBJECT-TYPE
    SYNTAX      AlarmStatus
    MAX-ACCESS  read-write
    STATUS      current
    DESCRIPTION 
        "
         underRepair(0) - 
         critical(1) - 
         major(2) - 
         minor(3) - 
         alarmOutstanding(4) - "
    REFERENCE   
        "ITU-T Rec. X.721 | ISO/IEC 10165-2, alarmStatus."
    ::= { sfpStatusEntry 5 }

sfpStatusProceduralStatus OBJECT-TYPE
    SYNTAX      ProceduralStatus
    MAX-ACCESS  read-only
    STATUS      current
    DESCRIPTION 
        "Indicates the procedural status of the SFP/SFP+ module in 
         accordance with ITU-T Rec. X.721 | ISO/IEC 10165-2 and the 
         ProceduralStatus textual convention of the OPENSS7-SMI-MIB.  
         The procedural status is set-valued and may contain any of the 
         following:
         
         - initializationRequired(0), the SFP/SFP+ module requires 
           management invoked initialization (the operational state is 
           disabled);
         - notInitialized(1), the SFP/SFP+ module initializes 
           autonomously but has not begun initialization (the 
           operational state is enabled or disabled);
         - initializing(2), the SFP/SFP+ module is initializing (the 
           operation state is enabled or disabled);
         - reporting(3), not used;
         - terminating(4), the SFP/SFP+ module is terminating."
    REFERENCE   
        "ITU-T Rec. X.721 | ISO/IEC 10165-2, proceduralStatus."
    ::= { sfpStatusEntry 6 }

sfpStandbyStatus OBJECT-TYPE
    SYNTAX      StandbyStatus
    MAX-ACCESS  read-only
    STATUS      current
    DESCRIPTION 
        "
         - hotStandby(0), the SFP/SFP+ module is not providing service, 
           but is operating in synchronism with another SFP/SFP+ module 
           that is backed-up (operational state, enabled; administrative 
           state, unlocked; availability status, off-line);
         - coldStandby(1), the SFP/SFP+ module backs up another 
           SFP/SFP+ module but is not synchronized with that SFP/SFP+ 
           module (operational state, enabled or disabled; 
           administrative state, locked or unlocked; procedural status, 
           not initialized or initialization required; availability 
           status, off-line);
         - providingService(2), the SFP/SFP+ module is providing service 
           and is backing up another SFP/SFP+ module (operational state, 
           enabled; administrative state, unlocked; availabiltiy status, 
           online)."
    REFERENCE   
        "ITU-T Rec. X.721 | ISO/IEC 10165-2, standbyStatus."
    ::= { sfpStatusEntry 7 }

sfpStatusAlarms OBJECT-TYPE
    SYNTAX      SfpAlarms
    MAX-ACCESS  read-only
    STATUS      current
    DESCRIPTION 
        "This object is set-valued and contains indications of which 
         alarm thresholds have been crossed for which monitored values.  
         Monitored values include temperature, Vcc voltage, transmitter 
         bias current, transmitted power, and received power.  The set 
         may include zero or more of the following:
         
         - tempHi(0), the temperature has exceeded the high threshold;
         - tempLo(1), the temperature was beneath the low threshold;
         - vccHi(2), the supply voltage has exceeded the high threshold;
         - vccLo(3), the supply voltage was beneath the low threshold;
         - txBiasHi(4), the Tx bias has exceeded the high threshold;
         - txBiasLo(5), the Tx bias was beneath the low threshold;
         - txPowerHi(6), the Tx power has exceeded the high threshold;
         - txPowerLo(7), the Tx power was beneath the low threshold;
         - rxPowerHi(8), the Rx power has exceeded the high threshold; 
         - rxPowerLo(9), the Rx power was beneath the low threshold.
         
         This set-value is read-only.  When read, the set-value contains 
         the current alarm conditions.  Members are added to, and 
         removed from, the set by the agent as the thresholds bounds are 
         crossed.
         
         An empty set indicates that there are no alarm conditions and 
         that the transceiver is within acceptable operating bounds.  A 
         non-empty set indicates an alarm condition and a corresponding 
         major or critical alarm condition will result."
    REFERENCE   
        "SFF-8472, Diagnostic Monitoring Interface for Optical 
             Transceivers."
    ::= { sfpStatusEntry 8 }

sfpStatusAlarmsHistory OBJECT-TYPE
    SYNTAX      SfpAlarms
    MAX-ACCESS  read-only
    STATUS      current
    DESCRIPTION 
        "This object is set-valued and contains indications of which 
         alarm thresholds have been crossed for which monitored values.  
         Monitored values include temperature, supply voltage, 
         tranmitter bias current, transmitted power, and received power.  
         The set may include zero or more of the following:
         
         - tempHi(0), the temperature has exceeded the high threshold;
         - tempLo(1), the temperature was beneath the low threshold;
         - vccHi(2), the supply voltage has exceeded the high threshold;
         - vccLo(3), the supply voltage was beneath the low threshold;
         - txBiasHi(4), the Tx bias has exceeded the high threshold;
         - txBiasLo(5), the Tx bias was beneath the low threshold;
         - txPowerHi(6), the Tx power has exceeded the high threshold;
         - txPowerLo(7), the Tx power was beneath the low threshold;
         - rxPowerHi(8), the Rx power has exceeded the high threshold; 
         - rxPowerLo(9), the Rx power was beneath the low threshold.
         
         Members are added to this set by the agent as a threshold is 
         crossed.  Members are removed from this set only by management 
         stations, by clearing the corresponding alarm conditions.  
         Historical values should survive an agent reboot.
         
         This object may be used by management stations investigating 
         the causes of a prior alarm condition."
    REFERENCE   
        "SFF-8472 Rev 10.4, Table 16"
    ::= { sfpStatusEntry 9 }

sfpStatusWarnings OBJECT-TYPE
    SYNTAX      SfpAlarms
    MAX-ACCESS  read-only
    STATUS      current
    DESCRIPTION 
        "This object is set-valued and contains indications of which 
         alarm thresholds have been crossed for which monitored values.  
         Monitored values include temperature, supply voltage, 
         transmitter bias current, transmitted power, and received 
         power.  The set may include zero ore more of the following:
         
         - tempHi(0), the temperature has exceeded the high threshold;
         - tempLo(1), the temperature was beneath the low threshold;
         - vccHi(2), the supply voltage has exceeded the high threshold;
         - vccLo(3), the supply voltage was beneath the low threshold;
         - txBiasHi(4), the Tx bias has exceeded the high threshold;
         - txBiasLo(5), the Tx bias was beneath the low threshold;
         - txPowerHi(6), the Tx power has exceeded the high threshold;
         - txPowerLo(7), the Tx power was beneath the low threshold;
         - rxPowerHi(8), the Rx power has exceeded the high threshold; 
         - rxPowerLo(9), the Rx power was beneath the low threshold.
         
         The set-value is read-only.  When read, the set-value contains 
         the current warning conditions.  Members are added to, and 
         removed from, the set by the agent as the threshold bounds are 
         crossed.
         
         An empty set indicates that there are no warning conditions and 
         that the transceiver is within nominal operating bounds.  A 
         non-empty set inidicates a warning condition and a 
         corresponding minor alarm condition will result."
    REFERENCE   
        "SFF-8472 Rev 10.4, Table 16"
    ::= { sfpStatusEntry 10 }

sfpStatusWarningsHistory OBJECT-TYPE
    SYNTAX      SfpAlarms
    MAX-ACCESS  read-only
    STATUS      current
    DESCRIPTION 
        "This object is set-valued and contains indications of which 
         alarm thresholds have been crossed for which monitored values.  
         Monitored values include temperature, supply voltage, 
         transmitter bias current, transmitted power, and received 
         power.  The set may include zero or more of the following:
         
         - tempHi(0), the temperature has exceeded the high threshold;
         - tempLo(1), the temperature was beneath the low threshold;
         - vccHi(2), the supply voltage has exceeded the high threshold;
         - vccLo(3), the supply voltage was beneath the low threshold;
         - txBiasHi(4), the Tx bias has exceeded the high threshold;
         - txBiasLo(5), the Tx bias was beneath the low threshold;
         - txPowerHi(6), the Tx power has exceeded the high threshold;
         - txPowerLo(7), the Tx power was beneath the low threshold;
         - rxPowerHi(8), the Rx power has exceeded the high threshold; 
         - rxPowerLo(9), the Rx power was beneath the low threshold.
         
         Members are added to this set by the agent as a threshold is 
         crossed.  Members are removed from this set only by management 
         stations, by clearing the corresponding alarm conditions.  
         Historical values should survive an agent reboot.
         
         This object may be used by management stations investigating 
         the causes of a prior alarm condition."
    REFERENCE   
        "SFF-8472 Rev 10.4, Table 16"
    ::= { sfpStatusEntry 11 }

sfpScalars OBJECT IDENTIFIER
    ::= { sfpObjects 2 }

sfpDefaults OBJECT IDENTIFIER
    ::= { sfpScalars 1 }

sfpNotifs OBJECT IDENTIFIER
    ::= { sfpObjects 3 }

sfpOids OBJECT IDENTIFIER
    ::= { sfpObjects 4 }

sfpProbableCauses OBJECT IDENTIFIER
    ::= { sfpOids 1 }

sfpSpecificProblems OBJECT IDENTIFIER
    ::= { sfpOids 2 }

temperatureHi OBJECT-IDENTITY
    STATUS      current
    DESCRIPTION 
        "Specific Problem.  This object identity is used with 
         probableCause in the equipmentAlarm notification.  Specific 
         Problem = 1 (temperatureHi) which represents a high temperature 
         threshold warning or alarm.
         
         Probable Cause = temperatureUnacceptable, Perceived Severity = 
         warning/minor/major/cleared, Specific Problem = 1 
         (temperatureHi)"
    REFERENCE   
        "SFF-8472 Rec 10.4, Table 16"
    ::= { sfpSpecificProblems 1 }

temperatureLo OBJECT-IDENTITY
    STATUS      current
    DESCRIPTION 
        "Specific Problem.  This object identity is used with 
         probableCause in the equipmentAlarm notification.  Specific 
         Problem = 2 (temperatureLo) which represents a low temperature 
         threshold warning or alarm.
         
         Probable Cause = temperatureUnacceptable, Perceived Severity = 
         warning/minor/major/cleared, Specific Problem = 1 
         (temperatureLo)"
    REFERENCE   
        "SFF-8472 Rec 10.4, Table 16"
    ::= { sfpSpecificProblems 2 }

voltageHi OBJECT-IDENTITY
    STATUS      current
    DESCRIPTION 
        "Specific Problem.  This object identity is used with 
         probableCause in the equipmentAlarm notification.  Specific 
         Problem = 3 (voltageHi) which represents a high supply voltage  
         threshold warning or alarm.
         
         Probable Cause = powerProblem, Perceived Severity = 
         warning/minor/major/cleared"
    REFERENCE   
        "SFF-8472 Rec 10.4, Table 16"
    ::= { sfpSpecificProblems 3 }

voltageLo OBJECT-IDENTITY
    STATUS      current
    DESCRIPTION 
        "Specific Problem.  This object identity is used with 
         probableCause in the equipmentAlarm notification.  Specific 
         Problem = 4 (voltageLo) which represents a low supply voltage  
         threshold warning or alarm.
         
         Probable Cause = powerProblem, Perceived Severity = 
         warning/minor/major/cleared"
    REFERENCE   
        "SFF-8472 Rec 10.4, Table 16"
    ::= { sfpSpecificProblems 4 }

txBiasHi OBJECT-IDENTITY
    STATUS      current
    DESCRIPTION 
        "Specific Problem.  This object identity is used with 
         probableCause in the equipmentAlarm notification.  Specific 
         Problem = 5 (txBiasLo) which represents a high transmitter bias 
         current threshold warning or alarm.
         
         probableCause = thresholdCrossed, Perceived Severity = 
         warning/minor/major/cleared"
    REFERENCE   
        "SFF-8472 Rec 10.4, Table 16"
    ::= { sfpSpecificProblems 5 }

txBiasLo OBJECT-IDENTITY
    STATUS      current
    DESCRIPTION 
        "Specific Problem.  This object identity is used with 
         probableCause in the equipmentAlarm notification.  Specific 
         Problem = 6 (txBiasHi) which represents a low transmitter bias 
         current threshold warning or alarm.
         
         probableCause = thresholdCrossed, Perceived Severity = 
         warning/minor/major/cleared"
    REFERENCE   
        "SFF-8472 Rec 10.4, Table 16"
    ::= { sfpSpecificProblems 6 }

txPowerHi OBJECT-IDENTITY
    STATUS      current
    DESCRIPTION 
        "Specific Problem.  This object identity is used with 
         probableCause in the equipmentAlarm notification.  Specific 
         Problem = 7 (txPowerHi) which represents a high transmitter 
         power threshold warning or alarm.
         
         Probable Cause = transmitFailure, Perceived Severity = 
         warning/minor/major/cleared"
    REFERENCE   
        "SFF-8472 Rec 10.4, Table 16"
    ::= { sfpSpecificProblems 7 }

txPowerLo OBJECT-IDENTITY
    STATUS      current
    DESCRIPTION 
        "Specific Problem.  This object identity is used with 
         probableCause in the equipmentAlarm notification.  Specific 
         Problem = 8 (txPowerLo) which represents a low transmitter 
         power threshold warning or alarm.
         
         Probable Cause = transmitFailure, Perceived Severity = 
         warning/minor/major"
    REFERENCE   
        "SFF-8472 Rec 10.4, Table 16"
    ::= { sfpSpecificProblems 8 }

rxPowerHi OBJECT-IDENTITY
    STATUS      current
    DESCRIPTION 
        "Specific Problem.  This object identity is used with 
         probableCause in the equipmentAlarm notification.  Specific 
         Problem = 9 (rxPowerHi) which represents a high receiver power 
         threshold warning or alarm.
         
         Probable Cause = receiveFailure, Perceived Severity = 
         warning/minor/major/cleared"
    REFERENCE   
        "SFF-8472 Rec 10.4, Table 16"
    ::= { sfpSpecificProblems 9 }

rxPowerLo OBJECT-IDENTITY
    STATUS      current
    DESCRIPTION 
        "Specific Problem.  This object identity is used with 
         probableCause in the equipmentAlarm notification.  Specific 
         Problem = 10 (rxPowerLo) which represents a low receiver power 
         threshold warning or alarm.
         
         Probable Cause = receiveFailure, Perceived Severity = 
         warning/minor/major/cleared"
    REFERENCE   
        "SFF-8472 Rec 10.4, Table 16"
    ::= { sfpSpecificProblems 10 }

rxLossOfSignal OBJECT-IDENTITY
    STATUS      current
    DESCRIPTION 
        "Specific Problem.  This object identity is used with 
         specificProblems in the equipmentAlarm notification.  Specific 
         Problem = 11 (rxLossOfSignal) represents a loss of received 
         signal event.
         
         The agent generates this alarm by monitoring the RX_LOS pin on 
         the SFP module, or the equivalent bit within the 2-wire address 
         space under the Diagnostic Monitoring Interface (DMI) for 
         Optical Modules (SFF-8472).  The assertion of the RX_LOS pin 
         indicates that the received optical power is below the 
         worst-case receiver sensitivity (as defined by the standard in 
         use); deassertion indicates normal operation.
         
         Probable Cause = lossOfSignal, Perceived Severity = 
         minor/major/cleared"
    REFERENCE   
        "SFF-8472 Rev. 10.4, Table 3.17,
         INF-8074, Table 1, Note 5."
    ::= { sfpSpecificProblems 11 }

txFailure OBJECT-IDENTITY
    STATUS      current
    DESCRIPTION 
        "Specific Problem.  This object identity is used with 
         specificProblems in the equipmentAlarm notification.  Specific 
         Problem = 12 (txFault) represents a transmitter fault 
         condition.
         
         The assertion of the TxFault pin indicates a detected laser 
         fault of some kind; deassertion indicates normal operation.
         
         Probable Cause = transmitterFailure, Perceived Severity = 
         minor/major/cleared"
    REFERENCE   
        "SFF-8472 Rev 10.4, Table 3.17,
         INF-8074, Table 1, Note 1."
    ::= { sfpSpecificProblems 12 }

sfpSpecificExtensions OBJECT IDENTIFIER
    ::= { sfpOids 3 }

sfpProbableCauses2 OBJECT IDENTIFIER
    ::= { sfpOids 4 }

sfpConformance OBJECT IDENTIFIER
    ::= { sfpMIB 2 }

sfpCompliance OBJECT IDENTIFIER
    ::= { sfpConformance 1 }

sfpGroups OBJECT IDENTIFIER
    ::= { sfpConformance 2 }

sfpModulePackage OBJECT-GROUP
    OBJECTS     { sfpModuleType, sfpModuleExtendedType, 
                  sfpModuleConnectorType, sfpModuleTransceiver, 
                  sfpModuleCompliance, sfpModuleEncoding, 
                  sfpModuleNormalBitRate, sfpModuleRateIdentifier, 
                  sfpModuleLinkLength9125k, sfpModuleLinkLength9125m, 
                  sfpModuleLinkLength50125m, sfpModuleLinkLength625125m, 
                  sfpModuleLinkLengthCopper, sfpModuleVendorName, 
                  sfpModuleVendorOUI, sfpModulePartNumber, 
                  sfpModuleRevisionLevel, sfpModuleLaserWavelength, 
                  sfpModulePassiveCableCompliance, 
                  sfpModuleActiveCableCompliance, sfpModuleOptions, 
                  sfpModuleUpperBitRate, sfpModuleLowerBitRate, 
                  sfpModuleVendorSerialNo, sfpModuleManufactureDate, 
                  sfpStatusEquipId, sfpStatusAdministrativeState, 
                  sfpStatusAvailabilityStatus, sfpStatusOperationalState, 
                  sfpStatusAlarmStatus, sfpStatusProceduralStatus, 
                  sfpStandbyStatus }
    STATUS      current
    DESCRIPTION 
        "This object group provides support for the 'Small Formfactor 
         Pluggable (SFP)', INF-8074i, specification."
    REFERENCE   
        "INF-8074i"
    ::= { sfpGroups 1 }

sfpRateSelectPackage OBJECT-GROUP
    OBJECTS     { sfpMonRateSelect, sfpMonSoftRateSelect, 
                  sfpMonSoftRateSelect1 }
    STATUS      current
    DESCRIPTION 
        "This object group provides support for the rate selection 
         portions of the 'SFP Rate and Application Select', SFF-8079, 
         specification."
    REFERENCE   
        "SFF-8079"
    ::= { sfpGroups 2 }

sfpApplicationSelectPackage OBJECT-GROUP
    OBJECTS     { sfpApplControlMode, sfpApplTableLength, 
                  sfpApplTableSelect, sfpApplSelectValue, 
                  sfpApplCodeSelect, sfpApplCodeCategory, 
                  sfpApplCodeValue, sfpMonApplSelect }
    STATUS      current
    DESCRIPTION 
        "This object group provides support for the application 
         selection portions of the 'SFP Rate and Application Select', 
         SFF-8079, specification."
    REFERENCE   
        "SFF-8079"
    ::= { sfpGroups 3 }

sfpRxLOSPackage OBJECT-GROUP
    OBJECTS     { sfpMonRxLossOfSignal }
    STATUS      current
    DESCRIPTION 
        "This object group provides support for the monitoring of the 
         RX_LOS pin in accordance with the 'Diagnostic Monitoring 
         Interface (DMI) for Optical Transceivers', SFF-8472."
    REFERENCE   
        "SFF-8472"
    ::= { sfpGroups 4 }

sfpPowerLevelPackage OBJECT-GROUP
    OBJECTS     { sfpMonPowerLevel, sfpMonSoftPowerLevel }
    STATUS      current
    DESCRIPTION 
        "This object group provides support for the monitoring and 
         setting of the power level in accordance with the 'Enhanced 
         Small Formfactor Pluggable (SFP+)', SFF-8431, and 'Diagnostic 
         Monitoring Interface (DMI) for Optical Transceivers', 
         SFF-8472, specifications."
    REFERENCE   
        "SFF-8431, SFF-8472"
    ::= { sfpGroups 5 }

sfpTxDisablePackage OBJECT-GROUP
    OBJECTS     { sfpMonTxDisable, sfpMonSoftTxDisable }
    STATUS      current
    DESCRIPTION 
        "This object group provides support for the monitoring and 
         setting of the TX_DISABLE pin in accordance with the 
         'Diagnostic Monitoring Interface (DMI) for Optical 
         Transceivers', SFF-8472."
    REFERENCE   
        "SFF-8472"
    ::= { sfpGroups 6 }

sfpTxFaultPackage OBJECT-GROUP
    OBJECTS     { sfpMonTxFaultState }
    STATUS      current
    DESCRIPTION 
        "This object group provides support for the monitoring of the 
         TX_FAULT pin in accordance with the 'Diagnostic Monitoring 
         Interface (DMI) for Optical Transceivers', SFF-8472."
    REFERENCE   
        "SFF-8472"
    ::= { sfpGroups 7 }

sfpDiagMonitorInterfacePackage OBJECT-GROUP
    OBJECTS     { sfpDiagType, sfpDiagOptions, sfpDiagDmiCompliance, 
                  sfpDiagTempHiAlarm, sfpDiagTempLoAlarm, 
                  sfpDiagTempHiWarning, sfpDiagTempLoWarning, 
                  sfpDiagVoltHiAlarm, sfpDiagVoltLoAlarm, 
                  sfpDiagVoltHiWarning, sfpDiagVoltLoWarning, 
                  sfpDiagBiasHiAlarm, sfpDiagBiasLoAlarm, 
                  sfpDiagBiasHiWarning, sfpDiagBiasLoWarning, 
                  sfpDiagTxPowerHiAlarm, sfpDiagTxPowerLoAlarm, 
                  sfpDiagTxPowerHiWarning, sfpDiagTxPowerLoWarning, 
                  sfpDiagRxPowerHiAlarm, sfpDiagRxPowerLoAlarm, 
                  sfpDiagRxPowerHiWarning, sfpDiagRxPowerLoWarning, 
                  sfpMonTemp, sfpMonVolt, sfpMonBias, sfpMonTxPower, 
                  sfpMonRxPower, sfpMonDataReadyBar, sfpStatusAlarms, 
                  sfpStatusAlarmsHistory, sfpStatusWarnings, 
                  sfpStatusWarningsHistory }
    STATUS      current
    DESCRIPTION 
        "This object group provides basic support for the 'Diagnostic 
         Monitoring Interface (DMI) for Optical Transceivers', SFF-8472."
    REFERENCE   
        "SFF-8472"
    ::= { sfpGroups 8 }

sfpDMIExternalCalibrationPackage OBJECT-GROUP
    OBJECTS     { sfpCalibRxPwr0, sfpCalibRxPwr1, sfpCalibRxPwr2, 
                  sfpCalibRxPwr3, sfpCalibRxPwr4, sfpCalibTxISlope, 
                  sfpCalibTxIOffset, sfpCalibTxPwrSlope, 
                  sfpCalibTxPwrOffset, sfpCalibTSlope, sfpCalibTOffset, 
                  sfpCalibVSlope, sfpCalibVOffset }
    STATUS      current
    DESCRIPTION 
        "This object group provides support for external calibration of 
         SFP/SFP+ modules."
    REFERENCE   
        "SFF-8472"
    ::= { sfpGroups 9 }

sfpINF8074Compliance MODULE-COMPLIANCE
    STATUS      current
    DESCRIPTION 
        "This compliance provides mandatory requirements for 
         implementations supporting 'Small Formfactor Pluggable (SFP) 
         Specifciation', INF-8074i, modules."

    MODULE      -- this module

        MANDATORY-GROUPS        { sfpModulePackage }

        GROUP   sfpRateSelectPackage
        DESCRIPTION   
              "PRESENT IF a module also supports the rate selection portions 
               of 'SFP Rate and Application Selection, SFF-8079'."

        GROUP   sfpApplicationSelectPackage
        DESCRIPTION   
              "PRESENT IF a module also supports the application selection 
               portions of 'SFP Rate and Application Selection, SFF-8079'."

        GROUP   sfpDiagMonitorInterfacePackage
        DESCRIPTION   
              "PRESENT IF a module also supports the 'Diagnostic Monitoring 
               Interface (DMI) for Optical Transceivers', SFF-8472."

        GROUP   sfpDMIExternalCalibrationPackage
        DESCRIPTION   
              "PRESENT IF the module also supports the optional external 
               calibration method of the 'Diagnostic Monitoring Interface 
               (DMI) for Optical Transceivers', SFF-8472."

        GROUP   sfpRxLOSPackage
        DESCRIPTION   
              "PRESENT IF the module also supports the RX_LOS pin monitoring 
               and software RX Loss Of Signal assertion of 'Diagnostic 
               Monitoring Interface (DMI) for Optical Transceivers', 
               SFF-8472."

        GROUP   sfpTxDisablePackage
        DESCRIPTION   
              "PRESENT IF the module also supports the TX_DISABLE pin 
               monitoring and software Tx Disable assertion of 'Diagnostic 
               Monitoring Interface (DMI) for Optical Transceivers', 
               SFF-8472."

        GROUP   sfpTxFaultPackage
        DESCRIPTION   
              "PRESENT IF the module also supports the TX_FAULT pin monitoring 
               of 'Diagnostic Monitoring Interface (DMI) for Optical 
               Transceivers', SFF-8472."

        GROUP   sfpPowerLevelPackage
        DESCRIPTION   
              "PRESENT IF a module also supports the SFP+ specification, 
               SFF-8431."

    MODULE OPENSS7-SMI-MIB

        GROUP   smiConditionalNotificationsGroup
        DESCRIPTION   
              "PRESENT IF the equipmentAlarm NOTIFICATION defined in 'ITU-T 
               Rec. X.721 (1992) | ISO/IEC 10165-2 : 1992' is supported by an 
               instance of this class."

    ::= { sfpCompliance 1 }

sfpSFF8079Compliance MODULE-COMPLIANCE
    STATUS      current
    DESCRIPTION 
        "This compliance adds mandatory requirements for implementation 
         supporting SFP Rate and Application Selection, SFF-8079."

    MODULE      -- this module

        MANDATORY-GROUPS        { sfpModulePackage, sfpRateSelectPackage, 
                  sfpApplicationSelectPackage }

        GROUP   sfpPowerLevelPackage
        DESCRIPTION   
              "PRESENT IF a module also supports the SFP+ specification, 
               SFF-8431."

        GROUP   sfpDiagMonitorInterfacePackage
        DESCRIPTION   
              "PRESENT IF a module also supports the 'Diagnostic Monitoring 
               Interface (DMI) for Optical Transceivers', SFF-8472."

        GROUP   sfpDMIExternalCalibrationPackage
        DESCRIPTION   
              "PRESENT IF the module also supports the optional external 
               calibration method of the 'Diagnostic Monitoring Interface 
               (DMI) for Optical Transceivers', SFF-8472."

        GROUP   sfpRxLOSPackage
        DESCRIPTION   
              "PRESENT IF the module also supports the RX_LOS pin monitoring 
               and software RX Loss Of Signal assertion of 'Diagnostic 
               Monitoring Interface (DMI) for Optical Transceivers', 
               SFF-8472."

        GROUP   sfpTxDisablePackage
        DESCRIPTION   
              "PRESENT IF the module also supports the TX_DISABLE pin 
               monitoring and software Tx Disable assertion of 'Diagnostic 
               Monitoring Interface (DMI) for Optical Transceivers', 
               SFF-8472."

        GROUP   sfpTxFaultPackage
        DESCRIPTION   
              "PRESENT IF the module also supports the TX_FAULT pin monitoring 
               of 'Diagnostic Monitoring Interface (DMI) for Optical 
               Transceivers', SFF-8472."

    MODULE OPENSS7-SMI-MIB

        GROUP   smiConditionalNotificationsGroup
        DESCRIPTION   
              "PRESENT IF the equipmentAlarm NOTIFICATION defined in 'ITU-T 
               Rec. X.721 (1992) | ISO/IEC 10165-2 : 1992' is supported by an 
               instance of this class."

    ::= { sfpCompliance 2 }

sfpSFF8431Compliance MODULE-COMPLIANCE
    STATUS      current
    DESCRIPTION 
        "This compliance adds mandatory requirements for implementations 
         supporting Enhanced Small Form Factor Pluggable Module SFP+, 
         SFF-8431."

    MODULE      -- this module

        MANDATORY-GROUPS        { sfpModulePackage, sfpRateSelectPackage, 
                  sfpApplicationSelectPackage, sfpPowerLevelPackage }

        GROUP   sfpDiagMonitorInterfacePackage
        DESCRIPTION   
              "PRESENT IF a module also supports the 'Diagnostic Monitoring 
               Interface (DMI) for Optical Transceivers', SFF-8472."

        GROUP   sfpDMIExternalCalibrationPackage
        DESCRIPTION   
              "PRESENT IF the module also supports the optional external 
               calibration method of the 'Diagnostic Monitoring Interface 
               (DMI) for Optical Transceivers', SFF-8472."

        GROUP   sfpRxLOSPackage
        DESCRIPTION   
              "PRESENT IF the module also supports the RX_LOS pin monitoring 
               and software RX Loss Of Signal assertion of 'Diagnostic 
               Monitoring Interface (DMI) for Optical Transceivers', 
               SFF-8472."

        GROUP   sfpTxDisablePackage
        DESCRIPTION   
              "PRESENT IF the module also supports the TX_DISABLE pin 
               monitoring and software Tx Disable assertion of 'Diagnostic 
               Monitoring Interface (DMI) for Optical Transceivers', 
               SFF-8472."

        GROUP   sfpTxFaultPackage
        DESCRIPTION   
              "PRESENT IF the module also supports the TX_FAULT pin monitoring 
               of 'Diagnostic Monitoring Interface (DMI) for Optical 
               Transceivers', SFF-8472."

    MODULE OPENSS7-SMI-MIB

        GROUP   smiConditionalNotificationsGroup
        DESCRIPTION   
              "PRESENT IF the equipmentAlarm NOTIFICATION defined in 'ITU-T 
               Rec. X.721 (1992) | ISO/IEC 10165-2 : 1992' is supported by an 
               instance of this class."

    ::= { sfpCompliance 3 }

sfpSFF8472Compliance MODULE-COMPLIANCE
    STATUS      current
    DESCRIPTION 
        "This compliance adds mandatory requirements for implementation 
         supporting Diagnostic Monitoring Interface for Optical 
         Transceivers, SFF-8472."

    MODULE      -- this module

        MANDATORY-GROUPS        { sfpModulePackage, 
                  sfpDiagMonitorInterfacePackage }

        GROUP   sfpDMIExternalCalibrationPackage
        DESCRIPTION   
              "PRESENT IF a module also supports external calibration per 
               SFF-8472."

        GROUP   sfpRateSelectPackage
        DESCRIPTION   
              "PRESENT IF a module also supports the rate selection portions 
               of 'SFP Rate and Application Selection, SFF-8079'."

        GROUP   sfpApplicationSelectPackage
        DESCRIPTION   
              "PRESENT IF a module also supports the application selection 
               portions of 'SFP Rate and Application Selection, SFF-8079'."

        GROUP   sfpRxLOSPackage
        DESCRIPTION   
              "PRESENT IF a module also supports optional monitoring of the 
               RX_LOS pin per SFF-8472."

        GROUP   sfpPowerLevelPackage
        DESCRIPTION   
              "PRESENT IF a module also supports SFF-8431 and the monitoring 
               and setting of power level per SFF-8472."

        GROUP   sfpTxDisablePackage
        DESCRIPTION   
              "PRESENT IF a module supports the optional monitoring and soft 
               setting of TX_DISABLE per SFF-8472."

        GROUP   sfpTxFaultPackage
        DESCRIPTION   
              "PRESENT IF a module supports the optional monitoring of the 
               TX_FAULT pin."

        OBJECT  sfpApplTableSelect
        MIN-ACCESS  read-only
        DESCRIPTION   
              "It is not necessary that the implementation be able to change 
               the application selection."

        OBJECT  sfpMonSoftRateSelect
        MIN-ACCESS  read-only
        DESCRIPTION   
              "It is not necessary that the implementation be able to set the 
               software setting of rate selection."

        OBJECT  sfpMonSoftRateSelect1
        MIN-ACCESS  read-only
        DESCRIPTION   
              "It is not necessary that the implementation be able to set the 
               software setting of rate selection (RS(1) or Application Select 
               [1])."

        OBJECT  sfpMonSoftPowerLevel
        MIN-ACCESS  read-only
        DESCRIPTION   
              "It is not necessary that the implementation be able to set the 
               power level."

        OBJECT  sfpMonSoftTxDisable
        MIN-ACCESS  read-only
        DESCRIPTION   
              "It is not necessary that the implementation be able to set the 
               software setting of transmitter disable."

        OBJECT  sfpStatusAdministrativeState
        MIN-ACCESS  read-only
        DESCRIPTION   
              "It is not necessary that the implementation be able to set the 
               administrative state."

        OBJECT  sfpStatusAlarmStatus
        MIN-ACCESS  read-only
        DESCRIPTION   
              "It is not necessary that the implementation be able to set or 
               clear the alarm status."

    MODULE OPENSS7-SMI-MIB

        GROUP   smiConditionalNotificationsGroup
        DESCRIPTION   
              "PRESENT IF the equipmentAlarm NOTIFICATION defined in 'ITU-T 
               Rec. X.721 (1992) | ISO/IEC 10165-2 : 1992' is supported by an 
               instance of this class."

    ::= { sfpCompliance 4 }

END -- end of module OPENSS7-SFP-MIB.
