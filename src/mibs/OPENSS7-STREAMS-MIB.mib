-- vim: ft=mib comments=\f\:\",\b\:\-\-,\:\-\-,\f\b\:-,\f\b\:· fo+=tcqlornw tw=64 nocin nosi sts=4 sw=4 et
-- =============================================================================
-- 
-- @(#) src/mibs/OPENSS7-STREAMS-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-STREAMS-MIB DEFINITIONS ::= BEGIN

IMPORTS
    openss7Modules
        FROM OPENSS7-SMI
    MODULE-COMPLIANCE, OBJECT-GROUP
        FROM SNMPv2-CONF
    Counter32, Gauge32, Integer32, MODULE-IDENTITY, OBJECT-TYPE, 
    Unsigned32
        FROM SNMPv2-SMI
    RowStatus, TEXTUAL-CONVENTION, TimeInterval, TruthValue
        FROM SNMPv2-TC;

strMIB MODULE-IDENTITY
    LAST-UPDATED "201106270546Z"
    ORGANIZATION 
        "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         mailto:bidulock@openss7.org"
    DESCRIPTION 
        "This MIB provides configuration and status information 
         for a STREAMS subsystem.
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201106270546Z"
    DESCRIPTION 
        "Passes smilint and reformatted using smidump."
    REVISION    "200901161403Z"
    DESCRIPTION 
        "Reindexed strMod tables on name instead of module id."
    REVISION    "200901151746Z"
    DESCRIPTION 
        "Additional spelling corrections."
    REVISION    "200810070142Z"
    DESCRIPTION 
        "Made strStrhold a TruthValue.  Also more spelling 
         corrections."
    REVISION    "200810052305Z"
    DESCRIPTION 
        "Corrected default values and spelling corrections."
    REVISION    "200710010804Z"
    DESCRIPTION 
        "This is the first version of this MIB."
    ::= { openss7Modules 1 }


StreamsModuleName ::= TEXTUAL-CONVENTION
    DISPLAY-HINT "1a"
    STATUS      current
    DESCRIPTION 
        "This textual convention describes a STREAMS module 
         name.  STREAMS module names can be restricted by some 
         implementations to as few as 8 characters in length.  
         ASCII characters are used with no interior whitespace.  
         The STREAMS module name corresponds to the actual name 
         of a STREAMS module or driver."
    SYNTAX      OCTET STRING (SIZE(1..8))

StreamsModuleList ::= TEXTUAL-CONVENTION
    DISPLAY-HINT "1a"
    STATUS      current
    DESCRIPTION 
        "This textual convention describes a STREAMS module 
         list.  A STREAMS module list is a list of STREAMS 
         module names following the StreamsModuleName textual 
         convention or the special name '[anchor]', separated by 
         whitespace, with no leading or trailing whitespace."
    SYNTAX      OCTET STRING (SIZE(0..255))

StreamsModuleQueues ::= TEXTUAL-CONVENTION
    STATUS      current
    DESCRIPTION 
        "This textual convention describes the STREAMS module 
         queues to which a module_info or module_stats structure 
         applies.  STREAMS modules and drivers have an upper 
         multiplex read and write queue (rq, wq) and STREAMS 
         multiplexing drivers also have a lower multiplex read 
         and write queue (muxrq, muxwq).  A particular structure 
         can apply to one or more queues."
    SYNTAX      BITS { rq(0), wq(1), muxrq(2), muxwq(3) }

strNotifications OBJECT IDENTIFIER
    ::= { strMIB 0 }

strObjects OBJECT IDENTIFIER
    ::= { strMIB 1 }

strTables OBJECT IDENTIFIER
    ::= { strObjects 1 }

strMod OBJECT IDENTIFIER
    ::= { strTables 1 }

strModTable OBJECT-TYPE
    SYNTAX      SEQUENCE OF StrModEntry
    MAX-ACCESS  not-accessible
    STATUS      current
    DESCRIPTION 
        "Provides a table of modules and drivers that provides 
         some information about their initial packet sizes and 
         water marks as well as providing an index for an 
         auxillary statistics table."
    REFERENCE   
        "scls(8)"
    ::= { strMod 1 }

strModEntry OBJECT-TYPE
    SYNTAX      StrModEntry
    MAX-ACCESS  not-accessible
    STATUS      current
    DESCRIPTION 
        "An entry in the STREAMS modules table for one driver or 
         module.  Each table entry is indexed by the module 
         identifier that is the STREAMS module identifier that 
         appears in the mi_idnum field of the module_info(9) 
         STREAMS structure."
    REFERENCE   
        "scls(8)"
    INDEX       { strModName }
    ::= { strModTable 1 }

StrModEntry ::= SEQUENCE {
    strModName          StreamsModuleName,
    strModIdnum         Unsigned32,
    strModType          INTEGER,
    strModMajor         Unsigned32,
    strModRowStatus     RowStatus
}

strModName OBJECT-TYPE
    SYNTAX      StreamsModuleName
    MAX-ACCESS  not-accessible
    STATUS      current
    DESCRIPTION 
        "Indicates the name of the STREAMS driver or module.  
         This is the module name that appears in the mi_idname 
         field of the module_info(9) STREAMS structure for the 
         module or driver.  It uses the StreamsModuleName 
         textual convention as STREAMS module names are limited 
         to FMNAMESZ in length.  Once this object is created in 
         an entry, it becomes read-only until it is destroyed."
    REFERENCE   
        "scls(8)"
    ::= { strModEntry 1 }

strModIdnum OBJECT-TYPE
    SYNTAX      Unsigned32 (0..16383)
    MAX-ACCESS  read-only
    STATUS      current
    DESCRIPTION 
        "Indicates the driver or module STREAMS module id.  The 
         STREAMS module id is unique within the entire system 
         and is used as an index to this and other tables.  This 
         is the module identifier that appears in the mi_idnum 
         field of the module_info(9) STREAMS structure for the 
         module or driver."
    REFERENCE   
        "scls(8)"
    ::= { strModEntry 2 }

strModType OBJECT-TYPE
    SYNTAX      INTEGER { module(1), driver(2) }
    MAX-ACCESS  read-only
    STATUS      current
    DESCRIPTION 
        "Indicates the type of the object, whether a STREAMS 
         driver(2) or module(1).  STREAMS modules and drivers 
         share a name space as well as a module identifier 
         space.  Once this object is created in an entry, it 
         becomes read-only until it is destroyed."
    REFERENCE   
        "scls(8)"
    ::= { strModEntry 3 }

strModMajor OBJECT-TYPE
    SYNTAX      Unsigned32 (0..16383)
    MAX-ACCESS  read-only
    STATUS      current
    DESCRIPTION 
        "Indicates the major device number of a STREAMS driver 
         or zero (0) for a STREAMS module.  Once this object is 
         created in an entry, it becomes read-only until it is 
         destroyed."
    REFERENCE   
        "scls(8)"
    ::= { strModEntry 4 }

strModRowStatus OBJECT-TYPE
    SYNTAX      RowStatus
    MAX-ACCESS  read-create
    STATUS      current
    DESCRIPTION 
        "Provides a mechanism whereby management stations, using 
         the RowStatus textual convention of the SNMPv2-TC 
         module, may create and delete conceptual rows in this 
         table.
         
         Attempting to create a conceptual row from a management 
         station results in an attempt to load the corresponding 
         module identifier, or assigned name, or assigned major 
         device number (when assigned as a driver).  If all of 
         these fail, the row will not be created and an error is 
         returned.
         
         Attempting to delete a conceptual row from a management 
         station results in an attempt to unload the 
         corresponding STREAMS driver or module.  If the 
         unloading of the module fails for any reason, the row 
         will not be destroyed and an error is returned."
    REFERENCE   
        "scls(8), modprobe(8), insmod(8), rmmod(8)"
    ::= { strModEntry 5 }

strModInfo OBJECT IDENTIFIER
    ::= { strTables 2 }

strModInfoTable OBJECT-TYPE
    SYNTAX      SEQUENCE OF StrModInfoEntry
    MAX-ACCESS  not-accessible
    STATUS      current
    DESCRIPTION 
        "Provides a side-table of STREAMS module information for 
         the strModTable.  This is information contained in one 
         or more module_info(9) structures associated with a 
         single STREAMS module or driver."
    REFERENCE   
        "module_info(9)"
    ::= { strModInfo 1 }

strModInfoEntry OBJECT-TYPE
    SYNTAX      StrModInfoEntry
    MAX-ACCESS  not-accessible
    STATUS      current
    DESCRIPTION 
        "Provides an entry in the STREAMS module parameters 
         table.  Each entry represents one unique parameters 
         collection for a queue.  Each STREAMS module can have 
         from zero to four parameters groups for queues.  When 
         there are not parameters groups, no entry exists in 
         this table for the module name.  When one to four, one 
         to four entries exist in the table.
         
         All STREAMS modules and non-multiplexing drivers will 
         have at least one and at most two entries in this table 
         for the upper multiplex.  Multiplexing drivers must 
         have at least one and at most four entries in this 
         table.
         
         ENTRY LIFECYCLE: Rows cannot be explicitly created nor 
         destroyed by management stations: configuration is 
         statically determined by the STREAMS driver or module 
         at the time that the driver of module is registered.  
         If the STREAMS subsystem has the ability to dynamiclly 
         load STREAMS drivers or module, rows are created by 
         internal system operations whenever a STREAMS driver or 
         module registers with the STREAMS subsystem.  If the 
         STREAMS subsystem has the ability to dynamically unload 
         STREAMS driver or modules, rows are destroyed by 
         internal system operations whenever a STREAMS driver or 
         module deregisters from the STREAMS subsystem.
         
         EFFECT OF CHANGING VALUES: Changing values in an entry 
         will only affect newly opened instances of the STREAMS 
         module for the queues indicated in the strModInfoQueues 
         column.  These values are only the default values for 
         the Stream in effect at open.  No existing Streams will 
         be affected by changing values.
         
         VALUE PERSISTENCE: Values perist across an agent reboot 
         but not across a STREAMS module reload.  After a 
         STREAMS module reload (that occurs on system reboot) 
         the values will revert back to the values compiled-in 
         for the STREAMS module."
    INDEX       { strModName, strModInfoIndex }
    ::= { strModInfoTable 1 }

StrModInfoEntry ::= SEQUENCE {
    strModInfoIndex         Unsigned32,
    strModInfoQueues        StreamsModuleQueues,
    strModInfoMinpsz        Integer32,
    strModInfoMaxpsz        Integer32,
    strModInfoHiwat         Unsigned32,
    strModInfoLowat         Unsigned32,
    strModInfoTraceLevel    Unsigned32
}

strModInfoIndex OBJECT-TYPE
    SYNTAX      Unsigned32 (1..4)
    MAX-ACCESS  not-accessible
    STATUS      current
    DESCRIPTION 
        "Provides an index for the STREAMS information entry.  
         STREAMS module and non-multiplexing driver can have one 
         or two entries.  STREAMS multiplexing drivers can have 
         one to four entries.  The ordinal value of this index 
         is unimportant and the indices are simply number from 1 
         to a maximum of 4."
    ::= { strModInfoEntry 1 }

strModInfoQueues OBJECT-TYPE
    SYNTAX      StreamsModuleQueues
    MAX-ACCESS  read-only
    STATUS      current
    DESCRIPTION 
        "Identifies to which queues in the module the STREAMS 
         information applies.  module_info(9) structures can be 
         referenced by more than one qinit(9) structure, where 
         the qinit(9) structure belongs to one of: the upper 
         read queue, rd(0), the upper write queue, wr(1), the 
         lower multiplex read queue, muxrq(2), or the lower 
         multiplex write queue, muxwq(3)."
    REFERENCE   
        "scls(8), sc(4), module_info(9)"
    ::= { strModInfoEntry 2 }

strModInfoMinpsz OBJECT-TYPE
    SYNTAX      Integer32
    MAX-ACCESS  read-write
    STATUS      current
    DESCRIPTION 
        "Specifies the minimum packet size associated with the 
         driver or module for the queues indicated in the 
         strModInfoQueues column.  This column has the same 
         value as the mi_minpsz field of the corresponding 
         module_info(9) structure."
    REFERENCE   
        "scls(8), sc(4), module_info(9)"
    ::= { strModInfoEntry 3 }

strModInfoMaxpsz OBJECT-TYPE
    SYNTAX      Integer32
    MAX-ACCESS  read-write
    STATUS      current
    DESCRIPTION 
        "Specifies the maximum packet size associated with the 
         driver or module for the queues indicated in the 
         strModInfoQueues column.  This column has the same 
         value as the mi_maxpsz field of the corresponding 
         module_info(9) structure."
    REFERENCE   
        "scls(8), sc(4), module_info(9)"
    ::= { strModInfoEntry 4 }

strModInfoHiwat OBJECT-TYPE
    SYNTAX      Unsigned32
    MAX-ACCESS  read-write
    STATUS      current
    DESCRIPTION 
        "Specifies the high water mark associated with the 
         driver or module for the queues indicated in the 
         strModInfoQueues column.  This column has the same 
         value as the mi_hiwat field of the corresponding 
         module_info(9) structure."
    REFERENCE   
        "scls(8), sc(4), module_info(9)"
    ::= { strModInfoEntry 5 }

strModInfoLowat OBJECT-TYPE
    SYNTAX      Unsigned32
    MAX-ACCESS  read-write
    STATUS      current
    DESCRIPTION 
        "Specifies the low water mark associated with the driver 
         or module for the queues indicated in the 
         strModInfoQueues column.  This column has the same 
         value as the mi_lowat field of the corresponding 
         module_info(9) structure."
    REFERENCE   
        "scls(8), sc(4), module_info(9)"
    ::= { strModInfoEntry 6 }

strModInfoTraceLevel OBJECT-TYPE
    SYNTAX      Unsigned32 (0..255)
    MAX-ACCESS  read-write
    STATUS      current
    DESCRIPTION 
        "Specifies the trace level associated with the driver or 
         module for the queues indicated in the strModInfoQueues 
         column.  This column does not correspond to a field in 
         the module_info(9) structure."
    REFERENCE   
        "scls(8), sc(4), module_info(9)"
    ::= { strModInfoEntry 7 }

strModStat OBJECT IDENTIFIER
    ::= { strTables 3 }

strModStatTable OBJECT-TYPE
    SYNTAX      SEQUENCE OF StrModStatEntry
    MAX-ACCESS  not-accessible
    STATUS      current
    DESCRIPTION 
        "Provides a side-table of STREAMS module statistics for 
         the strModTable.  This is statistics contained in on or 
         more module_stat(9) structures associated with a single 
         STREAMS module or driver."
    REFERENCE   
        "module_stat(9)"
    ::= { strModStat 1 }

strModStatEntry OBJECT-TYPE
    SYNTAX      StrModStatEntry
    MAX-ACCESS  not-accessible
    STATUS      current
    DESCRIPTION 
        "Provides an entry in the STREAMS module statistics 
         table.  Each entry represents one unique statistics 
         collection for a queue.  Each STREAMS module can have 
         from zero to four statistics groups for queues.  When 
         there are no statistics groups, no entry exists in this 
         table for the module name.  When one to four, one to 
         four entries exist in this table.
         
         Not all STREAMS drivers and modules will have an entry 
         in this table.  Modules and non-multiplexing drivers 
         can have zero, one or two entries, multiplexing drivers 
         can have zero through four entries.
         
         ENTRY LIFECYCLE: Rows cannot be explicitly create or 
         destroyed by management stations: configuration is 
         statically deteremined by the STREAMS driver or module 
         at the time that the driver of module is registered.  
         If the STREAMS subsystem has the ability to dynamically 
         load STREAMS drivers or modules, rows are created by 
         internal system operations whenever a STREAMS driver or 
         module regisers with the STREAMS subsystem.  If the 
         STREAMS subsystem has the ability to dynamically unload 
         STREAMS driver modules, rows are destroyed by internal 
         system operations whenever a STREAMS driver of module 
         deregisters from the STREAMS sybsystem.
         
         EFFECT OF CHANGING VALUES: All values in this entry are 
         read-only.  Counters in this table are only reset 
         during system reinialiation or STREAMS subsystem 
         reinitialization.  The scalar strDiscontinuityTime is 
         used to determine when the last discontinuity in 
         counter values occured."
    INDEX       { strModName, strModStatIndex }
    ::= { strModStatTable 1 }

StrModStatEntry ::= SEQUENCE {
    strModStatIndex     Unsigned32,
    strModStatQueues    StreamsModuleQueues,
    strModStatPcnt      Counter32,
    strModStatScnt      Counter32,
    strModStatOcnt      Counter32,
    strModStatCcnt      Counter32,
    strModStatAcnt      Counter32,
    strModStatPrivate   OCTET STRING,
    strModStatFlags     Unsigned32
}

strModStatIndex OBJECT-TYPE
    SYNTAX      Unsigned32 (1..4)
    MAX-ACCESS  not-accessible
    STATUS      current
    DESCRIPTION 
        "Provides an index for the STREAMS statistics entry.  
         STREAMS module and non-multiplexing drivers can have 
         zero, one or two entries.  STREAMS multiplexing drivers 
         can have zero to four entries."
    REFERENCE   
        "module_stat(9)"
    ::= { strModStatEntry 1 }

strModStatQueues OBJECT-TYPE
    SYNTAX      StreamsModuleQueues
    MAX-ACCESS  read-only
    STATUS      current
    DESCRIPTION 
        "Identifies to which queues in the module the STREAMS 
         statistics applies."
    REFERENCE   
        "scls(8), sc(4), module_stat(9)"
    ::= { strModStatEntry 2 }

strModStatPcnt OBJECT-TYPE
    SYNTAX      Counter32
    MAX-ACCESS  read-only
    STATUS      current
    DESCRIPTION 
        "Indicates the statistics associated with queue put 
         procedure calls.  While this is typically the number of 
         times that the put procedure was called, the module may 
         increment this count on some other basis, or not at 
         all.  See the specific module documentation for 
         information.
         
         This count is associated with the ms_pcnt member of the 
         queue's module_stat structure."
    REFERENCE   
        "module_stat(9)"
    ::= { strModStatEntry 3 }

strModStatScnt OBJECT-TYPE
    SYNTAX      Counter32
    MAX-ACCESS  read-only
    STATUS      current
    DESCRIPTION 
        "Indicates the statistics associated with queue put 
         procedure calls.  While this is typically the number of 
         times that the put procedure was called, the module may 
         increment this count on some other basis, or not at 
         all.  See the specific module documentation for 
         information.
         
         This count is associated with the ms_scnt member of the 
         queue's module_stat structure."
    REFERENCE   
        "module_stat(9)"
    ::= { strModStatEntry 4 }

strModStatOcnt OBJECT-TYPE
    SYNTAX      Counter32
    MAX-ACCESS  read-only
    STATUS      current
    DESCRIPTION 
        "Indicates the statistics associated with module open 
         routine calls.  While this is typically the number of 
         times that the module open routine was called, the 
         module may increment this count on some other basis, or 
         not at all.  See the specific module documentation for 
         information.
         
         This count is associated with the ms_ocnt member of the 
         queue's module_stat structure."
    REFERENCE   
        "module_stat(9)"
    ::= { strModStatEntry 5 }

strModStatCcnt OBJECT-TYPE
    SYNTAX      Counter32
    MAX-ACCESS  read-only
    STATUS      current
    DESCRIPTION 
        "Indicates the statistics assocaited with module close 
         routine calls.  While this is typically the number of 
         times that the module close routine was called, the 
         module may increment this count on some other basis, or 
         not at all.  See the specific module documentation for 
         information.
         
         This count is associated with the ms_ccnt member of the 
         queue's module_stat structure."
    REFERENCE   
        "module_stat(9)"
    ::= { strModStatEntry 6 }

strModStatAcnt OBJECT-TYPE
    SYNTAX      Counter32
    MAX-ACCESS  read-only
    STATUS      current
    DESCRIPTION 
        "Indicates the statistics associated with module admin 
         routine calls.  While this is typically the number of 
         times that the module admin routine was called, the 
         module may increment this count on some other basis, or 
         not at all.  See the specific module documentation for 
         information.
         
         This count is associated with the ms_acnt member of the 
         queue's module_stat structure."
    REFERENCE   
        "module_stat(9)"
    ::= { strModStatEntry 7 }

strModStatPrivate OBJECT-TYPE
    SYNTAX      OCTET STRING
    MAX-ACCESS  read-only
    STATUS      current
    DESCRIPTION 
        "Indicates the private statistics associated with the 
         module.  The format of this area is not defined by 
         STREAMS.  See the specific module documentation for 
         information.
         
         This data is associated with the ms_xprt and ms_xsize 
         members of the queue's module_stat structure.  If no 
         such structure is provided, or, if ms_xsize is zero, 
         this will be a null string."
    REFERENCE   
        "module_stat(9)"
    ::= { strModStatEntry 8 }

strModStatFlags OBJECT-TYPE
    SYNTAX      Unsigned32
    MAX-ACCESS  read-only
    STATUS      current
    DESCRIPTION 
        "Indicates the boolean statistics associated with the 
         module in a 32-bit flags word.  The format of these 
         flags is not defined by STREAMS.  See the specific 
         module documentation for information.
         
         This data is assocaited with the ms_flags member of the 
         queue's module_stat structure."
    REFERENCE   
        "module_stat(9)"
    ::= { strModStatEntry 9 }

strApsh OBJECT IDENTIFIER
    ::= { strTables 4 }

strApshTable OBJECT-TYPE
    SYNTAX      SEQUENCE OF StrApshEntry
    MAX-ACCESS  not-accessible
    STATUS      current
    DESCRIPTION 
        "Provides the STREAMS autopush table.  The autopush 
         table provides the STREAMS modules that are configured 
         by the system to be autopushed on top of driver minor 
         devices."
    REFERENCE   
        "autopush(8)"
    ::= { strApsh 1 }

strApshEntry OBJECT-TYPE
    SYNTAX      StrApshEntry
    MAX-ACCESS  not-accessible
    STATUS      current
    DESCRIPTION 
        "Provides an entry in the STREAMS autopush table.  Each 
         entry is indexed by the driver name and the initial 
         minor device number to which the entry belongs."
    REFERENCE   
        "autopush(8)"
    INDEX       { strModName, strApshMinor, strApshLastMinor }
    ::= { strApshTable 1 }

StrApshEntry ::= SEQUENCE {
    strApshMajor        Unsigned32,
    strApshMinor        Unsigned32,
    strApshLastMinor    Unsigned32,
    strApshModules      StreamsModuleList,
    strApshRowStatus    RowStatus
}

strApshMajor OBJECT-TYPE
    SYNTAX      Unsigned32 (1..16383)
    MAX-ACCESS  read-only
    STATUS      current
    DESCRIPTION 
        "Provides the primary major device number associated 
         with the driver."
    REFERENCE   
        "autopush(8)"
    ::= { strApshEntry 1 }

strApshMinor OBJECT-TYPE
    SYNTAX      Unsigned32 (0..16383 | 4294967295)
    MAX-ACCESS  not-accessible
    STATUS      current
    DESCRIPTION 
        "Provides the minor device number or the start of a 
         range of minor device numbers, to which the autopush 
         specification applies.  When specified as 'FFFFFFFF'X, 
         the specification applies to all minor device numbers 
         for this driver and LastMinor is ignored."
    REFERENCE   
        "autopush(8)"
    ::= { strApshEntry 2 }

strApshLastMinor OBJECT-TYPE
    SYNTAX      Unsigned32 (0..16383)
    MAX-ACCESS  not-accessible
    STATUS      current
    DESCRIPTION 
        "Provides the last minor device number in a range.  This 
         value is always zero (0) when the Minor number is 
         'FFFFFFFF'X.  The agent must ensure that the range 
         specified by this number does not overlap with other 
         ranges specified in this autopush specification entry."
    REFERENCE   
        "autopush(8)"
    ::= { strApshEntry 3 }

strApshModules OBJECT-TYPE
    SYNTAX      StreamsModuleList
    MAX-ACCESS  read-create
    STATUS      current
    DESCRIPTION 
        "Provides a STREAMS module list flowing the 
         StreamsModuleList textual convention.  This is a 
         space-separated list of Streams module names.  When 
         this entry is created, it is persistent accross agent 
         reboots, and might first be verified by the agent."
    REFERENCE   
        "autopush(8)"
    ::= { strApshEntry 4 }

strApshRowStatus OBJECT-TYPE
    SYNTAX      RowStatus
    MAX-ACCESS  read-create
    STATUS      current
    DESCRIPTION 
        "Provides management stations with the ability to add 
         rows to, or delete rows from, the STREAMS autopush 
         table."
    REFERENCE   
        "autopush(8)"
    ::= { strApshEntry 5 }

strStats OBJECT IDENTIFIER
    ::= { strTables 5 }

strStatsTable OBJECT-TYPE
    SYNTAX      SEQUENCE OF StrStatsEntry
    MAX-ACCESS  not-accessible
    STATUS      current
    DESCRIPTION 
        "The STREAMS statistics table provides information about 
         the current number of allocated primary STREAMS data 
         structures as well as the high water mark since the 
         last boot."
    ::= { strStats 1 }

strStatsEntry OBJECT-TYPE
    SYNTAX      StrStatsEntry
    MAX-ACCESS  not-accessible
    STATUS      current
    DESCRIPTION 
        "Each entry in the StrStatsTable represents the 
         allocation information for a given primary STREAMS data 
         structure.  These values are read-only."
    INDEX       { strStatsStructure }
    ::= { strStatsTable 1 }

StrStatsEntry ::= SEQUENCE {
    strStatsStructure       INTEGER,
    strStatsCurrentAllocs   Gauge32,
    strStatsHighWaterMark   Gauge32
}

strStatsStructure OBJECT-TYPE
    SYNTAX      INTEGER { dynStream(1), dynQueue(2), dynMsgblock(3), 
                    dynMdbblock(4), dynLinkblk(5), dynStrevent(6), 
                    dynQband(7), dynStrapush(8), dynDevinfo(9), 
                    dynModinfo(10), dynSynq(11), dynBuffers(12) }
    MAX-ACCESS  not-accessible
    STATUS      current
    DESCRIPTION 
        "Specifies the type of dynamically allocated structure 
         for which current and high water mark allocations are 
         being presented.
         
         - dynStreams: the numer of stream head structures 
           allocated.
         
         - dynQueue: the number of queue pairs allocated.
         
         - dynMsgblock: the number of message blocks allocated 
           without allocating an associated data block.
         
         - dynMdbblock: the number of message data block 
           combinations allocated.
         
         - dynLinkblk: the number of link blocks allocated.
         
         - dynStrevent: the number of STREAMS event structure 
           allocated.
         
         - dynQband: the number of queue band structures 
           allocated.
         
         - dynStrapush: the number of STREAMS autopush 
           structures allocated.
         
         - dynDevinfo: the number of device information 
           structures allocated.
         
         - dynModinfo: the number of module information 
           structures allocated.
         
         - dynSynq: the number of STREAMS synchronization queue 
           structures allocated.
         
         - dynBuffers: the number of bytes of message buffer 
           allocated.
         
         Of the statistic presented here, the statistics for 
         dynMdbblock is probably most important.  This is the 
         current and high water mark numbers for allocations of 
         combined message and data blocks.  The numbers cannot 
         exceed the value of strNstrmsgs.  If the high water 
         mark is the same as strNstrmsgs, that means that at 
         some time, the allocation of a message block was 
         refused because of this constraint."
    ::= { strStatsEntry 1 }

strStatsCurrentAllocs OBJECT-TYPE
    SYNTAX      Gauge32
    MAX-ACCESS  read-only
    STATUS      current
    DESCRIPTION 
        "Provides the number of objects of the structure type 
         currently allocated."
    ::= { strStatsEntry 2 }

strStatsHighWaterMark OBJECT-TYPE
    SYNTAX      Gauge32
    MAX-ACCESS  read-only
    STATUS      current
    DESCRIPTION 
        "Provides the maximum number of objects of the structure 
         type that were allocated at one time (the maximum 
         historical value of strStatsCurrentAlloc) since the 
         last time that the system was rebooted."
    ::= { strStatsEntry 3 }

strScalars OBJECT IDENTIFIER
    ::= { strObjects 2 }

strTunables OBJECT IDENTIFIER
    ::= { strScalars 1 }

strCltime OBJECT-TYPE
    SYNTAX      TimeInterval
    UNITS       "centiseconds"
    MAX-ACCESS  read-write
    STATUS      current
    DESCRIPTION 
        "Specifies the default time interval that a closing 
         Stream will linger for messages to clear its write 
         queues before finally closing.  Valid values are zero 
         (0) or greater (MAXINT).  The default value is the 
         tranditional UNIX value of 15 seconds (1500 
         centiseconds).  This system control defines the default 
         for all new Streams.  The value for a given Stream can 
         be changed with the streamio(7) input-output control 
         I_CLTIME(7), after the Stream is opened and before the 
         Stream is closed.  This value corresponds to the system 
         control sys.streams.cltime."
    REFERENCE   
        "sys.streams.cltime."
    DEFVAL      { 1500 }
    ::= { strTunables 1 }

strMaxApush OBJECT-TYPE
    SYNTAX      Unsigned32
    UNITS       "modules"
    MAX-ACCESS  read-write
    STATUS      current
    DESCRIPTION 
        "Specifies the maximum number of modules that can be 
         configured for autopush onto a STREAMS driver.  Valid 
         values are zero (0) or greater (MAXINT).  The default 
         value is the traditional UNIX value of 8 modules.  This 
         system control defines the maximum for all new autopush 
         configurations.  Existing autopush configurations are 
         unchanged.  This value corresponds to the system 
         control sys.streams.max_apush."
    REFERENCE   
        "sys.streams.max_apush."
    DEFVAL      { 8 }
    ::= { strTunables 2 }

strMaxMblk OBJECT-TYPE
    SYNTAX      Unsigned32
    UNITS       "message-data blocks (maximum)"
    MAX-ACCESS  read-write
    STATUS      current
    DESCRIPTION 
        "Specifies the maximum number of combined message data 
         blocks that will be held on the per-CPU free list 
         between runs of runqueues(9).  Valid values are zero 
         (0) or greater (MAXINT).  The default value is the 
         traditional UNIX value of 10 blocks.  This system 
         control defines the maximum for the next run of 
         runqueues(9) for all CPUs.  Increasing or decreasing 
         this number may have a positive or negative performance 
         impact.  This value corresponds to the system control 
         sys.streams.max_mblk."
    REFERENCE   
        "sys.streams.max_mblk."
    DEFVAL      { 10 }
    ::= { strTunables 3 }

strMaxStramod OBJECT-TYPE
    SYNTAX      Unsigned32
    UNITS       "autopush structures (maximum)"
    MAX-ACCESS  read-write
    STATUS      current
    DESCRIPTION 
        "Specifies the maximum number of autopush structures 
         that will be defined for the entire system.  Valid 
         values are zero (0) or greater (MAXINT).  The default 
         value is eight (8).  This system control defines the 
         system-wide maximum.  This value corresponds to the 
         system control sys.streams.max_stramod."
    REFERENCE   
        "sys.streams.max_stramod."
    DEFVAL      { 8 }
    ::= { strTunables 4 }

strMaxStrdev OBJECT-TYPE
    SYNTAX      Unsigned32 (0..16384)
    UNITS       "STREAMS devices (maximum)"
    MAX-ACCESS  read-only
    STATUS      current
    DESCRIPTION 
        "Specifies the maximum number of Streams devices.  This 
         is normally the maximum number of character devices 
         (MAX_CHRDEV).  Valid values are zero (0) or greater 
         (MAXINT).  The default value is MAX_CHRDEV (256 on 
         16-bit device number systems, 16384 on 32-bit device 
         number systems).  This is a read-only system control.  
         This value corresponds to system control 
         sys.streams.max_strdev.
         
         This value had more significance on systems that used 
         to allocate the character device switch tables as 
         static arrays.  Modern STREAMS subsystems use hashes 
         and linked lists and the number is limited by memory 
         rather than by index number as this value reflects."
    REFERENCE   
        "sys.streams.max_strdev."
    DEFVAL      { 16384 }
    ::= { strTunables 5 }

strMaxStrmod OBJECT-TYPE
    SYNTAX      Unsigned32 (0..16384)
    UNITS       "STREAMS modules (maximum)"
    MAX-ACCESS  read-only
    STATUS      current
    DESCRIPTION 
        "Specifies the maximum number of Streams modules.  This 
         is normally the maximum number of character devices 
         (MAX_CHRDEV).  Valid values are zero (0) or greater 
         (MAXINT).  The default value is MAX_CHRDEV (256 on 
         16-bit device number systems, 16384 on 32-bit device 
         number systems).  This is a read-only system control.  
         This value corresponds to system control 
         sys.streams.max_strmod.
         
         This value had more significance on systems that used 
         to allocate the module switch tables as static arrays.  
         Modern STREAMS subsystems use hashes and linked lists 
         and the number is limited by memory rather than by 
         index number as this value reflects."
    REFERENCE   
        "sys.streams.max_strmod."
    DEFVAL      { 16384 }
    ::= { strTunables 6 }

strMsgPriority OBJECT-TYPE
    SYNTAX      TruthValue
    UNITS       "priority (maximum)"
    MAX-ACCESS  read-write
    STATUS      current
    DESCRIPTION 
        "Specifies whether allocation priority will be honoured 
         or whether all allocations will be treated the same.  
         See allocb(9).  When true, allocation priority will be 
         honoured when allocating message blocks.  When false, 
         allocation priority will be ignored.  Valid values are 
         true or false.  The default value is false.  Changing 
         the value may have a positive or negative impact on 
         system performance.  This value corresponds to the 
         system control sys.streams.msg_priority."
    REFERENCE   
        "sys.streams.msg_priority."
    DEFVAL      { false }
    ::= { strTunables 7 }

strNband OBJECT-TYPE
    SYNTAX      Unsigned32 (1..256)
    UNITS       "queue bands (maximum)"
    MAX-ACCESS  read-only
    STATUS      current
    DESCRIPTION 
        "Specifies the number of queue bands available.  Valid 
         values are zero (0) or greater (MAXINT).  The default 
         value is the traditional UNIX value of 256.  This 
         system control defines the system-wide value.  This 
         system control is read-only.  This value corresponds to 
         the system control sys.streams.nband."
    REFERENCE   
        "sys.streams.nband."
    DEFVAL      { 256 }
    ::= { strTunables 8 }

strNstrmsgs OBJECT-TYPE
    SYNTAX      Unsigned32
    UNITS       "message-data blocks (maximum)"
    MAX-ACCESS  read-write
    STATUS      current
    DESCRIPTION 
        "Specifies the maximum number of combined message data 
         blocks that will be allocated.  Valid values are zero 
         (0) or greater (MAXINT).  The default value is 2^12.  
         Changing this value may have a positive or negative 
         impact on system performance.  Setting this value to a 
         small number may be useful for debugging STREAMS driver 
         and modules on non-production systems.  When set to a 
         large value, the maximum amount of allocated memory may 
         become the more constraining factor.  High and low 
         water mark statistics on a running system can be used 
         to tune this value. This value corresponds to the 
         system control sys.streams.nstrmsgs.
         
         The purpose of this limit is to keep buffer leaking 
         drivers from consuming all of the system resources."
    REFERENCE   
        "sys.streams.nstrmsgs."
    DEFVAL      { 4096 }
    ::= { strTunables 9 }

strNstrpush OBJECT-TYPE
    SYNTAX      Unsigned32
    UNITS       "modules per Stream (maximum)"
    MAX-ACCESS  read-write
    STATUS      current
    DESCRIPTION 
        "Specifies the maximum number of modules that can be 
         pushed on a Stream.  This includes both autopushed 
         modules and modules pushed using the I_PUSH(7) 
         input-output control of streamio(7).  Valid values are 
         zero (0) or greater (MAXINT).  The default value is the 
         traditional UNIX value of 64.  This is the default 
         value for all new Stream heads.  Existing streams are 
         unaffected.  Setting this value to other than 64 will 
         cause some validation tests to fail.  This value 
         corresponds to the system control 
         sys.streams.nstrpush."
    REFERENCE   
        "sys.streams.nstrpush."
    DEFVAL      { 64 }
    ::= { strTunables 10 }

strHiwat OBJECT-TYPE
    SYNTAX      Unsigned32
    UNITS       "octets"
    MAX-ACCESS  read-write
    STATUS      current
    DESCRIPTION 
        "Specifies the default high water mark (in message 
         bytes) for the Stream head.  Valid values are zero (0) 
         or greater (MAXINT).  The default value is 5120.  This 
         is the default value for all new Stream heads.  
         Existing Stream heads are unaffected.  The value on 
         existing Stream heads can be changed by a driver or 
         module by sending an M_SETOPTS(9) message to the Stream 
         head.  This value corresponds to the system control 
         sys.streams.hiwat."
    REFERENCE   
        "sys.streams.hiwat"
    DEFVAL      { 5120 }
    ::= { strTunables 11 }

strLowat OBJECT-TYPE
    SYNTAX      Unsigned32
    UNITS       "octets"
    MAX-ACCESS  read-write
    STATUS      current
    DESCRIPTION 
        "Specifies the default low water mark (in message bytes) 
         for the Stream head.  Valid values are zero (0) or 
         greater (MAXINT).  The default value is 1024.  This is 
         the default value for all new Stream heads.  Existing 
         Stream heads are unaffected.  The value on existing 
         Stream heads can be changed by a driver or module by 
         sending an M_SETOPTS(9) message to the Stream head.  
         This value corresponds to the system control 
         sys.streams.lowat."
    REFERENCE   
        "sys.streams.lowat"
    DEFVAL      { 1024 }
    ::= { strTunables 12 }

strMaxpsz OBJECT-TYPE
    SYNTAX      Integer32 (0..2147482648)
    UNITS       "octets"
    MAX-ACCESS  read-write
    STATUS      current
    DESCRIPTION 
        "Specifies the maximum packet size accepted (in message 
         bytes) for the Stream head.  Valid values are zero (0) 
         or greater (MAXINT).  The default value is 2^12.  This 
         is the default for all new Stream heads.  Existing 
         Stream heads are unaffected.  The value on existing 
         Stream heads can be changed by a driver or module by 
         sending a M_SETOPTS(9) message to the Stream head.  
         This value corresponds to system control 
         sys.streams.maxpsz.
         
         The Stream head only uses this value on the write side, 
         where it is used to determine the maximum message size, 
         not the maximum write size.  When a write occurs that 
         is larger than this maximum, multiple message blocks 
         are allocated so that the size of the message block 
         falls between the Minpsz and Maxpsz values.  When a 
         driver or module is opened, the values used by the 
         driver or module is used on the write side instead.
         
         On the read side, these values are set against the 
         Stream head and act as advise to the lower module on 
         maximum message sizes.
         
         For pipes and FIFOs, however, this value is the value 
         of the opposite Stream head's driver or module and the 
         value is used both on the read and write side of a pipe 
         or FIFO.  pipes and FIFOs rely on the value of 4096 for 
         POSIX conformance.  If the value is set beneath 4096, 
         POSIX conformance of pipes and FIFOs will be 
         abbrogated."
    REFERENCE   
        "sys.streams.maxpsz"
    DEFVAL      { 4096 }
    ::= { strTunables 13 }

strMinpsz OBJECT-TYPE
    SYNTAX      Integer32 (0..2147482648)
    UNITS       "octets"
    MAX-ACCESS  read-write
    STATUS      current
    DESCRIPTION 
        "Specifies the minimum packet size accepted (in message 
         bytes) for the Stream head.  Valid values are zero (0) 
         or greater (MAXINT).  The default value is zero (0).  
         This is the default value for all new Stream heads.  
         Existing Stream heads are unaffected.  The value on 
         existing Stream heads can be changed by a driver or 
         modules by sending an M_SETOPTS(9) message to the 
         Stream head.  This value corresponds to system control 
         sys.streams.minpsz.
         
         The Stream head only uses this value on the write side, 
         where it is used to determine the minimum message size, 
         not the minimum write size.  When a driver or module is 
         opened, the values used by the driver or module is used 
         on the write side instead.
         
         On the read side, these values are set against the 
         Stream head and act as advise to the lower module on 
         minimum message size.
         
         For pipes and FIFOs, however, this value is the value 
         of the opposite Stream head's driver or module and the 
         value is used both on the read and write side of a pipe 
         or FIFO.  pipes and FIFOs rely on the value of 0 for 
         POSIX conformance.  If the value is set above 0, POSIX 
         conformance of pipes and FIFOs will be abbrogated."
    REFERENCE   
        "sys.streams.minpsz"
    DEFVAL      { 0 }
    ::= { strTunables 14 }

strReuseFmodsw OBJECT-TYPE
    SYNTAX      TruthValue
    MAX-ACCESS  read-write
    STATUS      current
    DESCRIPTION 
        "Specifies whether fmodsw table entries will be reused.  
         When false, fmodsw table entries will not be reused.  
         When true, fmodsw table entries will be reused.  Valid 
         values are true or false.  The default value is false.  
         Corresponds to the control sys.streams.reuse_fmodsw."
    REFERENCE   
        "sys.streams.reuse_fmodsw"
    DEFVAL      { false }
    ::= { strTunables 15 }

strRtime OBJECT-TYPE
    SYNTAX      TimeInterval
    UNITS       "centiseconds"
    MAX-ACCESS  read-write
    STATUS      current
    DESCRIPTION 
        "Specifies the time interval that the stream head will 
         wait to forward held messages when SNDHOLD is set for 
         the Stream head.  Valid values are zero (0) or greater 
         (MAXINT).  The default value is 10 milliseconds (1 
         centisecond).  This is the system wide value for all 
         Streams.  Changing this value may have a positive or 
         negative impact on system performance.  Corresponds to 
         the system control sys.streams.rtime."
    REFERENCE   
        "sys.streams.rtime"
    DEFVAL      { 1 }
    ::= { strTunables 16 }

strStrhold OBJECT-TYPE
    SYNTAX      TruthValue
    MAX-ACCESS  read-write
    STATUS      current
    DESCRIPTION 
        "Specifies whether the SNDHOLD feature is active or not.  
         When false, the SNDHOLD feature is deactivated.  When 
         true, the SNDHOLD feature is activated.  Valid values 
         are true or false.  The default value is false.  This 
         is the default value for all new Streams.  Existing 
         Streams are unaffected.  This setting can be examined 
         and altered on an open Stream using the I_GWROPT and 
         I_SWROPT IO controls of streamio(7).  Corresponds to 
         the system control sys.streams.strhold."
    REFERENCE   
        "sys.streams.strhold"
    DEFVAL      { false }
    ::= { strTunables 17 }

strStrctlsz OBJECT-TYPE
    SYNTAX      Unsigned32 (1024..262144)
    UNITS       "octets"
    MAX-ACCESS  read-write
    STATUS      current
    DESCRIPTION 
        "Specifies the maximum STREAMS control part size.  Value 
         values are zero (0) to greater (MAXINT).  The default 
         value is 2^12.  This is the system wide maximum.  
         Existing allocations are unaffected by lowering this 
         value.  Changing this value can have an impact on users 
         of putpmsg(2s).  Corresponds to the system control 
         sys.streams.strctlsz."
    REFERENCE   
        "sys.streams.strctlsz"
    DEFVAL      { 4096 }
    ::= { strTunables 18 }

strStrmsgsz OBJECT-TYPE
    SYNTAX      Unsigned32 (1024..262144)
    UNITS       "octets"
    MAX-ACCESS  read-write
    STATUS      current
    DESCRIPTION 
        "Specifies the maximum STREAMS message size.  Value 
         values are zero (0) or greater (MAXINT).  The default 
         value is 2^18.  This is the system wide maximum.  
         Existing allocations are unaffected by lowering this 
         value.  Changing this value can have an impact on users 
         of write(2s), writev(2s), and putpmsg(2s).  Corresponds 
         to the system control sys.streams.strmsgsz."
    REFERENCE   
        "sys.streams.strmsgsz"
    DEFVAL      { 262144 }
    ::= { strTunables 19 }

strStrthresh OBJECT-TYPE
    SYNTAX      Unsigned32
    UNITS       "octets"
    MAX-ACCESS  read-write
    STATUS      current
    DESCRIPTION 
        "Specifies the maximum amount of memory that will be 
         allocated for use by the STREAMS subsystem via 
         kmem_alloc(9) or kmem_zalloc(9), or indirectly using 
         allocb(9) or allocating other STREAMS data structures.  
         Valid values are zero (0) or greater (MAXINT).  This is 
         the system wide maximum.   Existing allocations are 
         unaffected by lowering this value.  Changing this value 
         to a low value may have some use in debugging STREAMS 
         drivers and modules.  Corresponds to the system control 
         sys.streams.strthresh.  The value zero (0) means no 
         constraint.
         
         The purpose of this constraint is to keep memory 
         leaking drivers from consuming all system resources."
    REFERENCE   
        "sys.streams.strthresh"
    DEFVAL      { 0 }
    ::= { strTunables 20 }

strLowthresh OBJECT-TYPE
    SYNTAX      Unsigned32
    UNITS       "octets"
    MAX-ACCESS  read-write
    STATUS      current
    DESCRIPTION 
        "Specifies the amount of total STREAMS memory allocation 
         above which low priority message allocations will fail.  
         Low priority message allocations are those which pass 
         the BPRI_LO flag to an allocator function such as 
         allocb(9).  The value zero (0) means no constraint.
         
         Setting this threshold to a low value may have a 
         negative impact on STREAMS performance."
    REFERENCE   
        "sys.streams.lowthresh"
    DEFVAL      { 0 }
    ::= { strTunables 21 }

strMedthresh OBJECT-TYPE
    SYNTAX      Unsigned32
    UNITS       "octets"
    MAX-ACCESS  read-write
    STATUS      current
    DESCRIPTION 
        "Specifies the amount of total STREAMS memory allocation 
         above which medium priority message allocations will 
         fail.  Medium priority message allocations are those 
         which pass the BPRI_MED flag to an allocator function 
         such as allocb(9).  The value zero (0) means no 
         constraint.
         
         Setting this threshold to a low value may have a 
         negative impact on STREAMS performance."
    REFERENCE   
        "sys.streams.medthresh"
    DEFVAL      { 0 }
    ::= { strTunables 22 }

strIoctime OBJECT-TYPE
    SYNTAX      TimeInterval
    UNITS       "centiseconds"
    MAX-ACCESS  read-write
    STATUS      current
    DESCRIPTION 
        "Specifies the default time interval that a Stream will 
         await a response to an M_IOCTL message issued 
         downstream.  Valid values are zero (0) or greater 
         (MAXINT).  The default value is the traditional UNIX 
         value of 15 seconds (1500 centiseconds).  This system 
         control defines the default for all new Streams.  The 
         value for a given Stream can be changed with the 
         streamio(7) input-output control, after the Stream is 
         opened and before the Stream is closed.  This value 
         coresponds to the system control sys.streams.ioctime."
    REFERENCE   
        "sys.streams.ioctime"
    DEFVAL      { 1500 }
    ::= { strTunables 23 }

strStatistics OBJECT IDENTIFIER
    ::= { strScalars 2 }

strNotifs OBJECT IDENTIFIER
    ::= { strObjects 3 }

strOids OBJECT IDENTIFIER
    ::= { strObjects 4 }

strConformance OBJECT IDENTIFIER
    ::= { strMIB 2 }

strCompliances OBJECT IDENTIFIER
    ::= { strConformance 1 }

strGroups OBJECT IDENTIFIER
    ::= { strConformance 2 }

strTunablesMandatoryGroup OBJECT-GROUP
    OBJECTS     { strCltime, strMaxStramod, strMaxStrdev, strMaxStrmod, 
                  strNband, strNstrmsgs, strNstrpush, strHiwat, strLowat, 
                  strMaxpsz, strMinpsz, strStrctlsz, strStrmsgsz, 
                  strIoctime }
    STATUS      current
    DESCRIPTION 
        "A collection of mandatory tunables that are expected to 
         be implemented by all STREAMS subsystem 
         implementations."
    ::= { strGroups 1 }

strMessagePoolsConditionalGroup OBJECT-GROUP
    OBJECTS     { strMsgPriority, strStrthresh, strLowthresh, 
                  strMedthresh }
    STATUS      current
    DESCRIPTION 
        "A collection of objects related to the priority message 
         pooling function not present in all modern STREAMS 
         implementations."
    ::= { strGroups 2 }

strHoldConditionalGroup OBJECT-GROUP
    OBJECTS     { strRtime, strStrhold }
    STATUS      current
    DESCRIPTION 
        "A collection of tunables related to the Stream head 
         hold feature not present in all modern STREAMS 
         implementations."
    ::= { strGroups 3 }

strTunablesOptionalGroup OBJECT-GROUP
    OBJECTS     { strMaxApush, strMaxMblk, strReuseFmodsw }
    STATUS      current
    DESCRIPTION 
        "A collection of optional tunables that are not expected 
         to be implemented by most STREAMS subsystems."
    ::= { strGroups 4 }

strApshTableMandatoryGroup OBJECT-GROUP
    OBJECTS     { strApshMajor, strApshModules }
    STATUS      current
    DESCRIPTION 
        "A collection of objects necessary for implementing a 
         read-only strApshTable."
    ::= { strGroups 5 }

strApshTableConditionalGroup OBJECT-GROUP
    OBJECTS     { strApshRowStatus }
    STATUS      current
    DESCRIPTION 
        "A collection of objects necessary for implementing a 
         strApshTable that allows management stations to create 
         and delete entries."
    ::= { strGroups 6 }

strModTableMandatoryGroup OBJECT-GROUP
    OBJECTS     { strModIdnum, strModType, strModMajor }
    STATUS      current
    DESCRIPTION 
        "A collection of objects necessary for implementing a 
         read-only strModTable."
    ::= { strGroups 7 }

strModTableConditionalGroup OBJECT-GROUP
    OBJECTS     { strModRowStatus }
    STATUS      current
    DESCRIPTION 
        "A collection of objects necessary for implementing a 
         strModTable that allows management stations to create 
         and delete entries."
    ::= { strGroups 8 }

strModInfoTableMandatoryGroup OBJECT-GROUP
    OBJECTS     { strModInfoQueues, strModInfoMinpsz, strModInfoMaxpsz, 
                  strModInfoHiwat, strModInfoLowat }
    STATUS      current
    DESCRIPTION 
        "A collection of objects necessary for implementing a 
         strModInfoTable that provides STREAMS module 
         information."
    ::= { strGroups 9 }

strModInfoTableConditionalGroup OBJECT-GROUP
    OBJECTS     { strModInfoTraceLevel }
    STATUS      current
    DESCRIPTION 
        "A collection of objects necessary for implementing an 
         enhanced strModInfoTable that provides STREAMS module 
         information."
    ::= { strGroups 10 }

strModStatTableMandatoryGroup OBJECT-GROUP
    OBJECTS     { strModStatQueues, strModStatPcnt, strModStatScnt, 
                  strModStatOcnt, strModStatCcnt, strModStatAcnt }
    STATUS      current
    DESCRIPTION 
        "A collection of objects necessary for implementing a 
         strModStatTable that provides STREAMS module 
         statistics."
    ::= { strGroups 11 }

strModStatTableConditionalGroup OBJECT-GROUP
    OBJECTS     { strModStatPrivate, strModStatFlags }
    STATUS      current
    DESCRIPTION 
        "A collection of objects necessary for implementing an 
         enhanced strModStatTable that provides STREAMS module 
         statistics."
    ::= { strGroups 12 }

strStatsTableMandatoryGroup OBJECT-GROUP
    OBJECTS     { strStatsCurrentAllocs }
    STATUS      current
    DESCRIPTION 
        "A collection of objects necessary for implementing a 
         strStatsTable that provides STREAMS subsystem 
         statistics."
    ::= { strGroups 13 }

strStatsTableConditionalGroup OBJECT-GROUP
    OBJECTS     { strStatsHighWaterMark }
    STATUS      current
    DESCRIPTION 
        "A collection of objects necessary for implementing a 
         strStatsTable that includes high water marks."
    ::= { strGroups 14 }

strMIBCompliance MODULE-COMPLIANCE
    STATUS      current
    DESCRIPTION 
        "Provides the module compliance requirements for the 
         STREAMS MIB."

    MODULE      -- this module

        MANDATORY-GROUPS        { strTunablesMandatoryGroup, 
                  strModTableMandatoryGroup, 
                  strModInfoTableMandatoryGroup, 
                  strModStatTableMandatoryGroup, 
                  strApshTableMandatoryGroup, 
                  strStatsTableMandatoryGroup }

        GROUP   strTunablesOptionalGroup
        DESCRIPTION   
              "Optional tunables."

        GROUP   strMessagePoolsConditionalGroup
        DESCRIPTION   
              "Mandatory if the STREAMS implementation allocates 
               priority messages from fixed size buffer pools."

        GROUP   strHoldConditionalGroup
        DESCRIPTION   
              "Mandatory if the Stream head hold feature is 
               present in the STREAMS implementation."

        GROUP   strApshTableConditionalGroup
        DESCRIPTION   
              "Mandatory when the STREAMS implementation is 
               capable of adding entries to an autopush 
               specification while the system is running and 
               without rebooting."

        GROUP   strModTableConditionalGroup
        DESCRIPTION   
              "Mandatory when the STREAMS implementation is 
               capable of creating or destroying entries in the 
               module or driver switch table while the system is 
               running and without rebooting."

        GROUP   strModInfoTableConditionalGroup
        DESCRIPTION   
              "Mandatory if the STREAMS implementation supports 
               user settable trace levels for STREAMS modules."

        GROUP   strModStatTableConditionalGroup
        DESCRIPTION   
              "Mandatory if the STREAMS implementation supports 
               more than one module_stat structure per module."

        GROUP   strStatsTableConditionalGroup
        DESCRIPTION   
              "Mandatory when the STREAMS implementation keeps 
               track of high water marks."

        OBJECT  strCltime
        MIN-ACCESS  read-only
        DESCRIPTION   
              "It is permitted to provide this tunable as 
               read-only where the STREAMS subsystem is incapable 
               of changing it without exceptional action such as 
               recompiling the kernel."

        OBJECT  strMaxApush
        MIN-ACCESS  read-only
        DESCRIPTION   
              "It is permitted to provide this tunable as 
               read-only where the STREAMS subsystem is incapable 
               of changing it without exceptional action such as 
               recompiling the kernel."

        OBJECT  strMaxMblk
        MIN-ACCESS  read-only
        DESCRIPTION   
              "It is permitted to provide this tunable as 
               read-only where the STREAMS subsystem is incapable 
               of changing it without exceptional action such as 
               recompiling the kernel."

        OBJECT  strMaxStramod
        MIN-ACCESS  read-only
        DESCRIPTION   
              "It is permitted to provide this tunable as 
               read-only where the STREAMS subsystem is incapable 
               of changing it without exceptional action such as 
               recompiling the kernel."

        OBJECT  strMsgPriority
        MIN-ACCESS  read-only
        DESCRIPTION   
              "It is permitted to provide this tunable as 
               read-only where the STREAMS subsystem is incapable 
               of changing it without exceptional action such as 
               recompiling the kernel."

        OBJECT  strNstrmsgs
        MIN-ACCESS  read-only
        DESCRIPTION   
              "It is permitted to provide this tunable as 
               read-only where the STREAMS subsystem is incapable 
               of changing it without exceptional action such as 
               recompiling the kernel."

        OBJECT  strNstrpush
        MIN-ACCESS  read-only
        DESCRIPTION   
              "It is permitted to provide this tunable as 
               read-only where the STREAMS subsystem is incapable 
               of changing it without exceptional action such as 
               recompiling the kernel."

        OBJECT  strHiwat
        MIN-ACCESS  read-only
        DESCRIPTION   
              "It is permitted to provide this tunable as 
               read-only where the STREAMS subsystem is incapable 
               of changing it without exceptional action such as 
               recompiling the kernel."

        OBJECT  strLowat
        MIN-ACCESS  read-only
        DESCRIPTION   
              "It is permitted to provide this tunable as 
               read-only where the STREAMS subsystem is incapable 
               of changing it without exceptional action such as 
               recompiling the kernel."

        OBJECT  strMaxpsz
        MIN-ACCESS  read-only
        DESCRIPTION   
              "It is permitted to provide this tunable as 
               read-only where the STREAMS subsystem is incapable 
               of changing it without exceptional action such as 
               recompiling the kernel."

        OBJECT  strMinpsz
        MIN-ACCESS  read-only
        DESCRIPTION   
              "It is permitted to provide this tunable as 
               read-only where the STREAMS subsystem is incapable 
               of changing it without exceptional action such as 
               recompiling the kernel."

        OBJECT  strRtime
        MIN-ACCESS  read-only
        DESCRIPTION   
              "It is permitted to provide this tunable as 
               read-only where the STREAMS subsystem is incapable 
               of changing it without exceptional action such as 
               recompiling the kernel."

        OBJECT  strStrhold
        MIN-ACCESS  read-only
        DESCRIPTION   
              "It is permitted to provide this tunable as 
               read-only where the STREAMS subsystem is incapable 
               of changing it without exceptional action such as 
               recompiling the kernel."

        OBJECT  strStrctlsz
        MIN-ACCESS  read-only
        DESCRIPTION   
              "It is permitted to provide this tunable as 
               read-only where the STREAMS subsystem is incapable 
               of changing it without exceptional action such as 
               recompiling the kernel."

        OBJECT  strStrmsgsz
        MIN-ACCESS  read-only
        DESCRIPTION   
              "It is permitted to provide this tunable as 
               read-only where the STREAMS subsystem is incapable 
               of changing it without exceptional action such as 
               recompiling the kernel."

        OBJECT  strIoctime
        MIN-ACCESS  read-only
        DESCRIPTION   
              "It is permitted to provide this tunable as 
               read-only where the STREAMS subsystem is incapable 
               of changing it without exceptional action such as 
               recompiling the kernel."

        OBJECT  strStrthresh
        MIN-ACCESS  read-only
        DESCRIPTION   
              "It is permitted to provide this tunable as 
               read-only where the STREAMS subsystem is incapable 
               of changing it without exceptional action such as 
               recompiling the kernel."

        OBJECT  strLowthresh
        MIN-ACCESS  read-only
        DESCRIPTION   
              "It is permitted to provide this tunable as 
               read-only where the STREAMS subsystem is incapable 
               of changing it without exceptional action such as 
               recompiling the kernel."

        OBJECT  strMedthresh
        MIN-ACCESS  read-only
        DESCRIPTION   
              "It is permitted to provide this tunable as 
               read-only where the STREAMS subsystem is incapable 
               of changing it without exceptional action such as 
               recompiling the kernel."

        OBJECT  strModInfoMinpsz
        MIN-ACCESS  read-only
        DESCRIPTION   
              "It is permitted to provide this column as read-only 
               where the STREAMS subsystem is incapable of 
               changing it without exceptional action such as 
               recomipiling the kernel."

        OBJECT  strModInfoMaxpsz
        MIN-ACCESS  read-only
        DESCRIPTION   
              "It is permitted to provide this column as read-only 
               where the STREAMS subsystem is incapable of 
               changing it without exceptional action such as 
               recomipiling the kernel."

        OBJECT  strModInfoHiwat
        MIN-ACCESS  read-only
        DESCRIPTION   
              "It is permitted to provide this column as read-only 
               where the STREAMS subsystem is incapable of 
               changing it without exceptional action such as 
               recompiling the kernel."

        OBJECT  strModInfoLowat
        MIN-ACCESS  read-only
        DESCRIPTION   
              "It is permitted to provide this column as read-only 
               where the STREAMS subsystem is incapable of 
               changing it without exceptional action such as 
               recomipiling the kernel."

        OBJECT  strApshModules
        MIN-ACCESS  read-only
        DESCRIPTION   
              "As it is optional to permit addition of rows to the 
               strApshTable by management stations, this column 
               may be implemented as read-only when the capability 
               to add rows is not provided."

    ::= { strCompliances 1 }

END -- end of module OPENSS7-STREAMS-MIB.
