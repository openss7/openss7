-- vim: ft=mib comments=\f\:\",\b\:\-\-,\:\-\-,\f\b\:- fo+=tcqlornw tw=72 nocin nosi sts=4 sw=4 et
-- =============================================================================
-- 
-- @(#) src/mibs/OPENSS7-MX-MON-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: nonwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================


-- Log rotation.
-- - size
-- - interval
-- - filename (date and hour) designator
-- 
-- - once per hour
-- 
-- - archive folder
-- - move data to archive folder when collected
-- 
-- - maximum fill on data partition.
-- 
-- - where to transfer to

OPENSS7-MX-MON-MIB DEFINITIONS ::= BEGIN

IMPORTS
    openss7Modules
        FROM OPENSS7-SMI
    AdministrativeState, AvailabilityStatus, FullAction, IntervalsOfDay, 
    LogCapacityAlarmThreshold, OperationalState, ProceduralStatus, 
    SimpleNameType, UsageState, WeekMask
        FROM OPENSS7-SMI-MIB
    MilliSeconds
        FROM OPENSS7-TC
    SnmpAdminString
        FROM SNMP-FRAMEWORK-MIB
    MODULE-COMPLIANCE, OBJECT-GROUP
        FROM SNMPv2-CONF
    Counter32, Gauge32, MODULE-IDENTITY, OBJECT-TYPE, 
    Unsigned32
        FROM SNMPv2-SMI
    DisplayString, RowStatus, StorageType, TEXTUAL-CONVENTION, 
    TimeInterval, TimeStamp, TruthValue
        FROM SNMPv2-TC
    TransportAddress, TransportAddressType
        FROM TRANSPORT-ADDRESS-MIB;

mxMonMIB MODULE-IDENTITY
    LAST-UPDATED "201207200619Z"
    ORGANIZATION 
        "The OpenSS7 Project"
    CONTACT-INFO 
        "Brian Bidulock
         OpenSS7 Corporation
         1469 Jefferys Crescent
         Edmonton AB  T6L 6T1
         CANADA
         Tel: +1 780 490 1141
         Fax: +1 780 490 1241
         Mob: +1 780 953 0557
         E-Mail: bidulock@openss7.org"
    DESCRIPTION 
        "MIB Module for monitoring the MX multiplexing driver.  In the 
         OpenSS7 system the MX multiplexing driver is a TDM switching 
         module.
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201207200619Z"
    DESCRIPTION 
        "First release of this module."
    ::= { openss7Modules 81 }

-- ====================================================================
-- TEXTUAL CONVENTIONS
-- ====================================================================

TimesOfDay ::= TEXTUAL-CONVENTION
    DISPLAY-HINT "1d:1d,"
    STATUS      current
    DESCRIPTION 
        "This textual convention specifies times of day by hour and 
         minute and replaces the following ASN.1 syntax:
         
         TimesOfDay ::= SET OF Time24
         
         It consists of an octet string that is an integral multiple of 
         2 octets.  Each 2 octet grouping is coded as a Time24 textual 
         convention representing one time of day.  Each two-octet 
         grouping represents as separate time of day."
    REFERENCE   
        "ITU-T Rec. X.721 (1992) | ISO/IEC 10165-2 : 1992, 
               Attribute-ASN1Module.IntervalsOfDay"
    SYNTAX      OCTET STRING

TimesOfWeek ::= TEXTUAL-CONVENTION
    DISPLAY-HINT "1x"
    STATUS      current
    DESCRIPTION 
        "This textual convention specifies intervals in the day for days 
         of the week and replaces the following ASN.1 syntax:
         
         WeekMask ::= SET OF SEQUENCE {
            daysOfWeek BIT STRING {
                sunday(0),
                monday(1),
                tuesday(2),
                wednesday(3),
                thursday(4),
                friday(5),
                saturday(6) }(SIZE(7)),
            timesOfDay TimesOfDay }
         
         The first octet of the octet string is a day of seek indicator 
         that can have bit values: sunday(0), monday(1), tuesday(2), 
         wednesday(3), thursday(4), friday(5) and saturday(6), with bit 
         position 7 unused and set to zero.  The second octet of the 
         string is an interval count indicating the number, 'n', of 
         times of day (multiples of 2 octets) to follow.  The next nx2 
         octets represent the times of day following the TimesOfDay 
         textual convention.  The pattern is repeated again beginning 
         with the week octet."
    REFERENCE   
        "ITU-T Rec. X.721 (1992) | ISO/IEC 10165-2 : 1992, 
               Attribute-ASN1Module.WeekMask"
    SYNTAX      OCTET STRING

DataLinkType ::= TEXTUAL-CONVENTION
    STATUS      current
    DESCRIPTION 
        "This textual convention specifies the data link type of a 
         capture file or interface in a capture file using the 
         convention of the PCAP and PCAP-NG file formats."
    REFERENCE   
        "PCAP/PCAPNG file formst."
    SYNTAX      INTEGER { null(0), ethernet(1), expether(2), ax25(3), 
                    pronet(4), chaos(5), tokenring(6), arcnet(7), 
                    slip(8), ppp(9), fddi(10), ppphdlc(50), pppether(51), 
                    symantec(99), rfc1483(100), rawip(101), bsdslip(102), 
                    bsdppp(103), ciscohdlc(104), ieee80211(105), 
                    atmclip(106), frelay(107), loop(108), enc(109), 
                    lane8023(110), hippi(111), hdlc(112), linuxsll(113), 
                    ltalk(114), econet(115), ipfilter(116), pflog(117), 
                    prism(119), aironet(120), hhdlc(121), rfc2825(122), 
                    sunatm(123), rio(124), pcie(125), aurora(126), 
                    ieee80211radio(127), tzsp(128), arcnetlinux(129), 
                    ipieee1394(138), mtp2ph(139), mtp2(140), mtp3(141), 
                    sccp(142), docsis(143), irda(144) }

mxMonNotifications OBJECT IDENTIFIER
    ::= { mxMonMIB 1 }

mxMonObjects OBJECT IDENTIFIER
    ::= { mxMonMIB 2 }

-- ====================================================================
-- TABLES
-- ====================================================================

mxMonitor OBJECT IDENTIFIER
    ::= { mxMonObjects 1 }

mxMonitorName OBJECT-TYPE
    SYNTAX      SnmpAdminString
    MAX-ACCESS  read-write
    STATUS      current
    DESCRIPTION 
        "Provides the name of the probe.  The name of the probe can be 
         changed by writing to this object.  Note that changes will be 
         be effective in capture files until rotation."
    ::= { mxMonitor 1 }

mxMonitorHardware OBJECT-TYPE
    SYNTAX      SnmpAdminString
    MAX-ACCESS  read-write
    STATUS      current
    DESCRIPTION 
        "Provides as description of the hardware of the probe.  This 
         information will go in the shb_hardware option field of a 
         PCAP-NG file captured from this probe."
    ::= { mxMonitor 2 }

mxMonitorOs OBJECT-TYPE
    SYNTAX      SnmpAdminString
    MAX-ACCESS  read-write
    STATUS      current
    DESCRIPTION 
        "Provides the name of the operating system of the probe.  This 
         information will go in the shb_os option field of a PCAP-NG 
         section header in a file captured from this probe."
    ::= { mxMonitor 3 }

mxMonitorUserAppl OBJECT-TYPE
    SYNTAX      SnmpAdminString
    MAX-ACCESS  read-only
    STATUS      current
    DESCRIPTION 
        "Provides the name of the application and version runnning on 
         the probe.  This information will go in the shb_userappl option 
         field of a PCAP-NG section header in a file captured from this 
         probe."
    ::= { mxMonitor 4 }

mxMonitorTable OBJECT-TYPE
    SYNTAX      SEQUENCE OF MxMonitorEntry
    MAX-ACCESS  not-accessible
    STATUS      current
    DESCRIPTION 
        "Provides a table of sources that are to be monitored (messages 
         captured)."
    ::= { mxMonitor 5 }

mxMonitorEntry OBJECT-TYPE
    SYNTAX      MxMonitorEntry
    MAX-ACCESS  not-accessible
    STATUS      current
    DESCRIPTION 
        "Each row in the monitor table describes a message source that 
         is to be monitored.  Message sources can be entire drivers, 
         entire cards, specific spans or specific channels within a 
         specific span."
    INDEX       { mxMonitorSource }
    ::= { mxMonitorTable 1 }

MxMonitorEntry ::= SEQUENCE {
    mxMonitorSource             SimpleNameType,
    mxMonitorExport             TruthValue,
    mxMonitorAdminState         AdministrativeState,
    mxMonitorOperState          OperationalState,
    mxMonitorAvailStatus        AvailabilityStatus,
    mxMonitorProcStatus         ProceduralStatus,
    mxMonitorUsageState         UsageState,
    mxMonitorMessages           Counter32,
    mxMonitorMsgOctets          Counter32,
    mxMonitorSusCompressed      Counter32,
    mxMonitorMsuDrops           Counter32,
    mxMonitorFilterDrops        Counter32,
    mxMonitorActiveLinkDirs     Gauge32,
    mxMonitorActiveHslDirs      Gauge32,
    mxMonitorResetCounts        TruthValue,
    mxMonitorLastReset          TimeStamp,
    mxMonitorCurrent            TimeStamp
}

mxMonitorSource OBJECT-TYPE
    SYNTAX      SimpleNameType
    MAX-ACCESS  not-accessible
    STATUS      current
    DESCRIPTION 
        "Provides the identification of the source and scope of the 
         messages to be monitored.  An MX monitoring source is described 
         using a non-null codified ASCII string that has the following 
         components:
         
         - The driver name (or a single '*' indicating all drivers).  
           When different from '*', the driver name must conform to the 
           specification of a StreamsModuleName textual convention from 
           the OPENSS7-STREAMS-MIB.  When the driver name is a single 
           asterisk ('*'), the monitoring source refers to all sources 
           from all MX drivers.  When the source name ends in the driver 
           name (the driver name ends in a alphabetical character), the 
           monitoring source refers to all sources from the specified 
           driver.
         
         - One or more ASCII digits specifying an ordinal card number 
           (starting at zero 0) supported by the driver.  This component 
           is optional; however, it must be specified if the component 
           that follows is specified.  When the source name ends with 
           this component, the monitoring source refers to all sources 
           for the specified card.
         
         - A colon (':') followed by one or more ASCII digits specifying 
           an ordinal span number on the card (starting at zero).  When 
           the source name ends with this component, the monitoring 
           source refers to all sources for the specified span.
         
         - A period ('.') followed by one or more ASCII digits 
           specifying the ordinal channel number on the card.  The 
           ordinal channel number starts at one and spans through 24 for 
           T1/J1 spans and 31 for E1 spans.  The channel number zero (0) 
           is special and refers to a high-speed signalling link that 
           takes up the entire span.  When the source name ends with 
           this component, the monitoring source refers to the specified 
           channel(s)."
    ::= { mxMonitorEntry 1 }

mxMonitorExport OBJECT-TYPE
    SYNTAX      TruthValue
    MAX-ACCESS  read-create
    STATUS      current
    DESCRIPTION 
        "Specifies whether this monitor source will be exported as a 
         monitor source to remote system.  When true(1), the monitor 
         source will be exported; false(2), otherwise."
    DEFVAL      { true }
    ::= { mxMonitorEntry 2 }

mxMonitorAdminState OBJECT-TYPE
    SYNTAX      AdministrativeState
    MAX-ACCESS  read-create
    STATUS      current
    DESCRIPTION 
        "Provides the administrative state of the monitor source:
         
         - locked(0), capture of messages from this monitor source is 
           administratively prohibited;
         
         - unlocked(1), capture of messages from this monitor source is 
           administratively permitted;
         
         - shuttingDown(2), the monitor source is shutting down: once it 
           ceases generating messages, it will move to the locked(0) 
           state.
         
         The value shuttingDown(2) is only valid when read and not valid 
         when written.  This object is used primarily to enable or 
         disable capture from the monitor source."
    REFERENCE   
        "OPENSS7-SMI-MIB, ITU-T Rec. X.721 | ISO/IEC 10165-2, 
         administrativeState."
    DEFVAL      { unlocked }
    ::= { mxMonitorEntry 3 }

mxMonitorOperState OBJECT-TYPE
    SYNTAX      OperationalState
    MAX-ACCESS  read-only
    STATUS      current
    DESCRIPTION 
        "Provides the operational state of the monitor source:
         
         - enabled(0), message source is enabled;
         - disabled(1), message source is disabled.
         
         When enabled(0), messages generated by the source can be 
         captured; when disabled(1), they cannot."
    REFERENCE   
        "OPENSS7-SMI-MIB, ITU-T Rec. X.721 | ISO/IEC 10165-2, 
         operationalState."
    DEFVAL      { enabled }
    ::= { mxMonitorEntry 4 }

mxMonitorAvailStatus OBJECT-TYPE
    SYNTAX      AvailabilityStatus
    MAX-ACCESS  read-only
    STATUS      current
    DESCRIPTION 
        "Provides the availability status of the monitor source; it 
         may contain:
         
         - inTest(0), the monitor source is in test; administrative 
           state is locked(0), operational state is disabled(1);
         
         - failed(1), the monitor source has an internal fault that 
           prevents it from operating; operational state disabled(1);
         
         - powerOff(2), the monitor source is not powered on;
         
         - offLine(3), the monitor source requires a routing operation;
         
         - offDuty(4), the monitor source is off duty per schedule;
         
         - dependency(5), the monitor source cannot operate due to a 
           dependency;
         
         - degraded(6), the monitor source is operating with degraded 
           performance;
         
         - notInstalled(7), the monitor source is not installed.
           
         - logFull(8), not used."
    ::= { mxMonitorEntry 5 }

mxMonitorProcStatus OBJECT-TYPE
    SYNTAX      ProceduralStatus
    MAX-ACCESS  read-only
    STATUS      current
    DESCRIPTION 
        "Provides the procedural status of the monitor source:
         
         - initializationRequired(0), hardware or firmware associated 
           with the monitor source requires initialization and that 
           initialization has not yet been performed; a manual or 
           automatic action is required to initialize the monitor 
           source;
         - notInitialized(1), hardware or firmware associated with the 
           monitor source requires initialization and that 
           initialization has not completed yet;
         - initializing(2), hardware or firmware associated with the 
           monitor source requires initialization and that 
           initialization is proceeding but has not yet completed;
         - reporting(3), the monitor source is reporting its 
           results;
         - terminating(4), the monitor source is terminating.
         
         The procedural status for monitor sources result from actions 
         taken by the underlying device or device driver and not by 
         actions taken within this MIB."
    REFERENCE   
        "OPENSS7-SMI-MIB, ITU-T Rec. X.721 | ISO/IEC 10165-2, 
         proceduralStatus."
    ::= { mxMonitorEntry 6 }

mxMonitorUsageState OBJECT-TYPE
    SYNTAX      UsageState
    MAX-ACCESS  read-only
    STATUS      current
    DESCRIPTION 
        "Provides the usage state of the monitor source:
         
         - idle(0), the monitor source is not currently in use;
           
         - active(1), the monitor source is in use and has sufficient 
           operating capacity to provide for additional users 
           simultaneously;
           
         - busy(2), the monitor is in use an has no spare capacity.
           
         This usage state determines the use of the monitor source as a 
         monitor and not any use of the source in active communication.  
         For example, a channel monitor source could be idle(0) for 
         monitoring, and busy(2) in active communication."
    REFERENCE   
        "OPENSS7-SMI-MIB, ITU-T Rec. X.721 | ISO/IEC 10165-2, 
             usageState."
    ::= { mxMonitorEntry 7 }

mxMonitorMessages OBJECT-TYPE
    SYNTAX      Counter32
    UNITS       "messages"
    MAX-ACCESS  read-only
    STATUS      current
    DESCRIPTION 
        "Provides a count of the number of messages that were captured 
         from the source at the time that this object was read.  For an 
         active monitoring source and capture, this counter will 
         increase monotonically (wrapping) and rapidly.  The counter can 
         be reset to zero by writing to the mxMonitorResetCounts column.  
         
         Note that this counter is also reset to zero by the agent 
         whenever a capture file is rotated.
         
         Note that the mxMonitorCurrent column can be read in the same 
         request to obtain the time stamp corresponding to the read of 
         the message count."
    ::= { mxMonitorEntry 8 }

mxMonitorMsgOctets OBJECT-TYPE
    SYNTAX      Counter32
    UNITS       "message octets"
    MAX-ACCESS  read-only
    STATUS      current
    DESCRIPTION 
        "Provides a count of the number of message octets that were 
         captured from the source by the time that this object was read.  
         For an active monitoring source and capture, this counter will 
         increase monotonically (wrapping) and rapidly.  The counter can 
         be reset to zero by writing to the mxMonitorResetCounts column.  
         
         Note that this counter is also reset to zero by the agent 
         whenever a capture file is rotated.
         
         Note that the mxMonitorCurrent column can be read in the same 
         request to obtain the time stamp corresponding to the read of 
         the message octets."
    ::= { mxMonitorEntry 9 }

mxMonitorSusCompressed OBJECT-TYPE
    SYNTAX      Counter32
    UNITS       "SUs"
    MAX-ACCESS  read-only
    STATUS      current
    DESCRIPTION 
        "Provides a count of the number of FISUs or LSSUs that were 
         compressed due to repetition.  For an active monitoring source 
         and capture, this counter will increase monotonically 
         (wrapping) and rapidly.  The counter can be reset to zero by 
         writing to the mxMonitorResetCounts column.
         
         Note that this counter is also reset to zero by the agent 
         whenever a capture file is rotated.
         
         Note that the mxMonitorCurrent column can be read in the same 
         request to obtain the time stamp corresponding to the read of 
         the compressed signal units."
    ::= { mxMonitorEntry 10 }

mxMonitorMsuDrops OBJECT-TYPE
    SYNTAX      Counter32
    UNITS       "MSUs"
    MAX-ACCESS  read-only
    STATUS      current
    DESCRIPTION 
        "Provides a count of the number of MSUs that were dropped due to 
         inadequate resources.  For an active monitoring source and 
         capture, this counter should always remain at zero.  The 
         counter can be reset to zero by writing to the 
         mxMonitorResetCounts column.
         
         Note that this counter is also reset to zero by the agent 
         whenever a capture file is rotated.
         
         Note that the mxMonitorCurrent column can be read in the same 
         request to obtain the time stamp corresponding to the read of 
         the compressed signal units."
    ::= { mxMonitorEntry 11 }

mxMonitorFilterDrops OBJECT-TYPE
    SYNTAX      Counter32
    UNITS       "messages"
    MAX-ACCESS  read-only
    STATUS      current
    DESCRIPTION 
        "Provides a count of the number of messages that were rejected 
         by a filter.  For an active monitoring source and capture with 
         a stringent filter, this counter should increase rapidly and 
         wrap.  The counter can be reset to zero by writing to the 
         mxMonitorResetCounts column.
         
         Note that this counter is also reset to zero by the agent 
         whenever a capture file is rotated.
         
         Note that the mxMonitorCurrent clumn can be read in the same 
         request to obtain the time stamp corresponding to the read of 
         the compressed signal units."
    ::= { mxMonitorEntry 12 }

mxMonitorActiveLinkDirs OBJECT-TYPE
    SYNTAX      Gauge32
    UNITS       "channels"
    MAX-ACCESS  read-only
    STATUS      current
    DESCRIPTION 
        "Provides a high watermark of the number of low-speed (56 or 64 
         kbps) signalling link directions that were actively monitored 
         (i.e, messages were captured from the link for the direction) 
         since the watermark was reset.  This watermark can be reset to 
         zero by writing to the mxMoniorResetCounts column.  The 
         watermark is also reset to zero by the agent whenever a capture 
         file is rotated.  This column is useful for determining whether 
         the appropriate number of signalling links are being monitored 
         for a span, card, driver or default source."
    ::= { mxMonitorEntry 13 }

mxMonitorActiveHslDirs OBJECT-TYPE
    SYNTAX      Gauge32
    UNITS       "spans"
    MAX-ACCESS  read-only
    STATUS      current
    DESCRIPTION 
        "Provides a high watermark of the number of high-speed (1.536 or 
         1.892 kbps) signalling link directions that were actively 
         monitored (i.e, messages were captured from the link for the 
         direction) since the watermark was reset.  This watermark can 
         be reset to zero by writing to the mxMonitorResetCounts column.  
         The watermark is also reset to zero by the agent whenever a 
         capture file is rotated.  This is useful for determining 
         whether an appropriate number of signalling links are being 
         monitored for a card, driver or default source."
    ::= { mxMonitorEntry 14 }

mxMonitorResetCounts OBJECT-TYPE
    SYNTAX      TruthValue
    MAX-ACCESS  read-create
    STATUS      current
    DESCRIPTION 
        "When true(1) is written to this object, the counts provided in 
         mxMonitorMessages, mxMonitorMsgOctets, mxMonitorActiveLinkDirs 
         and mxMonitorActiveHslDirs are reset to zero."
    DEFVAL      { false }
    ::= { mxMonitorEntry 15 }

mxMonitorLastReset OBJECT-TYPE
    SYNTAX      TimeStamp
    MAX-ACCESS  read-only
    STATUS      current
    DESCRIPTION 
        "Provides the time (using the TimeStamp textual convention) at 
         which the counts provided in mxMonitorMessages, 
         mxMonitorMsgOctets, mxMonitorActiveLinkDirs and 
         mxMonitorActiveHslDirs were reset to zero.  The intent of this 
         object is to allow some support for scripting at the management 
         station."
    ::= { mxMonitorEntry 16 }

mxMonitorCurrent OBJECT-TYPE
    SYNTAX      TimeStamp
    MAX-ACCESS  read-only
    STATUS      current
    DESCRIPTION 
        "Provides the time (using the TimeStamp textual convention) at 
         which this object was read.  This time stamp can be used in 
         conjunction with the mxMonitorLastReset time stamp to determine 
         for what time interval the counts also read apply.  The intent 
         of this object is to allow some support for scripting at the 
         management station."
    ::= { mxMonitorEntry 17 }

-- =====================================================================
-- mxCapture group
-- =====================================================================
-- The mxCapture group is responsible for managing the naming, rotation, 
-- spooling, upload and archiving of capture files.
-- .....................................................................

mxCapture OBJECT IDENTIFIER
    ::= { mxMonObjects 2 }

mxCaptureNameString OBJECT-TYPE
    SYNTAX      SimpleNameType
    MAX-ACCESS  read-write
    STATUS      current
    DESCRIPTION 
        "Specifies the file name as a printf-style string that specifies 
         the base name of the file (without file extensions)."
    DEFVAL      { "mxmon-%Y-%M-%D-%H" }
    ::= { mxCapture 1 }

mxCaptureFormat OBJECT-TYPE
    SYNTAX      INTEGER { pcap(1), pcapng(2) }
    MAX-ACCESS  read-write
    STATUS      current
    DESCRIPTION 
        "Specifies the capture file format.  When written, the change 
         may not be effective until the next file rotation."
    DEFVAL      { pcapng }
    ::= { mxCapture 2 }

mxCaptureAdminState OBJECT-TYPE
    SYNTAX      AdministrativeState
    MAX-ACCESS  read-write
    STATUS      current
    DESCRIPTION 
        "This attribute represents the administrative capability of the 
         capture archive to perform its function.  The following 
         administrative states are defined:
         
         - locked(0), use of the capture archive has been prohibited by 
           a managing system.  Information from subordinate files may be 
           retrieved but new files shall not be created.  Files may be 
           deleted.
           
         - unlocked(1), use of the capture archive has been permitted by 
           a managing system.  Information from subordinate files may be 
           retrieved and, conditional on the values of other state and 
           status attributes, new files may be created.
           
         Whenever the administrative state of the capture archive is 
         changed, a state change notification is generated."
    REFERENCE   
        "ITU-T Rec. X.735 (1992) | ISO/IEC 10164-6 : 1993, 
               Section 8.1.1.1.3."
    DEFVAL      { unlocked }
    ::= { mxCapture 3 }

mxCaptureOpState OBJECT-TYPE
    SYNTAX      OperationalState
    MAX-ACCESS  read-only
    STATUS      current
    DESCRIPTION 
        "This attribute represents that operational capability of the 
         capture archive to perform its function.  The following 
         operational states are defined:
         
         - enabled(0), the log is operational and ready for use.  
           Information from subordinate records may be retrieved and, 
           conditional on the values of other state and status 
           attributes, new records may be created.
           
         - disabled(1), the log is not available for use.  New records 
           cannot be created.
           
         A change in operational state shall generate a state changed 
         notification."
    REFERENCE   
        "ITU-T Rec. X.735 (1992) | ISO/IEC 10164-6 : 1993, 
               Section 8.1.1.1.4."
    DEFVAL      { enabled }
    ::= { mxCapture 4 }

mxCaptureAvailStatus OBJECT-TYPE
    SYNTAX      AvailabilityStatus
    MAX-ACCESS  read-only
    STATUS      current
    DESCRIPTION 
        "This attribute reflects the availability status of the log.  
         The attribute may indicate a 'log-full' condition; indicating 
         that records can be retrieved but that no new records can be 
         added.
         
         The availability status package shall be present if any of the 
         scheduling packages are instantiated.  This attribute reflects 
         the availability status of the log.  When the resource has been 
         made unavailable in accordance with a predetermined time 
         schedule its value will be 'Off-Duty'.  The attribute is 
         read-only.  The value on creation is determined by the 
         scheduling parameters specified and the status of the resource.  
         The required value set for this attribute in this package is 
         'Off-Duty'.
         
         No state change notification is generated when this attribute 
         changes value.  Note: the log makes use of the availability 
         status to indicate the 'log-full' condition; the presence of 
         this conditional package makes available the 'Off-Duty' value 
         to the object."
    REFERENCE   
        "ITU-T Rec. X.735 (1992) | ISO/IEC 10164-6 : 1993, 
               Section 8.1.1.1.6.
         ITU-T Rec. X.735 (1992) | ISO/IEC 10164-6 : 1993, 
         Section 8.1.1.4.1."
    DEFVAL      { {} }
    ::= { mxCapture 5 }

mxCaptureFullAction OBJECT-TYPE
    SYNTAX      FullAction
    MAX-ACCESS  read-write
    STATUS      current
    DESCRIPTION 
        "Provides a specification of the action to be taken when the 
         maximum size of the log has been reached.  Options are:
         
         - wrap(0), the oldest records in the log, as determined by the 
           record time stamp, will be deleted to free resources for the 
           creation of new records;
           
         - halt(1), no more records will be logged; records already in 
           the log will be retained.
           
         Both options are supported by every log."
    DEFVAL      { wrap }
    ::= { mxCapture 6 }

mxCaptureMaxSize OBJECT-TYPE
    SYNTAX      Unsigned32
    MAX-ACCESS  read-write
    STATUS      current
    DESCRIPTION 
        "This attribute specifies the size of the log measured in number 
         of octets.  A log may have an indeterminate size.  A maximum 
         log size of zero shall be used to specify that the log size has 
         no predefined limit.
         
         Note: Since the log size is specified in octets, the actual 
         amount of information that is contained in a log will be 
         determined by the data representation in the log.  This data 
         representation is not subject to standardization.  The maximum 
         log size does not include the system overhead involved in 
         establishing the log.  Thus, immediately after creation, the 
         current log size should read zero."
    REFERENCE   
        "ITU-T Rec. X.735 (1992) | ISO/IEC 10164-6 : 1993,
                Section 8.1.1.2.1"
    DEFVAL      { 0 }
    ::= { mxCapture 7 }

mxCaptureCurrentSize OBJECT-TYPE
    SYNTAX      Gauge32
    MAX-ACCESS  read-only
    STATUS      current
    DESCRIPTION 
        "This attribute indicates the current size of the log measured 
         in octets.
         
         Note: Since the log size is specified in octets, the actual 
         amount of information that is contained in a log will be 
         determined by the data representation in the log.  This data 
         representation is not subject to standardization.  The maximum 
         log size does not include the system overhead involved in 
         establishing the log.  Thus, immediately after creation, the 
         current log size should read zero."
    REFERENCE   
        "ITU-T Rec. X.735 (1992) | ISO/IEC 10164-6 : 1993, 
               Section 8.1.1.2.2."
    DEFVAL      { 0 }
    ::= { mxCapture 8 }

mxCaptureNumberOfRecords OBJECT-TYPE
    SYNTAX      Gauge32
    MAX-ACCESS  read-only
    STATUS      current
    DESCRIPTION 
        "This attribute indicates the current number of records 
         contained in the log."
    REFERENCE   
        "ITU-T Rec. X.735 (1992) | ISO/IEC 10164-6 : 1993, 
               Section 8.1.1.2.3."
    DEFVAL      { 0 }
    ::= { mxCapture 9 }

mxCaptureAlarmThreshold OBJECT-TYPE
    SYNTAX      LogCapacityAlarmThreshold
    MAX-ACCESS  read-write
    STATUS      current
    DESCRIPTION 
        "The log alarm package provides for transmission of alarms when 
         a log full condition approaches.  This package shall be present 
         whenever a log is of finite size and halts logging when the log 
         full availability status occurs.
         
         This attribute specifies, as a percentage of maximum log size, 
         the points at which an event will be generated to indicate that 
         a log full or log wrap condition is approaching.  This 
         attribute is set-valued.  Support of this attribute is 
         mandatory for the halt behaviour.  When a log is created with 
         the wrap option the capacity threshold events are triggered as 
         if coupled to a gauge that counts from zero to the highest 
         capacity threshold value defined and then resets to zero."
    REFERENCE   
        "ITU-T Rec. X.735 (1992) | ISO/IEC 10164-6 : 1993, 
               Section 8.1.1.3."
    DEFVAL      { "\x64" }
    ::= { mxCapture 10 }

mxCaptureStartTime OBJECT-TYPE
    SYNTAX      TimeStamp
    MAX-ACCESS  read-write
    STATUS      current
    DESCRIPTION 
        "The duration package provides the ability to automatically 
         control the time that a managed object starts and stops 
         functioning through the use of the start and stop time 
         attributes.
         
         This attribute defines the date and time at which an unlocked 
         and enabled managed object starts functioning.  If the value of 
         the start time attribute is not specified in the create 
         request, its value defaults to the time of creation of the 
         managed object and thus causing it to function immediately.
         
         A change in the start time attribute results in an attribute 
         change notification."
    REFERENCE   
        "ITU-T Rec. X.735 (1992) | ISO/IEC 10164-6 : 1993, 
               Section 8.1.1.4.2."
    DEFVAL      { 0 }
    ::= { mxCapture 11 }

mxCaptureStopTime OBJECT-TYPE
    SYNTAX      TimeStamp
    MAX-ACCESS  read-write
    STATUS      current
    DESCRIPTION 
        "The duration package provides the ability to automatically 
         control the time that a managed object starts and stops 
         functioning through the use of the start and stop time 
         attributes.
         
         This attribute defines the date and time at which a managed 
         object stops functioning.  If the value of the stop time 
         attribute is not specified in the create request, its value 
         defaults to 'continuous operation'.  Continuous operation is 
         represented by a null value for the stop time.
         
         A change in the stop time attribute results in an attribute 
         change notification."
    REFERENCE   
        "ITU-T Rec. X.735 (1992) | ISO/IEC 10164-6 : 1993, 
               Section 8.1.1.4.2."
    DEFVAL      { 6983120 }
    ::= { mxCapture 12 }

mxCaptureIntervalsOfDay OBJECT-TYPE
    SYNTAX      IntervalsOfDay
    MAX-ACCESS  read-write
    STATUS      current
    DESCRIPTION 
        "The daily scheduling conditional package provides the 
         capability of scheduling logging with a periodicity of 
         24 hours.
         
         This attribute defines the list of time intervals 
         (interval-start and interval-end times of day) for which the 
         logs will exhibit the logging-on condition.  During excluded 
         intervals the log exhibits the logging-off condition.  If not 
         specified in the create request, the value of this component 
         defaults to a single interval encompassing the entire 24 hour 
         period of a day."
    REFERENCE   
        "ITU-T Rec. X.735 (1992) | ISO/IEC 10164-6 : 1993, 
               Section 8.1.1.4.3."
    DEFVAL      { "\x00\x00\x17\x3B" }
    ::= { mxCapture 13 }

mxCaptureWeekMask OBJECT-TYPE
    SYNTAX      WeekMask
    MAX-ACCESS  read-write
    STATUS      current
    DESCRIPTION 
        "The weekly scheduling conditional package provides the 
         capability of scheduling logging with a periodicity of 
         one week.  This structured attribute defines a set of 
         mask components, each specifying a set of time 
         intervals on a 24-hour time-of-day clock, pertaining to 
         selected days of the week.  The week mask attribute 
         defaults to a scheduling criteria of 'always-on' at 
         logs creation.
         
         The days of week component defines the days of the week 
         on which the log's scheduling mechanism will allow the 
         log to have intervals during which logging may occur.  
         This component, if not present is a create, will 
         default to all seven days of the week.
         
         The intervals of day component defines the list of time 
         intervals (interval-start and interval-end times of 
         day) for which the log will exhibit the logging-on 
         condition, if the current days is one of the days that 
         is selected within the corresponding days of week.  
         
         During excluded intervals the log exhibits the 
         logging-off condition.  If not specified in the create 
         report, the value of this component defaults to 
         a single interval encompassing the entire 24 hour 
         period of a day."
    REFERENCE   
        "ITU-T Rec. X.735 (1992) | ISO/IEC 10164-6 : 1993, 
               Section 8.1.1.4.4."
    DEFVAL      { "\x7F\x01\x00\x00\x17\x3B" }
    ::= { mxCapture 14 }

mxCaptureRotInterval OBJECT-TYPE
    SYNTAX      TimeInterval
    MAX-ACCESS  read-write
    STATUS      current
    DESCRIPTION 
        "Specifies the rotation of capture files based on the interval 
         of time since the capture file was last rotated.  When the 
         interval elapses since the last rotation, the file will be 
         rotated.  The time interval of zero is special: it specifies to 
         not rotate files based on interval."
    ::= { mxCapture 15 }

mxCaptureRotSize OBJECT-TYPE
    SYNTAX      Unsigned32
    UNITS       "bytes"
    MAX-ACCESS  read-write
    STATUS      current
    DESCRIPTION 
        "Specifies the rotation of capture files based on the file size 
         in bytes.  The capture file size includes the bytes in captured 
         messages as well as any overhead included in the record format.  
         When the file exceeds the specified size, the file will be 
         rotated.  The value zero (0) is special: it specifies to not 
         rotate files based on the size of the file."
    ::= { mxCapture 16 }

mxCaptureRotNumber OBJECT-TYPE
    SYNTAX      Unsigned32
    UNITS       "records"
    MAX-ACCESS  read-write
    STATUS      current
    DESCRIPTION 
        "Specifies the rotation of capture files based on the number of 
         records (messages) contained within the capture file. When the 
         number of messages matches the specified value, the file will 
         be rotated.  The value zero (0) is special: it specifies to not 
         rotate files based on the number of records."
    DEFVAL      { 0 }
    ::= { mxCapture 17 }

mxCaptureCachePath OBJECT-TYPE
    SYNTAX      SnmpAdminString
    MAX-ACCESS  read-write
    STATUS      current
    DESCRIPTION 
        "Specifies the file system path to the directory where files are 
         cached while they are being captured.  The default if not 
         specified on row creation is '/var/local/openss7/cache'."
    DEFVAL      { "/var/local/openss7/cache" }
    ::= { mxCapture 18 }

mxCaptureSpoolPath OBJECT-TYPE
    SYNTAX      SnmpAdminString
    MAX-ACCESS  read-write
    STATUS      current
    DESCRIPTION 
        "Specifies the file system path to the directory where files are 
         spooled once they have been rotated.  The default if not 
         specified on row creation is '/var/local/openss7/spool'."
    DEFVAL      { "/var/local/openss7/spool" }
    ::= { mxCapture 19 }

mxCaptureArchivePath OBJECT-TYPE
    SYNTAX      SnmpAdminString
    MAX-ACCESS  read-write
    STATUS      current
    DESCRIPTION 
        "Specifies the file system path to the directory where files are 
         archived once they have been uploaded.  The default if not 
         specified on row creation is '/var/local/openss7/archive'"
    DEFVAL      { "/var/local/openss7/archive" }
    ::= { mxCapture 20 }

mxCaptureArchiveSubdirs OBJECT-TYPE
    SYNTAX      BITS { daily(0), weekly(1), monthly(2), yearly(3) }
    MAX-ACCESS  read-write
    STATUS      current
    DESCRIPTION 
        "Specifies the subdirectories that will be used within the 
         archive file system directory to organize archived files by 
         date.  This object is single-valued and can contain zero or 
         more of the following values:
         
         - daily(0), collect files by day of generation within a daily 
           subdirectory whose name is the date (YYYY-MM-DD);
           
         - weekly(1), collect files and daily subdirectories (if any) 
           within a weekly subdirectory whose name is the date of the 
           beginning of the week (YYYY-MM-DD);
           
         - monthly(2), collect files, daily and weekly subdirectories 
           (if any) within a monthly subdirectory whose name is the year 
           and month (YYYY-MM);
           
         - yearly(3), collect files, daily, weekly and monthly 
           subdirectories (if any) within a yearly subdirectory whose 
           name is the year (YYYY).
           
         The default value on row creation when no set is specified is 
         daily(0) and monthly(2)."
    DEFVAL      { {daily, monthly} }
    ::= { mxCapture 21 }

mxCaptureCompression OBJECT-TYPE
    SYNTAX      INTEGER { none(0), gz(1), bz2(2), xz(3), zip(4) }
    MAX-ACCESS  read-write
    STATUS      current
    DESCRIPTION 
        "When an active capture or correlation file is rotated and 
         spooled it is compressed.  Compression is maintained on the 
         file when it is archived.  This object specifies what 
         compression to use.  This object is single-valued and can have 
         one of the following values:
         
         - none(0), no compression, no filename extension;
         
         - gz(1), gzip compression, .gz filename extension;
         
         - bz2(2), bzip2 compression, .bz2 filename extension;
         
         - xz(3), xz compression, .xz filename extension;
         
         - zip(4), zip archive, .zip filename extension.
         
         When a compression of other than none(0) is specified, the 
         corresponding file extension will be added to the file name.  
         Zip archive contain the single original file.  The default 
         value if unspecified on row creation is xz(3) compression."
    DEFVAL      { xz }
    ::= { mxCapture 22 }

mxCaptureFileSystemAlloc OBJECT-TYPE
    SYNTAX      Unsigned32
    UNITS       "percent"
    MAX-ACCESS  read-write
    STATUS      current
    DESCRIPTION 
        "Specifies the percentage of the file system in which the 
         mxCaptureArchivePath exists that is allocated to archival 
         capture files.  The total amount of space occupied by archival 
         capture files will not exceed this limit.
         
         When a row is created and this amount is not specified, the 
         default value is 90%."
    DEFVAL      { 90 }
    ::= { mxCapture 23 }

mxCaptureMaxDiskUsage OBJECT-TYPE
    SYNTAX      Unsigned32
    UNITS       "percent"
    MAX-ACCESS  read-write
    STATUS      current
    DESCRIPTION 
        "Specifies the percentage of the allocation portion of the file 
         system in which the mxCaptureArchivePath exists that is usable 
         for archival capture files.  The total amount of space occupied 
         by archival capture files will not exceed this limit.
         
         When a row is created and this amount is not specified, the 
         efault value is 80%."
    DEFVAL      { 80 }
    ::= { mxCapture 24 }

mxCaptureDiscardPolicy OBJECT-TYPE
    SYNTAX      INTEGER { ignore(0), oldest(1), largest(2) }
    MAX-ACCESS  read-write
    STATUS      current
    DESCRIPTION 
        "Specifies the discard policy for archival capture files when 
         file system allocation and disk usage limits are exceeded.  
         This object is single-valued and can assume one of the 
         following values:
         
         - ignore(0), ignores file system and disk usage limits;
           
         - oldest(1), the oldest archival capture files are discarded;
           
         - largest(2), the largest archive capture files are discarded.
           
         When a row is created and this amount is not specified, the 
         default value is oldest(1)."
    DEFVAL      { oldest }
    ::= { mxCapture 25 }

mxCaptureUpload OBJECT-TYPE
    SYNTAX      Unsigned32
    MAX-ACCESS  read-write
    STATUS      current
    DESCRIPTION 
        "Provides an index into the mxUploadTable that defines the 
         upload server to which to upload spooled files."
    ::= { mxCapture 26 }

mxCaptureTable OBJECT-TYPE
    SYNTAX      SEQUENCE OF MxCaptureEntry
    MAX-ACCESS  not-accessible
    STATUS      current
    DESCRIPTION 
        "Provides a table of capture files."
    ::= { mxCapture 27 }

mxCaptureEntry OBJECT-TYPE
    SYNTAX      MxCaptureEntry
    MAX-ACCESS  not-accessible
    STATUS      current
    DESCRIPTION 
        "Each row in the mxCaptureTable provides information concerning 
         a single capture file and provides some actions that can be 
         performed on the file."
    INDEX       { mxCaptureIndex }
    ::= { mxCaptureTable 1 }

MxCaptureEntry ::= SEQUENCE {
    mxCaptureIndex              Unsigned32,
    mxCaptureName               SnmpAdminString,
    mxCaptureCompressed         INTEGER,
    mxCaptureState              INTEGER,
    mxCaptureLinkType           DataLinkType,
    mxCaptureSize               Gauge32,
    mxCaptureCompSize           Gauge32,
    mxCaptureMessages           Gauge32,
    mxCaptureMsgOctets          Gauge32,
    mxCaptureSusCompressed      Gauge32,
    mxCaptureMsuDrops           Gauge32,
    mxCaptureFilterDrops        Gauge32,
    mxCaptureActiveLinkDirs     Gauge32,
    mxCaptureActiveHslDirs      Gauge32,
    mxCaptureInterval           Gauge32,
    mxCaptureBegTime            TimeStamp,
    mxCaptureEndTime            TimeStamp,
    mxCaptureActionResult       INTEGER
}

mxCaptureIndex OBJECT-TYPE
    SYNTAX      Unsigned32
    MAX-ACCESS  not-accessible
    STATUS      current
    DESCRIPTION 
        "Provides a non-zero ordinal index into the capture file table 
         that uniquely identifies the capture file.  Files do not obtain 
         a new index as they are rotated.  Indices are not small integer 
         numbers, and are reverse assigned (subsequent indices are 
         smaller in value than previously assigned indices).  Indices 
         are ordinal and monotonically decreasing.  The current capture 
         file will, therefore, always be the smallest index and appear 
         first when the table is walked."
    ::= { mxCaptureEntry 1 }

mxCaptureName OBJECT-TYPE
    SYNTAX      SnmpAdminString
    MAX-ACCESS  read-write
    STATUS      current
    DESCRIPTION 
        "Provides the base name (without file system path or extensions) 
         of the capture file.  The file name may be changed by writing 
         to this object.  Note that files in the current(0) state cannot 
         be renamed."
    ::= { mxCaptureEntry 2 }

mxCaptureCompressed OBJECT-TYPE
    SYNTAX      INTEGER { none(0), gz(1), bz2(2), xz(3), zip(4) }
    MAX-ACCESS  read-write
    STATUS      current
    DESCRIPTION 
        "Provides the compression applied to the file on the file 
         system.  Compression is single-valued and can assume one of the 
         following values:
         
         - none(0), the file is not compressed;
         - gz(1), the file is gzip compressed;
         - bz2(2), the file is bzip2 compressed;
         - xz(3), the file is xz compressed;
         - zip(4), the file is zip compressed.
         
         The file can be decompressed or recompressed by writing to this 
         object.  Note that files in the current(0) state cannot be 
         compressed."
    ::= { mxCaptureEntry 3 }

mxCaptureState OBJECT-TYPE
    SYNTAX      INTEGER { current(0), spooled(1), archived(2), 
                    deleted(3) }
    MAX-ACCESS  read-only
    STATUS      current
    DESCRIPTION 
        "Indicates the state of the file.  File state is single-valued 
         and can be one of the following:
         
         - current(0), the file is a current capture file that is 
           actively capturing messages; current files cannot be 
           compressed or renamed;
         
         - spooled(1), the file has been rotated and is no longer 
           capturing messages; however, it is awaiting upload or 
           download;
         
         - archived(2), the file has been rotated and also uploaded or 
           downloaded and is archived; archived files are subject to 
           deletion;
         
         - deleted(3), the file has been removed from the archive.
         
         Management stations can change the state of the file using the 
         mxCaptureActionResult object."
    ::= { mxCaptureEntry 4 }

mxCaptureLinkType OBJECT-TYPE
    SYNTAX      DataLinkType
    MAX-ACCESS  read-only
    STATUS      current
    DESCRIPTION 
        "Indicates the PCAP file format link type associated with the 
         capture file.  The link type is single-valued and can assume 
         one of the following values:
         
         - ethernet(1), complete ethernet frames;
         
         - linuxsll(113), Linux SLL cooked header;
         
         - mtp2ph(139), MTP level 2 with pseudo-header indicating link 
           id and direction;
         
         - mtp2(140), MTP level 2 without pseudo-header;
         
         - mtp3(141), MTP level 3 without pseudo-header; MTP level 2 
           (link layer) headers are stripped;
         
         - sccp(142), SCCP without pseudo-header; MTP level 2 and 3 
           (link layer) headers are stripped.
           
         For traditional SS7 monitoring, link types should typically be 
         mtp2ph(139) because it retains the most information.  For 
         SIGTRAN monitoring, link types should typically be ethernet(1) 
         because it retains the most information."
    ::= { mxCaptureEntry 5 }

mxCaptureSize OBJECT-TYPE
    SYNTAX      Gauge32
    UNITS       "bytes"
    MAX-ACCESS  read-only
    STATUS      current
    DESCRIPTION 
        "Indicates the size of the uncompressed file in bytes.  When no 
         compression is applied to the file, this value will be the same 
         as the mxCaptureCompSize."
    ::= { mxCaptureEntry 6 }

mxCaptureCompSize OBJECT-TYPE
    SYNTAX      Gauge32
    UNITS       "bytes"
    MAX-ACCESS  read-only
    STATUS      current
    DESCRIPTION 
        "Indicates the size of the compressed file in bytes.  When no 
         compression is applied to the file, this value will be the same 
         as the mxCaptureSize."
    ::= { mxCaptureEntry 7 }

mxCaptureMessages OBJECT-TYPE
    SYNTAX      Gauge32
    UNITS       "messages"
    MAX-ACCESS  read-only
    STATUS      current
    DESCRIPTION 
        "Indicates the number of messages contained in the file."
    ::= { mxCaptureEntry 8 }

mxCaptureMsgOctets OBJECT-TYPE
    SYNTAX      Gauge32
    UNITS       "message octets"
    MAX-ACCESS  read-only
    STATUS      current
    DESCRIPTION 
        "Indicates the total number of message octets contained in the 
         file."
    ::= { mxCaptureEntry 9 }

mxCaptureSusCompressed OBJECT-TYPE
    SYNTAX      Gauge32
    UNITS       "SUs"
    MAX-ACCESS  read-only
    STATUS      current
    DESCRIPTION 
        "Indicates the number of FISUs or LSSUs that were compressed 
         due to repetition in the file."
    ::= { mxCaptureEntry 10 }

mxCaptureMsuDrops OBJECT-TYPE
    SYNTAX      Gauge32
    UNITS       "MSUs"
    MAX-ACCESS  read-only
    STATUS      current
    DESCRIPTION 
        "Indicates the number of MSUs that were dropped due to 
         inadequate resources.  This gauge should usually be zero."
    ::= { mxCaptureEntry 11 }

mxCaptureFilterDrops OBJECT-TYPE
    SYNTAX      Gauge32
    UNITS       "messages"
    MAX-ACCESS  read-only
    STATUS      current
    DESCRIPTION 
        "Indicates the number of messages that were rejected by a 
         filter.  This gauge could be large or small depending on the 
         stringency of the filter and the amount of traffic filtered."
    ::= { mxCaptureEntry 12 }

mxCaptureActiveLinkDirs OBJECT-TYPE
    SYNTAX      Gauge32
    UNITS       "low-speed links"
    MAX-ACCESS  read-only
    STATUS      current
    DESCRIPTION 
        "Provides a count of the number of low-speed (56 or 64 kbps) 
         signalling link directions that were actively captured (i.e, 
         the file contains messages that were captured from the link for 
         the direction.  This column is useful for determining whether 
         the appropriate number of signalling links are being captured 
         for a span, card, driver or default source.  This column is 
         useful for determining whether the appropriate number of high- 
         and low-speed links have been captured for a span, card, driver 
         or default source."
    ::= { mxCaptureEntry 13 }

mxCaptureActiveHslDirs OBJECT-TYPE
    SYNTAX      Gauge32
    UNITS       "high-speed links"
    MAX-ACCESS  read-only
    STATUS      current
    DESCRIPTION 
        "Provides a count of the number of high-speed (1.536 or 1.892 
         kbps) signalling link directions that were actively captured 
         (i.e, the file contains messages that were captured from the 
         link for the direction.  This column is useful for determining 
         whether the appropriate number of high- and low-speed links are 
         being captured for a card, driver or default source."
    ::= { mxCaptureEntry 14 }

mxCaptureInterval OBJECT-TYPE
    SYNTAX      Gauge32
    UNITS       "milliseconds"
    MAX-ACCESS  read-only
    STATUS      current
    DESCRIPTION 
        "Indicates the time interval covered by the file.  This is the 
         difference in time between the last message captured and the 
         first message captured."
    ::= { mxCaptureEntry 15 }

mxCaptureBegTime OBJECT-TYPE
    SYNTAX      TimeStamp
    MAX-ACCESS  read-only
    STATUS      current
    DESCRIPTION 
        "Indicates the time (using the TimeStamp textual convention) 
         that the capture file was opened (capturing of messages to the 
         file began)."
    ::= { mxCaptureEntry 16 }

mxCaptureEndTime OBJECT-TYPE
    SYNTAX      TimeStamp
    MAX-ACCESS  read-only
    STATUS      current
    DESCRIPTION 
        "Indicates the time (using the TimeStamp textual convention) 
         that the capture file was closed (capturing of messages to the 
         file ended)."
    ::= { mxCaptureEntry 17 }

mxCaptureActionResult OBJECT-TYPE
    SYNTAX      INTEGER { success(0), failure(1), spool(2), archive(3), 
                    delete(4), upload(5) }
    MAX-ACCESS  read-write
    STATUS      current
    DESCRIPTION 
        "Provides actions and their results.  The action-result is 
         single-valued and can assume one of the following values:
         
         - success(0), the last action was successful;
         - failure(1), the last action failed;
         - spool(2), change the state of a file in the current or 
           archived states to spooled; when successfully applied to a 
           current capture file, the capture file is rotated; when to an 
           archived file, the file is respooled;
         - archive(3), change the state of a spooled file to archived; 
           this action unspools and archives a spooled file;
         - delete(4), delete the capture file; this action can only be 
           applied to archived files;
         - upload(5), initiate an upload of the file; this action can 
           only be applied to spooled files; once upload is complete, 
           the file will be archived.
         
         When written, only values spool(2), archive(3), delete(4) and 
         upload(5) are valid and represent the action to be performed.  
         When read, only values success(0) or failure(1) will be 
         returned and represent the result of the previous action."
    ::= { mxCaptureEntry 18 }

mxCaptureIfTable OBJECT-TYPE
    SYNTAX      SEQUENCE OF MxCaptureIfEntry
    MAX-ACCESS  not-accessible
    STATUS      current
    DESCRIPTION 
        "Provides a table of interfaces associated with a capture file."
    ::= { mxCapture 28 }

mxCaptureIfEntry OBJECT-TYPE
    SYNTAX      MxCaptureIfEntry
    MAX-ACCESS  not-accessible
    STATUS      current
    DESCRIPTION 
        "Each row in the mxCaptureIfTable provides information 
         concerning a single interface with data contained in the 
         capture file and provides some actions that can be performed on 
         the interface."
    INDEX       { mxCaptureIndex, mxCaptureIfIndex }
    ::= { mxCaptureIfTable 1 }

MxCaptureIfEntry ::= SEQUENCE {
    mxCaptureIfIndex            Unsigned32,
    mxCaptureIfLinkType         DataLinkType,
    mxCaptureIfSnapLen          Unsigned32,
    mxCaptureIfName             SnmpAdminString,
    mxCaptureIfDescription      SnmpAdminString,
    mxCaptureIfMacAddr          OCTET STRING,
    mxCaptureIfEuiAddr          OCTET STRING,
    mxCaptureIfSpeed            Unsigned32,
    mxCaptureIfTsRes            Unsigned32,
    mxCaptureIfTzone            Unsigned32,
    mxCaptureIfFilter           SnmpAdminString,
    mxCaptureIfOs               SnmpAdminString,
    mxCaptureIfFcsLen           Unsigned32,
    mxCaptureIfTsOffset         Unsigned32
}

mxCaptureIfIndex OBJECT-TYPE
    SYNTAX      Unsigned32
    MAX-ACCESS  not-accessible
    STATUS      current
    DESCRIPTION 
        "Provides an positive ordinal index (beginning at 0) into the 
         mxCaptureIfTable identifying the interface associated with this 
         conceptual row.  This index also corresponds to the ordinal 
         index of the interface description block that appears in the 
         pcapng file."
    ::= { mxCaptureIfEntry 1 }

mxCaptureIfLinkType OBJECT-TYPE
    SYNTAX      DataLinkType
    MAX-ACCESS  read-only
    STATUS      current
    DESCRIPTION 
        "Identifies the tcpdump data link type associated with this 
         interface."
    ::= { mxCaptureIfEntry 2 }

mxCaptureIfSnapLen OBJECT-TYPE
    SYNTAX      Unsigned32
    MAX-ACCESS  read-write
    STATUS      current
    DESCRIPTION 
        "TODO"
    ::= { mxCaptureIfEntry 3 }

mxCaptureIfName OBJECT-TYPE
    SYNTAX      SnmpAdminString
    MAX-ACCESS  read-only
    STATUS      current
    DESCRIPTION 
        "TODO"
    ::= { mxCaptureIfEntry 4 }

mxCaptureIfDescription OBJECT-TYPE
    SYNTAX      SnmpAdminString
    MAX-ACCESS  read-only
    STATUS      current
    DESCRIPTION 
        "TODO"
    ::= { mxCaptureIfEntry 5 }

mxCaptureIfMacAddr OBJECT-TYPE
    SYNTAX      OCTET STRING
    MAX-ACCESS  read-only
    STATUS      current
    DESCRIPTION 
        "TODO"
    ::= { mxCaptureIfEntry 6 }

mxCaptureIfEuiAddr OBJECT-TYPE
    SYNTAX      OCTET STRING
    MAX-ACCESS  read-only
    STATUS      current
    DESCRIPTION 
        "TODO"
    ::= { mxCaptureIfEntry 7 }

mxCaptureIfSpeed OBJECT-TYPE
    SYNTAX      Unsigned32
    MAX-ACCESS  read-only
    STATUS      current
    DESCRIPTION 
        "TODO"
    ::= { mxCaptureIfEntry 8 }

mxCaptureIfTsRes OBJECT-TYPE
    SYNTAX      Unsigned32
    MAX-ACCESS  read-only
    STATUS      current
    DESCRIPTION 
        "TODO"
    ::= { mxCaptureIfEntry 9 }

mxCaptureIfTzone OBJECT-TYPE
    SYNTAX      Unsigned32
    MAX-ACCESS  read-only
    STATUS      current
    DESCRIPTION 
        "TODO"
    ::= { mxCaptureIfEntry 10 }

mxCaptureIfFilter OBJECT-TYPE
    SYNTAX      SnmpAdminString
    MAX-ACCESS  read-only
    STATUS      current
    DESCRIPTION 
        "TODO"
    ::= { mxCaptureIfEntry 11 }

mxCaptureIfOs OBJECT-TYPE
    SYNTAX      SnmpAdminString
    MAX-ACCESS  read-only
    STATUS      current
    DESCRIPTION 
        "FIXME"
    ::= { mxCaptureIfEntry 12 }

mxCaptureIfFcsLen OBJECT-TYPE
    SYNTAX      Unsigned32
    MAX-ACCESS  read-only
    STATUS      current
    DESCRIPTION 
        "FIXME"
    ::= { mxCaptureIfEntry 13 }

mxCaptureIfTsOffset OBJECT-TYPE
    SYNTAX      Unsigned32
    MAX-ACCESS  read-only
    STATUS      current
    DESCRIPTION 
        "FIXME"
    ::= { mxCaptureIfEntry 14 }

-- =====================================================================
-- mxPush group
-- =====================================================================
-- The mxPush group is responsible for managing live feeds of captured 
-- messages to remote entities.
-- .....................................................................

mxPush OBJECT IDENTIFIER
    ::= { mxMonObjects 3 }

mxPushTable OBJECT-TYPE
    SYNTAX      SEQUENCE OF MxPushEntry
    MAX-ACCESS  not-accessible
    STATUS      current
    DESCRIPTION 
        "The probe is capable of exporting its monitor source 
         definitions from the mxMonitorTable to remote collectors.  In 
         doing so, either the probe or the collector can establish the 
         connection.  This mxPushTable contains the transport adddress 
         of the collectors to which exported monitor sources are to be 
         pushed: that is, this probe will initiate establishment of a 
         connection to the remote collector.
         
         The mxPullTable defines connections that are initiated in the 
         opposite direciton."
    ::= { mxPush 1 }

mxPushEntry OBJECT-TYPE
    SYNTAX      MxPushEntry
    MAX-ACCESS  not-accessible
    STATUS      current
    DESCRIPTION 
        "Each row in this table describes one collector to which this 
         probe will export its monitor sources."
    INDEX       { mxPushIndex }
    ::= { mxPushTable 1 }

MxPushEntry ::= SEQUENCE {
    mxPushIndex             Unsigned32,
    mxPushHostname          DisplayString,
    mxPushXportAddrType     TransportAddressType,
    mxPushXportAddr         TransportAddress,
    mxPushXportProfile      SimpleNameType,
    mxPushAssocState        INTEGER,
    mxPushStorageType       StorageType,
    mxPushRowStatus         RowStatus
}

mxPushIndex OBJECT-TYPE
    SYNTAX      Unsigned32
    MAX-ACCESS  not-accessible
    STATUS      current
    DESCRIPTION 
        "Provides a non-zero ordinal index into the mxPushTable."
    ::= { mxPushEntry 1 }

mxPushHostname OBJECT-TYPE
    SYNTAX      DisplayString
    MAX-ACCESS  read-create
    STATUS      current
    DESCRIPTION 
        "Provides the specification of one transport endpoint to which 
         to push monitor sources expressed as a hostname and port 
         address specification."
    ::= { mxPushEntry 2 }

mxPushXportAddrType OBJECT-TYPE
    SYNTAX      TransportAddressType
    MAX-ACCESS  read-create
    STATUS      current
    DESCRIPTION 
        "Specifies the transport address type.  For sctpipv4(9), the 
         transport address is an IPv4 address and port number; for 
         sctpipv6(10), it is an IPv6 address and port number."
    REFERENCE   
        "TRANSPORT-ADDRESS-MIB, TransportAddressType"
    DEFVAL      { sctpIpv4 }
    ::= { mxPushEntry 3 }

mxPushXportAddr OBJECT-TYPE
    SYNTAX      TransportAddress
    MAX-ACCESS  read-create
    STATUS      current
    DESCRIPTION 
        "Specifies the transport address of the remote host to which to 
         push monitor sources.  The address is of type 
         mxPushXportAddrType."
    REFERENCE   
        "TRANSPORT-ADDRESS-MIB, TransportAddressType"
    ::= { mxPushEntry 4 }

mxPushXportProfile OBJECT-TYPE
    SYNTAX      SimpleNameType
    MAX-ACCESS  read-create
    STATUS      current
    DESCRIPTION 
        "Specifies the transport address protocol parameters profile 
         that is to be used to supply protocol parameters, timers, and 
         options for the connection.  The values of this object must be 
         the same as the name of a row in the mxXportProfileTable."
    ::= { mxPushEntry 5 }

mxPushAssocState OBJECT-TYPE
    SYNTAX      INTEGER { idle(0), connog(1), connic(2), established(3), 
                    shuttingdown(4) }
    MAX-ACCESS  read-only
    STATUS      current
    DESCRIPTION 
        "Provides the state of the SCTP association use to export 
         monitor sources from the remote probe corresponding to this 
         row.  The state can be:
         
         - idle(0), no SCTP association formed;
         - connog(1), connecting outgoing, SCTP association being 
           established by this host;
         - connic(2), connecting incoming, SCTP association being 
           established by remote host;
         - established(3), SCTP association is established and active;
         - shuttindown(4), the SCTP associat is shutting down.
           
         Only SCTP associations that are in the established(3) state can 
         capture packets or have filters applied."
    ::= { mxPushEntry 6 }

mxPushStorageType OBJECT-TYPE
    SYNTAX      StorageType
    MAX-ACCESS  read-create
    STATUS      current
    DESCRIPTION 
        "Specifies the storage type for this conceptual row.  On write, 
         only storage types volatile() and nonVolatile() are 
         applicable."
    DEFVAL      { nonVolatile }
    ::= { mxPushEntry 7 }

mxPushRowStatus OBJECT-TYPE
    SYNTAX      RowStatus
    MAX-ACCESS  read-create
    STATUS      current
    DESCRIPTION 
        "Provides a mechanism whereby mangaement stations may create and 
         destroy rows in this table."
    ::= { mxPushEntry 8 }

-- =====================================================================
-- mxPull group
-- =====================================================================
-- The mxPull group is responsible for managing live feeds of captured 
-- messages from remote entities.
-- .....................................................................

mxPull OBJECT IDENTIFIER
    ::= { mxMonObjects 4 }

mxPullTable OBJECT-TYPE
    SYNTAX      SEQUENCE OF MxPullEntry
    MAX-ACCESS  not-accessible
    STATUS      current
    DESCRIPTION 
        "The collector is capable of importing other monitor source 
         definitions from the mxMonitorTable of remote probes.  In doing 
         so, either the collector or the probe can establish the 
         connection.  This mxPullTable contains the transport addresses 
         of the probes from which imported monitor sources are to be 
         pulled: that is, the collector will initiate establishement of 
         a connection to the remote probe.
         
         The mxPushTable defines connections that are initiated in the 
         opposite direction."
    ::= { mxPull 1 }

mxPullEntry OBJECT-TYPE
    SYNTAX      MxPullEntry
    MAX-ACCESS  not-accessible
    STATUS      current
    DESCRIPTION 
        "Each row in this table describes one probe from which this 
         collector will import monitor sources."
    INDEX       { mxPullIndex }
    ::= { mxPullTable 1 }

MxPullEntry ::= SEQUENCE {
    mxPullIndex             Unsigned32,
    mxPullHostname          DisplayString,
    mxPullXportAddrType     TransportAddressType,
    mxPullXportAddr         TransportAddress,
    mxPullXportProfile      SimpleNameType,
    mxPullAssocState        INTEGER,
    mxPullStorageType       StorageType,
    mxPullRowStatus         RowStatus
}

mxPullIndex OBJECT-TYPE
    SYNTAX      Unsigned32
    MAX-ACCESS  not-accessible
    STATUS      current
    DESCRIPTION 
        "Provides a non-zero ordinal row index into the mxPullTable."
    ::= { mxPullEntry 1 }

mxPullHostname OBJECT-TYPE
    SYNTAX      DisplayString
    MAX-ACCESS  read-create
    STATUS      current
    DESCRIPTION 
        "Providse the specification of one transport endpoint from which 
         to pull monitor sources expressed as a hostname and port 
         address specification."
    ::= { mxPullEntry 2 }

mxPullXportAddrType OBJECT-TYPE
    SYNTAX      TransportAddressType
    MAX-ACCESS  read-create
    STATUS      current
    DESCRIPTION 
        "Specifies the transport address type.  For sctpIpv4(9), the 
         transport address is an IPv4 address and port number; for 
         sctpIpv6(10), it is an IPv6 address and port number."
    REFERENCE   
        "TRANSPORT-ADDRESS-MIB, TransportAddressType"
    ::= { mxPullEntry 3 }

mxPullXportAddr OBJECT-TYPE
    SYNTAX      TransportAddress
    MAX-ACCESS  read-create
    STATUS      current
    DESCRIPTION 
        "Specifies the trasnport address of the remote host from which 
         to pull monitor sources.  The address is of type 
         mxPullXportAddrType."
    REFERENCE   
        "TRANSPORT-ADDRESS-MIB, TransportAddressType"
    ::= { mxPullEntry 4 }

mxPullXportProfile OBJECT-TYPE
    SYNTAX      SimpleNameType
    MAX-ACCESS  read-create
    STATUS      current
    DESCRIPTION 
        "Specifies the transport address protocol parameters profile 
         that is to be used to supply protocol parameters, timers, and 
         options for the connection.  The values of this object must be 
         the same as the name of a row in the mxXportProfileTable."
    ::= { mxPullEntry 5 }

mxPullAssocState OBJECT-TYPE
    SYNTAX      INTEGER { idle(0), connog(1), connic(2), established(3), 
                    shuttingdown(4) }
    MAX-ACCESS  read-only
    STATUS      current
    DESCRIPTION 
        "Provides the state of the SCTP association use to import 
         monitor sources from the remote probe corresponding to this 
         row.  The state can be:
         
         - idle(0), no SCTP association formed;
         - connog(1), connecting outgoing, SCTP association being 
           established by this host;
         - connic(2), connecting incoming, SCTP association being 
           established by remote host;
         - established(3), SCTP association is established and active;
         - shuttindown(4), the SCTP associat is shutting down.
           
         Only SCTP associations that are in the established(3) state can 
         capture packets or have filters applied."
    ::= { mxPullEntry 6 }

mxPullStorageType OBJECT-TYPE
    SYNTAX      StorageType
    MAX-ACCESS  read-create
    STATUS      current
    DESCRIPTION 
        "Specifies the storage type for this conceptual row.  On write, 
         only storage types volatile() and nonVolatile() are 
         applicable."
    ::= { mxPullEntry 7 }

mxPullRowStatus OBJECT-TYPE
    SYNTAX      RowStatus
    MAX-ACCESS  read-create
    STATUS      current
    DESCRIPTION 
        "Provides a mechanism whereby management stations may create and 
         destroy rows in this table."
    ::= { mxPullEntry 8 }

-- =====================================================================
-- mxUpload group
-- =====================================================================
-- The mxUpload group is responsible for managing the uploading of 
-- capture files to central repository servers.
-- .....................................................................

mxUpload OBJECT IDENTIFIER
    ::= { mxMonObjects 5 }

mxUploadTable OBJECT-TYPE
    SYNTAX      SEQUENCE OF MxUploadEntry
    MAX-ACCESS  not-accessible
    STATUS      current
    DESCRIPTION 
        "Provides a table of collectors to which the probe is to upload 
         capture files on a regular schedule."
    ::= { mxUpload 1 }

mxUploadEntry OBJECT-TYPE
    SYNTAX      MxUploadEntry
    MAX-ACCESS  not-accessible
    STATUS      current
    DESCRIPTION 
        "Each row in the table specifies a single collector to which to 
         upload capture files on a regular schedule."
    INDEX       { mxUploadIndex }
    ::= { mxUploadTable 1 }

MxUploadEntry ::= SEQUENCE {
    mxUploadIndex       Unsigned32,
    mxUploadSpec        SnmpAdminString,
    mxUploadUsername    SnmpAdminString,
    mxUploadPassword    SnmpAdminString,
    mxUploadAdminState  AdministrativeState,
    mxUploadStatus      RowStatus
}

mxUploadIndex OBJECT-TYPE
    SYNTAX      Unsigned32
    MAX-ACCESS  not-accessible
    STATUS      current
    DESCRIPTION 
        "Provides a non-zero ordinal index into the mxUploadTable.  
         Aside from being an index, this object has no other 
         significance."
    ::= { mxUploadEntry 1 }

mxUploadSpec OBJECT-TYPE
    SYNTAX      SnmpAdminString
    MAX-ACCESS  read-create
    STATUS      current
    DESCRIPTION 
        "Specifies the method and path to which to upload files on the 
         remote server.  This string consists of several components:
         
         1. The method for upload.  This can be one of rsync, http, 
            https, ftp, ftps."
    ::= { mxUploadEntry 2 }

mxUploadUsername OBJECT-TYPE
    SYNTAX      SnmpAdminString
    MAX-ACCESS  read-create
    STATUS      current
    DESCRIPTION 
        "Provides a username for use with the upload string when 
         required.  A username will not be provided unless demanded by 
         the remote server."
    DEFVAL      { "openss7" }
    ::= { mxUploadEntry 3 }

mxUploadPassword OBJECT-TYPE
    SYNTAX      SnmpAdminString
    MAX-ACCESS  read-create
    STATUS      current
    DESCRIPTION 
        "Provides a password for use with the upload string when 
         required.  A password will not be provided unless demanded by 
         the remote server.  A read of this object will only return the 
         number of '*' characters equal to the length of the password."
    DEFVAL      { "openss7" }
    ::= { mxUploadEntry 4 }

mxUploadAdminState OBJECT-TYPE
    SYNTAX      AdministrativeState
    MAX-ACCESS  read-create
    STATUS      current
    DESCRIPTION 
        "Provides the administrative state of uploads to the remote 
         collector:
         
         - locked(0), the probe is prohibited from uploading files to 
           the remote server;
         - unlocked(1), the probe is permitted to upload files to the 
           remote server according to the upload schedule;
         - shuttingDown(2), the probe is actively uploading files to the 
           remote server and will move to the locked(0) state once the 
           upload is complete.
           
         This is used to control the state of uploads.  Set to locked(0) 
         to suppress uploading.  Set to unlocked(1) to enable uploading."
    DEFVAL      { locked }
    ::= { mxUploadEntry 5 }

mxUploadStatus OBJECT-TYPE
    SYNTAX      RowStatus
    MAX-ACCESS  read-create
    STATUS      current
    DESCRIPTION 
        "Provides a mechanism whereby management stations can add and 
         remove rows from this table."
    ::= { mxUploadEntry 7 }

-- =====================================================================
-- mxDownload group
-- =====================================================================
-- The mxDownload group is responsible for managing the downloading of 
-- capture files to central repository servers.
-- .....................................................................

mxDownload OBJECT IDENTIFIER
    ::= { mxMonObjects 6 }

mxDownloadTable OBJECT-TYPE
    SYNTAX      SEQUENCE OF MxDownloadEntry
    MAX-ACCESS  not-accessible
    STATUS      current
    DESCRIPTION 
        "Provides a table of probes from which the collector is to 
         download capture files on a regular schedule."
    ::= { mxDownload 1 }

mxDownloadEntry OBJECT-TYPE
    SYNTAX      MxDownloadEntry
    MAX-ACCESS  not-accessible
    STATUS      current
    DESCRIPTION 
        "Each row in the table specifies a single probe from which to 
         download capture files on a regular schedule."
    INDEX       { mxDownloadIndex }
    ::= { mxDownloadTable 1 }

MxDownloadEntry ::= SEQUENCE {
    mxDownloadIndex         Unsigned32,
    mxDownloadSpec          SnmpAdminString,
    mxDownloadUsername      SnmpAdminString,
    mxDownloadPassword      SnmpAdminString,
    mxDownloadAdminState    AdministrativeState,
    mxDownloadStatus        RowStatus
}

mxDownloadIndex OBJECT-TYPE
    SYNTAX      Unsigned32
    MAX-ACCESS  not-accessible
    STATUS      current
    DESCRIPTION 
        "Provides a non-zero ordinal index into the mxDownloadTable.  
         Aside from being an index, this object has no other 
         significance."
    ::= { mxDownloadEntry 1 }

mxDownloadSpec OBJECT-TYPE
    SYNTAX      SnmpAdminString
    MAX-ACCESS  read-create
    STATUS      current
    DESCRIPTION 
        "Specifies the method and path form which to download files from 
         the remote servier.  This string consists of several 
         components:
         
         1. The method of download.  This can be one of rsync, http, 
            https, ftp, ftps."
    ::= { mxDownloadEntry 2 }

mxDownloadUsername OBJECT-TYPE
    SYNTAX      SnmpAdminString
    MAX-ACCESS  read-create
    STATUS      current
    DESCRIPTION 
        "Provides a username for use with the download string when 
         required.  A username will not be provided unless demanded by 
         the remote server."
    DEFVAL      { "openss7" }
    ::= { mxDownloadEntry 3 }

mxDownloadPassword OBJECT-TYPE
    SYNTAX      SnmpAdminString
    MAX-ACCESS  read-create
    STATUS      current
    DESCRIPTION 
        "Provides a password for use with the download string when 
         required.  A password will not be provided unless demanded by 
         the remote server.  A read of this object will only return the 
         number of '*' characters equal to the length of the password."
    DEFVAL      { "openss7" }
    ::= { mxDownloadEntry 4 }

mxDownloadAdminState OBJECT-TYPE
    SYNTAX      AdministrativeState
    MAX-ACCESS  read-create
    STATUS      current
    DESCRIPTION 
        "Provides the administrative state of dowloads form the remote 
         probe:
         
         - locked(0), the collector is prohibited from downloading files 
           from the remote server;
         - unlocked(1), the collector is permitted to download files 
           from the remote server according to the download schedule;
         - shuttingDown(2), the collector is actively downloading files 
           from the remote server and will move to the locked(0) state 
           once the download is complete.
           
         This is used to control the state of downloads.  Set to 
         locked(0) to suppress downloading.  Set to unlocked(1) to 
         enable downloading."
    DEFVAL      { locked }
    ::= { mxDownloadEntry 5 }

mxDownloadStatus OBJECT-TYPE
    SYNTAX      RowStatus
    MAX-ACCESS  read-create
    STATUS      current
    DESCRIPTION 
        "Provides a mechanism whereby management stations can add and 
         remove rows from this table."
    ::= { mxDownloadEntry 6 }

-- =====================================================================
-- mxCollect group
-- =====================================================================
-- The mxCollect group is responsible for managing the collection of 
-- messages from additional remote sources.
-- .....................................................................

mxCollect OBJECT IDENTIFIER
    ::= { mxMonObjects 7 }

mxCollectTable OBJECT-TYPE
    SYNTAX      SEQUENCE OF MxCollectEntry
    MAX-ACCESS  not-accessible
    STATUS      current
    DESCRIPTION 
        "Provides a table of collectors to which to provide live feeds."
    ::= { mxCollect 1 }

mxCollectEntry OBJECT-TYPE
    SYNTAX      MxCollectEntry
    MAX-ACCESS  not-accessible
    STATUS      current
    DESCRIPTION 
        "Each row in the table specifies a single collector to which to 
         send live feeds."
    INDEX       { mxCollectIndex }
    ::= { mxCollectTable 1 }

MxCollectEntry ::= SEQUENCE {
    mxCollectIndex          Unsigned32,
    mxCollectXportAddrType  TransportAddressType,
    mxCollectXportAddr      TransportAddress,
    mxCollectAdminState     AdministrativeState,
    mxCollectOpState        OperationalState,
    mxCollectRowStatus      RowStatus
}

mxCollectIndex OBJECT-TYPE
    SYNTAX      Unsigned32
    MAX-ACCESS  not-accessible
    STATUS      current
    DESCRIPTION 
        "Provides a non-zero ordinal index into the mxCollectTable."
    ::= { mxCollectEntry 1 }

mxCollectXportAddrType OBJECT-TYPE
    SYNTAX      TransportAddressType
    MAX-ACCESS  read-create
    STATUS      current
    DESCRIPTION 
        "Provides the type of the remote monitor source transport 
         address.  For IPv4 this is sctpIpv4(9); for IPv6, 
         sctpIpv6(10)."
    REFERENCE   
        "TRANSPORT-ADDRESS-MIB, TransportAddressType."
    ::= { mxCollectEntry 2 }

mxCollectXportAddr OBJECT-TYPE
    SYNTAX      TransportAddress
    MAX-ACCESS  read-create
    STATUS      current
    DESCRIPTION 
        "Provides the remote monitoring point's transport address of 
         type mxCollectXportAddrType.  This is an IP address and port 
         number."
    REFERENCE   
        "TRASNPORT-ADDRESS-MIB, TransportAddress"
    ::= { mxCollectEntry 3 }

mxCollectAdminState OBJECT-TYPE
    SYNTAX      AdministrativeState
    MAX-ACCESS  read-create
    STATUS      current
    DESCRIPTION 
        "Provides the administrative state of collection from the remote 
         monitoring point.  When locked(0), collection from the remote 
         monitoring point is prohibited (regardless of the operational 
         state of the connection); when unlocked, collection is 
         permitted."
    DEFVAL      { locked }
    ::= { mxCollectEntry 4 }

mxCollectOpState OBJECT-TYPE
    SYNTAX      OperationalState
    MAX-ACCESS  read-only
    STATUS      current
    DESCRIPTION 
        "Provides the operational state of collection from the remote 
         monitoring point.  When enabled(0), collection is being 
         performed; otherwise, disabled(1)."
    ::= { mxCollectEntry 5 }

mxCollectRowStatus OBJECT-TYPE
    SYNTAX      RowStatus
    MAX-ACCESS  read-create
    STATUS      current
    DESCRIPTION 
        "Provides a mechanism whereby management staions can add remote 
         monintoring points to the mxCollectTable."
    ::= { mxCollectEntry 6 }

-- =====================================================================
-- mxSctp group
-- =====================================================================
-- The mxSctp group is responsible for providing SCTP protocol 
-- parameters and defaults for use with the creation and operation of 
-- SCTP associations.
-- .....................................................................

mxSctp OBJECT IDENTIFIER
    ::= { mxMonObjects 8 }

mxSctpDefaultNoDelay OBJECT-TYPE
    SYNTAX      TruthValue
    MAX-ACCESS  read-write
    STATUS      current
    DESCRIPTION 
        "Provides the default value to be used in the mxSctpNoDelay 
         column when rows are created in the mxSctpTable and no value is 
         specified."
    DEFVAL      { false }
    ::= { mxSctp 1 }

mxSctpDefaultMaxseg OBJECT-TYPE
    SYNTAX      Unsigned32
    MAX-ACCESS  read-write
    STATUS      current
    DESCRIPTION 
        "Provides the default value to be used in the mxSctpMaxseg 
         column when rows are created in the mxSctpTable and no value is 
         specified."
    DEFVAL      { 536 }
    ::= { mxSctp 2 }

mxSctpDefaultHeartbeatItvl OBJECT-TYPE
    SYNTAX      MilliSeconds
    UNITS       "seconds"
    MAX-ACCESS  read-write
    STATUS      current
    DESCRIPTION 
        "Provides the default value to be used in the 
         mxSctpHeartbeatItvl column when rows are created in the 
         mxSctpTable and no value is specified."
    DEFVAL      { 60000 }
    ::= { mxSctp 3 }

mxSctpDefaultHeartbeat OBJECT-TYPE
    SYNTAX      TruthValue
    MAX-ACCESS  read-write
    STATUS      current
    DESCRIPTION 
        "Provides the default value to be used in the mxSctpHeartbeat 
         column when rows are created in the mxSctpTable and no value is 
         specified."
    DEFVAL      { true }
    ::= { mxSctp 4 }

mxSctpDefaultRtoInitial OBJECT-TYPE
    SYNTAX      MilliSeconds
    UNITS       "seconds"
    MAX-ACCESS  read-write
    STATUS      current
    DESCRIPTION 
        "Provides the default value to be used in the mxSctpRtoInitial 
         column when rows are created in the mxSctpTable and no value is 
         specified."
    DEFVAL      { 3000 }
    ::= { mxSctp 5 }

mxSctpDefaultRtoMin OBJECT-TYPE
    SYNTAX      MilliSeconds
    UNITS       "seconds"
    MAX-ACCESS  read-write
    STATUS      current
    DESCRIPTION 
        "Provides the default value to be used in the mxSctpRtoMin 
         column when rows are created in the mxSctpTable and no value is 
         specified."
    DEFVAL      { 1000 }
    ::= { mxSctp 6 }

mxSctpDefaultRtoMax OBJECT-TYPE
    SYNTAX      MilliSeconds
    UNITS       "seconds"
    MAX-ACCESS  read-write
    STATUS      current
    DESCRIPTION 
        "Provides the default value to be used in the mxSctpRtoMax 
         column when rows are created in the mxSctpTable and no value is 
         specified."
    DEFVAL      { 60000 }
    ::= { mxSctp 7 }

mxSctpDefaultPathMaxRetrans OBJECT-TYPE
    SYNTAX      Unsigned32
    MAX-ACCESS  read-write
    STATUS      current
    DESCRIPTION 
        "Provides the default value to be used in the 
         mxSctpPathMaxRetrans column when rows are created in the 
         mxSctpTable and no value is specified."
    DEFVAL      { 5 }
    ::= { mxSctp 8 }

mxSctpDefaultCookieLife OBJECT-TYPE
    SYNTAX      MilliSeconds
    UNITS       "seconds"
    MAX-ACCESS  read-write
    STATUS      current
    DESCRIPTION 
        "Provides the default value to be used in the mxSctpCookieLife 
         column when rows are created in the mxSctpTable and no value is 
         specified."
    DEFVAL      { 0 }
    ::= { mxSctp 9 }

mxSctpDefaultCookieInc OBJECT-TYPE
    SYNTAX      MilliSeconds
    UNITS       "seconds"
    MAX-ACCESS  read-write
    STATUS      current
    DESCRIPTION 
        "Provides the default value to be used in the mxSctpCookieInc 
         column when rows are created in the mxSctpTable and no value is 
         specified."
    DEFVAL      { 5000 }
    ::= { mxSctp 10 }

mxSctpDefaultMaxInitRetries OBJECT-TYPE
    SYNTAX      Unsigned32
    MAX-ACCESS  read-write
    STATUS      current
    DESCRIPTION 
        "Provides the default value to be used in the 
         mxSctpMaxInitRetries column when rows are created in the 
         mxSctpTable and no value is specified."
    DEFVAL      { 8 }
    ::= { mxSctp 11 }

mxSctpDefaultMaxBurst OBJECT-TYPE
    SYNTAX      Unsigned32
    MAX-ACCESS  read-write
    STATUS      current
    DESCRIPTION 
        "Provides the default value to be used in the mxSctpMaxBurst 
         column when rows are created in the mxSctpTable and no value is 
         specified."
    DEFVAL      { 3 }
    ::= { mxSctp 12 }

mxSctpDefaultAssocMaxRetrans OBJECT-TYPE
    SYNTAX      Unsigned32
    MAX-ACCESS  read-write
    STATUS      current
    DESCRIPTION 
        "Provides the default value to be used in the 
         mxSctpAssocMaxRetrans column when rows are created in the 
         mxSctpTable and no value is specified."
    DEFVAL      { 10 }
    ::= { mxSctp 13 }

mxSctpDefaultSackDelay OBJECT-TYPE
    SYNTAX      MilliSeconds
    UNITS       "seconds"
    MAX-ACCESS  read-write
    STATUS      current
    DESCRIPTION 
        "Provides the default value to be used in the mxSctpSackDelay 
         column when rows are created in the mxSctpTable and no value is 
         specified."
    DEFVAL      { 200 }
    ::= { mxSctp 14 }

mxSctpDefaultLifetime OBJECT-TYPE
    SYNTAX      MilliSeconds
    UNITS       "seconds"
    MAX-ACCESS  read-write
    STATUS      current
    DESCRIPTION 
        "Provides the default value to be used in the mxSctpLifetime 
         column when rows are created in the mxSctpTable and no value is 
         specified."
    DEFVAL      { 0 }
    ::= { mxSctp 15 }

mxSctpTable OBJECT-TYPE
    SYNTAX      SEQUENCE OF MxSctpEntry
    MAX-ACCESS  not-accessible
    STATUS      current
    DESCRIPTION 
        "The mxSctpTable provides a table of SCTP protocol parameters 
         where each row provides one SCTP protocol parameter profile for 
         use in establishing and accepting SCTP associations."
    ::= { mxSctp 16 }

mxSctpEntry OBJECT-TYPE
    SYNTAX      MxSctpEntry
    MAX-ACCESS  not-accessible
    STATUS      current
    DESCRIPTION 
        "Each row in this table consists of a single SCTP prptocol 
         parameter profile indexed by its name."
    INDEX       { mxSctpProfileName }
    ::= { mxSctpTable 1 }

MxSctpEntry ::= SEQUENCE {
    mxSctpProfileName       SimpleNameType,
    mxSctpNoDelay           TruthValue,
    mxSctpMaxseg            Unsigned32,
    mxSctpHeartbeatItvl     MilliSeconds,
    mxSctpHeartbeat         TruthValue,
    mxSctpRtoInitial        MilliSeconds,
    mxSctpRtoMin            MilliSeconds,
    mxSctpRtoMax            MilliSeconds,
    mxSctpPathMaxRetrans    Unsigned32,
    mxSctpCookieLife        MilliSeconds,
    mxSctpCookieInc         MilliSeconds,
    mxSctpMaxInitRetries    Unsigned32,
    mxSctpMaxBurst          Unsigned32,
    mxSctpAssocMaxRetrans   Unsigned32,
    mxSctpSackDelay         MilliSeconds,
    mxSctpLifetime          MilliSeconds,
    mxSctpRowStatus         RowStatus
}

mxSctpProfileName OBJECT-TYPE
    SYNTAX      SimpleNameType
    MAX-ACCESS  not-accessible
    STATUS      current
    DESCRIPTION 
        "Provides the non-null name index of each row in the mxSctpTable."
    ::= { mxSctpEntry 1 }

mxSctpNoDelay OBJECT-TYPE
    SYNTAX      TruthValue
    MAX-ACCESS  read-create
    STATUS      current
    DESCRIPTION 
        "This column defined, under this SCTP profile, whether the Nagle 
         algorithm should be applied to SCTP associations.  The Nagle 
         algorithm increases the size of the packets placed on the 
         network at the expense of delaying the transmission of some 
         data during congestion episodes.  When set to true(1), the 
         Nagle algorithm is suppressed; otherwise, set to false(2), the 
         Nagle algorithm is in effect.
         
         The default value for newly created profiles is determined by 
         the setting of mxSctpDefaultNoDelay."
    ::= { mxSctpEntry 2 }

mxSctpMaxseg OBJECT-TYPE
    SYNTAX      Unsigned32
    MAX-ACCESS  read-create
    STATUS      current
    DESCRIPTION 
        "This column defines the maximum SCTP payload size for outgoing 
         packets.  Values greater than the association MTU are ignored 
         and have no effect.  The value determines the maximum size (in 
         octets) above which SCTP will fragment larget DATA chunks into 
         smaller DATA chunks, and beneath which SCTP will bundle DATA 
         chunks into single packets or combine smaller DATA chunks into 
         larger DATA chunks.  Normally this value is the association MTU 
         value minus the size of the current IP and SCTP headers, minus 
         the size of one DATA chunk header.  When set to a lower value, 
         the lower value will be used.
         
         The default value for newly created profiles is determined by 
         the setting of mxSctpDefaultMaxseg."
    ::= { mxSctpEntry 3 }

mxSctpHeartbeatItvl OBJECT-TYPE
    SYNTAX      MilliSeconds
    UNITS       "seconds"
    MAX-ACCESS  read-create
    STATUS      current
    DESCRIPTION 
        "This column defines the time interval (in milliseconds) between 
         successive HEARTBEAT messages used to probe destination 
         transport addresses for RTT calculation and activity.  Valid 
         values are zero (0) - do not heartbeat, or a value of 1 
         millisecond or greater.
         
         The default value for newly create profiles is determined by 
         the setting of mxSctpDefaultHeartbeatItvl."
    ::= { mxSctpEntry 4 }

mxSctpHeartbeat OBJECT-TYPE
    SYNTAX      TruthValue
    MAX-ACCESS  read-create
    STATUS      current
    DESCRIPTION 
        "This column determines whether HEARTBEAT messages used to probe 
         destination transport addresses for RTT calculation and 
         activity will be sent periodically.  The default value from RFC 
         4960 is true(1).
         
         Disabling heartbeats reduces the protocol's responsiveness in 
         detection of failures and redirection of traffic away from 
         failed paths and interfaces.  This column should normally be 
         left at its default value.
         
         The default value for newly created profiles is determined by 
         the setting of slM2paDefaultSctpHeartbeat."
    ::= { mxSctpEntry 5 }

mxSctpRtoInitial OBJECT-TYPE
    SYNTAX      MilliSeconds
    UNITS       "seconds"
    MAX-ACCESS  read-create
    STATUS      current
    DESCRIPTION 
        "This column defines the initial time interval (in milliseconds) 
         that will be used as an initial RTO (retransmission timeout) 
         value when sending packets to a destination for the first time.  
         Valid values are zero or greater but must be within the range 
         mxSctpRtoMin to mxSctpRtoMax.  The default value is the value 
         recommended by RFC 2960 and RFC 4960 (1000 milliseconds, or 1 
         second).
         
         Note that, in general, the RTO initial should not be less than 
         the peer's maximum SACK delay, otherwise, excessive 
         retransmission migh occur while the peer is delaying 
         acknowledgements.
         
         The default value for newly created profiles is determined by 
         the setting of mxSctpDefaultRtoInitial."
    ::= { mxSctpEntry 6 }

mxSctpRtoMin OBJECT-TYPE
    SYNTAX      MilliSeconds
    UNITS       "seconds"
    MAX-ACCESS  read-create
    STATUS      current
    DESCRIPTION 
        "This column defines the minimum timer interval (in 
         milliseconds) that will be used as an RTO (retransmission 
         timeout) value when sending packets to a destination transport 
         address and expecting acknowledgements.  Valid values are zero 
         or greater and must be less than or equal to mxSctpRtoInitial 
         and strictly less than and mxSctpRtoMax.  The default value is 
         the value recommended by RFC 2960 and RFC 4960 (1000 
         milliseconds, or 1 second).
         
         Note that, in general, the RTO minimum should not be less than 
         the peer's maximum SACK delay, otherwise, excessive 
         retransmission might occur while the peer is delaying 
         acknowledgements.
         
         The default value for newly created profiles is determined by 
         the setting of mxSctpDefaultRtoMin."
    ::= { mxSctpEntry 7 }

mxSctpRtoMax OBJECT-TYPE
    SYNTAX      MilliSeconds
    UNITS       "seconds"
    MAX-ACCESS  read-create
    STATUS      current
    DESCRIPTION 
        "This column defines the maximum time interval (in milliseconds) 
         that will be used as an RTO (retransmission timeout) value when 
         sending packets to a destination transport address and 
         expecting acknowledgements.  Valid values are zero or greater 
         but must be greater than or equal to mxSctpRtoInitial and 
         strictly greater than mxSctpRtoMin.  The default value is the 
         value recommended by RFC 2960 and RFC 4960 (60000 milliseconds, 
         or 60 seconds).
         
         Note that, in general, the RTO maximum should not be less than 
         the peer's maximum SACK delay, otherwise, excessive 
         retransmission might occur while the peer is delaying 
         acknowledgements.
         
         The default value for newly created profiles is determined by 
         the setting of mxSctpDefaultRtoMax."
    ::= { mxSctpEntry 8 }

mxSctpPathMaxRetrans OBJECT-TYPE
    SYNTAX      Unsigned32
    MAX-ACCESS  read-create
    STATUS      current
    DESCRIPTION 
        "This column defines the number of times that SCTP will attempt 
         retransmitting a packet to a given destination transport 
         address before it considers that destination transport address 
         inactive.  Valid values are zero or greater.  The default value 
         is the value recommended in RFC 2960 (5 retransmissions).
         
         Adjusting this value has an effect on th period of time taken 
         to fail-over between destinations for multi-homed connections.  
         Lower values (including zero) will yield faster fail-over 
         response times.  Lower values, however, may cause thrashing 
         between destinations contributing to congestion in the network.  
         Default values are applicable to Internet applications.
         
         The default value for newly created profiles is determined by 
         the setting of mxSctpDefaultPathMaxRetrans."
    ::= { mxSctpEntry 9 }

mxSctpCookieLife OBJECT-TYPE
    SYNTAX      MilliSeconds
    UNITS       "seconds"
    MAX-ACCESS  read-create
    STATUS      current
    DESCRIPTION 
        "This column defines the time interval (in milliseconds) in 
         conjunction with mxSctpCookieInc beyond which a COOKIE-ECHO 
         received with a cookie sent in an INIT-ACK will no longer be 
         accepted.  For SCTP, this also limits the maximum time interval 
         for which the HMAC secret key for the cookie will be valid.  
         Valid values are zero or greater.  Values of zero will  be 
         converted to a system clock tick.  The default value is the 
         value recommended by RFC 2960 (60,000 milliseconds, or 60 
         seconds).
         
         Reducing this value will increase the probability that passive 
         connection attempts will fail due to expired cookies.  
         Increasing the value will reduce the overall security of the 
         system by permitting attackers an increased interval within 
         which to crack HMACs and guess verification tags.  This value 
         may be adjusted in conjunction with mxSctpCookieInc to meet 
         most objectives for successful passive connection attempts with 
         the best security afforded by smaller values of 
         mxSctpCookieLife.
         
         Unfortunately, the mxSctpCookieLife and mxSctpCookieInc must be 
         adjusted to accommodate the slowest peer on the slowest 
         connection.  The default setting is adequate for Internet 
         applications.
         
         The default value for newly created profiles is determined by 
         the setting of mxSctpDefaultCookieLife."
    ::= { mxSctpEntry 10 }

mxSctpCookieInc OBJECT-TYPE
    SYNTAX      MilliSeconds
    UNITS       "seconds"
    MAX-ACCESS  read-create
    STATUS      current
    DESCRIPTION 
        "This column defines the time increment (in milliseconds) that 
         will be added to the lifespan of the cookie in an INIT-ACK if 
         the received INIT requests cookie preservative to lengthen the 
         lifespan of the cookie.  Valid values are zero or greater.  The 
         default value is the value recommended in RFC 2960 5.2.6 (1000 
         milliseconds, or 1 second).
         
         This value can be adjusted in conjunction with mxSctpCookieLife 
         to meet objectives of successful passive connection attempts 
         and security.  The default setting is adequate for Internet 
         applications.
         
         The default value for newly created profiles is determined by 
         the setting of mxSctpDefaultCookieInc."
    ::= { mxSctpEntry 11 }

mxSctpMaxInitRetries OBJECT-TYPE
    SYNTAX      Unsigned32
    MAX-ACCESS  read-create
    STATUS      current
    DESCRIPTION 
        "This column defines the number of times that an INIT or 
         COOKIE-ECHO will be resent to a given destination before 
         abandoning an active open attempt.  Value values are zero or 
         greater.  The default value is the value recommended by RFC 
         2960 (8 retries).
         
         The default value for newly created profiles is determined by 
         the setting of mxSctpDefaultMaxInitRetries."
    ::= { mxSctpEntry 12 }

mxSctpMaxBurst OBJECT-TYPE
    SYNTAX      Unsigned32
    MAX-ACCESS  read-create
    STATUS      current
    DESCRIPTION 
        "This column defines the maximum number of MTUs of new data 
         chunks that will be sent in a burst in accordance with SCTP 
         Specification Errata and Issues, RFC 4460 and RFC 4960.  The 
         default value is the value recommended in RFC 4960 (4 MTUs).
         
         The default value for newly create profiles is determined by 
         the setting of mxSctpDefaultMaxBurst."
    ::= { mxSctpEntry 13 }

mxSctpAssocMaxRetrans OBJECT-TYPE
    SYNTAX      Unsigned32
    MAX-ACCESS  read-create
    STATUS      current
    DESCRIPTION 
        "This column defines the number of times that the sending 
         endpoint will attempt retransmitting a packet on any active 
         destination transport address before it aborts the association.  
         Value values are zero or greater.  The default value is the 
         value recommended in RFC 2960 (10 retransmissions).
         
         This value should be larger than sum of the path maximum number 
         of retransmission values of each of the destinations.
         
         Setting this value to less than the sum of the path maximum 
         retransmission values for all of the destinations has the 
         interesting effect of permitting a connection to persist even 
         when all destinations have been deemed inactive.
         
         The default value for newly created profiles is determined by 
         the setting of mxSctpDefaultAssocMaxRetrans."
    DEFVAL      { 20 }
    ::= { mxSctpEntry 14 }

mxSctpSackDelay OBJECT-TYPE
    SYNTAX      MilliSeconds
    UNITS       "seconds"
    MAX-ACCESS  read-create
    STATUS      current
    DESCRIPTION 
        "This column defines the interval of time (in milliseconds) that 
         will be used as an RTO (retransmission timeout) value when 
         sending packets to a destination transport address.  Valid 
         values are zero or to 500 milliseconds (RFC 2960 forbids 
         setting this value larger than 500 milliseconds).  The default 
         value is the value recommended in RFC 2960 (200 milliseconds).
         
         The default value for newly created profiles is determined by 
         the setting of mxSctpDefaultSackDelay."
    DEFVAL      { 20 }
    ::= { mxSctpEntry 15 }

mxSctpLifetime OBJECT-TYPE
    SYNTAX      MilliSeconds
    UNITS       "seconds"
    MAX-ACCESS  read-create
    STATUS      current
    DESCRIPTION 
        "The default value for newly created rows is determined by the 
         setting of mxSctpDefaultLifetime."
    ::= { mxSctpEntry 16 }

mxSctpRowStatus OBJECT-TYPE
    SYNTAX      RowStatus
    MAX-ACCESS  read-create
    STATUS      current
    DESCRIPTION 
        "Provides a mechanism whereby management stations, following the 
         RowStatus textual convention from the SNMPv2-TC module, may 
         create or destroy conceptual rows in this table.  Profiles that 
         are referenced by another table cannot be deleted until the 
         reference is removed."
    REFERENCE   
        "STD 58, SNMPv2-TC RowStatus."
    ::= { mxSctpEntry 17 }

-- =====================================================================
-- mxFilter group
-- =====================================================================
-- The mxFilter group is responsible for managing the filtering of local 
-- and remote monitor sources.
-- .....................................................................

mxFilter OBJECT IDENTIFIER
    ::= { mxMonObjects 9 }

mxFilterTable OBJECT-TYPE
    SYNTAX      SEQUENCE OF MxFilterEntry
    MAX-ACCESS  not-accessible
    STATUS      current
    DESCRIPTION 
        "Provides a table of filter programs for use in filtering the 
         packets collected for a given monitoring source, whether local 
         or remote."
    ::= { mxFilter 1 }

mxFilterEntry OBJECT-TYPE
    SYNTAX      MxFilterEntry
    MAX-ACCESS  not-accessible
    STATUS      current
    DESCRIPTION 
        "Each row in this table corresponds to a single filter program.  
         The program lines themselves are conatined under the 
         corresponding index (mxFilterIndex) in the mxFilterProgTable.  
         Filter programs can be compiled and activated for use using 
         this table."
    INDEX       { mxFilterIndex }
    ::= { mxFilterTable 1 }

MxFilterEntry ::= SEQUENCE {
    mxFilterIndex           Unsigned32,
    mxFilterState           INTEGER,
    mxFilterActionResult    INTEGER,
    mxFilterRowStatus       RowStatus
}

mxFilterIndex OBJECT-TYPE
    SYNTAX      Unsigned32
    MAX-ACCESS  not-accessible
    STATUS      current
    DESCRIPTION 
        "Provides a non-zero ordinal index into the rows of the 
         mxFilterTable."
    ::= { mxFilterEntry 1 }

mxFilterState OBJECT-TYPE
    SYNTAX      INTEGER { vacant(0), uninit(1), compiled(2), failed(3) }
    MAX-ACCESS  read-only
    STATUS      current
    DESCRIPTION 
        "Provides the state of the filter program.  The program can be:
         - vacant(0), no filter program, unsusable;
         - uninit(1), uninitialized, unusable;
         - compiled(2), compiled and ready to use;
         - failed(3), compilation failed, unusabled.
         Only filter programs in the compiled(2) state are usable for 
         filtering collected packets."
    ::= { mxFilterEntry 2 }

mxFilterActionResult OBJECT-TYPE
    SYNTAX      INTEGER { success(0), failure(1), compile(2) }
    MAX-ACCESS  read-create
    STATUS      current
    DESCRIPTION 
        "Provides a mechanism for compiling filter programs.  The result 
         (on read) can be:
         - success(0), the filter program was compiled successfully; 
           the state is compiled(2);
         - failure(1), the filter program compilation failure; the state 
           is vacant(0) or failed(3);
         
         The action (on write) can be:
         - compile(2), compile the filter program and report result.
         
         To compile a filter program, write compile(2) to this column 
         and then read the success(0) or failure(1) result."
    ::= { mxFilterEntry 3 }

mxFilterRowStatus OBJECT-TYPE
    SYNTAX      RowStatus
    MAX-ACCESS  read-create
    STATUS      current
    DESCRIPTION 
        "Provides a mechanism whereby management stations may add or 
         delete rows from this table.  Destroying a row in this table 
         will also destroy all of the corresponding rows in the 
         mxFilterProgTable at the same mxFilterIndex as the destroyed 
         row.  All entries in this table persist across agent reboots."
    ::= { mxFilterEntry 4 }

-- =====================================================================

mxFilterProgTable OBJECT-TYPE
    SYNTAX      SEQUENCE OF MxFilterProgEntry
    MAX-ACCESS  not-accessible
    STATUS      current
    DESCRIPTION 
        "This is a side table of the mxFilterTable the provides a way of 
         specifying multiple filter program lines.  Each row in the 
         table corresponds to one line of filter program (indexed by 
         mxFilterProgIndex) that belongs to one filter (indexed by 
         mxFilterIndex).  Filter programs must be successfully compiled 
         before they are usable.  Filter programs are compiled using the 
         corresponding mxFilterIndex row in the mxFilterTable."
    ::= { mxFilter 2 }

mxFilterProgEntry OBJECT-TYPE
    SYNTAX      MxFilterProgEntry
    MAX-ACCESS  not-accessible
    STATUS      current
    DESCRIPTION 
        "Each row in this table provides on line of filter program 
         formattted according to tcpdump BPF filter syntax."
    INDEX       { mxFilterIndex, mxFilterProgIndex }
    ::= { mxFilterProgTable 1 }

MxFilterProgEntry ::= SEQUENCE {
    mxFilterProgIndex       Unsigned32,
    mxFilterProgLine        SnmpAdminString,
    mxFilterProgRowStatus   RowStatus
}

mxFilterProgIndex OBJECT-TYPE
    SYNTAX      Unsigned32
    MAX-ACCESS  not-accessible
    STATUS      current
    DESCRIPTION 
        "Provides a non-zero oridinal index into the filter program 
         lines corresponding to a given filter program (indexed by 
         mxFilterIndex).  Line indexes that have a lesser numeric value 
         appear before lines that have a greater numeric value.  The 
         value zero (0) is forbidden.  If numbers are missing in oridnal 
         sequence, they are considered blank or void lines during filter 
         program compilation."
    ::= { mxFilterProgEntry 1 }

mxFilterProgLine OBJECT-TYPE
    SYNTAX      SnmpAdminString
    MAX-ACCESS  read-create
    STATUS      current
    DESCRIPTION 
        "Provides one line of the filter program using tcpdump BPF 
         filter format."
    ::= { mxFilterProgEntry 2 }

mxFilterProgRowStatus OBJECT-TYPE
    SYNTAX      RowStatus
    MAX-ACCESS  read-create
    STATUS      current
    DESCRIPTION 
        "Provides a mechanism whereby management stations may add filter 
         program lines to this table.  When the mxFilterIndex for the 
         created row does not already exist, one will be created in the 
         mxFilterTable.  When the last line for a given mxFilterIndex is 
         destroyed, the entry in the mxFilterTable is not destroyed by 
         must be destroyed explicitly by using the row status of the 
         mxFilterTable.  All rows in this table are persistent across 
         agent reboot."
    ::= { mxFilterProgEntry 3 }

-- =====================================================================
-- mxBuffer group
-- =====================================================================
-- The mxBuffer group is responsible for managing the buffering of local 
-- to remote monitor sources.
-- .....................................................................

mxBuffer OBJECT IDENTIFIER
    ::= { mxMonObjects 10 }

mxBufferAdminState OBJECT-TYPE
    SYNTAX      AdministrativeState
    MAX-ACCESS  read-write
    STATUS      current
    DESCRIPTION 
        "Represents the administrative capability of the capture buffer 
         to perform its function.  The following states are defined:
         
         - locked(0), use of the capture buffer has been prohibited by a 
           managing system.  Information from subordinate records may be 
           retrieved but new records shall not be created.  Records may 
           be deleted.
         
         - unlocked(1), use of the capture buffer has been permitted by 
           a managing system.  Information from subordinate records may 
           be retrieved and, conditional on the values of other state 
           and status attributes, new records may be created.
         
         Whenever the administrative state of the capture buffer is 
         changed, a state change notification is generated."
    REFERENCE   
        "ITU-T Rec. X.735 (1992) | ISO/IEC 10164-6 : 1993, 
               Section 8.1.1.1.3."
    DEFVAL      { unlocked }
    ::= { mxBuffer 1 }

mxBufferOpState OBJECT-TYPE
    SYNTAX      OperationalState
    MAX-ACCESS  read-only
    STATUS      current
    DESCRIPTION 
        "Represents the operational capability of the capture buffer to 
         perform its function.  The following states are defined:
         
         - enabled(0), the buffer is operational and ready for use.  
           Information from subordinate records may be retrieved and, 
           conditional on the values of other state and status 
           attributes, new records may be created.
         
         - disabled(1), the buffer is not available for use.  New 
           records cannot be created.
         
         A change in operational state shall generate a state changed 
         notification."
    REFERENCE   
        "ITU-T Rec. X.735 (1992) | ISO/IEC 10164-6 : 1993, 
               Section 8.1.1.1.4."
    DEFVAL      { enabled }
    ::= { mxBuffer 2 }

mxBufferAvailStatus OBJECT-TYPE
    SYNTAX      AvailabilityStatus
    MAX-ACCESS  read-only
    STATUS      current
    DESCRIPTION 
        "Reflects the availability status of the buffer.  May indicate a 
         'log-full' condition; indicating that records can be retrieved 
         but that no new records can be added.
         
         The availability status package shall be present if any of the 
         scheduling packages are instantiated.  This attribute reflects 
         the availability status of the buffer.  When the resource has 
         been made unavailable in accordance with a predetermined time 
         schedule its value will be 'Off-Duty'.  The attribute is 
         read-only.  The value on creation is determined by the 
         scheduling parameters specified and the status of the resource.  
         The required value set for this attribute in this package is 
         'Off-Duty'.
         
         No state change notification is generated when this attribute 
         changes value.  Note: the buffer makes use of the availability 
         status to indicate the 'log-full' condition; the presence of 
         this conditional package makes available the 'Off-Duty' value 
         to the object."
    REFERENCE   
        "ITU-T Rec. X.735 (1992) | ISO/IEC 10164-6 : 1993, 
               Section 8.1.1.1.6.
         ITU-T Rec. X.735 (1992) | ISO/IEC 10164-6 : 1993, 
         Section 8.1.1.4.1."
    DEFVAL      { {} }
    ::= { mxBuffer 3 }

mxBufferFullAction OBJECT-TYPE
    SYNTAX      FullAction
    MAX-ACCESS  read-write
    STATUS      current
    DESCRIPTION 
        "Provides a specification of the action to be taken when the 
         maximum size of the buffer has been reached.  Options are:
         
         - wrap(0), the oldest record in the buffer, as determined by 
           the record time stamp, will be deleted to free resources for 
           the creation of new records.
         
         - halt(1), no more records will be buffered; records already in 
           the buffer will be retained.
         
         Both options are supported by every buffer."
    DEFVAL      { wrap }
    ::= { mxBuffer 4 }

mxBufferMaxSize OBJECT-TYPE
    SYNTAX      Unsigned32
    UNITS       "octets"
    MAX-ACCESS  read-write
    STATUS      current
    DESCRIPTION 
        "Specifies the size of the buffer measured in number of octets.  
         A buffer may have an indeterminate size.  A maximum buffer size 
         of zero shall be used to specify that the buffer size has no 
         predefined limit.
         
         Note: Since the buffer size is specified in octets, the actual 
         amount of information that is contained in the buffer will be 
         determined by the data representation in the buffer.  This data 
         representation is not subject to standardization.  The maximum 
         buffer size does not include the system overhead involved in 
         establishing the buffer.  Thus, immediately after creation, the 
         current buffer size should read zero."
    REFERENCE   
        "ITU-T Rec. X.735 (1992) | ISO/IEC 10164-6 : 1993,
                Section 8.1.1.2.1"
    DEFVAL      { 0 }
    ::= { mxBuffer 5 }

mxBufferMaxMsgs OBJECT-TYPE
    SYNTAX      Unsigned32
    UNITS       "messages"
    MAX-ACCESS  read-write
    STATUS      current
    DESCRIPTION 
        "Specifies the maximum number of messages that will be stored in 
         the buffer before wrapping or halting occurs.  The value zero 
         (0) specifies that wrapping or halting is not based on the 
         number of messages in the buffer."
    DEFVAL      { 0 }
    ::= { mxBuffer 6 }

mxBufferMaxTime OBJECT-TYPE
    SYNTAX      Unsigned32
    UNITS       "seconds"
    MAX-ACCESS  read-write
    STATUS      current
    DESCRIPTION 
        "Specifies the maximum time interval for which messages will be 
         stored in the buffer before wrapping or halting occurs.  The 
         value zero (0) is special and specifies that wrapping or 
         halting is not based on the time interval buffered."
    DEFVAL      { 0 }
    ::= { mxBuffer 7 }

mxBufferCurrentSize OBJECT-TYPE
    SYNTAX      Gauge32
    UNITS       "octets"
    MAX-ACCESS  read-only
    STATUS      current
    DESCRIPTION 
        "Indicates the current size of the buffer measured in octets.
         
         Note: Since the buffer size is specified in octets, the actual 
         amount of information that is contained in the buffer will be 
         determined by the data representation in the buffer.  This data 
         representation is not subject to standardization.  The maximum 
         buffer size does not include the system overhead involved in 
         establishing the buffer.  Thus, immediately after creation, the 
         current buffer size should read zero."
    REFERENCE   
        "ITU-T Rec. X.735 (1992) | ISO/IEC 10164-6 : 1993, 
               Section 8.1.1.2.2."
    DEFVAL      { 0 }
    ::= { mxBuffer 8 }

mxBufferNumberOfRecords OBJECT-TYPE
    SYNTAX      Gauge32
    UNITS       "messages"
    MAX-ACCESS  read-only
    STATUS      current
    DESCRIPTION 
        "This attribute indicates the current number of records 
         contained in the buffer."
    REFERENCE   
        "ITU-T Rec. X.735 (1992) | ISO/IEC 10164-6 : 1993, 
               Section 8.1.1.2.3."
    DEFVAL      { 0 }
    ::= { mxBuffer 9 }

mxBufferCurrentInterval OBJECT-TYPE
    SYNTAX      Gauge32
    UNITS       "seconds"
    MAX-ACCESS  read-only
    STATUS      current
    DESCRIPTION 
        "Indicates the current time interval (in seconds) over which 
         messages are contained in the buffer."
    DEFVAL      { 0 }
    ::= { mxBuffer 10 }

mxBufferAlarmThreshold OBJECT-TYPE
    SYNTAX      LogCapacityAlarmThreshold
    MAX-ACCESS  read-write
    STATUS      current
    DESCRIPTION 
        "The log alarm package provides for transmission of alarms when 
         a buffer full condition approaches.  This package shall be 
         present whenever a buffer is of finite size and halts buffering 
         when the 'log-full' availability status occurs.
         
         This attribute specifies, as a percentage of maximum buffer 
         size, the points at which an event will be generated to 
         indicate that a 'log-full' or 'log-wrap' condition is 
         approaching.  This attribute is set-valued.  Support of this 
         attribute is mandatory for the halt behaviour.  When a buffer 
         is created with the wrap option, the capacity threshold events 
         are triggered as if couple to a gauge that counts from zero to 
         the highest capacity threshold value defined and then resets to 
         zero."
    REFERENCE   
        "ITU-T Rec. X.735 (1992) | ISO/IEC 10164-6 : 1993, 
               Section 8.1.1.3."
    DEFVAL      { "\x64" }
    ::= { mxBuffer 11 }

mxBufferByteHiWaterMark OBJECT-TYPE
    SYNTAX      Gauge32
    UNITS       "message bytes"
    MAX-ACCESS  read-only
    STATUS      current
    DESCRIPTION 
        "Provides the high watermark of the number of message bytes 
         captured in the capture buffer.  This is the maximum number of 
         message bytes that were in the buffer since the last reset.  
         mxBufferReset can be used to reset this gauge to zero.
         
         This value can be used to properly size the capture buffer so 
         that it is unlikely to wrap or halt."
    DEFVAL      { 0 }
    ::= { mxBuffer 12 }

mxBufferByteLoWaterMark OBJECT-TYPE
    SYNTAX      Gauge32
    UNITS       "message bytes"
    MAX-ACCESS  read-only
    STATUS      current
    DESCRIPTION 
        "Provides the low watermark of the number of message bytes 
         captured in the capture buffer.  This is the minimum number of 
         message bytes that were in the buffer since the high watermark 
         was last set.  mxBufferReset can be used to reset this gauge to 
         zero.
         
         This value can be used to properly size the capture buffer so 
         that it is unlikely to wrap or halt."
    DEFVAL      { 0 }
    ::= { mxBuffer 13 }

mxBufferMsgsHiWaterMark OBJECT-TYPE
    SYNTAX      Gauge32
    UNITS       "messages"
    MAX-ACCESS  read-only
    STATUS      current
    DESCRIPTION 
        "Provides the high watermark of the number of messages captured 
         in the capture buffer.  This is the maximum number of messages 
         that were in the buffer since the last reset.  mxBufferReset 
         can be used to reset this gauge to zero.
         
         This value can be used to properly size the capture buffer so 
         that it is unlikely to wrap or halt."
    DEFVAL      { 0 }
    ::= { mxBuffer 14 }

mxBufferMsgsLoWaterMark OBJECT-TYPE
    SYNTAX      Gauge32
    UNITS       "messages"
    MAX-ACCESS  read-only
    STATUS      current
    DESCRIPTION 
        "Provides the low watermark of the number of messages captured 
         in the capture buffer.  This is the minimum number of messages 
         that were in the buffer since the high watermark was last set.  
         mxBufferReset can be used to reset this gauge to zero.
         
         This value can be used to properly size the capture buffer so 
         that it is unlikely to wrap or halt."
    DEFVAL      { 0 }
    ::= { mxBuffer 15 }

mxBufferTimeHiWaterMark OBJECT-TYPE
    SYNTAX      Gauge32
    UNITS       "seconds"
    MAX-ACCESS  read-only
    STATUS      current
    DESCRIPTION 
        "Provides the high watermark of the duration of time, in 
         seconds, between the first and last messages captured in the 
         capture buffer.  This is the maximum duration of time of 
         messages in the buffer since the last reset.  mxBufferReset can 
         be used to reset this gauge to zero.
         
         This value can be used to properly size the capture buffer so 
         that it is unlikely to wrap or halt."
    DEFVAL      { 0 }
    ::= { mxBuffer 16 }

mxBufferTimeLoWaterMark OBJECT-TYPE
    SYNTAX      Gauge32
    UNITS       "seconds"
    MAX-ACCESS  read-only
    STATUS      current
    DESCRIPTION 
        "Provides the low watermark of the duration of time, in seconds, 
         between the first and last messages captured in the capture 
         buffer.  This is the minimum duration of time that was 
         contained in the buffer since the high watermark was last set.  
         mxBufferReset can be used to reset this gauge to zero.
         
         This value can be used to properly size the capture buffer so 
         that it is unlikely to wrap or halt."
    DEFVAL      { 0 }
    ::= { mxBuffer 17 }

mxBufferDrops OBJECT-TYPE
    SYNTAX      Counter32
    UNITS       "messages dropped"
    MAX-ACCESS  read-only
    STATUS      current
    DESCRIPTION 
        "Provides the number of messages dropped as a result of buffer 
         wrap or buffer halt.  When the buffer is set for wrap(0), this 
         is the number of messages dropped from the front of the buffer.  
         When the buffer is set for halt(1), this is the number of 
         messages dropped from the end of the buffer.  This number is 
         reset by reading the first or last message in the buffer 
         (respectively).  It may also be reset using mxBufferReset."
    DEFVAL      { 0 }
    ::= { mxBuffer 18 }

mxBufferReset OBJECT-TYPE
    SYNTAX      INTEGER { reset(0) }
    MAX-ACCESS  read-write
    STATUS      current
    DESCRIPTION 
        "When written, resets the buffer high and low watermarks to 
         zero.  Also, reset the number of message buffer drops."
    DEFVAL      { reset }
    ::= { mxBuffer 19 }

-- =====================================================================

mxMonGroups OBJECT IDENTIFIER
    ::= { mxMonMIB 3 }

mxMonCompliances OBJECT IDENTIFIER
    ::= { mxMonMIB 4 }

mxMonMonitorGroup OBJECT-GROUP
    OBJECTS     { mxMonitorExport, mxMonitorAdminState, 
                  mxMonitorOperState, mxMonitorAvailStatus, 
                  mxMonitorProcStatus, mxMonitorUsageState, 
                  mxMonitorMessages, mxMonitorMsgOctets, 
                  mxMonitorSusCompressed, mxMonitorMsuDrops, 
                  mxMonitorFilterDrops, mxMonitorActiveLinkDirs, 
                  mxMonitorActiveHslDirs, mxMonitorResetCounts, 
                  mxMonitorLastReset, mxMonitorCurrent }
    STATUS      current
    DESCRIPTION 
        "A collection of objects providing managements of monitor 
         sources."
    ::= { mxMonGroups 1 }

mxMonCaptureScalarGroup OBJECT-GROUP
    OBJECTS     { mxCaptureNameString, mxCaptureAdminState, 
                  mxCaptureOpState, mxCaptureAvailStatus, 
                  mxCaptureFullAction, mxCaptureMaxSize, 
                  mxCaptureCurrentSize, mxCaptureNumberOfRecords, 
                  mxCaptureAlarmThreshold, mxCaptureStartTime, 
                  mxCaptureStopTime, mxCaptureIntervalsOfDay, 
                  mxCaptureWeekMask, mxCaptureRotInterval, 
                  mxCaptureRotSize, mxCaptureRotNumber, 
                  mxCaptureCachePath, mxCaptureSpoolPath, 
                  mxCaptureArchivePath, mxCaptureArchiveSubdirs, 
                  mxCaptureCompression, mxCaptureFileSystemAlloc, 
                  mxCaptureMaxDiskUsage, mxCaptureDiscardPolicy, 
                  mxCaptureUpload }
    STATUS      current
    DESCRIPTION 
        "A collection of scalar objects that control the overall 
         capture, spooling and archival processes."
    ::= { mxMonGroups 2 }

mxMonCaptureTableGroup OBJECT-GROUP
    OBJECTS     { mxCaptureName, mxCaptureCompressed, mxCaptureState, 
                  mxCaptureLinkType, mxCaptureSize, mxCaptureCompSize, 
                  mxCaptureMessages, mxCaptureMsgOctets, 
                  mxCaptureSusCompressed, mxCaptureMsuDrops, 
                  mxCaptureFilterDrops, mxCaptureActiveLinkDirs, 
                  mxCaptureActiveHslDirs, mxCaptureInterval, 
                  mxCaptureBegTime, mxCaptureEndTime, 
                  mxCaptureActionResult }
    STATUS      current
    DESCRIPTION 
        "A collection of tabular objects that control individual files 
         in the capture, spooling and archival processes."
    ::= { mxMonGroups 3 }

mxMonPushGroup OBJECT-GROUP
    OBJECTS     { mxPushHostname, mxPushXportAddrType, mxPushXportAddr, 
                  mxPushXportProfile, mxPushAssocState, 
                  mxPushStorageType, mxPushRowStatus }
    STATUS      current
    DESCRIPTION 
        "A collection of tabular objects that control the export of 
         monitor sources to remote collectors."
    ::= { mxMonGroups 4 }

mxMonPullGroup OBJECT-GROUP
    OBJECTS     { mxPullHostname, mxPullXportAddrType, mxPullXportAddr, 
                  mxPullXportProfile, mxPullAssocState, 
                  mxPullStorageType, mxPullRowStatus }
    STATUS      current
    DESCRIPTION 
        "A collection of tabular objects that control the import of 
         monitor sources from remote probes."
    ::= { mxMonGroups 5 }

mxMonUploadGroup OBJECT-GROUP
    OBJECTS     { mxUploadSpec, mxUploadUsername, mxUploadPassword, 
                  mxUploadAdminState, mxUploadStatus }
    STATUS      current
    DESCRIPTION 
        "A collection of tabular objects that control the uploading of 
         files to a remote collector."
    ::= { mxMonGroups 6 }

mxMonDownloadGroup OBJECT-GROUP
    OBJECTS     { mxDownloadSpec, mxDownloadUsername, mxDownloadPassword, 
                  mxDownloadAdminState, mxDownloadStatus }
    STATUS      current
    DESCRIPTION 
        "A collection of tabular objects that control the donwloading of 
         files from a remote probe."
    ::= { mxMonGroups 7 }

mxMonCollectGroup OBJECT-GROUP
    OBJECTS     { mxCollectXportAddrType, mxCollectXportAddr, 
                  mxCollectAdminState, mxCollectOpState, 
                  mxCollectRowStatus }
    STATUS      current
    DESCRIPTION 
        "A collection of tabular objects that control the collection of 
         files."
    ::= { mxMonGroups 8 }

mxMonSctpScalarsGroup OBJECT-GROUP
    OBJECTS     { mxSctpDefaultNoDelay, mxSctpDefaultMaxseg, 
                  mxSctpDefaultHeartbeatItvl, mxSctpDefaultHeartbeat, 
                  mxSctpDefaultRtoInitial, mxSctpDefaultRtoMin, 
                  mxSctpDefaultRtoMax, mxSctpDefaultPathMaxRetrans, 
                  mxSctpDefaultCookieLife, mxSctpDefaultCookieInc, 
                  mxSctpDefaultMaxInitRetries, mxSctpDefaultMaxBurst, 
                  mxSctpDefaultAssocMaxRetrans, mxSctpDefaultSackDelay, 
                  mxSctpDefaultLifetime }
    STATUS      current
    DESCRIPTION 
        "A collection of scalar objects that provide defaults for SCTP 
         protocol parameter profiles."
    ::= { mxMonGroups 9 }

mxMonSctpTableGroup OBJECT-GROUP
    OBJECTS     { mxSctpNoDelay, mxSctpMaxseg, mxSctpHeartbeatItvl, 
                  mxSctpHeartbeat, mxSctpRtoInitial, mxSctpRtoMin, 
                  mxSctpRtoMax, mxSctpPathMaxRetrans, mxSctpCookieLife, 
                  mxSctpCookieInc, mxSctpMaxInitRetries, mxSctpMaxBurst, 
                  mxSctpAssocMaxRetrans, mxSctpSackDelay, mxSctpLifetime, 
                  mxSctpRowStatus }
    STATUS      current
    DESCRIPTION 
        "A collection of tabular objects that provide SCTP protocol 
         parameter profiles."
    ::= { mxMonGroups 10 }

mxMonFilterGroup OBJECT-GROUP
    OBJECTS     { mxFilterState, mxFilterActionResult, mxFilterRowStatus, 
                  mxFilterProgLine, mxFilterProgRowStatus }
    STATUS      current
    DESCRIPTION 
        "A collection of tabular objects that implement BPF filters."
    ::= { mxMonGroups 11 }

mxMonBufferScalarGroup OBJECT-GROUP
    OBJECTS     { mxBufferAdminState, mxBufferOpState, 
                  mxBufferAvailStatus, mxBufferFullAction, 
                  mxBufferMaxSize, mxBufferMaxMsgs, mxBufferMaxTime, 
                  mxBufferCurrentSize, mxBufferNumberOfRecords, 
                  mxBufferCurrentInterval, mxBufferAlarmThreshold, 
                  mxBufferByteHiWaterMark, mxBufferByteLoWaterMark, 
                  mxBufferMsgsHiWaterMark, mxBufferMsgsLoWaterMark, 
                  mxBufferTimeHiWaterMark, mxBufferTimeLoWaterMark, 
                  mxBufferDrops, mxBufferReset }
    STATUS      current
    DESCRIPTION 
        "A collection of scalar objects that manage the capture buffer."
    ::= { mxMonGroups 12 }

mxMonBasicCompliance MODULE-COMPLIANCE
    STATUS      current
    DESCRIPTION 
        "Provides the module compliance requirements for the MX monitor 
         MIB."

    MODULE      -- this module

        MANDATORY-GROUPS        { mxMonMonitorGroup, 
                  mxMonCaptureScalarGroup, mxMonCaptureTableGroup, 
                  mxMonUploadGroup, mxMonDownloadGroup }

        GROUP   mxMonPushGroup
        DESCRIPTION   
              "Conditional items when a probe is implemented."

        GROUP   mxMonPullGroup
        DESCRIPTION   
              "Conditional items when a collector is implemented."

        GROUP   mxMonSctpScalarsGroup
        DESCRIPTION   
              "Conditional items when a live feeds are implemented."

        GROUP   mxMonSctpTableGroup
        DESCRIPTION   
              "Conditional items when a live feeds are implemented."

        GROUP   mxMonFilterGroup
        DESCRIPTION   
              "Conditional items when a filters are implemented."

        GROUP   mxMonBufferScalarGroup
        DESCRIPTION   
              "Conditional items when a live feeds are implemented."

        GROUP   mxMonCollectGroup
        DESCRIPTION   
              "Don't know what this is for yet..."

        OBJECT  mxMonitorAdminState
        SYNTAX  AdministrativeState { locked(0), unlocked(1), 
                    shuttingDown(2) }
        WRITE-SYNTAX    AdministrativeState { locked(0), unlocked(1) }
        DESCRIPTION   
              "This object has a different read and write syntax."

        OBJECT  mxCaptureAdminState
        SYNTAX  AdministrativeState { locked(0), unlocked(1), 
                    shuttingDown(2) }
        WRITE-SYNTAX    AdministrativeState { locked(0), unlocked(1) }
        DESCRIPTION   
              "This object has a different read and write syntax."

        OBJECT  mxCaptureActionResult
        SYNTAX  INTEGER { success(0), failure(1) }
        WRITE-SYNTAX    INTEGER { spool(2), archive(3), delete(4), 
                    upload(5) }
        DESCRIPTION   
              "This object has a different read and write syntax."

        OBJECT  mxUploadAdminState
        SYNTAX  AdministrativeState { locked(0), unlocked(1), 
                    shuttingDown(2) }
        WRITE-SYNTAX    AdministrativeState { locked(0), unlocked(1) }
        DESCRIPTION   
              "This object has a different read and write syntax."

        OBJECT  mxUploadStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxDownloadAdminState
        SYNTAX  AdministrativeState { locked(0), unlocked(1), 
                    shuttingDown(2) }
        WRITE-SYNTAX    AdministrativeState { locked(0), unlocked(1) }
        DESCRIPTION   
              "This object has a different read and write syntax."

        OBJECT  mxDownloadStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxPushRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxPullRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxSctpRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxFilterActionResult
        SYNTAX  INTEGER { success(0), failure(1) }
        WRITE-SYNTAX    INTEGER { compile(2) }
        DESCRIPTION   
              "This object has a different read and write syntax."

        OBJECT  mxFilterRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxFilterProgRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxBufferAdminState
        SYNTAX  AdministrativeState { locked(0), unlocked(1), 
                    shuttingDown(2) }
        WRITE-SYNTAX    AdministrativeState { locked(0), unlocked(1) }
        DESCRIPTION   
              "This object has a different read and write syntax."

        OBJECT  mxCollectAdminState
        SYNTAX  AdministrativeState { locked(0), unlocked(1), 
                    shuttingDown(2) }
        WRITE-SYNTAX    AdministrativeState { locked(0), unlocked(1) }
        DESCRIPTION   
              "This object has a different read and write syntax."

        OBJECT  mxCollectRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

    ::= { mxMonCompliances 1 }

mxMonProbeCompliance MODULE-COMPLIANCE
    STATUS      current
    DESCRIPTION 
        "Provides the module compliance requirements for the MX monitor 
         MIB when the implementation is a probe only.  A probe is a 
         network element that captures messages and archives them in 
         files that are uploaded to a collector according to a schedule.  
         
         The probe may also provide its monitoring sources as live feeds 
         to network management stations or to collectors that will 
         capture their own files from the live feed."

    MODULE      -- this module

        MANDATORY-GROUPS        { mxMonMonitorGroup, 
                  mxMonCaptureScalarGroup, mxMonCaptureTableGroup, 
                  mxMonUploadGroup }

        GROUP   mxMonPushGroup
        DESCRIPTION   
              "Conditional items to export monitor sources to 
               collectors."

        GROUP   mxMonSctpScalarsGroup
        DESCRIPTION   
              "Conditional items when a live feeds are implemented."

        GROUP   mxMonSctpTableGroup
        DESCRIPTION   
              "Conditional items when a live feeds are implemented."

        GROUP   mxMonFilterGroup
        DESCRIPTION   
              "Conditional items when a filters are implemented."

        GROUP   mxMonBufferScalarGroup
        DESCRIPTION   
              "Conditional items when a live feeds are implemented."

        OBJECT  mxMonitorAdminState
        SYNTAX  AdministrativeState { locked(0), unlocked(1), 
                    shuttingDown(2) }
        WRITE-SYNTAX    AdministrativeState { locked(0), unlocked(1) }
        DESCRIPTION   
              "This object has a different read and write syntax."

        OBJECT  mxCaptureAdminState
        SYNTAX  AdministrativeState { locked(0), unlocked(1), 
                    shuttingDown(2) }
        WRITE-SYNTAX    AdministrativeState { locked(0), unlocked(1) }
        DESCRIPTION   
              "This object has a different read and write syntax."

        OBJECT  mxCaptureActionResult
        SYNTAX  INTEGER { success(0), failure(1) }
        WRITE-SYNTAX    INTEGER { spool(2), archive(3), delete(4), 
                    upload(5) }
        DESCRIPTION   
              "This object has a different read and write syntax."

        OBJECT  mxUploadAdminState
        SYNTAX  AdministrativeState { locked(0), unlocked(1), 
                    shuttingDown(2) }
        WRITE-SYNTAX    AdministrativeState { locked(0), unlocked(1) }
        DESCRIPTION   
              "This object has a different read and write syntax."

        OBJECT  mxUploadStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxPushRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxSctpRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxFilterActionResult
        SYNTAX  INTEGER { success(0), failure(1) }
        WRITE-SYNTAX    INTEGER { compile(2) }
        DESCRIPTION   
              "This object has a different read and write syntax."

        OBJECT  mxFilterRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxFilterProgRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxBufferAdminState
        SYNTAX  AdministrativeState { locked(0), unlocked(1), 
                    shuttingDown(2) }
        WRITE-SYNTAX    AdministrativeState { locked(0), unlocked(1) }
        DESCRIPTION   
              "This object has a different read and write syntax."

    ::= { mxMonCompliances 2 }

mxMonCollectorCompliance MODULE-COMPLIANCE
    STATUS      current
    DESCRIPTION 
        "Provides the module compliance requirements for the MX monitor 
         MIB when the implementation is a collector only."

    MODULE      -- this module

        MANDATORY-GROUPS        { mxMonDownloadGroup }

        GROUP   mxMonCaptureScalarGroup
        DESCRIPTION   
              "Conditional items when collector is to capture from live 
               monitor feeds."

        GROUP   mxMonCaptureTableGroup
        DESCRIPTION   
              "Conditional items when collector is to capture from live 
               monitor feeds."

        GROUP   mxMonPullGroup
        DESCRIPTION   
              "Conditional items when a collector is implemented."

        GROUP   mxMonSctpScalarsGroup
        DESCRIPTION   
              "Conditional items when a live feeds are implemented."

        GROUP   mxMonSctpTableGroup
        DESCRIPTION   
              "Conditional items when a live feeds are implemented."

        GROUP   mxMonFilterGroup
        DESCRIPTION   
              "Conditional items when a filters are implemented."

        OBJECT  mxCaptureAdminState
        SYNTAX  AdministrativeState { locked(0), unlocked(1), 
                    shuttingDown(2) }
        WRITE-SYNTAX    AdministrativeState { locked(0), unlocked(1) }
        DESCRIPTION   
              "This object has a different read and write syntax."

        OBJECT  mxCaptureActionResult
        SYNTAX  INTEGER { success(0), failure(1) }
        WRITE-SYNTAX    INTEGER { spool(2), archive(3), delete(4), 
                    upload(5) }
        DESCRIPTION   
              "This object has a different read and write syntax."

        OBJECT  mxDownloadAdminState
        SYNTAX  AdministrativeState { locked(0), unlocked(1), 
                    shuttingDown(2) }
        WRITE-SYNTAX    AdministrativeState { locked(0), unlocked(1) }
        DESCRIPTION   
              "This object has a different read and write syntax."

        OBJECT  mxDownloadStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxPullRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxSctpRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxFilterActionResult
        SYNTAX  INTEGER { success(0), failure(1) }
        WRITE-SYNTAX    INTEGER { compile(2) }
        DESCRIPTION   
              "This object has a different read and write syntax."

        OBJECT  mxFilterProgRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

    ::= { mxMonCompliances 3 }

mxMonNmsCompliance MODULE-COMPLIANCE
    STATUS      current
    DESCRIPTION 
        "Provides the module compliance requirements for the MX monitor 
         MIB when the implementation is a Network Mangement Station 
         (NMS).
         
         Network management stations require the ability to accept a 
         monitor source feed from a probe and act upon the live data 
         stream."

    MODULE      -- this module

        MANDATORY-GROUPS        { mxMonPullGroup, mxMonSctpScalarsGroup, 
                  mxMonSctpTableGroup }

        GROUP   mxMonPullGroup
        DESCRIPTION   
              "Conditional items when a network management station is 
               implemented."

        GROUP   mxMonFilterGroup
        DESCRIPTION   
              "Conditional items when a filters are implemented."

        OBJECT  mxPullRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

        OBJECT  mxFilterActionResult
        SYNTAX  INTEGER { success(0), failure(1) }
        WRITE-SYNTAX    INTEGER { compile(2) }
        DESCRIPTION   
              "This object has a different read and write syntax."

        OBJECT  mxFilterProgRowStatus
        SYNTAX  RowStatus { active(1), notInService(2), notReady(3), 
                    createAndGo(4), createAndWait(5), destroy(6) }
        WRITE-SYNTAX    RowStatus { active(1), notInService(2), 
                    createAndGo(4), createAndWait(5), destroy(6) }
        DESCRIPTION   
              "This object has a different read and write syntax."

    ::= { mxMonCompliances 4 }

END -- end of module OPENSS7-MX-MON-MIB.

-- vim: ft=mib comments=\f\:\",\b\:\-\-,\:\-\-,\f\b\:- fo+=tcqlornw tw=72 nocin nosi sts=4 sw=4 et
