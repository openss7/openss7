-- vim: ft=mib comments=\f\b\:\"ITU\-T,\f\b\:ITU\-T,\f\:\",\b\:\-\-,\:\-\-,\f\b\:\-,\f\b\:\· fo+=tcqlornw12 tw=64 ai nocin nosi sts=4 sw=4 et
-- =============================================================================
-- 
-- @(#) src/mibs/OPENSS7-TLM-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-NLM-MIB DEFINITIONS ::= BEGIN

IMPORTS
    AreaAddresses, CircuitID, CircuitType, DatabaseState, HopMetric, 
    ISType, IntermediateSystemPriority, Password, Passwords, SystemId
        FROM OPENSS7-ISIS-MIB
    openss7X
        FROM OPENSS7-SMI
    AdministrativeState, OperationalState, SimpleNameType
        FROM OPENSS7-SMI-MIB
    MilliSeconds
        FROM OPENSS7-TC
    SnmpAdminString
        FROM SNMP-FRAMEWORK-MIB
    Counter64, Gauge32, Integer32, MODULE-IDENTITY, OBJECT-IDENTITY, 
    OBJECT-TYPE, Unsigned32
        FROM SNMPv2-SMI
    RowPointer, RowStatus, TEXTUAL-CONVENTION, TruthValue
        FROM SNMPv2-TC;

nlmMIB MODULE-IDENTITY
    LAST-UPDATED "201502181310Z"
    ORGANIZATION 
        "The OpenSS7 Project"
    CONTACT-INFO 
        "Brian Bidulock
         OpenSS7 Corporation
         1469 Jefferys Crescent
         Edmonton, Alberta T6L 6T1
         CANADA
         Tel: +1 780 490 1141
         Fax: +1 780 490 1241
         Mob: +1 780 953 0557
         mailto:bidulock@openss7.org"
    DESCRIPTION 
        "This MIB provides configuration and status information 
         of an OSI CLNS/CONS subsystem, where the CLNS is in 
         accordance with ITU-T Rec. X.233 (1997) | ISO/IEC 
         8473-1 : 1998, ISO/IEC 8473-2, ITU-T Rec. X.622 
         | ISO/IEC 8473-3, ITU-T Rec. X.623 | ISO/IEC 8473-4 and 
         also ES-IS in accordance with ISO/IEC 9542, IS-IS in 
         accordance with ISO/IEC 10589 and IDRP in accordance 
         with ISO/IEC 10747.  Accordingly, the CLNS can be 
         provided by an IEEE 802.2 subnetwork, X.25 PLP, or an 
         OSI datalink.
         
	 This MIB provides configuration and status information for an 
	 OSI CONS subsystem, where the CONS is in accordance with ITU-T 
	 Rec. X.622 | ISO/IEC 8881 and management information from ITU-T 
	 Rec. X.283 | ISO/IEC 10733.  In addition, this MIB supports 
	 SNARE operation for both End-Systems and SNAREs in accordance 
	 with ISO/IEC 10030.  The MIB makes use of the 
	 OPENSS7-X25-PLP-MIB for the underlying X.25 Packet Layer 
	 Protocol supporting the OSI CONS.
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201502181310Z"
    DESCRIPTION 
        "Initial version of this mib."
    ::= { openss7X 283 }

 -- top level organization of the MIB

-- nlmNotifications    OBJECT IDENTIFIER ::= { nlmMIB         0 }
-- nlmObjects          OBJECT IDENTIFIER ::= { nlmMIB         1 }
-- nlmConformance      OBJECT IDENTIFIER ::= { nlmMIB         2 }

-- nlmTables           OBJECT IDENTIFIER ::= { nlmObjects     1 }
-- nlmScalars          OBJECT IDENTIFIER ::= { nlmObjects     2 }
-- nlmNotifs           OBJECT IDENTIFIER ::= { nlmObjects     3 }
-- nlmOids             OBJECT IDENTIFIER ::= { nlmObjects     4 }

-- nlmCompliances      OBJECT IDENTIFIER ::= { nlmConformance 1 }
-- nlmGroups           OBJECT IDENTIFIER ::= { nlmConformance 2 }

-- nlmSubsystem        OBJECT IDENTIFIER ::= { nlmTables  1 }
-- nlmEntity           OBJECT IDENTIFIER ::= { nlmTables  2 }
-- nlmLinkage          OBJECT IDENTIFIER ::= { nlmTables  3 }
-- nlmCLNS             OBJECT IDENTIFIER ::= { nlmTables  4 }
-- nlmCONS             OBJECT IDENTIFIER ::= { nlmTables  5 }
-- nlmConnection       OBJECT IDENTIFIER ::= { nlmTables  6 }
-- nlmNSAP             OBJECT IDENTIFIER ::= { nlmTables  7 }
-- nlmX25PLE           OBJECT IDENTIFIER ::= { nlmTables  8 }
-- nlmVirtualCircuit   OBJECT IDENTIFIER ::= { nlmTables  9 }
-- nlmDSeriesCounts    OBJECT IDENTIFIER ::= { nlmTables 10 }

DTEAddress ::= TEXTUAL-CONVENTION
    STATUS      current
    DESCRIPTION 
        "
         DTEAddress ::= SEQUENCE {
            numberingPlanId [0] ENUMERATED {
                unknown(0),
                x121(1),
                e164(2) },
            addressDigits [1] OCTET STRING }"
    REFERENCE   
        "ITU-T Rec. X.283 (1997) | ISO/IEC 10733 : 1998, 
               NLM.DTEAddress"
    SYNTAX      OCTET STRING (SIZE(0..16))

Direction ::= TEXTUAL-CONVENTION
    STATUS      current
    DESCRIPTION 
        ""
    REFERENCE   
        "ITU-T Rec. X.283 (1997) | ISO/IEC 10733 : 1998, 
               NLM.Direction"
    SYNTAX      INTEGER { incoming(0), outgoing(1) }

DiscardReason ::= TEXTUAL-CONVENTION
    STATUS      current
    DESCRIPTION 
        ""
    REFERENCE   
        "ITU-T Rec. X.283 (1997) | ISO/IEC 10733 : 1998, 
               NLM.DiscardReason"
    SYNTAX      Integer32 (0..255)

EndToEndDelay ::= TEXTUAL-CONVENTION
    STATUS      current
    DESCRIPTION 
        ""
    REFERENCE   
        "ITU-T Rec. X.283 (1997) | ISO/IEC 10733 : 1998, 
               NLM.EndToEndDelay"
    SYNTAX      Integer32 (0..65535)

FastSelect ::= TEXTUAL-CONVENTION
    STATUS      current
    DESCRIPTION 
        ""
    REFERENCE   
        "ITU-T Rec. X.283 (1997) | ISO/IEC 10733 : 1998, 
               NLM.FastSelect"
    SYNTAX      INTEGER { notSpecified(0), fastSelect(1), 
                    fastSelectWithRestrictedResponse(2), noFastSelect(3) }

ISO9542Subsets ::= TEXTUAL-CONVENTION
    STATUS      current
    DESCRIPTION 
        ""
    REFERENCE   
        "ITU-T Rec. X.283 (1997) | ISO/IEC 10733 : 1998, 
               NLM.ISO9542Subsets"
    SYNTAX      INTEGER { configuration(0), redirection(1) }

Lifetime ::= TEXTUAL-CONVENTION
    STATUS      current
    DESCRIPTION 
        ""
    REFERENCE   
        "ITU-T Rec. X.283 (1997) | ISO/IEC 10733 : 1998, 
               NLM.Lifetime"
    SYNTAX      Integer32 (0..255)

LocalDistinguishedName ::= TEXTUAL-CONVENTION
    STATUS      current
    DESCRIPTION 
        ""
    REFERENCE   
        "ITU-T Rec. X.283 (1997) | ISO/IEC 10733 : 1998, 
               NLM.LocalDistinguishedName"
    SYNTAX      OCTET STRING (SIZE(0..256))

LocalDistinguishedNames ::= TEXTUAL-CONVENTION
    STATUS      current
    DESCRIPTION 
        ""
    REFERENCE   
        "ITU-T Rec. X.283 (1997) | ISO/IEC 10733 : 1998, 
               NLM.LocalDistinguishedNames"
    SYNTAX      OCTET STRING (SIZE(0..256))

LogicalChannelId ::= TEXTUAL-CONVENTION
    STATUS      current
    DESCRIPTION 
        ""
    REFERENCE   
        "ITU-T Rec. X.283 (1997) | ISO/IEC 10733 : 1998, 
               NLM.LogicalChannelId"
    SYNTAX      Integer32 (1..4095)

LogicalChannelIds ::= TEXTUAL-CONVENTION
    STATUS      current
    DESCRIPTION 
        "
         SET OF LogicalChannelId"
    REFERENCE   
        "ITU-T Rec. X.283 (1997) | ISO/IEC 10733 : 1998, 
               NLM.LogicalChannelAssignments"
    SYNTAX      OCTET STRING (SIZE(0..256))

LogicalChannelRange ::= TEXTUAL-CONVENTION
    STATUS      current
    DESCRIPTION 
        "
         LogicalChannelRange ::= SEQUENCE {
            low [1] LogicalChannelId,
            high [2] LogicalChannelId }"
    REFERENCE   
        "ITU-T Rec. X.283 (1997) | ISO/IEC 10733 : 1998, 
               NLM.LogicalChannelRange"
    SYNTAX      OCTET STRING (SIZE(0 | 4))

NAddress ::= TEXTUAL-CONVENTION
    STATUS      current
    DESCRIPTION 
        ""
    REFERENCE   
        "ITU-T Rec. X.283 (1997) | ISO/IEC 10733 : 1998, 
               NLM.NAddress"
    SYNTAX      OCTET STRING (SIZE(0..20))

NAddresses ::= TEXTUAL-CONVENTION
    STATUS      current
    DESCRIPTION 
        "
         NAddresses ::= SET OF NAddress"
    REFERENCE   
        "ITU-T Rec. X.283 (1997) | ISO/IEC 10733 : 1998, 
               NLM.NAddresses"
    SYNTAX      OCTET STRING (SIZE(0..240))

NUI ::= TEXTUAL-CONVENTION
    STATUS      current
    DESCRIPTION 
        ""
    REFERENCE   
        "ITU-T Rec. X.283 (1997) | ISO/IEC 10733 : 1998, 
               NLM.NUI"
    SYNTAX      OCTET STRING (SIZE(0..256))

ProtocolVersion ::= TEXTUAL-CONVENTION
    STATUS      current
    DESCRIPTION 
        ""
    REFERENCE   
        "ITU-T Rec. X.283 (1997) | ISO/IEC 10733 : 1998, 
               NLM.ProtocolVersion"
    SYNTAX      INTEGER { iSO8208V1(0), iSO8208V2(1), x2584(2), x2488(3) }

RedirectHoldingTime ::= TEXTUAL-CONVENTION
    STATUS      current
    DESCRIPTION 
        ""
    REFERENCE   
        "ITU-T Rec. X.283 (1997) | ISO/IEC 10733 : 1998, 
               NLM.RedirectHoldingTime"
    SYNTAX      Integer32 (1..65535000)

RedirectReason ::= TEXTUAL-CONVENTION
    STATUS      current
    DESCRIPTION 
        ""
    REFERENCE   
        "ITU-T Rec. X.283 (1997) | ISO/IEC 10733 : 1998, 
               NLM.RedirectReason"
    SYNTAX      Integer32 (1..127)

ROASequence ::= TEXTUAL-CONVENTION
    STATUS      current
    DESCRIPTION 
        ""
    REFERENCE   
        "ITU-T Rec. X.283 (1997) | ISO/IEC 10733 : 1998, 
               NLM.ROASequence"
    SYNTAX      OCTET STRING (SIZE(0..256))

SDUSize ::= TEXTUAL-CONVENTION
    STATUS      current
    DESCRIPTION 
        ""
    REFERENCE   
        "ITU-T Rec. X.283 (1997) | ISO/IEC 10733 : 1998, 
               NLM.SDUSize"
    SYNTAX      Integer32 (1..65535)

SNPAAddress ::= TEXTUAL-CONVENTION
    STATUS      current
    DESCRIPTION 
        ""
    REFERENCE   
        "ITU-T Rec. X.283 (1997) | ISO/IEC 10733 : 1998, 
               NLM.SNPAAddress"
    SYNTAX      OCTET STRING (SIZE(0..16))

ManualISSNPAAddress ::= TEXTUAL-CONVENTION
    STATUS      current
    DESCRIPTION 
        ""
    REFERENCE   
        "ITU-T Rec. X.283 (1997) | ISO/IEC 10733 : 1998, 
               NLM.ManualISSNPAAddress"
    SYNTAX      OCTET STRING (SIZE(0..256))

SupportedProtocol ::= TEXTUAL-CONVENTION
    STATUS      current
    DESCRIPTION 
        ""
    REFERENCE   
        "ITU-T Rec. X.283 (1997) | ISO/IEC 10733 : 1998, 
               NLM.SupportedProtocol"
    SYNTAX      INTEGER { protocol8473(0), protocol9542ES(1), 
                    protocol9542IS(2) }

SupportedProtocols ::= TEXTUAL-CONVENTION
    STATUS      current
    DESCRIPTION 
        ""
    REFERENCE   
        "ITU-T Rec. X.283 (1997) | ISO/IEC 10733 : 1998, 
               NLM.SupportedProtocols"
    SYNTAX      BITS { protocol8473(0), protocol9542ES(1), 
                    protocol9542IS(2) }

SystemType ::= TEXTUAL-CONVENTION
    STATUS      current
    DESCRIPTION 
        ""
    REFERENCE   
        "ITU-T Rec. X.283 (1997) | ISO/IEC 10733 : 1998, 
               NLM.SystemType"
    SYNTAX      INTEGER { eS(1), iS(2) }

SystemTypes ::= TEXTUAL-CONVENTION
    STATUS      current
    DESCRIPTION 
        ""
    REFERENCE   
        "ITU-T Rec. X.283 (1997) | ISO/IEC 10733 : 1998, 
               NLM.SystemTypes"
    SYNTAX      BITS { eS(1), iS(2) }

X25PLEMode ::= TEXTUAL-CONVENTION
    STATUS      current
    DESCRIPTION 
        ""
    REFERENCE   
        "ITU-T Rec. X.283 (1997) | ISO/IEC 10733 : 1998, 
               NLM.X25PLEMode"
    SYNTAX      INTEGER { dTE(0), dCE(1), dTEasDCE(2) }

PacketSequencing ::= TEXTUAL-CONVENTION
    STATUS      current
    DESCRIPTION 
        "The modulo of the packet sequence number space.  
         Expressed as an integer.  The ITU-T Recommendation 
         | International Standard only requires support for at 
         least one of the two values 8 and 128, but it is 
         possible that some future revision may extend the 
         range.  A system is only required to support the 
         setting of values which are also required by the 
         protocol standard.  A system shall return an error when 
         an attempt is made to set the value to a value which is 
         not supported by that system."
    REFERENCE   
        "ITU-T Rec. X.283 (1997) | ISO/IEC 10733 : 1998, 
               NLM.PacketSequencing"
    SYNTAX      Unsigned32

nlmNotifications OBJECT IDENTIFIER
    ::= { nlmMIB 0 }

nlmObjects OBJECT IDENTIFIER
    ::= { nlmMIB 1 }

nlmTables OBJECT IDENTIFIER
    ::= { nlmObjects 1 }

-- ==========================================

nlmSubsystem OBJECT IDENTIFIER
    ::= { nlmTables 1 }

nlmSubsystemTable OBJECT-TYPE
    SYNTAX      SEQUENCE OF NlmSubsystemEntry
    MAX-ACCESS  not-accessible
    STATUS      current
    DESCRIPTION 
        ""
    REFERENCE   
        "ITU-T Rec. X.283 (1997) | ISO/IEC 10733 : 1998, 
               networkSubsystem MOC"
    ::= { nlmSubsystem 1 }

nlmSubsystemEntry OBJECT-TYPE
    SYNTAX      NlmSubsystemEntry
    MAX-ACCESS  not-accessible
    STATUS      current
    DESCRIPTION 
        "Managed object for network layer subsystem.  There is 
         exactly one of these MOs within a system.  It exists to 
         provide a container for the network entity MOs, nSAP 
         MOs and the 'SNPA' MOs as described in clause.
         
         The networkSubsystem managed object cannot be created 
         or deleted explicitly by management operation.  It 
         exists inherently in a system; created and deleted as 
         part of system operation."
    REFERENCE   
        "ITU-T Rec. X.283 (1997) | ISO/IEC 10733 : 1998, 
               networkSubsystem MO"
    INDEX       { nlmSubsystemId }
    ::= { nlmSubsystemTable 1 }

NlmSubsystemEntry ::= SEQUENCE {
    nlmSubsystemId  SnmpAdminString
}

nlmSubsystemId OBJECT-TYPE
    SYNTAX      SnmpAdminString
    MAX-ACCESS  not-accessible
    STATUS      current
    DESCRIPTION 
        ""
    REFERENCE   
        "ITU-T Rec. X.723 (1993) : ISO/IEC 10165-5 : 1993, 
               subsystemId"
    DEFVAL      { "NetworkSubsystem" }
    ::= { nlmSubsystemEntry 1 }

-- ==========================================

nlmEntity OBJECT IDENTIFIER
    ::= { nlmTables 2 }

nlmEntityTable OBJECT-TYPE
    SYNTAX      SEQUENCE OF NlmEntityEntry
    MAX-ACCESS  not-accessible
    STATUS      current
    DESCRIPTION 
        ""
    REFERENCE   
        "ITU-T Rec. X.283 (1997) | ISO/IEC 10733 : 1998, 
               networkEntity MOC"
    ::= { nlmEntity 1 }

nlmEntityEntry OBJECT-TYPE
    SYNTAX      NlmEntityEntry
    MAX-ACCESS  not-accessible
    STATUS      current
    DESCRIPTION 
        "The network entity managed object.  There may be 
         multiple instances of these MOs within a system.  Its 
         definition permits it to be deleted and created by 
         management operation, or to created and deleted 
         automatically as part of system operation."
    REFERENCE   
        "ITU-T Rec. X.283 (1997) | ISO/IEC 10733 : 1998, 
               networkEntity MO"
    INDEX       { nlmEntityId }
    ::= { nlmEntityTable 1 }

NlmEntityEntry ::= SEQUENCE {
    nlmEntityId                     SimpleNameType,
    nlmEntityLocalSapNames          SnmpAdminString,
    nlmEntityOperationalState       OperationalState,
    nlmEntityNetworkEntityTitles    NAddresses,
    nlmEntitySystemTypes            SystemTypes,
    nlmEntityRowStatus              RowStatus
}

nlmEntityId OBJECT-TYPE
    SYNTAX      SimpleNameType
    MAX-ACCESS  not-accessible
    STATUS      current
    DESCRIPTION 
        "Provides a simple name type for the network entity that 
         acts as an index into the network entity table."
    REFERENCE   
        "ITU-T Rec. X.723 (1993_ | ISO/IEC 10165-5 : 1993, 
               communicationsEntityId"
    ::= { nlmEntityEntry 1 }

nlmEntityLocalSapNames OBJECT-TYPE
    SYNTAX      SnmpAdminString
    MAX-ACCESS  read-only
    STATUS      current
    DESCRIPTION 
        "The local SAP names are represented as a list of 
         strings, separated by commas.  Under OpenSS7 OSI stack, 
         the local SAP names identify the filesystem path to the 
         STREAMS characer device that provides the network user 
         interface to the local SAP.  For example: /dev/clnp."
    REFERENCE   
        "ITU-T Rec. X.723 (1993) | ISO/IEC 10165-5 : 1993, 
               localSapNames"
    ::= { nlmEntityEntry 2 }

nlmEntityOperationalState OBJECT-TYPE
    SYNTAX      OperationalState
    MAX-ACCESS  read-only
    STATUS      current
    DESCRIPTION 
        "Provides the operational state of the network entity in 
         accordance with the OperationalState textual 
         convention of the OPENSS7-SMI-MIB and ITU-T Rec. X.721 
         (1992) | ISO/IEC 10165-2 : 1992."
    REFERENCE   
        "ITU-T Rec. X.721 (1992) | ISO/IEC 10165-2 : 1992, 
               operationalState"
    ::= { nlmEntityEntry 3 }

nlmEntityNetworkEntityTitles OBJECT-TYPE
    SYNTAX      NAddresses
    MAX-ACCESS  read-create
    STATUS      current
    DESCRIPTION 
        "Provides a list of network entity titles corresponding 
         to the network entity.  Network entity titles are 
         represented as NSAP addresses expressed in zero to 40 
         (event length) hexadecimal characters.  Multiple 
         addresses are separated by commas."
    REFERENCE   
        "ITU-T Rec. X.283 (1997) | ISO/IEC 10733 : 1998, 
               networkEntityTitles ATTRIBUTE"
    ::= { nlmEntityEntry 4 }

nlmEntitySystemTypes OBJECT-TYPE
    SYNTAX      SystemTypes
    MAX-ACCESS  read-only
    STATUS      current
    DESCRIPTION 
        "The set of system roles supported by this network 
         entity.  This may be end system, intermeidate system, 
         or both.  The actual role in which a particular 
         instance of the protocol machine is operating is 
         determined by the operationalSystemType attribute of 
         the cLNS or cONS MO."
    REFERENCE   
        "ITU-T Rec. X.283 (1997) | ISO/IEC 10733 : 1998, 
               systemTypes ATTRIBUTE"
    ::= { nlmEntityEntry 5 }

nlmEntityRowStatus OBJECT-TYPE
    SYNTAX      RowStatus
    MAX-ACCESS  read-create
    STATUS      current
    DESCRIPTION 
        "Provides a mechanism whereby management stations may 
         create or delete network entities.  Rows in this table 
         must persist across management system restart/reboot."
    REFERENCE   
        "ITU-T Rec. X.283 (1997) | ISO/IEC 10733 : 1998, 
               networkEntity--networkSubsystem-Management 
               NAME BINDING"
    ::= { nlmEntityEntry 6 }

-- ==========================================

nlmLinkage OBJECT IDENTIFIER
    ::= { nlmTables 3 }

nlmLinkageTable OBJECT-TYPE
    SYNTAX      SEQUENCE OF NlmLinkageEntry
    MAX-ACCESS  not-accessible
    STATUS      current
    DESCRIPTION 
        ""
    REFERENCE   
        "ITU-T Rec. X.283 (1997) | ISO/IEC 10733 : 1998, 
               linkage MOC"
    ::= { nlmLinkage 1 }

nlmLinkageEntry OBJECT-TYPE
    SYNTAX      NlmLinkageEntry
    MAX-ACCESS  not-accessible
    STATUS      current
    DESCRIPTION 
        "There is one of these MOs associated with each separate 
         provision of the underlying service to the superior 
         protocol machine.  Its definition permits it to be 
         created and deleted explicitly by management operation, 
         but in some systems it will exist inherently and 
         neither creation nor deletion by management operation 
         will be possible.  Name bindings are defined for both 
         cases.
         
         When the linkage is operable, the operationalState 
         shall have the value enabled(); otherwise, it shall 
         have the value disabled().  Transitions of 
         operationalState shall be reported using the 
         stateChange notification.  A linkage MO may be created 
         in the enabled() operational state."
    REFERENCE   
        "ITU-T Rec. X.283 (1997) | ISO/IEC 10733 : 1998, 
               linkage MO"
    INDEX       { nlmLinkageId }
    ::= { nlmLinkageTable 1 }

NlmLinkageEntry ::= SEQUENCE {
    nlmLinkageId                                        SimpleNameType,
    nlmLinkageOperationalState                          OperationalState,
    nlmLinkageAdministrativeState                       AdministrativeState,
    nlmLinkageSnServiceProvider                         LocalDistinguishedName,
    nlmLinkageSnSAP                                     LocalDistinguishedName,
    nlmLinkageOperationalProtocols                      SupportedProtocols,
-- linkage-ISO9542IS-P PACKAGE
    nlmLinkageISO9542OperationalSubsets                 ISO9542Subsets,
    nlmLinkageHoldingTimerMultiplier                    Integer32,
    nlmLinkageISConfigurationTimer                      MilliSeconds,
    nlmLinkageSuggestedESConfigurationTimer             MilliSeconds,
    nlmLinkageRedirectHoldingTime                       RedirectHoldingTime,
    nlmLinkageESReachabilityChanges                     Counter64,
    nlmLinkageInvalid9542PDUs                           Counter64,
-- linkage-ISO9542ES-P PACKAGE
--  nlmLinkageISO9542OperationalSubsets                 ISO9542Subsets,
--  nlmLinkageHoldingTimerMultiplier                    Integer32,
    nlmLinkageManualISSNPAAddress                       ManualISSNPAAddress,
    nlmLinkageDefaultESConfigTimer                      MilliSeconds,
    nlmLinkageActiveESConfigTimer                       MilliSeconds,
    nlmLinkageISReachabilityChanges                     Counter64,
--  nlmLinkageInvalid9542PDUs                           Counter64,
-- linkage-ISO9542Checksum-P PACKAGE
    nlmLinkageEnableChecksum                            TruthValue,
-- linkageInitialMinimumTimer-P PACKAGE
    nlmLinkageInitialMinimumTimer                       MilliSeconds,
-- linkageReserveTimer-P PACKAGE
    nlmLinkageReserveTimer                              MilliSeconds,
-- linkageIdleTimer-P PACKAGE
    nlmLinkageIdleTimer                                 MilliSeconds,
-- linkage-ISO8473-ISO8208SNDCF-P PACKAGE
    nlmLinkageCallsPlaced                               Counter64,
    nlmLinkageCallsFailed                               Counter64,
-- linkageCODLService-P PACKAGE
--  nlmLinkageCallsPlaced                               Counter64,
--  nlmLinkageCallsFailed                               Counter64,
-- "ISO/IEC 10589":linkageISISBasic-P PACKAGE
    nlmLinkageType                                      CircuitType,
    nlmLinkageISISHelloTimer                            MilliSeconds,
    nlmLinkageL1DefaultMetric                           HopMetric,
    nlmLinkageL1DelayMetric                             HopMetric,
    nlmLinkageL1ExpenseMetric                           HopMetric,
    nlmLinkageL1ErrorMetric                             HopMetric,
    nlmLinkageExternalDomain                            TruthValue,
    nlmLinkageChangesInAdjacencyState                   Counter64,
    nlmLinkageInitialisationFailures                    Counter64,
    nlmLinkageRejectedAdjacencies                       Counter64,
    nlmLinkageISISControlPDUsSent                       Counter64,
    nlmLinkageISISControlPDUsReceived                   Counter64,
    nlmLinkageIDFieldLengthMismatches                   Counter64,
    nlmLinkageMaximumAreaAdressesMismatches             Counter64,
-- "ISO/IEC 10589":linkageISISAuthentication-P
    nlmLinkageCircuitTransmitPassword                   Password,
    nlmLinkageCircuitReceivePasswords                   Passwords,
    nlmLinkageAuthenticationFailures                    Counter64,
-- "ISO/IEC 10589":linkageISISBroadcast-P
    nlmLinkageL1IntermediateSystemPriority              IntermediateSystemPriority,
    nlmLinkageL1CircuitID                               CircuitID,
    nlmLinkageL1DesignatedIntermediateSystem            SystemId,
    nlmLinkageLanL1DesignatedIntermediateSystemChanges  Counter64,
-- "ISO/IEC 10589":linkageISISDACallEstablishmentMetricIncrement-P
    nlmLinkageCallEstablishmentDefaultMetricIncrement   HopMetric,
    nlmLinkageCallEstablishmentDelayMetricIncrement     HopMetric,
    nlmLinkageCallEstablishmentExpenseMetricIncrement   HopMetric,
    nlmLinkageCallEstablishmentErrorMetricIncrement     HopMetric,
-- "ISO/IEC 10589":linkageISISPtToPt-P
    nlmLinkagePtPtCircuitID                             CircuitID,
-- "ISO/IEC 10589":linkageISISStatic-P
    nlmLinkageOutgoingCallIVMO                          SimpleNameType,
--  nlmLinkagePtPtCircuitID                             CircuitID,
    nlmLinkageNeighbourSNPAAdress                       SNPAAddress,
-- "ISO/IEC 10589":linkageISISLevel2-P
    nlmLinkageL2DefaultMetric                           HopMetric,
    nlmLinkageL2DelayMetric                             HopMetric,
    nlmLinkageL2ExpenseMetric                           HopMetric,
    nlmLinkageL2ErrorMetric                             HopMetric,
    nlmLinkageManualL2OnlyMode                          TruthValue,
-- "ISO/IEC 10589":linkageISISLevel2Broadcast-P
    nlmLinkageL2IntermediateSystemPriority              IntermediateSystemPriority,
    nlmLinkageL2CircuitID                               CircuitID,
    nlmLinkageL2DesignatedIntermediateSystem            SystemId,
    nlmLinkageLanL2DesignatedIntermediateSystemChanges  Counter64,
--
    nlmLinkageRowStatus                                 RowStatus
}

nlmLinkageId OBJECT-TYPE
    SYNTAX      SimpleNameType
    MAX-ACCESS  not-accessible
    STATUS      current
    DESCRIPTION 
        "Provides a simple name for the linkage and index into 
         the linkage table."
    REFERENCE   
        "ITU-T Rec. X.283 (1997) | ISO/IEC 10733 : 1998, 
               linkageId ATTRIBUTE"
    ::= { nlmLinkageEntry 1 }

nlmLinkageOperationalState OBJECT-TYPE
    SYNTAX      OperationalState
    MAX-ACCESS  read-only
    STATUS      current
    DESCRIPTION 
        "Provides the operational state of the linkage in 
         accordance with the OperationalState textual convention 
         of the OPENSS7-SMI-MIB."
    REFERENCE   
        "ITU-T Rec. X.721 (1992) | ISO/IEC 10165-2 : 1992, 
               operationalState"
    ::= { nlmLinkageEntry 2 }

nlmLinkageAdministrativeState OBJECT-TYPE
    SYNTAX      AdministrativeState
    MAX-ACCESS  read-create
    STATUS      current
    DESCRIPTION 
        "Provides the administrative state of the linkage in 
         accordance with the AdministrativeState textual 
         convention of the OPENSS7-SMI-MIB."
    REFERENCE   
        "ITU-T Rec. X.721 (1992) | ISO/IEC 10165-2 : 1992, 
               administrativeState"
    ::= { nlmLinkageEntry 3 }

nlmLinkageSnServiceProvider OBJECT-TYPE
    SYNTAX      LocalDistinguishedName
    MAX-ACCESS  read-create
    STATUS      current
    DESCRIPTION 
        "Distinguished name of the subnetwork service provider.  
         This attribute identifies the subnetwork entity to be 
         used to support the linkage, when enabled.  The 
         subnetwork service provider may be in the Datalink 
         Layer, or it may be in the Network Layer (for example 
         when operating ISO 8473 over the ISO 8208 SNDCF), or, 
         Transport Layer (for example when operating ISO 8473 
         over RFC 1070 (ISO-UDP)).
         
         The value of this object must be explicitly set by the 
         management station before the linkage can be placed in 
         the active(1) state; otherwise, the attempt to create 
         the row or change the row status will fail.
         
         Once an initial value has been provided for this 
         object, it cannot be changed without taking the linkage 
         out of service using its row status, notInService(2)."
    REFERENCE   
        "ITU-T Rec. X.283 (1997) | ISO/IEC 10733 : 1998, 
               sN-ServiceProvider ATTRIBUTE"
    ::= { nlmLinkageEntry 4 }

nlmLinkageSnSAP OBJECT-TYPE
    SYNTAX      LocalDistinguishedName
    MAX-ACCESS  read-only
    STATUS      current
    DESCRIPTION 
        "Distinguished name of the service provider SAP MO (if 
         present). This is obtained via an internal interface 
         when the linkage is enabled. The sN-SAP may be 
         a relationship to an SAP MO in the Datalink Layer, or 
         it may be a relationship to another Managed Object 
         within the Network Layer which is not an SAP MO. For 
         example, when operating ITU-T Rec. X.233 | ISO/IEC 
         8473-1 over the ISO/IEC 8208 or ITU-T Rec. X.25 SNDCF, 
         it is a relationship to the same x25PLE-DTE MO which is 
         pointed to by the sN-ServiceProvider Attribute."
    REFERENCE   
        "ITU-T Rec. X.283 (1997) | ISO/IEC 10733 : 1998, 
               sN-SAP ATTRIBUTE"
    ::= { nlmLinkageEntry 5 }

nlmLinkageOperationalProtocols OBJECT-TYPE
    SYNTAX      SupportedProtocols
    MAX-ACCESS  read-create
    STATUS      current
    DESCRIPTION 
        "
         The value of this object must be explicitly set by the 
         management station before the linkage can be placed in 
         the active(1) state; otherwise, the attempt to create 
         the row or change the row status will fail.
         
         Once an initial value has been provided for this 
         object, it cannot be changed without taking the linkage 
         out of service using its row status, notInService(2)."
    REFERENCE   
        "ITU-T Rec. X.283 (1997) | ISO/IEC 10733 : 1998, 
               operationalProtocols ATTRIBUTE"
    ::= { nlmLinkageEntry 6 }

-- linkage-ISO9542IS-P PACKAGE
nlmLinkageISO9542OperationalSubsets OBJECT-TYPE
    SYNTAX      ISO9542Subsets
    MAX-ACCESS  read-create
    STATUS      current
    DESCRIPTION 
        "The set of ISO 9542 subsets operational on this 
         linkage."
    REFERENCE   
        "ITU-T Rec. X.283 (1997) | ISO/IEC 10733 : 1998, 
               iSO9542OperationalSubsets ATTRIBUTE"
    ::= { nlmLinkageEntry 7 }

nlmLinkageHoldingTimerMultiplier OBJECT-TYPE
    SYNTAX      Integer32 (2..63)
    MAX-ACCESS  read-create
    STATUS      current
    DESCRIPTION 
        "The factor to derive holding timer from configuration 
         timer.  This value, when multiplied by a configuration 
         timer yields the value of the holding timer parameter 
         issued with configuration information.  The semantics 
         of this parameter are such that it is permissible to 
         also add a delta value to the result to compensate for 
         possible delays and imprecision of timers.  The result 
         of the calculation is truncated, upon overflow, to the 
         maximum value for the parameter permitted by the 
         protocol (65535)."
    REFERENCE   
        "ITU-T Rec. X.283 (1997) | ISO/IEC 10733 : 1998, 
               holdingTimerMultiplier ATTRIBUTE"
    DEFVAL      { 3 }
    ::= { nlmLinkageEntry 8 }

nlmLinkageISConfigurationTimer OBJECT-TYPE
    SYNTAX      MilliSeconds
    UNITS       "ms"
    MAX-ACCESS  read-create
    STATUS      current
    DESCRIPTION 
        "Value for the ISO 9542 IS configuration timer.  It is 
         used to determine how often an IS reports configuration 
         information to ESs."
    REFERENCE   
        "ITU-T Rec. X.283 (1997) | ISO/IEC 10733 : 1998, 
               iSConfigurationTimer ATTRIBUTE"
    DEFVAL      { 10000 }
    ::= { nlmLinkageEntry 9 }

nlmLinkageSuggestedESConfigurationTimer OBJECT-TYPE
    SYNTAX      MilliSeconds
    UNITS       "ms"
    MAX-ACCESS  read-create
    STATUS      current
    DESCRIPTION 
        "Value to be used for the ISO 9542 suggested ES 
         configuration timer value, advertised in IS hellos 
         generated by this network entity.
         
         It is far from clear that this attribute would be able 
         to be set to a specific value in all implementations.  
         For example, the DIS 10589 ES poll protocol relies on 
         the IS being able to set this to different values in 
         different circumstances.  It may be useful to be able 
         to get the current value."
    REFERENCE   
        "ITU-T Rec. X.283 (1997) | ISO/IEC 10733 : 1998, 
               suggestedESConfigurationTimer ATTRIBUTE"
    DEFVAL      { 600000 }
    ::= { nlmLinkageEntry 10 }

nlmLinkageRedirectHoldingTime OBJECT-TYPE
    SYNTAX      RedirectHoldingTime
    MAX-ACCESS  read-create
    STATUS      current
    DESCRIPTION 
        "The holding time (in seconds) to be specified in 
         Redirect PDUs generated by this system."
    REFERENCE   
        "ITU-T Rec. X.283 (1997) | ISO/IEC 10733 : 1998, 
               redirectHoldingTime ATTRIBUTE"
    DEFVAL      { 600000 }
    ::= { nlmLinkageEntry 11 }

nlmLinkageESReachabilityChanges OBJECT-TYPE
    SYNTAX      Counter64
    MAX-ACCESS  read-only
    STATUS      current
    DESCRIPTION 
        "Count of the number of changes in reachability of End 
         Systems from this system."
    REFERENCE   
        "ITU-T Rec. X.283 (1997) | ISO/IEC 10733 : 1998, 
               eSReachabilityChanges ATTRIBUTE"
    ::= { nlmLinkageEntry 12 }

nlmLinkageInvalid9542PDUs OBJECT-TYPE
    SYNTAX      Counter64
    MAX-ACCESS  read-only
    STATUS      current
    DESCRIPTION 
        "Counter of invalid 9542 PDUs received.  This is the 
         number of ISO 9542 PDUs received that are discareded as 
         a result of the PDU header error detection or protocol 
         error processing functions specified in ISO 9542.  This 
         counter is therefore a count of the number of 
         communicationsAlarm notifications with 
         a specificProbelm value of NLM.iSO9542PDUDiscard 
         generated."
    REFERENCE   
        "ITU-T Rec. X.283 (1997) | ISO/IEC 10733 : 1998, 
               invalid9542PDUs ATTRIBUTE"
    ::= { nlmLinkageEntry 13 }

-- linkage-ISO9542ES-P PACKAGE
--  nlmLinkageISO9542OperationalSubsets     ISO9542Subsets
--  nlmLinkageHoldingTimerMultiplier        Integer32
nlmLinkageManualISSNPAAddress OBJECT-TYPE
    SYNTAX      ManualISSNPAAddress
    MAX-ACCESS  read-create
    STATUS      current
    DESCRIPTION 
        "The set of SNPA Addresses to which calls associated 
         with the SNDCF are to be established in the absence of 
         any other information.  The maximum set cardinality 
         shall be implementation specific.  An attempt to set 
         the value of an element of this set to a type of 
         SNPAAddress that is not supported by this linkage shall 
         result in a failure of the SET operation."
    REFERENCE   
        "ITU-T Rec. X.283 (1997) | ISO/IEC 10733 : 1998, 
               manualISSNPAAddress ATTRIBUTE"
    ::= { nlmLinkageEntry 14 }

nlmLinkageDefaultESConfigTimer OBJECT-TYPE
    SYNTAX      MilliSeconds
    UNITS       "ms"
    MAX-ACCESS  read-create
    STATUS      current
    DESCRIPTION 
        "Default value for the ISO 9542 ES configuration timer.  
         This value is used when the ES has not yet received, or 
         has not chosen to accept, a suggested configuration 
         timer value from an Intermediate System."
    REFERENCE   
        "ITU-T Rec. X.283 (1997) | ISO/IEC 10733 : 1998, 
               defaultESConfigTimer ATTRIBUTE"
    ::= { nlmLinkageEntry 15 }

nlmLinkageActiveESConfigTimer OBJECT-TYPE
    SYNTAX      MilliSeconds
    UNITS       "ms"
    MAX-ACCESS  read-only
    STATUS      current
    DESCRIPTION 
        "Currently active value for the ISO 9542 ES 
         configuraiton timer."
    REFERENCE   
        "ITU-T Rec. X.283 (1997) | ISO/IEC 10733 : 1998, 
               activeESConfigTimer ATTRIBUTE"
    ::= { nlmLinkageEntry 16 }

nlmLinkageISReachabilityChanges OBJECT-TYPE
    SYNTAX      Counter64
    MAX-ACCESS  read-only
    STATUS      current
    DESCRIPTION 
        "Counter of the number of changes in reachability of 
         Intermediate Systems from this system."
    REFERENCE   
        "ITU-T Rec. X.283 (1997) | ISO/IEC 10733 : 1998, 
               iSReachabilityChanges ATTRIBUTE"
    ::= { nlmLinkageEntry 17 }

--  nlmLinkageInvalid9542PDUs               Counter64
-- linkage-ISO9542Checksum-P PACKAGE
nlmLinkageEnableChecksum OBJECT-TYPE
    SYNTAX      TruthValue
    MAX-ACCESS  read-create
    STATUS      current
    DESCRIPTION 
        "When true(1), the generation of checksums is enabled."
    REFERENCE   
        "ITU-T Rec. X.283 (1997) | ISO/IEC 10733 : 1998, 
               enableChecksum ATTRIBUTE"
    DEFVAL      { false }
    ::= { nlmLinkageEntry 18 }

-- linkageInitialMinimumTimer-P PACKAGE
nlmLinkageInitialMinimumTimer OBJECT-TYPE
    SYNTAX      MilliSeconds
    UNITS       "ms"
    MAX-ACCESS  read-create
    STATUS      current
    DESCRIPTION 
        "Minimum time in milliseconds to retain call after 
         establishment.  This timer determines the interval (in 
         milliseconds) that a call shall remain connected after 
         being established, irrespective of traffic.  This 
         should be set small enough so that the call is cleared 
         before the start of the next charging interval."
    REFERENCE   
        "ITU-T Rec. X.283 (1997) | ISO/IEC 10733 : 1998, 
               initialMinimumTimer ATTRIBUTE"
    DEFVAL      { 0 }
    ::= { nlmLinkageEntry 19 }

-- linkageReserveTimer-P PACKAGE
nlmLinkageReserveTimer OBJECT-TYPE
    SYNTAX      MilliSeconds
    UNITS       "ms"
    MAX-ACCESS  read-create
    STATUS      current
    DESCRIPTION 
        "The time in seconds to reserve resources for call 
         re-establishment.  This timer determines the interval 
         (in seconds) for which an attempt shall be made to 
         retain those resources, as determined by the 
         implementation, whose retention will increase the 
         probablity of successful re-establishment of an idled 
         virtual call."
    REFERENCE   
        "ITU-T Rec. X.283 (1997) | ISO/IEC 10733 : 1998, 
               reserveTimer ATTRIBUTE"
    DEFVAL      { 0 }
    ::= { nlmLinkageEntry 20 }

-- linkageIdleTimer-P PACKAGE
nlmLinkageIdleTimer OBJECT-TYPE
    SYNTAX      MilliSeconds
    UNITS       "ms"
    MAX-ACCESS  read-create
    STATUS      current
    DESCRIPTION 
        "The time in seconds before release of an idle call.  
         This timer determines the interval (in milliseconds) 
         ofr which a call is permitted to remain idle (i.e. no 
         data traffic in either direction) before being released 
         by the subnetwork dependent convergence function."
    REFERENCE   
        "ITU-T Rec. X.283 (1997) | ISO/IEC 10733 : 1998, 
               idleTimer ATTRIBUTE"
    DEFVAL      { 960000 }
    ::= { nlmLinkageEntry 21 }

-- linkage-ISO8473-ISO8208SNDCF-P PACKAGE
nlmLinkageCallsPlaced OBJECT-TYPE
    SYNTAX      Counter64
    UNITS       "calls"
    MAX-ACCESS  read-only
    STATUS      current
    DESCRIPTION 
        "The number of ISO 8208/X.25/CODL virtual calls 
         successfully established by the subnetwork dependent 
         convergence function (SNDCF)."
    REFERENCE   
        "ITU-T Rec. X.283 (1997) | ISO/IEC 10733 : 1998, 
               callsPlaced ATTRIBUTE"
    ::= { nlmLinkageEntry 22 }

nlmLinkageCallsFailed OBJECT-TYPE
    SYNTAX      Counter64
    UNITS       "calls"
    MAX-ACCESS  read-only
    STATUS      current
    DESCRIPTION 
        "The number of 8208/X.25/CODL virtual call failures 
         while attempting establishment by the subnetwork 
         dependent convergence function (SNDCF)."
    REFERENCE   
        "ITU-T Rec. X.283 (1997) | ISO/IEC 10733 : 1998, 
               callsFailed ATTRIBUTE"
    ::= { nlmLinkageEntry 23 }

-- linkageCODLService-P PACKAGE
--  nlmLinkageCallsPlaced                   Counter64
--  nlmLinkageCallsFailed                   Counter64
-- "ISO/IEC 10589":linkageISISBasic-P PACKAGE
nlmLinkageType OBJECT-TYPE
    SYNTAX      CircuitType
    MAX-ACCESS  read-create
    STATUS      current
    DESCRIPTION 
        "The type of the circuit. This attribute may only be set 
         when the linkage MO is created. Subsequently it is 
         read-only."
    REFERENCE   
        "ISO/IEC 10589: 2001, type ATTRIBUTE"
    ::= { nlmLinkageEntry 24 }

nlmLinkageISISHelloTimer OBJECT-TYPE
    SYNTAX      MilliSeconds
    MAX-ACCESS  read-create
    STATUS      current
    DESCRIPTION 
        "The period between IIH PDUs. It is also used as the 
         period between ISH PDUs when polling the ES 
         configuration.
         
         This attribute specifies the interval between certain 
         events in the operation of the protocol state machine. 
         If the value of this attribute is changed to a new 
         value while the protocol state machine is in operation, 
         the implementation shall take the necessary steps to 
         ensure that for any time interval which was in progress 
         when the corresponding attribute was changed, the next 
         expiration of that interval takes place no later than 
         the expiration of the interval in progress or the 
         specified interval, whichever is sooner. The precision 
         with which this time shall be implemented shall be the 
         same as that associated with the basic operation of the 
         timer attribute."
    REFERENCE   
        "ISO/IEC 10589: 2001, iSISHelloTimer ATTRIBUTE"
    DEFVAL      { 3000 } -- 3 seconds
    ::= { nlmLinkageEntry 25 }

nlmLinkageL1DefaultMetric OBJECT-TYPE
    SYNTAX      HopMetric
    MAX-ACCESS  read-create
    STATUS      current
    DESCRIPTION 
        "The default metric value of this circuit for Level 1 traffic."
    REFERENCE   
        "ISO/IEC 10589: 2001, l1DefaultMetric ATTRIBUTE"
    DEFVAL      { 20 }
    ::= { nlmLinkageEntry 26 }

nlmLinkageL1DelayMetric OBJECT-TYPE
    SYNTAX      HopMetric
    MAX-ACCESS  read-create
    STATUS      current
    DESCRIPTION 
        "The delay metric value of this circuit for Level 
         1 traffic. The value of zero is reserved to indicate 
         that this metric is not supported."
    REFERENCE   
        "ISO/IEC 10589: 2001, l1DelayMetric ATTRIBUTE"
    DEFVAL      { 0 }
    ::= { nlmLinkageEntry 27 }

nlmLinkageL1ExpenseMetric OBJECT-TYPE
    SYNTAX      HopMetric
    MAX-ACCESS  read-create
    STATUS      current
    DESCRIPTION 
        "The expense metric value of this circuit for Level 
         1 traffic. The value of zero is reserved to indicate 
         that this metric is not supported."
    REFERENCE   
        "ISO/IEC 10589: 2001, l1ExpenseMetric ATTRIBUTE"
    DEFVAL      { 0 }
    ::= { nlmLinkageEntry 28 }

nlmLinkageL1ErrorMetric OBJECT-TYPE
    SYNTAX      HopMetric
    MAX-ACCESS  read-create
    STATUS      current
    DESCRIPTION 
        "The error metric value of this circuit for Level 
         1 traffic. The value of zero is reserved to indicate 
         that this metric is not supported."
    REFERENCE   
        "ISO/IEC 10589: 2001, l1ErrorMetric ATTRIBUTE"
    DEFVAL      { 0 }
    ::= { nlmLinkageEntry 29 }

nlmLinkageExternalDomain OBJECT-TYPE
    SYNTAX      TruthValue
    MAX-ACCESS  read-create
    STATUS      current
    DESCRIPTION 
        "If TRUE, suppress normal transmission of and 
         interpretation of Intra-domain ISIS PDUs on this 
         circuit."
    REFERENCE   
        "ISO/IEC 10589: 2001, externalDomain ATTRIBUTE"
    DEFVAL      { true }
    ::= { nlmLinkageEntry 30 }

nlmLinkageChangesInAdjacencyState OBJECT-TYPE
    SYNTAX      Counter64
    MAX-ACCESS  read-only
    STATUS      current
    DESCRIPTION 
        "Number of Adjacency State Change events generated."
    REFERENCE   
        "ISO/IEC 10589: 2001, changesInAdjacencyState ATTRIBUTE"
    ::= { nlmLinkageEntry 31 }

nlmLinkageInitialisationFailures OBJECT-TYPE
    SYNTAX      Counter64
    MAX-ACCESS  read-only
    STATUS      current
    DESCRIPTION 
        "Number of Initialisation Failure events generated."
    REFERENCE   
        "ISO/IEC 10589: 2001, initialisationFailures ATTRIBUTE"
    ::= { nlmLinkageEntry 32 }

nlmLinkageRejectedAdjacencies OBJECT-TYPE
    SYNTAX      Counter64
    MAX-ACCESS  read-only
    STATUS      current
    DESCRIPTION 
        "Number of Rejected Adjacency events generated."
    REFERENCE   
        "ISO/IEC 10589: 2001, rejectedAdjacencies ATTRIBUTE"
    ::= { nlmLinkageEntry 33 }

nlmLinkageISISControlPDUsSent OBJECT-TYPE
    SYNTAX      Counter64
    MAX-ACCESS  read-only
    STATUS      current
    DESCRIPTION 
        "Number of control PDUs sent on this circuit."
    REFERENCE   
        "ISO/IEC 10589: 2001, iSISControlPDUsSent ATTRIBUTE"
    ::= { nlmLinkageEntry 34 }

nlmLinkageISISControlPDUsReceived OBJECT-TYPE
    SYNTAX      Counter64
    MAX-ACCESS  read-only
    STATUS      current
    DESCRIPTION 
        "Number of control PDUs received on this circuit."
    REFERENCE   
        "ISO/IEC 10589: 2001, iSISControlPDUsReceived ATTRIBUTE"
    ::= { nlmLinkageEntry 35 }

nlmLinkageIDFieldLengthMismatches OBJECT-TYPE
    SYNTAX      Counter64
    MAX-ACCESS  read-only
    STATUS      current
    DESCRIPTION 
        "Number of times the iDFieldLengthMismatch event has 
         been generated."
    REFERENCE   
        "ISO/IEC 10589: 2001, iDFieldLengthMismatches ATTRIBUTE"
    ::= { nlmLinkageEntry 36 }

nlmLinkageMaximumAreaAdressesMismatches OBJECT-TYPE
    SYNTAX      Counter64
    MAX-ACCESS  read-only
    STATUS      current
    DESCRIPTION 
        "Count of maximumAreaAddressesMismatch events."
    REFERENCE   
        "ISO/IEC 10589: 2001, maximumAreaAddressesMismatches ATTRIBUTE"
    ::= { nlmLinkageEntry 37 }

-- "ISO/IEC 10589":linkageISISAuthentication-P
nlmLinkageCircuitTransmitPassword OBJECT-TYPE
    SYNTAX      Password
    MAX-ACCESS  read-create
    STATUS      current
    DESCRIPTION 
        "The value to be used as a transmit password in IIH PDUs 
         transmitted by this Intermediate System."
    REFERENCE   
        "ISO/IEC 10589: 2001, circuitTransmitPassword ATTRIBUTE"
    DEFVAL      { "" }
    ::= { nlmLinkageEntry 38 }

nlmLinkageCircuitReceivePasswords OBJECT-TYPE
    SYNTAX      Passwords
    MAX-ACCESS  read-create
    STATUS      current
    DESCRIPTION 
        "The values to be used as receive passwords to check the 
         receipt of IIH PDUs."
    REFERENCE   
        "ISO/IEC 10589: 2001, circuitReceivePasswords ATTRIBUTE"
    DEFVAL      { "" }
    ::= { nlmLinkageEntry 39 }

nlmLinkageAuthenticationFailures OBJECT-TYPE
    SYNTAX      Counter64
    MAX-ACCESS  read-only
    STATUS      current
    DESCRIPTION 
        "Count of authentication Failure events."
    REFERENCE   
        "ISO/IEC 10589: 2001, authenticationFailures ATTRIBUTE"
    ::= { nlmLinkageEntry 40 }

-- "ISO/IEC 10589":linkageISISBroadcast-P
nlmLinkageL1IntermediateSystemPriority OBJECT-TYPE
    SYNTAX      IntermediateSystemPriority
    MAX-ACCESS  read-create
    STATUS      current
    DESCRIPTION 
        "Priority for becoming LAN Level 1 Designated Intermediate System."
    REFERENCE   
        "ISO/IEC 10589: 2001, l1IntermediateSystemPriority ATTRIBUTE"
    DEFVAL      { 64 }
    ::= { nlmLinkageEntry 41 }

nlmLinkageL1CircuitID OBJECT-TYPE
    SYNTAX      CircuitID
    MAX-ACCESS  read-create
    STATUS      current
    DESCRIPTION 
        "The LAN ID allocated by the LAN Level 1 Designated 
         Intermediate System. Where this system is not aware of 
         the value (because it is not participating in the Level 
         1 Designated Intermediate System election), this 
         attribute has the value which would be proposed for 
         this circuit. (i.e. the concatenation of the local 
         system ID and the one octet local Circuit ID for this 
         circuit."
    REFERENCE   
        "ISO/IEC 10589: 2001, l1CircuitID ATTRIBUTE"
    ::= { nlmLinkageEntry 42 }

nlmLinkageL1DesignatedIntermediateSystem OBJECT-TYPE
    SYNTAX      SystemId
    MAX-ACCESS  read-create
    STATUS      current
    DESCRIPTION 
        "The ID of the LAN Level 1 Designated Intermediate 
         System on this circuit.  If, for any reason this system 
         is not partaking in the relevant Designated 
         Intermediate System election process, then the value 
         returned is the zero length OCTET STRING."
    REFERENCE   
        "ISO/IEC 10589: 2001, l1DesignatedIntermediateSsytem ATTRIBUTE"
    ::= { nlmLinkageEntry 43 }

nlmLinkageLanL1DesignatedIntermediateSystemChanges OBJECT-TYPE
    SYNTAX      Counter64
    MAX-ACCESS  read-only
    STATUS      current
    DESCRIPTION 
        "Number of LAN L1 Designated Intermediate System Change 
         events generated."
    REFERENCE   
        "ISO/IEC 10589: 2001, 
         lanL1DesignatedIntermediateSystemChanges ATTRIBUTE"
    ::= { nlmLinkageEntry 44 }

-- "ISO/IEC 10589":linkageISISDACallEstablishmentMetricIncrement-P
nlmLinkageCallEstablishmentDefaultMetricIncrement OBJECT-TYPE
    SYNTAX      HopMetric
    MAX-ACCESS  read-create
    STATUS      current
    DESCRIPTION 
        "Additional value to be reported for the default metric 
         value of unestablished DA adjacencies."
    REFERENCE   
        "ISO/IEC 10589: 2001, 
         callEstablishmentDefaultMetricIncrement ATTRIBUTE"
    DEFVAL      { 0 }
    ::= { nlmLinkageEntry 45 }

nlmLinkageCallEstablishmentDelayMetricIncrement OBJECT-TYPE
    SYNTAX      HopMetric
    MAX-ACCESS  read-create
    STATUS      current
    DESCRIPTION 
        "Additional value to be reported for the delay metric 
         value of unestablished DA adjacencies."
    REFERENCE   
        "ISO/IEC 10589: 2001, 
         callEstablishmentDelayMetricIncrement ATTRIBUTE"
    DEFVAL      { 0 }
    ::= { nlmLinkageEntry 46 }

nlmLinkageCallEstablishmentExpenseMetricIncrement OBJECT-TYPE
    SYNTAX      HopMetric
    MAX-ACCESS  read-create
    STATUS      current
    DESCRIPTION 
        "Additional value to be reported for the Expense metric 
         value of unestablished DA adjacencies."
    REFERENCE   
        "ISO/IEC 10589: 2001, 
         callEstablishmentExpenseMetricIncrement ATTRIBUTE"
    DEFVAL      { 0 }
    ::= { nlmLinkageEntry 47 }

nlmLinkageCallEstablishmentErrorMetricIncrement OBJECT-TYPE
    SYNTAX      HopMetric
    MAX-ACCESS  read-create
    STATUS      current
    DESCRIPTION 
        "Additional value to be reported for the Error metric 
         value of unestablished DA adjacencies."
    REFERENCE   
        "ISO/IEC 10589: 2001, 
         callEstablishmentErrorMetricIncrement ATTRIBUTE"
    DEFVAL      { 0 }
    ::= { nlmLinkageEntry 48 }

-- "ISO/IEC 10589":linkageISISPtToPt-P
nlmLinkagePtPtCircuitID OBJECT-TYPE
    SYNTAX      CircuitID
    MAX-ACCESS  read-create
    STATUS      current
    DESCRIPTION 
        "The ID of the circuit allocated during initialisation. 
         If no value has been negotiated (either because the 
         adjacency is to an End system, or because 
         initialisation has not yet successfully completed), 
         this attribute has the value which would be proposed 
         for this circuit. (i.e. the concatenation of the local 
         system ID and the one octet local Circuit ID for this 
         circuit."
    REFERENCE   
        "ISO/IEC 10589: 2001, ptPtCircuitID ATTRIBUTE"
    ::= { nlmLinkageEntry 49 }

-- "ISO/IEC 10589":linkageISISStatic-P
nlmLinkageOutgoingCallIVMO OBJECT-TYPE
    SYNTAX      SimpleNameType
    MAX-ACCESS  read-create
    STATUS      current
    DESCRIPTION 
        "Reference to the virtualCallIVMO to be used to 
         establish communication with a neighbour over this 
         circuit. This IVMO contains, among other things,the 
         SNPA Address to use as the called address."
    REFERENCE   
        "ISO/IEC 10589: 2001, outgoingCallIVMO ATTRIBUTE"
    DEFVAL      { "Default" }
    ::= { nlmLinkageEntry 50 }

--  nlmLinkagePtPtCircuitID                     CircuitID
nlmLinkageNeighbourSNPAAdress OBJECT-TYPE
    SYNTAX      SNPAAddress
    MAX-ACCESS  read-create
    STATUS      current
    DESCRIPTION 
        "The SNPA address of the neighbour system."
    REFERENCE   
        "ISO/IEC 10589: 2001, neighbourSNPAAddress ATTRIBUTE"
    DEFVAL      { "\x00" }
    ::= { nlmLinkageEntry 51 }

-- "ISO/IEC 10589":linkageISISLevel2-P
nlmLinkageL2DefaultMetric OBJECT-TYPE
    SYNTAX      HopMetric
    MAX-ACCESS  read-create
    STATUS      current
    DESCRIPTION 
        "The default metric value of this circuit for Level 
         2 traffic."
    REFERENCE   
        "ISO/IEC 10589: 2001, l2DefaultMetric ATTRIBUTE"
    DEFVAL      { 20 }
    ::= { nlmLinkageEntry 52 }

nlmLinkageL2DelayMetric OBJECT-TYPE
    SYNTAX      HopMetric
    MAX-ACCESS  read-create
    STATUS      current
    DESCRIPTION 
        "The delay metric value of this circuit for Level 
         2 traffic. The value of zero is reserved to indicate 
         that this metric is not supported."
    REFERENCE   
        "ISO/IEC 10589: 2001, l2DelayMetric ATTRIBUTE"
    DEFVAL      { 0 }
    ::= { nlmLinkageEntry 53 }

nlmLinkageL2ExpenseMetric OBJECT-TYPE
    SYNTAX      HopMetric
    MAX-ACCESS  read-create
    STATUS      current
    DESCRIPTION 
        "The expense metric value of this circuit for Level 
         2 traffic. The value of zero is reserved to indicate 
         that this metric is not supported."
    REFERENCE   
        "ISO/IEC 10589: 2001, l2ExpenseMetric ATTRIBUTE"
    DEFVAL      { 0 }
    ::= { nlmLinkageEntry 54 }

nlmLinkageL2ErrorMetric OBJECT-TYPE
    SYNTAX      HopMetric
    MAX-ACCESS  read-create
    STATUS      current
    DESCRIPTION 
        "The error metric value of this circuit for Level 
         2 traffic. The value of zero is reserved to indicate 
         that this metric is not supported."
    REFERENCE   
        "ISO/IEC 10589: 2001, l2ErrorMetric ATTRIBUTE"
    DEFVAL      { 0 }
    ::= { nlmLinkageEntry 55 }

nlmLinkageManualL2OnlyMode OBJECT-TYPE
    SYNTAX      TruthValue
    MAX-ACCESS  read-create
    STATUS      current
    DESCRIPTION 
        "When True, indicates that this Circuit is to be used 
         only for Level 2.
         
         This attribute shall only permit the REPLACE operation 
         to be performed on it while the MO is in the Disabled 
         Operational State. An attempt to perform a REPLACE 
         operation while the MO is in the Enabled Operation 
         State shall fail with the generation of the 
         constraintViolation specific error."
    REFERENCE   
        "ISO/IEC 10589: 2001, manualL2OnlyMode ATTRIBUTE"
    DEFVAL      { false }
    ::= { nlmLinkageEntry 56 }

-- "ISO/IEC 10589":linkageISISLevel2Broadcast-P
nlmLinkageL2IntermediateSystemPriority OBJECT-TYPE
    SYNTAX      IntermediateSystemPriority
    MAX-ACCESS  read-create
    STATUS      current
    DESCRIPTION 
        "Priority for becoming LAN Level 2 Designated 
         Intermediate System."
    REFERENCE   
        "ISO/IEC 10589: 2001, l2IntermediateSystemPriority ATTRIBUTE"
    DEFVAL      { 64 }
    ::= { nlmLinkageEntry 57 }

nlmLinkageL2CircuitID OBJECT-TYPE
    SYNTAX      CircuitID
    MAX-ACCESS  read-create
    STATUS      current
    DESCRIPTION 
        "The LAN ID allocated by the LAN Level 2 Designated 
         Intermediate System. Where this system is not aware of 
         the value (because it is not participating in the Level 
         2 Designated Intermediate System election), this 
         attribute has the value which would be proposed for 
         this circuit. (i.e. the concatenation of the local 
         system ID and the one octet local Circuit ID for this 
         circuit."
    REFERENCE   
        "ISO/IEC 10589: 2001, l2CircuitID ATTRIBUTE"
    ::= { nlmLinkageEntry 58 }

nlmLinkageL2DesignatedIntermediateSystem OBJECT-TYPE
    SYNTAX      SystemId
    MAX-ACCESS  read-create
    STATUS      current
    DESCRIPTION 
        "The ID of the LAN Level 2 Designated Intermediate 
         System on this circuit. If, for any reason this system 
         is not partaking in the relevant Designated 
         Intermediate System election process, then the value 
         returned is the zero length OCTET STRING."
    REFERENCE   
        "ISO/IEC 10589: 2001, l2DesignatedIntermediateSystem ATTRIBUTE"
    ::= { nlmLinkageEntry 59 }

nlmLinkageLanL2DesignatedIntermediateSystemChanges OBJECT-TYPE
    SYNTAX      Counter64
    MAX-ACCESS  read-only
    STATUS      current
    DESCRIPTION 
        "Number of LAN L2 Designated Intermediate System Change 
         events generated."
    REFERENCE   
        "ISO/IEC 10589: 2001, 
         lanL2DesignatedIntermediateSystemChanges ATTRIBUTE"
    ::= { nlmLinkageEntry 60 }

--
nlmLinkageRowStatus OBJECT-TYPE
    SYNTAX      RowStatus
    MAX-ACCESS  read-create
    STATUS      current
    DESCRIPTION 
        "Provides a mechanism whereby management stations may 
         create and delete linkages in this table.  The contents 
         of this table must persist across agent 
         restart/reboot."
    REFERENCE   
        "ITU-T Rec. X.283 (1997) | ISO/IEC 10733 : 1998, 
               linkage-cLNS, linkage-cONS NAME BINDING"
    ::= { nlmLinkageEntry 61 }


-- ==========================================

nlmCLNS OBJECT IDENTIFIER
    ::= { nlmTables 4 }

nlmCLNSTable OBJECT-TYPE
    SYNTAX      SEQUENCE OF NlmCLNSEntry
    MAX-ACCESS  not-accessible
    STATUS      current
    DESCRIPTION 
        ""
    REFERENCE   
        "ITU-T Rec. X.283 (1997) | ISO/IEC 10733 : 1998, 
               cLNS MANAGED OBJECT CLASS"
    ::= { nlmCLNS 1 }

nlmCLNSEntry OBJECT-TYPE
    SYNTAX      NlmCLNSEntry
    MAX-ACCESS  not-accessible
    STATUS      current
    DESCRIPTION 
        "The connectionless-mode network service managed object.  
         There is no more than one of these MOs per network 
         entity.  Its definition permits it to be created and 
         deleted explicitly by management operation, but in some 
         systems it will exist inherently and neither creation 
         nor deletion by management operation will be possible.  
         Name bindings are defined for both cases.
         
         When the protocol machine is operable, the 
         operationalState shall have the value enabled(0); 
         otherwise, it shall have the value disabled(1).  
         Transitions of operationalState shall be reported using 
         the stateChange notification.  An cLNS MO may be 
         created in the enabled(0) operational state."
    REFERENCE   
        "ITU-T Rec. X.283 (1997) | ISO/IEC 10733 : 1998, 
               cLNS MANAGED OBJECT"
    INDEX       { nlmEntityId }
    ::= { nlmCLNSTable 1 }

NlmCLNSEntry ::= SEQUENCE {
    nlmCLNSClProtocolMachineId                      SimpleNameType,
    nlmCLNSOperationalState                         OperationalState,
    nlmCLNSTotalRemoteSAPs                          Counter64,
    nlmCLNSAdministrativeState                      AdministrativeState,
    nlmCLNSSupportedProtocols                       SupportedProtocols,
    nlmCLNSOperationalSystemType                    SystemType,
-- cLNS8473-P PACKAGE
    nlmCLNSOctetsSentCounter                        Counter64,
    nlmCLNSOctetsReceivedCounter                    Counter64,
    nlmCLNSSegmentsReceived                         Counter64,
    nlmCLNSSegmentsSent                             Counter64,
    nlmCLNSSegmentsDiscarded                        Counter64,
    nlmCLNSAssemblingSegmentsDiscarded              Counter64,
    nlmCLNSErrorReportsReceived                     Counter64,
    nlmCLNSPDUDiscards                              Counter64,
    nlmCLNSCongestionDiscards                       Counter64,
    nlmCLNSMaximumLifetime                          Lifetime,
-- cLNSChecksum-P PACKAGE
    nlmCLNSEnableChecksum                           TruthValue,
-- "ISO/IEC 10589":cLNSISISBasic-P PACKAGE
    nlmCLNSversion                                  SnmpAdminString,
    nlmCLNSiSType                                   ISType,
    nlmCLNSsystemId                                 SystemId,
    nlmCLNSmaximumPathSplits                        Integer32,
    nlmCLNSminimumLSPTransmissionInterval           MilliSeconds,
    nlmCLNSmaximumLSPGenerationInterval             MilliSeconds,
    nlmCLNSminimumBroadcastLSPTransmissionInterval  MilliSeconds,
    nlmCLNScompleteSNPInterval                      MilliSeconds,
    nlmCLNSoriginatingL1LSPBufferSize               Integer32,
    nlmCLNSmanualAreaAddresses                      AreaAddresses,
    nlmCLNSmaximumAreaAddresses                     Integer32,
    nlmCLNSminimumLSPGenerationInterval             MilliSeconds,
    nlmCLNSpollESHelloRate                          MilliSeconds,
    nlmCLNSpartialSNPInterval                       MilliSeconds,
    nlmCLNSwaitingTime                              MilliSeconds,
    nlmCLNSdRISISHelloTimer                         MilliSeconds,
    nlmCLNSl1State                                  DatabaseState,
    nlmCLNSareaAddresses                            AreaAddresses,
    nlmCLNScorruptedLSPsDetected                    Counter64,
    nlmCLNSlSPL1DatabaseOverloads                   Counter64,
    nlmCLNSmanualAddressesDroppedFromArea           Counter64,
    nlmCLNSattemptsToExceedMaximumSequenceNumber    Counter64,
    nlmCLNSsequenceNumberSkips                      Counter64,
    nlmCLNSownLSPPurges                             Counter64,
    nlmCLNSiDFieldLengthMismatches                  Counter64,
    nlmCLNSmaximumAreaAddressesMismatches           Counter64,
    nlmCLNSoriginatingLSPBufferSizeMismatches       Counter64,
    nlmCLNSlSPTooLargeToPropagate                   Counter64,
-- "ISO/IEC 10589":cLNSISISAuthentication-P PACKAGE
    nlmCLNSareaTransmitPassword                     Password,
    nlmCLNSareaReceivePasswords                     Passwords,
    nlmCLNSauthenticationFailures                   Counter64,
-- "ISO/IEC 10589":cLNSISISPartitionRepair-P PACKAGE
    nlmCLNSmaximumVirtualAdjacencies                Integer32,
    nlmCLNSpartitionAreaAddresses                   AreaAddresses,
    nlmCLNSpartitionDesignatedL2IntermediateSystem  SystemId,
    nlmCLNSpartitionVirtualLinkChanges              Counter64,
-- "ISO/IEC 10589":cLNSISISLevel2-P PACKAGE
    nlmCLNSoriginatingL2LSPBufferSize               Integer32,
    nlmCLNSl2State                                  DatabaseState,
    nlmCLNSlSPL2DatabaseOverloads                   Counter64,
-- "ISO/IEC 10589":cLNSISISLevel2Authentication-P PACKAGE
    nlmCLNSdomainTransmitPassword                   Password,
    nlmCLNSdomainReceivePasswords                   Passwords,
-- cLNS-networkEntity-Management NAME BINDING
    nlmCLNSRowStatus                                RowStatus
}

nlmCLNSClProtocolMachineId OBJECT-TYPE
    SYNTAX      SimpleNameType
    MAX-ACCESS  read-create
    STATUS      current
    DESCRIPTION 
        "Provides a simple name for this connectionless-mode 
         protocol state machine."
    REFERENCE   
        "ITU-T Rec. X.723 (1993) : ISO/IEC 10165-5 : 1993, 
               clProtocolMachineId ATTRIBUTE"
    DEFVAL      { "CLNS" }
    ::= { nlmCLNSEntry 1 }

nlmCLNSOperationalState OBJECT-TYPE
    SYNTAX      OperationalState
    MAX-ACCESS  read-create
    STATUS      current
    DESCRIPTION 
        "Provides the operational state of the 
         connectionless-mode protocol machine in accordance with 
         the OperationalState textual convention of the 
         OPENSS7-SMI-MIB and ITU-T Rec. X.721 (1992) | ISO/IEC 
         10165-2 : 1992.
         
         The value of this object must be explicitly set by the 
         management station before the protocol machine can be 
         placed in the active(1) state; otherwise, the attempt 
         to create the row or change the row status will fail.
         
         Once an initial value has been provided for this 
         object, it cannot be changed without taking the 
         protocol machine out of service using its row statue, 
         notInService(2)."
    REFERENCE   
        "ITU-T Rec. X.721 (1992) | ISO/IEC 10165-2 : 1992, 
               operationalState ATTRIBUTE"
    DEFVAL      { enabled }
    ::= { nlmCLNSEntry 2 }

nlmCLNSTotalRemoteSAPs OBJECT-TYPE
    SYNTAX      Counter64
    MAX-ACCESS  read-only
    STATUS      current
    DESCRIPTION 
        "Counts the number of remote (N) SAPs that the 
         containing clProtocolMachine has communicated with. 
         Incremented by 1 every time communication with a remote 
         (N) SAP is achieved."
    REFERENCE   
        "ITU-T Rec. X.721 (1992) | ISO/IEC 10165-2 : 1992, 
               totalRemoteSAPs ATTRIBUTE"
    ::= { nlmCLNSEntry 3 }

nlmCLNSAdministrativeState OBJECT-TYPE
    SYNTAX      AdministrativeState
    MAX-ACCESS  read-create
    STATUS      current
    DESCRIPTION 
        "Provides the administrative state of the linkage in 
         accordance with the AdministrativeState textual 
         convention of the OPENSS7-SMI-MIB."
    REFERENCE   
        "ITU-T Rec. X.721 (1992) | ISO/IEC 10165-2 : 1992, 
               administrativeState ATTRIBUTE"
    DEFVAL      { unlocked }
    ::= { nlmCLNSEntry 4 }

nlmCLNSSupportedProtocols OBJECT-TYPE
    SYNTAX      SupportedProtocols
    MAX-ACCESS  read-only
    STATUS      current
    DESCRIPTION 
        "The set of connectionless network protocols supported 
         by this instance of the CLNS protocol machine, 
         expressed except where otherwise indicated (for example 
         because there are more than one protocol described in 
         a single International Standard) as the registered 
         object identifiers of the relevant International 
         Standard.  The operation of a particular protocol over 
         a particular linkage is determined by the linkage 
         operationalProtocols attributed.  The value of the 
         supportedProtocols attribute is determined by the 
         implementation."
    REFERENCE   
        "ITU-T Rec. X.283 (1997) | ISO/IEC 10733 : 1998, 
               supportedProtocols ATTRIBUTE"
    ::= { nlmCLNSEntry 5 }

nlmCLNSOperationalSystemType OBJECT-TYPE
    SYNTAX      SystemType
    MAX-ACCESS  read-create
    STATUS      current
    DESCRIPTION 
        "The system role in which this interface is operating.  
         A value of eS(1) indicates that the system shall 
         perform no forwarding operations upon non-local PDUs.  
         A value of iS(2) indicates that the ssytem is permitted 
         to perform forwarding operations, but the decision to 
         forward individual PDUs, or not to forward them, shall 
         be taken on the basis of the available routing 
         information."
    REFERENCE   
        "ITU-T Rec. X.283 (1997) | ISO/IEC 10733 : 1998, 
               operationalSystemType ATTRIBUTE"
    ::= { nlmCLNSEntry 6 }

-- cLNS8473-P PACKAGE
nlmCLNSOctetsSentCounter OBJECT-TYPE
    SYNTAX      Counter64
    MAX-ACCESS  read-only
    STATUS      current
    DESCRIPTION 
        "Specifies the total number of user data octets sent by 
         the connectionless network protocol state machine."
    REFERENCE   
        "ITU-T Rec. X.721 (1992) | ISO/IEC 10165-2 : 1992, 
               octetsSentCounter"
    ::= { nlmCLNSEntry 7 }

nlmCLNSOctetsReceivedCounter OBJECT-TYPE
    SYNTAX      Counter64
    MAX-ACCESS  read-only
    STATUS      current
    DESCRIPTION 
        "Specifies the total number of user data octets received 
         by the connectionless network protocol state machine."
    REFERENCE   
        "ITU-T Rec. X.721 (1992) | ISO/IEC 10165-2 : 1992, 
               octetsReceivedCounter"
    ::= { nlmCLNSEntry 8 }

nlmCLNSSegmentsReceived OBJECT-TYPE
    SYNTAX      Counter64
    MAX-ACCESS  read-only
    STATUS      current
    DESCRIPTION 
        "Counter of segments received.  This is the number of 
         data and error report NPDUs received prior to 
         reassembly, including those that may subsequently be 
         discarded."
    REFERENCE   
        "ITU-T Rec. X.283 (1997) | ISO/IEC 10733 : 1998, 
               segmentsReceived ATTRIBUTE"
    ::= { nlmCLNSEntry 9 }

nlmCLNSSegmentsSent OBJECT-TYPE
    SYNTAX      Counter64
    MAX-ACCESS  read-only
    STATUS      current
    DESCRIPTION 
        "Counter of segments sent.  This is the number of data 
         and error report NPDUs sent after segmenetation 
         processing occurs."
    REFERENCE   
        "ITU-T Rec. X.283 (1997) | ISO/IEC 10733 : 1998, 
               segmentsSent ATTRIBUTE"
    ::= { nlmCLNSEntry 10 }

nlmCLNSSegmentsDiscarded OBJECT-TYPE
    SYNTAX      Counter64
    MAX-ACCESS  read-only
    STATUS      current
    DESCRIPTION 
        "Counter of segments discarded.  This is the number of 
         data and error report NPDUs discarded without being 
         delivered to a network service user or forwarded.  This 
         includes segments discarded for any reason except 
         reassembly time expiry."
    REFERENCE   
        "ITU-T Rec. X.283 (1997) | ISO/IEC 10733 : 1998, 
               segmentsDiscarded ATTRIBUTE"
    ::= { nlmCLNSEntry 11 }

nlmCLNSAssemblingSegmentsDiscarded OBJECT-TYPE
    SYNTAX      Counter64
    MAX-ACCESS  read-only
    STATUS      current
    DESCRIPTION 
        "Counter of segments discarded due to reassembly time 
         expiry.  This is the number of data and error report 
         NPDUs discarded due to reassembly time expiry."
    REFERENCE   
        "ITU-T Rec. X.283 (1997) | ISO/IEC 10733 : 1998, 
               assemblingSegmentsDiscarded ATTRIBUTE"
    ::= { nlmCLNSEntry 12 }

nlmCLNSErrorReportsReceived OBJECT-TYPE
    SYNTAX      Counter64
    MAX-ACCESS  read-only
    STATUS      current
    DESCRIPTION 
        "Counter of received error reports. This is the number 
         of error report NPDUs received which were addressed to 
         the local network entity."
    REFERENCE   
        "ITU-T Rec. X.283 (1997) | ISO/IEC 10733 : 1998, 
               errorReportsReceived ATTRIBUTE"
    ::= { nlmCLNSEntry 13 }

nlmCLNSPDUDiscards OBJECT-TYPE
    SYNTAX      Counter64
    MAX-ACCESS  read-only
    STATUS      current
    DESCRIPTION 
        "Counter of PDUs discarded (except for congestion). This 
         is the number of data or error report PDUs discarded 
         for any of the reasons specified in ITU-T Rec. X.233 
         | ISO/IEC 8473-1 Table 7 with the exception of `PDU 
         discarded due to congestion'. This counter is 
         incremented irrespective of the setting of the Error 
         Report bit in the received PDU.
         
         NOTE: This counter is therefore a count of the number 
         of communicationsAlarm notifications with 
         a specificProblem value of pDUDiscard generated (as 
         opposed to CMIP events, may be suppressed) as required 
         by GDMO subclause 9.8.5 (SC21 N4852)."
    REFERENCE   
        "ITU-T Rec. X.283 (1997) | ISO/IEC 10733 : 1998, 
               pDUDiscards ATTRIBUTE"
    ::= { nlmCLNSEntry 14 }

nlmCLNSCongestionDiscards OBJECT-TYPE
    SYNTAX      Counter64
    MAX-ACCESS  read-only
    STATUS      current
    DESCRIPTION 
        "Counter of PDUs discarded due to congestion. This is 
         the number of data or error report PDUs discarded due 
         to congestion. This counter is incremented irrespective 
         of the setting of the Error Report bit in the received 
         PDU."
    REFERENCE   
        "ITU-T Rec. X.283 (1997) | ISO/IEC 10733 : 1998, 
               congestionDiscards ATTRIBUTE"
    ::= { nlmCLNSEntry 15 }

nlmCLNSMaximumLifetime OBJECT-TYPE
    SYNTAX      Lifetime
    UNITS       "half seconds"
    MAX-ACCESS  read-create
    STATUS      current
    DESCRIPTION 
        "Maximum PDU lifetime (in half seconds). This attribute 
         controls the maximum value (in half seconds) which may 
         be placed in the lifetime field of any ITU-T Rec. X.233 
         | ISO/IEC 8473-1 data or error report PDU generated by 
         the local network entity. It does not affect the 
         lifetime field of any PDUs not generated by this 
         network entity, for example those relayed by this 
         system acting as an Intermediate System. PDUs generated 
         by the local network entity are permitted to have 
         a lower value of lifetime field than this attribute, 
         but shall not have a larger value. The means by which 
         the value of the lifetime field is determined for an 
         individual PDU is outside the scope of this 
         Specification, provided that it meets the above 
         constraints."
    REFERENCE   
        "ITU-T Rec. X.283 (1997) | ISO/IEC 10733 : 1998, 
               maximumLifetime ATTRIBUTE"
    ::= { nlmCLNSEntry 16 }

-- cLNSChecksum-P PACKAGE
nlmCLNSEnableChecksum OBJECT-TYPE
    SYNTAX      TruthValue
    MAX-ACCESS  read-create
    STATUS      current
    DESCRIPTION 
        "When true(1), the generation of checksums is enabled."
    REFERENCE   
        "ITU-T Rec. X.283 (1997) | ISO/IEC 10733 : 1998, 
               enableChecksum ATTRIBUTE"
    DEFVAL      { false }
    ::= { nlmCLNSEntry 17 }

-- "ISO/IEC 10589":cLNSISISBasic-P PACKAGE
nlmCLNSversion OBJECT-TYPE
    SYNTAX      SnmpAdminString
    MAX-ACCESS  read-only
    STATUS      current
    DESCRIPTION 
        "The edition of this International Standard to which the 
         implementation conforms."
    REFERENCE   
        "ISO/IEC 10589: 2001, version ATTRIBUTE"
    ::= { nlmCLNSEntry 18 }

nlmCLNSiSType OBJECT-TYPE
    SYNTAX      ISType
    MAX-ACCESS  read-create
    STATUS      current
    DESCRIPTION 
        "The type of this Intermediate System. The value of this 
         attribute is only settable via the create parameter.
         
         Value is supplied either by the protocol machine if the 
         MO is automatically created, or supplied via the CREATE 
         Operation. The value cannot be changed thereafter."
    REFERENCE   
        "ISO/IEC 10589: 2001, iSType ATTRIBUTE"
    ::= { nlmCLNSEntry 19 }

nlmCLNSsystemId OBJECT-TYPE
    SYNTAX      SystemId
    MAX-ACCESS  read-create
    STATUS      current
    DESCRIPTION 
        "The ID for the local system, to be appended to each of 
         the system's area address(es) to form the Network 
         Entity Titles valid for this IS. The derivation of 
         a value for SystemId is a local matter."
    REFERENCE   
        "ISO/IEC 10589: 2001, systemId ATTRIBUTE"
    ::= { nlmCLNSEntry 20 }

nlmCLNSmaximumPathSplits OBJECT-TYPE
    SYNTAX      Integer32 (1..32)
    MAX-ACCESS  read-create
    STATUS      current
    DESCRIPTION 
        "Maximum number of paths which it is permitted to split 
         traffic between.
         
         This attribute shall only permit the REPLACE operation 
         to be performed on it while the MO is in the Disabled 
         Operational State. An attempt to perform a REPLACE 
         operation while the MO is in the Enabled Operation 
         State shall fail with the generation of the 
         constraintViolation specific error."
    REFERENCE   
        "ISO/IEC 10589: 2001, maximumPathSplits ATTRIBUTE"
    DEFVAL      { 2 }
    ::= { nlmCLNSEntry 21 }

nlmCLNSminimumLSPTransmissionInterval OBJECT-TYPE
    SYNTAX      MilliSeconds
    MAX-ACCESS  read-create
    STATUS      current
    DESCRIPTION 
        "Minimum interval between retransmissions of an LSP.
         
         This attribute specifies the interval between certain 
         events in the operation of the protocol state machine. 
         If the value of this attribute is changed to a new 
         value while the protocol state machine is in operation, 
         the implementation shall take the necessary steps to 
         ensure that for any time interval which was in progress 
         when the corresponding attribute was changed, the next 
         expiration of the that interval takes place the 
         specified time after the original start of that 
         interval, or immediately, whichever is later. The 
         precision with which this time shall be implemented 
         shall be the same as that associated with the basic 
         operation of the timer attribute."
    REFERENCE   
        "ISO/IEC 10589: 2001, minimumLSPTransmissionInterval ATTRIBUTE"
    DEFVAL      { 5000 } -- 5 seconds
    ::= { nlmCLNSEntry 22 }

nlmCLNSmaximumLSPGenerationInterval OBJECT-TYPE
    SYNTAX      MilliSeconds
    MAX-ACCESS  read-create
    STATUS      current
    DESCRIPTION 
        "Maximum interval between generated LSPs by this system.
         
         This attribute specifies the interval between certain 
         events in the operation of the protocol state machine. 
         If the value of this attribute is changed to a new 
         value while the protocol state machine is in operation, 
         the implementation shall take the necessary steps to 
         ensure that for any time interval which was in progress 
         when the corresponding attribute was changed, the next 
         expiration of the that interval takes place the 
         specified time after the original start of that 
         interval, or immediately, whichever is later. The 
         precision with which this time shall be implemented 
         shall be the same as that associated with the basic 
         operation of the timer attribute."
    REFERENCE   
        "ISO/IEC 10589: 2001, maximumLSPGenerationInterval ATTRIBUTE"
    DEFVAL      { 900000 } -- 900 seconds
    ::= { nlmCLNSEntry 23 }

nlmCLNSminimumBroadcastLSPTransmissionInterval OBJECT-TYPE
    SYNTAX      MilliSeconds
    MAX-ACCESS  read-create
    STATUS      current
    DESCRIPTION 
        "Minimum interval between transmission of LSPs on 
         a broadcast circuit (See clause 7.3.15.6). This timer 
         shall be capable of a resolution not coarser than 10 
         ms.
         
         Note: this is defined for all Circuits, but would only 
         be required if one of them were a broadcast Circuit.
         
         This attribute specifies the interval between certain 
         events in the operation of the protocol state machine. 
         If the value of this attribute is changed to a new 
         value while the protocol state machine is in operation, 
         the implementation shall take the necessary steps to 
         ensure that for any time interval which was in progress 
         when the corresponding attribute was changed, the next 
         expiration of the that interval takes place the 
         specified time after the original start of that 
         interval, or immediately, whichever is later. The 
         precision with which this time shall be implemented 
         shall be the same as that associated with the basic 
         operation of the timer attribute."
    REFERENCE   
        "ISO/IEC 10589: 2001, 
         minimumBroadcastLSPTransmissionInterval ATTRIBUTE"
    DEFVAL      { 33 } -- 33 milliseconds
    ::= { nlmCLNSEntry 24 }

nlmCLNScompleteSNPInterval OBJECT-TYPE
    SYNTAX      MilliSeconds
    MAX-ACCESS  read-create
    STATUS      current
    DESCRIPTION 
        "Interval between generation of Complete Sequence 
         Numbers PDUs by a Designated Intermediate System on 
         a broadcast circuit.
         
         Note: this is defined for all linkages, but would only 
         be required if one of them were a broadcast linkage.
         
         This attribute specifies the interval between certain 
         events in the operation of the protocol state machine. 
         If the value of this attribute is changed to a new 
         value while the protocol state machine is in operation, 
         the implementation shall take the necessary steps to 
         ensure that for any time interval which was in progress 
         when the corresponding attribute was changed, the next 
         expiration of the that interval takes place the 
         specified time after the original start of that 
         interval, or immediately, whichever is later. The 
         precision with which this time shall be implemented 
         shall be the same as that associated with the basic 
         operation of the timer attribute."
    REFERENCE   
        "ISO/IEC 10589: 2001, completeSNPInterval ATTRIBUTE"
    DEFVAL      { 10000 } -- 10 seconds
    ::= { nlmCLNSEntry 25 }

nlmCLNSoriginatingL1LSPBufferSize OBJECT-TYPE
    SYNTAX      Integer32 (512..1492)
    MAX-ACCESS  read-create
    STATUS      current
    DESCRIPTION 
        "The maximum size of Level 1 LSPs and SNPs originated by 
         this system.
         
         This attribute shall only permit the REPLACE operation 
         to be performed on it while the MO is in the Disabled 
         Operational State. An attempt to perform a REPLACE 
         operation while the MO is in the Enabled Operation 
         State shall fail with the generation of the 
         constraintViolation specific error."
    REFERENCE   
        "ISO/IEC 10589: 2001, originatingL1LSPBufferSize ATTRIBUTE"
    DEFVAL      { 512 } -- ??
    ::= { nlmCLNSEntry 26 }

nlmCLNSmanualAreaAddresses OBJECT-TYPE
    SYNTAX      AreaAddresses
    MAX-ACCESS  read-create
    STATUS      current
    DESCRIPTION 
        "The union of the sets of manualAreaAddresses reported 
         in all Level 1 Link State PDUs received by this 
         Intermediate System."
    REFERENCE   
        "ISO/IEC 10589: 2001, manualAreaAddresses ATTRIBUTE"
    DEFVAL      { "" }
    ::= { nlmCLNSEntry 27 }

nlmCLNSmaximumAreaAddresses OBJECT-TYPE
    SYNTAX      Integer32 (0..254)
    MAX-ACCESS  read-create
    STATUS      current
    DESCRIPTION 
        "Maximum number of area addresses to be permitted for 
         this ISs area. Note that all ISs in the area must have 
         the same value configured for this attribute if correct 
         operation is to be assured.
         
         This attribute shall only permit the REPLACE operation 
         to be performed on it while the MO is in the Disabled 
         Operational State. An attempt to perform a REPLACE 
         operation while the MO is in the Enabled Operation 
         State shall fail with the generation of the 
         constraintViolation specific error."
    REFERENCE   
        "ISO/IEC 10589: 2001, maximumAreaAddresses ATTRIBUTE"
    DEFVAL      { 3 }
    ::= { nlmCLNSEntry 28 }

nlmCLNSminimumLSPGenerationInterval OBJECT-TYPE
    SYNTAX      MilliSeconds
    MAX-ACCESS  read-create
    STATUS      current
    DESCRIPTION 
        "Minimum interval between successive generation of LSPs 
         with the same LSPID by this IS.
         
         This attribute specifies the interval between certain 
         events in the operation of the protocol state machine. 
         If the value of this attribute is changed to a new 
         value while the protocol state machine is in operation, 
         the implementation shall take the necessary steps to 
         ensure that for any time interval which was in progress 
         when the corresponding attribute was changed, the next 
         expiration of the that interval takes place the 
         specified time after the original start of that 
         interval, or immediately, whichever is later. The 
         precision with which this time shall be implemented 
         shall be the same as that associated with the basic 
         operation of the timer attribute."
    REFERENCE   
        "ISO/IEC 10589: 2001, minimumLSPGenerationInterval ATTRIBUTE"
    DEFVAL      { 30000 } -- 30 seconds
    ::= { nlmCLNSEntry 29 }

nlmCLNSpollESHelloRate OBJECT-TYPE
    SYNTAX      MilliSeconds
    MAX-ACCESS  read-create
    STATUS      current
    DESCRIPTION 
        "The value to be used for the suggested ES configuration 
         timer in ISH PDUs when soliciting the ES 
         configuration."
    REFERENCE   
        "ISO/IEC 10589: 2001, pollESHelloRate ATTRIBUTE"
    DEFVAL      { 50000 } -- 50 seconds
    ::= { nlmCLNSEntry 30 }

nlmCLNSpartialSNPInterval OBJECT-TYPE
    SYNTAX      MilliSeconds
    MAX-ACCESS  read-create
    STATUS      current
    DESCRIPTION 
        "Minimum interval between sending Partial Sequence 
         Number PDUs.
         
         This attribute specifies the interval between certain 
         events in the operation of the protocol state machine. 
         If the value of this attribute is changed to a new 
         value while the protocol state machine is in operation, 
         the implementation shall take the necessary steps to 
         ensure that for any time interval which was in progress 
         when the corresponding attribute was changed, the next 
         expiration of the that interval takes place the 
         specified time after the original start of that 
         interval, or immediately, whichever is later. The 
         precision with which this time shall be implemented 
         shall be the same as that associated with the basic 
         operation of the timer attribute."
    REFERENCE   
        "ISO/IEC 10589: 2001, partialSNPInterval ATTRIBUTE"
    DEFVAL      { 2000 } -- 2 seconds
    ::= { nlmCLNSEntry 31 }

nlmCLNSwaitingTime OBJECT-TYPE
    SYNTAX      MilliSeconds
    MAX-ACCESS  read-create
    STATUS      current
    DESCRIPTION 
        "Amount of time to delay in waiting state before 
         entering On state.
         
         This attribute specifies the interval between certain 
         events in the operation of the protocol state machine. 
         If the value of this attribute is changed to a new 
         value while the protocol state machine is in operation, 
         the implementation shall take the necessary steps to 
         ensure that for any time interval which was in progress 
         when the corresponding attribute was changed, the next 
         expiration of the that interval takes place the 
         specified time after the original start of that 
         interval, or immediately, whichever is later. The 
         precision with which this time shall be implemented 
         shall be the same as that associated with the basic 
         operation of the timer attribute."
    REFERENCE   
        "ISO/IEC 10589: 2001, waitingTime ATTRIBUTE"
    DEFVAL      { 60000 } -- 60 seconds
    ::= { nlmCLNSEntry 32 }

nlmCLNSdRISISHelloTimer OBJECT-TYPE
    SYNTAX      MilliSeconds
    MAX-ACCESS  read-create
    STATUS      current
    DESCRIPTION 
        "The interval between the generation of IIH PDUs by the 
         designated IS on a LAN.
         
         This attribute specifies the interval between certain 
         events in the operation of the protocol state machine. 
         If the value of this attribute is changed to a new 
         value while the protocol state machine is in operation, 
         the implementation shall take the necessary steps to 
         ensure that for any time interval which was in progress 
         when the corresponding attribute was changed, the next 
         expiration of that interval takes place no later than 
         the expiration of the interval in progress or the 
         specified interval, whichever is sooner. The precision 
         with which this time shall be implemented shall be the 
         same as that associated with the basic operation of the 
         timer attribute."
    REFERENCE   
        "ISO/IEC 10589: 2001, dRISISHelloTimer ATTRIBUTE"
    DEFVAL      { 1000 } -- 1 second
    ::= { nlmCLNSEntry 33 }

nlmCLNSl1State OBJECT-TYPE
    SYNTAX      DatabaseState
    MAX-ACCESS  read-only
    STATUS      current
    DESCRIPTION 
        "The state of the Level 1 database."
    REFERENCE   
        "ISO/IEC 10589: 2001, l1State ATTRIBUTE"
    ::= { nlmCLNSEntry 34 }

nlmCLNSareaAddresses OBJECT-TYPE
    SYNTAX      AreaAddresses
    MAX-ACCESS  read-only
    STATUS      current
    DESCRIPTION 
        "The union of the sets of manualAreaAddresses reported 
         in all Level 1 Link State PDUs received by this 
         Intermediate System."
    REFERENCE   
        "ISO/IEC 10589: 2001, areaAddresses ATTRIBUTE"
    ::= { nlmCLNSEntry 35 }

nlmCLNScorruptedLSPsDetected OBJECT-TYPE
    SYNTAX      Counter64
    MAX-ACCESS  read-only
    STATUS      current
    DESCRIPTION 
        "Number of Corrupted LSP Detected events generated."
    REFERENCE   
        "ISO/IEC 10589: 2001, corruptedLSPsDetected ATTRIBUTE"
    ::= { nlmCLNSEntry 36 }

nlmCLNSlSPL1DatabaseOverloads OBJECT-TYPE
    SYNTAX      Counter64
    MAX-ACCESS  read-only
    STATUS      current
    DESCRIPTION 
        "Number of times the l1LSPDatabaseOverload event has 
         been generated."
    REFERENCE   
        "ISO/IEC 10589: 2001, lSPL1DatabaseOverloads ATTRIBUTE"
    ::= { nlmCLNSEntry 37 }

nlmCLNSmanualAddressesDroppedFromArea OBJECT-TYPE
    SYNTAX      Counter64
    MAX-ACCESS  read-only
    STATUS      current
    DESCRIPTION 
        "Number of times the manualAddressesDroppedFromArea 
         event has been generated."
    REFERENCE   
        "ISO/IEC 10589: 2001, manualAddressesDroppedFromArea ATTRIBUTE"
    ::= { nlmCLNSEntry 38 }

nlmCLNSattemptsToExceedMaximumSequenceNumber OBJECT-TYPE
    SYNTAX      Counter64
    MAX-ACCESS  read-only
    STATUS      current
    DESCRIPTION 
        "Number of times the 
         attemptToExceedMaximumSequenceNumber event has been 
         generated."
    REFERENCE   
        "ISO/IEC 10589: 2001, 
         attemptsToExceedMaximumSequenceNumber ATTRIBUTE"
    ::= { nlmCLNSEntry 39 }

nlmCLNSsequenceNumberSkips OBJECT-TYPE
    SYNTAX      Counter64
    MAX-ACCESS  read-only
    STATUS      current
    DESCRIPTION 
        "Number of times the sequenceNumberSkipped event has 
         been generated."
    REFERENCE   
        "ISO/IEC 10589: 2001, sequenceNumberSkips ATTRIBUTE"
    ::= { nlmCLNSEntry 40 }

nlmCLNSownLSPPurges OBJECT-TYPE
    SYNTAX      Counter64
    MAX-ACCESS  read-only
    STATUS      current
    DESCRIPTION 
        "Number of times the ownLSPPurged event has been 
         generated."
    REFERENCE   
        "ISO/IEC 10589: 2001, ownLSPPurges ATTRIBUTE"
    ::= { nlmCLNSEntry 41 }

nlmCLNSiDFieldLengthMismatches OBJECT-TYPE
    SYNTAX      Counter64
    MAX-ACCESS  read-only
    STATUS      current
    DESCRIPTION 
        "Number of times the iDFieldLengthMismatch event has 
         been generated."
    REFERENCE   
        "ISO/IEC 10589: 2001, iDFieldLengthMismatches ATTRIBUTE"
    ::= { nlmCLNSEntry 42 }

nlmCLNSmaximumAreaAddressesMismatches OBJECT-TYPE
    SYNTAX      Counter64
    MAX-ACCESS  read-only
    STATUS      current
    DESCRIPTION 
        "Count of maximumAreaAddressesMismatch events."
    REFERENCE   
        "ISO/IEC 10589: 2001, maximumAreaAddressesMismatches ATTRIBUTE"
    ::= { nlmCLNSEntry 43 }

nlmCLNSoriginatingLSPBufferSizeMismatches OBJECT-TYPE
    SYNTAX      Counter64
    MAX-ACCESS  read-only
    STATUS      current
    DESCRIPTION 
        "Count of originatingLSPBufferSizeMismatch events."
    REFERENCE   
        "ISO/IEC 10589: 2001, originatingLSPBufferSizeMismatches ATTRIBUTE"
    ::= { nlmCLNSEntry 44 }

nlmCLNSlSPTooLargeToPropagate OBJECT-TYPE
    SYNTAX      Counter64
    MAX-ACCESS  read-only
    STATUS      current
    DESCRIPTION 
        "Count of lSPTooLargeToPropagate events."
    REFERENCE   
        "ISO/IEC 10589: 2001, lSPTooLargeToPropagate ATTRIBUTE"
    ::= { nlmCLNSEntry 45 }

-- "ISO/IEC 10589":cLNSISISAuthentication-P PACKAGE
nlmCLNSareaTransmitPassword OBJECT-TYPE
    SYNTAX      Password
    MAX-ACCESS  read-create
    STATUS      current
    DESCRIPTION 
        "The value to be used as a transmit password in Level 
         1 LSP, and SNP PDUs transmitted by this Intermediate 
         System."
    REFERENCE   
        "ISO/IEC 10589: 2001, areaTransmitPassword ATTRIBUTE"
    DEFVAL      { "" }
    ::= { nlmCLNSEntry 46 }

nlmCLNSareaReceivePasswords OBJECT-TYPE
    SYNTAX      Passwords
    MAX-ACCESS  read-create
    STATUS      current
    DESCRIPTION 
        "The values to be used as receive passwords to check the 
         receipt of Level 1 LSP, and SNP PDUs."
    REFERENCE   
        "ISO/IEC 10589: 2001, areaReceivePasswords ATTRIBUTE"
    DEFVAL      { "" }
    ::= { nlmCLNSEntry 47 }

nlmCLNSauthenticationFailures OBJECT-TYPE
    SYNTAX      Counter64
    MAX-ACCESS  read-only
    STATUS      current
    DESCRIPTION 
        "Count of authentication Failure events."
    REFERENCE   
        "ISO/IEC 10589: 2001, authenticationFailures ATTRIBUTE"
    ::= { nlmCLNSEntry 48 }

-- "ISO/IEC 10589":cLNSISISPartitionRepair-P PACKAGE
nlmCLNSmaximumVirtualAdjacencies OBJECT-TYPE
    SYNTAX      Integer32 (0..32)
    MAX-ACCESS  read-create
    STATUS      current
    DESCRIPTION 
        "Maximum number of Virtual Adjacencies which may be 
         created to repair partitioned Level 1 domains.
         
         This attribute places limits on some 'resource'. In 
         general implementations may allocate resources up to 
         this limit when the managed object is enabled and it 
         may be impossible to change the allocation without 
         first disabling and re-enabling the managed object. 
         Therefore this International Standard only requires 
         that it shall be possible to perform a REPLACE 
         operation on this attribute while the MO is disabled. 
         However some implementations may be able to change the 
         allocation of resources without first disabling the MO. 
         In this case it is permitted to increase the value of 
         the attribute at any time, but it shall not be 
         decreased below the currently 'used' value of the 
         resource. Where an attempt to perform a REPLACE 
         operation fails either because the MO is enabled, or 
         because an attempt has been made to decrease the value, 
         the REPLACE operation shall fail with the generation of 
         the constraintViolation specific error."
    REFERENCE   
        "ISO/IEC 10589: 2001, maximumVirtualAdjacencies ATTRIBUTE"
    DEFVAL      { 2 }
    ::= { nlmCLNSEntry 49 }

nlmCLNSpartitionAreaAddresses OBJECT-TYPE
    SYNTAX      AreaAddresses
    MAX-ACCESS  read-only
    STATUS      current
    DESCRIPTION 
        "The set union of all manualAreaAddresses of all 
         Intermediate systems in the partition reachable by 
         non-virtual links (calculated from their Level 
         1 LSPs)."
    REFERENCE   
        "ISO/IEC 10589: 2001, partitionAreaAddresses ATTRIBUTE"
    ::= { nlmCLNSEntry 50 }

nlmCLNSpartitionDesignatedL2IntermediateSystem OBJECT-TYPE
    SYNTAX      SystemId
    MAX-ACCESS  read-only
    STATUS      current
    DESCRIPTION 
        "The ID of the Partition Designated Level 2 Intermediate 
         System for this system."
    REFERENCE   
        "ISO/IEC 10589: 2001, 
         partitionDesignatedL2IntermediateSystem ATTRIBUTE"
    ::= { nlmCLNSEntry 51 }

nlmCLNSpartitionVirtualLinkChanges OBJECT-TYPE
    SYNTAX      Counter64
    MAX-ACCESS  read-only
    STATUS      current
    DESCRIPTION 
        "Number of times the partitionVirtualLink hange event 
         has been generated."
    REFERENCE   
        "ISO/IEC 10589: 2001, partitionVirtualLinkChanges ATTRIBUTE"
    ::= { nlmCLNSEntry 52 }

-- "ISO/IEC 10589":cLNSISISLevel2-P PACKAGE
nlmCLNSoriginatingL2LSPBufferSize OBJECT-TYPE
    SYNTAX      Integer32 (512..1492)
    MAX-ACCESS  read-create
    STATUS      current
    DESCRIPTION 
        "The maximum size of Level 2 LSPs and SNPs originated by 
         this system.
         
         This attribute shall only permit the REPLACE operation 
         to be performed on it while the MO is in the Disabled 
         Operational State. An attempt to perform a REPLACE 
         operation while the MO is in the Enabled Operation 
         State shall fail with the generation of the 
         constraintViolation specific error."
    REFERENCE   
        "ISO/IEC 10589: 2001, originatingL2LSPBufferSize ATTRIBUTE"
    DEFVAL      { 512 } -- ??
    ::= { nlmCLNSEntry 53 }

nlmCLNSl2State OBJECT-TYPE
    SYNTAX      DatabaseState
    MAX-ACCESS  read-only
    STATUS      current
    DESCRIPTION 
        "The state of the Level 2 database."
    REFERENCE   
        "ISO/IEC 10589: 2001, l2State ATTRIBUTE"
    ::= { nlmCLNSEntry 54 }

nlmCLNSlSPL2DatabaseOverloads OBJECT-TYPE
    SYNTAX      Counter64
    MAX-ACCESS  read-only
    STATUS      current
    DESCRIPTION 
        "Number of times the l2LSPDatabaseOverload event has 
         been generated."
    REFERENCE   
        "ISO/IEC 10589: 2001, lSPL2DatabaseOverloads ATTRIBUTE"
    ::= { nlmCLNSEntry 55 }

-- "ISO/IEC 10589":cLNSISISLevel2Authentication-P PACKAGE
nlmCLNSdomainTransmitPassword OBJECT-TYPE
    SYNTAX      Password
    MAX-ACCESS  read-create
    STATUS      current
    DESCRIPTION 
        "The value to be used as a transmit password in Level 
         2 LSP, and SNP PDUs transmitted by this Intermediate 
         System."
    REFERENCE   
        "ISO/IEC 10589: 2001, domainTransmitPassword ATTRIBUTE"
    DEFVAL      { "" }
    ::= { nlmCLNSEntry 56 }

nlmCLNSdomainReceivePasswords OBJECT-TYPE
    SYNTAX      Passwords
    MAX-ACCESS  read-create
    STATUS      current
    DESCRIPTION 
        "The values to be used as receive passwords to check the 
         receipt of Level 2 LSP, and SNP PDUs."
    REFERENCE   
        "ISO/IEC 10589: 2001, domainReceivePasswords ATTRIBUTE"
    DEFVAL      { "" }
    ::= { nlmCLNSEntry 57 }

-- cLNS-networkEntity-Management NAME BINDING
nlmCLNSRowStatus OBJECT-TYPE
    SYNTAX      RowStatus
    MAX-ACCESS  read-create
    STATUS      current
    DESCRIPTION 
        "Provides a mechanism whereby management stations may 
         create or delete protocol machines in this table.  The 
         contents of this table must persist across management 
         system restart/reboot."
    REFERENCE   
        "ITU-T Rec. X.283 (1997) | ISO/IEC 10733 : 1998, 
               cLNS-networkEntity-Management NAME BINDING"
    ::= { nlmCLNSEntry 58 }

-- ==========================================

nlmCONS OBJECT IDENTIFIER
    ::= { nlmTables 5 }

nlmCONSTable OBJECT-TYPE
    SYNTAX      SEQUENCE OF NlmCONSEntry
    MAX-ACCESS  not-accessible
    STATUS      current
    DESCRIPTION 
        ""
    REFERENCE   
        "ITU-T Rec. X.283 (1997) | ISO/IEC 10733 : 1998, cONS 
               MANAGED OBJECT CLASS"
    ::= { nlmCONS 1 }

nlmCONSEntry OBJECT-TYPE
    SYNTAX      NlmCONSEntry
    MAX-ACCESS  not-accessible
    STATUS      current
    DESCRIPTION 
        "5.8 The connection-mode network service managed object
         
         There is no more than one of these MOs per network 
         entity.  Its definition permits it to be created and 
         deleted explicitly by management operation, but in some 
         systems it will exist inherently and neither creation 
         nor deletion by management operation will be possible. 
         Name bindings are defined for both cases.
         
         When the protocol machine is operable, the 
         operationalState shall have the value 'enabled'; 
         otherwise it shall have the value 'disabled'.  
         Transitions of operationalState shall be reported using 
         the stateChange notification. A cONS MO may be created 
         in the 'enabled' operational state."
    REFERENCE   
        "ITU-T Rec. X.283 (1997) | ISO/IEC 10733 : 1998, cONS 
               MANAGED OBJECT"
    INDEX       { nlmEntityId }
    ::= { nlmCONSTable 1 }

NlmCONSEntry ::= SEQUENCE {
    nlmCONSCoProtocolMachineId      SimpleNameType,
    nlmCONSOperationalState         OperationalState,
    nlmCONSAdministrativeState      AdministrativeState,
    nlmCONSOperationalSystemType    SystemType,
    nlmCONSRowStatus                RowStatus
}

nlmCONSCoProtocolMachineId OBJECT-TYPE
    SYNTAX      SimpleNameType
    MAX-ACCESS  read-create
    STATUS      current
    DESCRIPTION 
        ""
    REFERENCE   
        "ITU-T Rec. X.723 (1993) : ISO/IEC 10165-5 : 1993, 
               coProtocolMachineId"
    DEFVAL      { "CONS" }
    ::= { nlmCONSEntry 1 }

nlmCONSOperationalState OBJECT-TYPE
    SYNTAX      OperationalState
    MAX-ACCESS  read-create
    STATUS      current
    DESCRIPTION 
        "Provides the operational state of the connection-mode 
         protocol machine in accordance with the 
         OperationalState textual convention of the 
         OPENSS7-SMI-MIB and ITU-T Rec. X.721 (1992) | ISO/IEC 
         10165-2 : 1992.
         
         The value of this object must be explicitly set by the 
         management station before the protocol machine can be 
         placed in the active(1) state; otherwise, the attempt 
         to create the row or change the row status will fail.
         
         Once an initial value has been provided for this 
         object, it cannot be changed without taking the 
         protocol machine out of service using its row statue, 
         notInService(2)."
    REFERENCE   
        "ITU-T Rec. X.721 (1992) | ISO/IEC 10165-2 : 1992, 
               operationalState ATTRIBUTE"
    DEFVAL      { enabled }
    ::= { nlmCONSEntry 2 }

nlmCONSAdministrativeState OBJECT-TYPE
    SYNTAX      AdministrativeState
    MAX-ACCESS  read-create
    STATUS      current
    DESCRIPTION 
        "Provides the administrative state of the protocol 
         machine in accordance with the AdministrativeState 
         textual convention of the OPENSS7-SMI-MIB."
    REFERENCE   
        "ITU-T Rec. X.721 (1992) | ISO/IEC 10165-2 : 1992, 
               administrativeState ATTRIBUTE"
    DEFVAL      { unlocked }
    ::= { nlmCONSEntry 3 }

nlmCONSOperationalSystemType OBJECT-TYPE
    SYNTAX      SystemType
    MAX-ACCESS  read-create
    STATUS      current
    DESCRIPTION 
        "The system role in which this instance is operating. 
         A value of ES indicates that the system shall perform 
         no forwarding operations upon non-local PDUs. A value 
         of IS indicates that the system is permitted to perform 
         forwarding operations, but the decision to forward 
         individual PDUs, or not to forward them, shall be taken 
         on the basis of the available routing information."
    REFERENCE   
        "ITU-T Rec. X.721 (1992) | ISO/IEC 10165-2 : 1992, 
               operationalSystemType ATTRIBUTE"
    DEFVAL      { eS }
    ::= { nlmCONSEntry 4 }

nlmCONSRowStatus OBJECT-TYPE
    SYNTAX      RowStatus
    MAX-ACCESS  read-create
    STATUS      current
    DESCRIPTION 
        "Provides a mechanism whereby management stations may 
         create or delete protocol machines in this table.  The 
         contents of this table must persist across management 
         system restart/reboot."
    REFERENCE   
        "ITU-T Rec. X.283 (1997) | ISO/IEC 10733 : 1998, 
               cONS-networkEntity-Management NAME BINDING"
    ::= { nlmCONSEntry 5 }

-- ==========================================

nlmConnection OBJECT IDENTIFIER
    ::= { nlmTables 6 }

nlmConnectionTable OBJECT-TYPE
    SYNTAX      SEQUENCE OF NlmConnectionEntry
    MAX-ACCESS  not-accessible
    STATUS      current
    DESCRIPTION 
        ""
    REFERENCE   
        "ITU-T Rec. X.283 (1997) | ISO/IEC 10733 : 1998, 
               networkConnection MANAGED OBJECT CLASS"
    ::= { nlmConnection 1 }

nlmConnectionEntry OBJECT-TYPE
    SYNTAX      NlmConnectionEntry
    MAX-ACCESS  not-accessible
    STATUS      current
    DESCRIPTION 
        "5.9 The network connection managed object
         
         There is one instance of this MO corresponding to each 
         network connection. It is created and deleted by the 
         operation of the protocol machine.
         
         In some configurations the underlyingConnectionNames 
         attribute may contain more than one distinguished name. 
         In this case, the type of the underlying MO (and hence 
         the particular underlying resource) can only be 
         determined by inspection of the MO pointed to by this 
         distinguished name.
         
         The 'GMI':underlyingConnectionNames attribute shall 
         contain the distinguished name(s) of the other MO(s) 
         that represent the resources used to support this 
         connection.  In the case of the CONS operating directly 
         over X.25, this shall be the single distinguished name 
         of the underlying virtual call or permanent virtual 
         circuit MO."
    REFERENCE   
        "ITU-T Rec. X.283 (1997) | ISO/IEC 10733 : 1998, 
               networkConnection MANAGED OBJECT"
    INDEX       { nlmEntityId, nlmConnectionId }
    ::= { nlmConnectionTable 1 }

NlmConnectionEntry ::= SEQUENCE {
    nlmConnectionId                         SimpleNameType,
    nlmConnectionUnderlyingConnectionNames  SnmpAdminString,
-- singlePeerConnectionP2 PACKAGE
    nlmConnectionSupportedConnectionNames   SnmpAdminString,
-- 
    nlmConnectionLocalNSAPMO                LocalDistinguishedName,
    nlmConnectionRemoteNSAPAddress          NAddress
}

nlmConnectionId OBJECT-TYPE
    SYNTAX      SimpleNameType
    MAX-ACCESS  not-accessible
    STATUS      current
    DESCRIPTION 
        "The name or number of the connection."
    REFERENCE   
        "ITU-T Rec. X.723 (1993) : ISO/IEC 10165-5 : 1993, 
               connectionId ATTRIBUTE"
    ::= { nlmConnectionEntry 1 }

nlmConnectionUnderlyingConnectionNames OBJECT-TYPE
    SYNTAX      SnmpAdminString
    MAX-ACCESS  read-only
    STATUS      current
    DESCRIPTION 
        "This attribute contains the distinguished names of 
         managed objects that represent connections that are 
         employed by the connection that has this attribute."
    REFERENCE   
        "ITU-T Rec. X.723 (1993) : ISO/IEC 10165-5 : 1993, 
               underlyingConnectionNames ATTRIBUTE"
    ::= { nlmConnectionEntry 2 }

-- singlePeerConnectionP2 PACKAGE
nlmConnectionSupportedConnectionNames OBJECT-TYPE
    SYNTAX      SnmpAdminString
    MAX-ACCESS  read-only
    STATUS      current
    DESCRIPTION 
        "This attribute contains the distinguished names of 
         managed objects that represent connections that are 
         supported by the connection that has this attribute."
    REFERENCE   
        "ITU-T Rec. X.723 (1993) : ISO/IEC 10165-5 : 1993, 
               supportedConnectionNames ATTRIBUTE"
    ::= { nlmConnectionEntry 3 }

-- 
nlmConnectionLocalNSAPMO OBJECT-TYPE
    SYNTAX      LocalDistinguishedName
    MAX-ACCESS  read-only
    STATUS      current
    DESCRIPTION 
        "Pointer to local nSAP MO. This is a relationship 
         attribute which points to the local nSAP MO which is 
         associated with the connection."
    REFERENCE   
        "ITU-T Rec. X.283 (1997) | ISO/IEC 10733 : 1998, 
               localNSAPMO ATTRIBUTE"
    ::= { nlmConnectionEntry 4 }

nlmConnectionRemoteNSAPAddress OBJECT-TYPE
    SYNTAX      NAddress
    MAX-ACCESS  read-only
    STATUS      current
    DESCRIPTION 
        "The remote NSAP Address associated with the 
         connection."
    REFERENCE   
        "ITU-T Rec. X.283 (1997) | ISO/IEC 10733 : 1998, 
               remoteNSAPAddress ATTRIBUTE"
    ::= { nlmConnectionEntry 5 }

-- ==========================================

nlmNSAP OBJECT IDENTIFIER
    ::= { nlmTables 7 }

nlmNSAPTable OBJECT-TYPE
    SYNTAX      SEQUENCE OF NlmNSAPEntry
    MAX-ACCESS  not-accessible
    STATUS      current
    DESCRIPTION 
        ""
    REFERENCE   
        "ITU-T Rec. X.283 (1997) | ISO/IEC 10733 : 1998, nSAP 
               MANAGED OBJECT CLASS"
    ::= { nlmNSAP 1 }

nlmNSAPEntry OBJECT-TYPE
    SYNTAX      NlmNSAPEntry
    MAX-ACCESS  not-accessible
    STATUS      current
    DESCRIPTION 
        "5.5 The NSAP managed object
         
         There is one nSAP MO for each set of NSAPs supported by 
         the Network Subsystem associated with a single 
         Transport layer client.  Each NSAP MO corresponds to 
         a set of one or more NSAPs supported by the Network 
         Subsystem.
         
         There is not more than one Transport layer client 
         associated with a single nSAP MO, but there may be more 
         than one nSAP MO, and corresponding sets of NSAPs, 
         associated with a single Transport layer client.  Its 
         definition permits it to be created and deleted 
         explicitly by management operation or to be created and 
         deleted automatically as part of system operation."
    REFERENCE   
        "ITU-T Rec. X.283 (1997) | ISO/IEC 10733 : 1998, nSAP 
               MANAGED OBJECT"
    INDEX       { nlmNSAPSapId }
    ::= { nlmNSAPTable 1 }

NlmNSAPEntry ::= SEQUENCE {
    nlmNSAPSapId                SimpleNameType,
    nlmNSAPSap2Address          NAddresses,
    nlmNSAPUserEntityNames      LocalDistinguishedName,
    nlmNSAPProviderEntityNames  LocalDistinguishedNames,
    nlmNSAPRowStatus            RowStatus
}

nlmNSAPSapId OBJECT-TYPE
    SYNTAX      SimpleNameType
    MAX-ACCESS  not-accessible
    STATUS      current
    DESCRIPTION 
        "Provides a simple name for this NSAP within the network 
         subsystem."
    REFERENCE   
        "ITU-T Rec. X.723 (1993) | ISO/IEC 10165-5 : 1993, 
               sapId ATTRIBUTE"
    ::= { nlmNSAPEntry 1 }

nlmNSAPSap2Address OBJECT-TYPE
    SYNTAX      NAddresses
    MAX-ACCESS  read-create
    STATUS      current
    DESCRIPTION 
        "The set of NSAP addresses associated with this NSAP."
    REFERENCE   
        "ITU-T Rec. X.723 (1993) | ISO/IEC 10165-5 : 1993, 
               sapId ATTRIBUTE"
    ::= { nlmNSAPEntry 2 }

nlmNSAPUserEntityNames OBJECT-TYPE
    SYNTAX      LocalDistinguishedName
    MAX-ACCESS  read-only
    STATUS      current
    DESCRIPTION 
        "The user entity names utilizing this NSAP.  Note that 
         at most one transport entity can be associated with 
         a given NSAP.  When no transport entity is associated 
         with this NSAP, this object will be a null string."
    REFERENCE   
        "ITU-T Rec. X.723 (1993) | ISO/IEC 10165-5 : 1993, 
               userEntityNames ATTRIBUTE"
    DEFVAL      { "" }
    ::= { nlmNSAPEntry 3 }

nlmNSAPProviderEntityNames OBJECT-TYPE
    SYNTAX      LocalDistinguishedNames
    MAX-ACCESS  read-only
    STATUS      current
    DESCRIPTION 
        "The distinguished names of the datalink layer entities 
         that provide services to this NSAP."
    REFERENCE   
        "ITU-T Rec. X.723 (1993) | ISO/IEC 10165-5 : 1993, 
               providerEntityNames ATTRIBUTE"
    ::= { nlmNSAPEntry 4 }

nlmNSAPRowStatus OBJECT-TYPE
    SYNTAX      RowStatus
    MAX-ACCESS  read-create
    STATUS      current
    DESCRIPTION 
        "Provides a mechanism whereby management stations may 
         create or delete NSAPs.  Rows created by management 
         action in this table must persist across management 
         system restart/reboot."
    REFERENCE   
        "ITU-T Rec. X.283 (1997) | ISO/IEC 10733 : 1998, 
               nSAP-networkSubsystem-management NAME BINDING"
    ::= { nlmNSAPEntry 5 }

-- ==========================================

nlmX25PLE OBJECT IDENTIFIER
    ::= { nlmTables 8 }

nlmX25PLETable OBJECT-TYPE
    SYNTAX      SEQUENCE OF NlmX25PLEEntry
    MAX-ACCESS  not-accessible
    STATUS      current
    DESCRIPTION 
        "
         Note: When CONS is operating over a LAN (LLC2), the 
         X.25 packet layer entity can operate in either DCE-mode 
         or DTE-mode on a given connection."
    REFERENCE   
        "ITU-T Rec. X.283 (1997) | ISO/IEC 10733 : 1998, x25PLE 
               MANAGED OBJECT CLASS"
    ::= { nlmX25PLE 1 }

nlmX25PLEEntry OBJECT-TYPE
    SYNTAX      NlmX25PLEEntry
    MAX-ACCESS  not-accessible
    STATUS      current
    DESCRIPTION 
        "5.10.1 The X.25 PLE managed object
         
         This MO class is never instantiated. It serves as 
         a generic x25PLE MO from which both the x25PLE-DTE and 
         x25PLE-DCE MO classes are derived.
         
         Note that the values of the x25PLEId naming attribute 
         are required to be unique across all instances of MOs 
         derived from this, which have a common superior."
    REFERENCE   
        "ITU-T Rec. X.283 (1997) | ISO/IEC 10733 : 1998, x25PLE 
               MANAGED OBJECT"
    INDEX       { nlmX25PLEId }
    ::= { nlmX25PLETable 1 }

NlmX25PLEEntry ::= SEQUENCE {
    nlmX25PLEId                                 SimpleNameType,
    nlmX25PLEOperationalState                   OperationalState,
    nlmX25PLEAdministrativeState                AdministrativeState,
    nlmX25PLEProtocolVersionSupported           ProtocolVersion,
    nlmX25PLELocalDTEAddress                    DTEAddress,
    nlmX25PLEx25PLEMode                         X25PLEMode,
--  nlmX25PLEDefaultThroughputClasses           OCTET STRING,
    nlmX25PLEDefaultThroughputClassIncoming     Integer32,
    nlmX25PLEDefaultThroughputClassOutgoing     Integer32,
    nlmX25PLEFlowControlParameterNegotiation    TruthValue,
--  nlmX25PLEDefaultPacketSizes                 OCTET STRING,
    nlmX25PLEDefaultPacketSizeIncoming          Unsigned32,
    nlmX25PLEDefaultPacketSizeOutgoing          Unsigned32,
--  nlmX25PLEDefaultWindowSizes                 OCTET STRING,
    nlmX25PLEDefaultWindowSizeIncoming          Unsigned32,
    nlmX25PLEDefaultWindowSizeOutgoing          Unsigned32,
    nlmX25PLEThroughputClassNegotiation         TruthValue,
    nlmX25PLESnServiceProvider                  LocalDistinguishedName,
    nlmX25PLESnSAP                              LocalDistinguishedName,
--  nlmX25PLELogicalChannelAssignments          OCTET STRING,
    nlmX25PLELogicalChannelAssignmentsPVC       LogicalChannelIds,
    nlmX25PLELogicalChannelAssignmentsIC        LogicalChannelRange,
    nlmX25PLELogicalChannelAssignments2W        LogicalChannelRange,
    nlmX25PLELogicalChannelAssignmentsOG        LogicalChannelRange,
    nlmX25PLERowStatus                          RowStatus
}

nlmX25PLEId OBJECT-TYPE
    SYNTAX      SimpleNameType
    MAX-ACCESS  not-accessible
    STATUS      current
    DESCRIPTION 
        "The name of this instance of x25PLE MO."
    REFERENCE   
        "ITU-T Rec. X.283 (1997) | ISO/IEC 10733 : 1998, 
               x25PLEId ATTRIBUTE"
    ::= { nlmX25PLEEntry 1 }

nlmX25PLEOperationalState OBJECT-TYPE
    SYNTAX      OperationalState
    MAX-ACCESS  read-only
    STATUS      current
    DESCRIPTION 
        "Provides the operational state of the X.25 packet layer 
         entity in accordance with the OperationalState textual 
         convention of the OPENSS7-SMI-MIB and ITU-T Rec. X.721 
         (1992) | ISO/IEC 10165-2 : 1992."
    REFERENCE   
        "ITU-T Rec. X.721 (1992) | ISO/IEC 10165-2 : 1992, 
               operationalState"
    ::= { nlmX25PLEEntry 2 }

nlmX25PLEAdministrativeState OBJECT-TYPE
    SYNTAX      AdministrativeState
    MAX-ACCESS  read-create
    STATUS      current
    DESCRIPTION 
        "Provides the administrative state of the X.25 packet 
         layer entity in accordance with the AdministrativeState 
         textual convention of the OPENSS7-SMI-MIB."
    REFERENCE   
        "ITU-T Rec. X.721 (1992) | ISO/IEC 10165-2 : 1992, 
               administrativeState"
    ::= { nlmX25PLEEntry 3 }

nlmX25PLEProtocolVersionSupported OBJECT-TYPE
    SYNTAX      ProtocolVersion
    MAX-ACCESS  read-create
    STATUS      current
    DESCRIPTION 
        "The supported ITU-T Recommendation | International 
         Standard protocol version available on the PLE 
         interface."
    REFERENCE   
        "ITU-T Rec. X.283 (1997) | ISO/IEC 10733 : 1998, 
               protocolVersionSupported ATTRIBUTE"
    ::= { nlmX25PLEEntry 4 }

nlmX25PLELocalDTEAddress OBJECT-TYPE
    SYNTAX      DTEAddress
    MAX-ACCESS  read-create
    STATUS      current
    DESCRIPTION 
        "The full DTE address of this PLE expressed as an X.121, 
         E.164, etc. address."
    REFERENCE   
        "ITU-T Rec. X.283 (1997) | ISO/IEC 10733 : 1998, 
               localDTEAddress ATTRIBUTE"
    ::= { nlmX25PLEEntry 5 }

nlmX25PLEx25PLEMode OBJECT-TYPE
    SYNTAX      X25PLEMode
    MAX-ACCESS  read-create
    STATUS      current
    DESCRIPTION 
        "The DCE/DTE mode in which the X.25 PLE is currently 
         operating.  One of the following modes of operation may 
         be indicated.  dTE(0) DTE mode applying to both ITU-T 
         Rec.  X.25 and ISO/IEC 8208 operation, dCE(1) DCE mode 
         applying to ITU-T Rec.  X.25 operation only, and 
         dCEasDTE(2) DTE acting as a DCE applying to ISO/IEC 
         8208 operation only."
    REFERENCE   
        "ITU-T Rec. X.283 (1997) | ISO/IEC 10733 : 1998, 
               x25PLEMode ATTRIBUTE"
    ::= { nlmX25PLEEntry 6 }

--  nlmX25PLEDefaultThroughputClasses           OCTET STRING
nlmX25PLEDefaultThroughputClassIncoming OBJECT-TYPE
    SYNTAX      Integer32
    MAX-ACCESS  read-create
    STATUS      current
    DESCRIPTION 
        "The default throughput class values. A value of NULL 
         indicates the normal default.  Any other value 
         indicates the value agreed by the 
         defaultThroughputClassesAssignment facility."
    REFERENCE   
        "ITU-T Rec. X.283 (1997) | ISO/IEC 10733 : 1998, 
               defaultThroughputClasses ATTRIBUTE"
    ::= { nlmX25PLEEntry 7 }

nlmX25PLEDefaultThroughputClassOutgoing OBJECT-TYPE
    SYNTAX      Integer32
    MAX-ACCESS  read-create
    STATUS      current
    DESCRIPTION 
        "The default throughput class values. A value of NULL 
         indicates the normal default.  Any other value 
         indicates the value agreed by the 
         defaultThroughputClassesAssignment facility."
    REFERENCE   
        "ITU-T Rec. X.283 (1997) | ISO/IEC 10733 : 1998, 
               defaultThroughputClasses ATTRIBUTE"
    ::= { nlmX25PLEEntry 8 }

nlmX25PLEFlowControlParameterNegotiation OBJECT-TYPE
    SYNTAX      TruthValue
    MAX-ACCESS  read-create
    STATUS      current
    DESCRIPTION 
        "The subscription of the flow control parameter 
         negotiation facility as described in ITU-T 
         Recommendation X.2.  When this has the value 'true', 
         the use of flow control parameter negotiation (by 
         specifying values for the window and packet size in 
         call request and accept packets) is permitted.  When it 
         has the value 'false', no such values shall be 
         specified in call request and accept packets, and any 
         values specified in an IVMO or via an internal 
         interface shall be ignored."
    REFERENCE   
        "ITU-T Rec. X.283 (1997) | ISO/IEC 10733 : 1998, 
               flowControlParameterNegotiation ATTRIBUTE"
    ::= { nlmX25PLEEntry 9 }

--  nlmX25PLEDefaultPacketSizes                 OCTET STRING
nlmX25PLEDefaultPacketSizeIncoming OBJECT-TYPE
    SYNTAX      Unsigned32
    MAX-ACCESS  read-create
    STATUS      current
    DESCRIPTION 
        "The default value of the packet sizes. A value of NULL 
         indicates the ISO/IEC 8208 or ITU-T Rec. X.25 default 
         value of 128.  Any other value indicates the value 
         agreed by the nonstandard default packet sizes 
         facility."
    REFERENCE   
        "ITU-T Rec. X.283 (1997) | ISO/IEC 10733 : 1998, 
               defaultPacketSizes ATTRIBUTE"
    ::= { nlmX25PLEEntry 10 }

nlmX25PLEDefaultPacketSizeOutgoing OBJECT-TYPE
    SYNTAX      Unsigned32
    MAX-ACCESS  read-create
    STATUS      current
    DESCRIPTION 
        "The default value of the packet sizes. A value of NULL 
         indicates the ISO/IEC 8208 or ITU-T Rec. X.25 default 
         value of 128.  Any other value indicates the value 
         agreed by the nonstandard default packet sizes 
         facility."
    REFERENCE   
        "ITU-T Rec. X.283 (1997) | ISO/IEC 10733 : 1998, 
               defaultPacketSizes ATTRIBUTE"
    ::= { nlmX25PLEEntry 12 }

--  nlmX25PLEDefaultWindowSizes                 OCTET STRING
nlmX25PLEDefaultWindowSizeIncoming OBJECT-TYPE
    SYNTAX      Unsigned32
    MAX-ACCESS  read-create
    STATUS      current
    DESCRIPTION 
        "The default value of the window sizes. A value of NULL 
         indicates the ITU-T Recommendation | International 
         Standard default value of 2. Any other value indicates 
         the value agreed by the nonstandard default window 
         sizes facility."
    REFERENCE   
        "ITU-T Rec. X.283 (1997) | ISO/IEC 10733 : 1998, 
               defaultWindowSizes ATTRIBUTE"
    ::= { nlmX25PLEEntry 13 }

nlmX25PLEDefaultWindowSizeOutgoing OBJECT-TYPE
    SYNTAX      Unsigned32
    MAX-ACCESS  read-create
    STATUS      current
    DESCRIPTION 
        "The default value of the window sizes. A value of NULL 
         indicates the ITU-T Recommendation | International 
         Standard default value of 2. Any other value indicates 
         the value agreed by the nonstandard default window 
         sizes facility."
    REFERENCE   
        "ITU-T Rec. X.283 (1997) | ISO/IEC 10733 : 1998, 
               defaultWindowSizes ATTRIBUTE"
    ::= { nlmX25PLEEntry 14 }

nlmX25PLEThroughputClassNegotiation OBJECT-TYPE
    SYNTAX      TruthValue
    MAX-ACCESS  read-create
    STATUS      current
    DESCRIPTION 
        "The subscription of the throughput class negotiation 
         facility as described in ITU-T Recommendation X.2. 
         Expressed as a boolean where a value of 'True' 
         indicates subscription and a value of 'False' indicates 
         non-subscription."
    REFERENCE   
        "ITU-T Rec. X.283 (1997) | ISO/IEC 10733 : 1998, 
               throughputClassNegotiation ATTRIBUTE"
    ::= { nlmX25PLEEntry 15 }

nlmX25PLESnServiceProvider OBJECT-TYPE
    SYNTAX      LocalDistinguishedName
    MAX-ACCESS  read-create
    STATUS      current
    DESCRIPTION 
        "Distinguished name of the SN service provider MO. This 
         attribute identifies the subnetwork entity to be used 
         to support the linkage, when enabled. The subnetwork 
         service provider may be in the Datalink Layer, or it 
         may be in the Network Layer (for example when operating 
         ITU-T Rec. X.233 | ISO/IEC 8473-1 over the ISO/IEC 8208 
         or ITU-T Rec. X.25 SNDCF)."
    REFERENCE   
        "ITU-T Rec. X.283 (1997) | ISO/IEC 10733 : 1998, 
               sN-ServiceProvider ATTRIBUTE"
    ::= { nlmX25PLEEntry 16 }

nlmX25PLESnSAP OBJECT-TYPE
    SYNTAX      LocalDistinguishedName
    MAX-ACCESS  read-create
    STATUS      current
    DESCRIPTION 
        "Distinguished name of the service provider SAP MO (if 
         present). This is obtained via an internal interface 
         when the linkage is enabled. The sN-SAP may be 
         a relationship to an SAP MO in the Datalink Layer, or 
         it may be a relationship to another Managed Object 
         within the Network Layer which is not an SAP MO. For 
         example, when operating ITU-T Rec. X.233 | ISO/IEC 
         8473-1 over the ISO/IEC 8208 or ITU-T Rec. X.25 SNDCF, 
         it is a relationship to the same x25PLE-DTE MO which is 
         pointed to by the sN-ServiceProvider Attribute."
    REFERENCE   
        "ITU-T Rec. X.283 (1997) | ISO/IEC 10733 : 1998, 
               sN-SAP ATTRIBUTE"
    ::= { nlmX25PLEEntry 17 }

--  nlmX25PLELogicalChannelAssignments          OCTET STRING
nlmX25PLELogicalChannelAssignmentsPVC OBJECT-TYPE
    SYNTAX      LogicalChannelIds
    MAX-ACCESS  read-create
    STATUS      current
    DESCRIPTION 
        "Represents the logical channel assignments of this PLE, 
         expressed as a four-tuple where the values represent 
         the set (with maximum permitted cardinality (LIC - 1), 
         minimum required cardinality of zero) of PVC channels 
         (with maximum value (LIC - 1), and minimum value 1) 
         assigned, the incoming channel range, the two-way 
         channel range, the outgoing channel range, 
         respectively.  The presence of each of the ranges shall 
         be optional.  Absence of a particular range shall 
         signify that there are no channels of that type 
         assigned.  Within each range, the low value shall be 
         less than or equal to the high value, and there shall 
         be no value in any set or range which is greater than 
         or equal to a value in a subsequent range when ordered 
         as above.  This attribute is subject to the rules for 
         logical assignments described in 3.7 of ISO/IEC 8208 or 
         ITU-T Rec. X.25."
    REFERENCE   
        "ITU-T Rec. X.283 (1997) | ISO/IEC 10733 : 1998, 
               logicalChannelAssignments ATTRIBUTE"
    ::= { nlmX25PLEEntry 18 }

nlmX25PLELogicalChannelAssignmentsIC OBJECT-TYPE
    SYNTAX      LogicalChannelRange
    MAX-ACCESS  read-create
    STATUS      current
    DESCRIPTION 
        "Represents the logical channel assignments of this PLE, 
         expressed as a four-tuple where the values represent 
         the set (with maximum permitted cardinality (LIC - 1), 
         minimum required cardinality of zero) of PVC channels 
         (with maximum value (LIC - 1), and minimum value 1) 
         assigned, the incoming channel range, the two-way 
         channel range, the outgoing channel range, 
         respectively.  The presence of each of the ranges shall 
         be optional.  Absence of a particular range shall 
         signify that there are no channels of that type 
         assigned.  Within each range, the low value shall be 
         less than or equal to the high value, and there shall 
         be no value in any set or range which is greater than 
         or equal to a value in a subsequent range when ordered 
         as above.  This attribute is subject to the rules for 
         logical assignments described in 3.7 of ISO/IEC 8208 or 
         ITU-T Rec. X.25."
    REFERENCE   
        "ITU-T Rec. X.283 (1997) | ISO/IEC 10733 : 1998, 
               logicalChannelAssignments ATTRIBUTE"
    ::= { nlmX25PLEEntry 19 }

nlmX25PLELogicalChannelAssignments2W OBJECT-TYPE
    SYNTAX      LogicalChannelRange
    MAX-ACCESS  read-create
    STATUS      current
    DESCRIPTION 
        "Represents the logical channel assignments of this PLE, 
         expressed as a four-tuple where the values represent 
         the set (with maximum permitted cardinality (LIC - 1), 
         minimum required cardinality of zero) of PVC channels 
         (with maximum value (LIC - 1), and minimum value 1) 
         assigned, the incoming channel range, the two-way 
         channel range, the outgoing channel range, 
         respectively.  The presence of each of the ranges shall 
         be optional.  Absence of a particular range shall 
         signify that there are no channels of that type 
         assigned.  Within each range, the low value shall be 
         less than or equal to the high value, and there shall 
         be no value in any set or range which is greater than 
         or equal to a value in a subsequent range when ordered 
         as above.  This attribute is subject to the rules for 
         logical assignments described in 3.7 of ISO/IEC 8208 or 
         ITU-T Rec. X.25."
    REFERENCE   
        "ITU-T Rec. X.283 (1997) | ISO/IEC 10733 : 1998, 
               logicalChannelAssignments ATTRIBUTE"
    ::= { nlmX25PLEEntry 20 }

nlmX25PLELogicalChannelAssignmentsOG OBJECT-TYPE
    SYNTAX      LogicalChannelRange
    MAX-ACCESS  read-create
    STATUS      current
    DESCRIPTION 
        "Represents the logical channel assignments of this PLE, 
         expressed as a four-tuple where the values represent 
         the set (with maximum permitted cardinality (LIC - 1), 
         minimum required cardinality of zero) of PVC channels 
         (with maximum value (LIC - 1), and minimum value 1) 
         assigned, the incoming channel range, the two-way 
         channel range, the outgoing channel range, 
         respectively.  The presence of each of the ranges shall 
         be optional.  Absence of a particular range shall 
         signify that there are no channels of that type 
         assigned.  Within each range, the low value shall be 
         less than or equal to the high value, and there shall 
         be no value in any set or range which is greater than 
         or equal to a value in a subsequent range when ordered 
         as above.  This attribute is subject to the rules for 
         logical assignments described in 3.7 of ISO/IEC 8208 or 
         ITU-T Rec. X.25."
    REFERENCE   
        "ITU-T Rec. X.283 (1997) | ISO/IEC 10733 : 1998, 
               logicalChannelAssignments ATTRIBUTE"
    ::= { nlmX25PLEEntry 21 }

nlmX25PLERowStatus OBJECT-TYPE
    SYNTAX      RowStatus
    MAX-ACCESS  read-create
    STATUS      current
    DESCRIPTION 
        ""
    REFERENCE   
        "ITU-T Rec. X.283 (1997) | ISO/IEC 10733 : 1998, 
               x25PLE-networkSubsystem-Management NAME BINDING"
    ::= { nlmX25PLEEntry 22 }


-- ==========================================

nlmX25PLEIVMOTable OBJECT-TYPE
    SYNTAX      SEQUENCE OF NlmX25PLEIVMOEntry
    MAX-ACCESS  not-accessible
    STATUS      current
    DESCRIPTION 
        ""
    REFERENCE   
        "ITU-T Rec. X.283 (1997) | ISO/IEC 10733 : 1998, 
               x25PLEIVMO MANAGED OBJECT CLASS"
    ::= { nlmX25PLE 2 }

nlmX25PLEIVMOEntry OBJECT-TYPE
    SYNTAX      NlmX25PLEIVMOEntry
    MAX-ACCESS  not-accessible
    STATUS      current
    DESCRIPTION 
        "5.10.2 The X.25 PLE initial values managed object
         
         This MO class is never instantiated. It serves as 
         a generic x25PLE IVMO from which both the 
         x25PLEIVMO-DTE and x25PLEIVMO-DCE MO classes are 
         derived.
         
         Note that the values of the x25PLEIVMOId naming 
         attribute are required to be unique across all 
         instances of MOs derived from this, which have a common 
         superior."
    REFERENCE   
        "ITU-T Rec. X.283 (1997) | ISO/IEC 10733 : 1998, 
               x25PLEIVMO MANAGED OBJECT"
    INDEX       { nlmX25PLEIVMOId }
    ::= { nlmX25PLEIVMOTable 1 }

NlmX25PLEIVMOEntry ::= SEQUENCE {
    nlmX25PLEIVMOId                                 SimpleNameType,
    nlmX25PLEIVMODefaultPacketSizeIncoming          Unsigned32,
    nlmX25PLEIVMODefaultPacketSizeOutgoing          Unsigned32,
    nlmX25PLEIVMODefaultThroughputClassIncoming     Integer32,
    nlmX25PLEIVMODefaultThroughputClassOutgoing     Integer32,
    nlmX25PLEIVMODefaultWindowSizeIncoming          Unsigned32,
    nlmX25PLEIVMODefaultWindowSizeOutgoing          Unsigned32,
    nlmX25PLEIVMOFlowControlParameterNegotiation    TruthValue,
    nlmX25PLEIVMOLocalDTEAddress                    DTEAddress,
    nlmX25PLEIVMOLogicalChannelAssignmentsPVC       LogicalChannelIds,
    nlmX25PLEIVMOLogicalChannelAssignmentsIC        LogicalChannelRange,
    nlmX25PLEIVMOLogicalChannelAssignments2W        LogicalChannelRange,
    nlmX25PLEIVMOLogicalChannelAssignmentsOG        LogicalChannelRange,
    nlmX25PLEIVMOSnServiceProvider                  LocalDistinguishedName,
    nlmX25PLEIVMOThroughputClassNegotiation         TruthValue,
    nlmX25PLEIVMOx25PLEMode                         X25PLEMode
}

nlmX25PLEIVMOId OBJECT-TYPE
    SYNTAX      SimpleNameType
    MAX-ACCESS  not-accessible
    STATUS      current
    DESCRIPTION 
        "The name of this instance of x25PLE IVMO."
    REFERENCE   
        "ITU-T Rec. X.283 (1997) | ISO/IEC 10733 : 1998, 
                x25PLEIVMOId ATTRIBUTE"
    ::= { nlmX25PLEIVMOEntry 1 }

nlmX25PLEIVMODefaultPacketSizeIncoming OBJECT-TYPE
    SYNTAX      Unsigned32
    MAX-ACCESS  read-create
    STATUS      current
    DESCRIPTION 
        "The default value of the packet sizes. A value of NULL 
         indicates the ISO/IEC 8208 or ITU-T Rec. X.25 default 
         value of 128.  Any other value indicates the value 
         agreed by the nonstandard default packet sizes 
         facility."
    REFERENCE   
        "ITU-T Rec. X.283 (1997) | ISO/IEC 10733 : 1998, 
                defaultPacketSizes ATTRIBUTE"
    DEFVAL  { 128 }
    ::= { nlmX25PLEIVMOEntry 2 }

nlmX25PLEIVMODefaultPacketSizeOutgoing OBJECT-TYPE
    SYNTAX      Unsigned32
    MAX-ACCESS  read-create
    STATUS      current
    DESCRIPTION 
        "The default value of the packet sizes. A value of NULL 
         indicates the ISO/IEC 8208 or ITU-T Rec. X.25 default 
         value of 128.  Any other value indicates the value 
         agreed by the nonstandard default packet sizes 
         facility."
    REFERENCE   
        "ITU-T Rec. X.283 (1997) | ISO/IEC 10733 : 1998, 
                defaultPacketSizes ATTRIBUTE"
    DEFVAL  { 128 }
    ::= { nlmX25PLEIVMOEntry 3 }

nlmX25PLEIVMODefaultThroughputClassIncoming OBJECT-TYPE
    SYNTAX      Integer32
    MAX-ACCESS  read-create
    STATUS      current
    DESCRIPTION 
        "The default throughput class values. A value of NULL 
         indicates the normal default.  Any other value 
         indicates the value agreed by the 
         defaultThroughputClassesAssignment facility."
    REFERENCE   
        "ITU-T Rec. X.283 (1997) | ISO/IEC 10733 : 1998, 
                defaultThroughputClasses ATTRIBUTE"
    DEFVAL  { 0 }
    ::= { nlmX25PLEIVMOEntry 4 }

nlmX25PLEIVMODefaultThroughputClassOutgoing OBJECT-TYPE
    SYNTAX      Integer32
    MAX-ACCESS  read-create
    STATUS      current
    DESCRIPTION 
        "The default throughput class values. A value of NULL 
         indicates the normal default.  Any other value 
         indicates the value agreed by the 
         defaultThroughputClassesAssignment facility."
    REFERENCE   
        "ITU-T Rec. X.283 (1997) | ISO/IEC 10733 : 1998, 
                defaultThroughputClasses ATTRIBUTE"
    DEFVAL  { 0 }
    ::= { nlmX25PLEIVMOEntry 5 }

nlmX25PLEIVMODefaultWindowSizeIncoming OBJECT-TYPE
    SYNTAX      Unsigned32
    MAX-ACCESS  read-create
    STATUS      current
    DESCRIPTION 
        "The default value of the window sizes. A value of NULL 
         indicates the ITU-T Recommendation | International 
         Standard default value of 2. Any other value indicates 
         the value agreed by the nonstandard default window 
         sizes facility."
    REFERENCE   
        "ITU-T Rec. X.283 (1997) | ISO/IEC 10733 : 1998, 
                defaultWindowSizes ATTRIBUTE"
    DEFVAL      { 2 }
    ::= { nlmX25PLEIVMOEntry 6 }

nlmX25PLEIVMODefaultWindowSizeOutgoing OBJECT-TYPE
    SYNTAX      Unsigned32
    MAX-ACCESS  read-create
    STATUS      current
    DESCRIPTION 
        "The default value of the window sizes. A value of NULL 
         indicates the ITU-T Recommendation | International 
         Standard default value of 2. Any other value indicates 
         the value agreed by the nonstandard default window 
         sizes facility."
    REFERENCE   
        "ITU-T Rec. X.283 (1997) | ISO/IEC 10733 : 1998, 
                defaultWindowSizes ATTRIBUTE"
    DEFVAL      { 2 }
    ::= { nlmX25PLEIVMOEntry 7 }

nlmX25PLEIVMOFlowControlParameterNegotiation OBJECT-TYPE
    SYNTAX      TruthValue
    MAX-ACCESS  read-create
    STATUS      current
    DESCRIPTION 
        "The subscription of the flow control parameter 
         negotiation facility as described in ITU-T 
         Recommendation X.2.  When this has the value 'true', 
         the use of flow control parameter negotiation (by 
         specifying values for the window and packet size in 
         call request and accept packets) is permitted.  When it 
         has the value 'false', no such values shall be 
         specified in call request and accept packets, and any 
         values specified in an IVMO or via an internal 
         interface shall be ignored."
    REFERENCE   
        "ITU-T Rec. X.283 (1997) | ISO/IEC 10733 : 1998, 
                flowControlParameterNegotiation ATTRIBUTE"
    ::= { nlmX25PLEIVMOEntry 8 }

nlmX25PLEIVMOLocalDTEAddress OBJECT-TYPE
    SYNTAX      DTEAddress
    MAX-ACCESS  read-create
    STATUS      current
    DESCRIPTION 
        "The full DTE address of this PLE expressed as an X.121, 
         E.164, etc. address."
    REFERENCE   
        "ITU-T Rec. X.283 (1997) | ISO/IEC 10733 : 1998, 
                localDTEAddress ATTRIBUTE"
    ::= { nlmX25PLEIVMOEntry 9 }

nlmX25PLEIVMOLogicalChannelAssignmentsPVC OBJECT-TYPE
    SYNTAX      LogicalChannelIds
    MAX-ACCESS  read-create
    STATUS      current
    DESCRIPTION 
        "Represents the logical channel assignments of this PLE, 
         expressed as a four-tuple where the values represent 
         the set (with maximum permitted cardinality (LIC - 1), 
         minimum required cardinality of zero) of PVC channels 
         (with maximum value (LIC - 1), and minimum value 1) 
         assigned, the incoming channel range, the two-way 
         channel range, the outgoing channel range, 
         respectively.  The presence of each of the ranges shall 
         be optional.  Absence of a particular range shall 
         signify that there are no channels of that type 
         assigned.  Within each range, the low value shall be 
         less than or equal to the high value, and there shall 
         be no value in any set or range which is greater than 
         or equal to a value in a subsequent range when ordered 
         as above.  This attribute is subject to the rules for 
         logical assignments described in 3.7 of ISO/IEC 8208 or 
         ITU-T Rec. X.25."
    REFERENCE   
        "ITU-T Rec. X.283 (1997) | ISO/IEC 10733 : 1998, 
                logicalChannelAssignments ATTRIBUTE"
    ::= { nlmX25PLEIVMOEntry 10 }

nlmX25PLEIVMOLogicalChannelAssignmentsIC OBJECT-TYPE
    SYNTAX      LogicalChannelRange
    MAX-ACCESS  read-create
    STATUS      current
    DESCRIPTION 
        "Represents the logical channel assignments of this PLE, 
         expressed as a four-tuple where the values represent 
         the set (with maximum permitted cardinality (LIC - 1), 
         minimum required cardinality of zero) of PVC channels 
         (with maximum value (LIC - 1), and minimum value 1) 
         assigned, the incoming channel range, the two-way 
         channel range, the outgoing channel range, 
         respectively.  The presence of each of the ranges shall 
         be optional.  Absence of a particular range shall 
         signify that there are no channels of that type 
         assigned.  Within each range, the low value shall be 
         less than or equal to the high value, and there shall 
         be no value in any set or range which is greater than 
         or equal to a value in a subsequent range when ordered 
         as above.  This attribute is subject to the rules for 
         logical assignments described in 3.7 of ISO/IEC 8208 or 
         ITU-T Rec. X.25."
    REFERENCE   
        "ITU-T Rec. X.283 (1997) | ISO/IEC 10733 : 1998, 
                logicalChannelAssignments ATTRIBUTE"
    ::= { nlmX25PLEIVMOEntry 11 }

nlmX25PLEIVMOLogicalChannelAssignments2W OBJECT-TYPE
    SYNTAX      LogicalChannelRange
    MAX-ACCESS  read-create
    STATUS      current
    DESCRIPTION 
        "Represents the logical channel assignments of this PLE, 
         expressed as a four-tuple where the values represent 
         the set (with maximum permitted cardinality (LIC - 1), 
         minimum required cardinality of zero) of PVC channels 
         (with maximum value (LIC - 1), and minimum value 1) 
         assigned, the incoming channel range, the two-way 
         channel range, the outgoing channel range, 
         respectively.  The presence of each of the ranges shall 
         be optional.  Absence of a particular range shall 
         signify that there are no channels of that type 
         assigned.  Within each range, the low value shall be 
         less than or equal to the high value, and there shall 
         be no value in any set or range which is greater than 
         or equal to a value in a subsequent range when ordered 
         as above.  This attribute is subject to the rules for 
         logical assignments described in 3.7 of ISO/IEC 8208 or 
         ITU-T Rec. X.25."
    REFERENCE   
        "ITU-T Rec. X.283 (1997) | ISO/IEC 10733 : 1998, 
                logicalChannelAssignments ATTRIBUTE"
    ::= { nlmX25PLEIVMOEntry 12 }

nlmX25PLEIVMOLogicalChannelAssignmentsOG OBJECT-TYPE
    SYNTAX      LogicalChannelRange
    MAX-ACCESS  read-create
    STATUS      current
    DESCRIPTION 
        "Represents the logical channel assignments of this PLE, 
         expressed as a four-tuple where the values represent 
         the set (with maximum permitted cardinality (LIC - 1), 
         minimum required cardinality of zero) of PVC channels 
         (with maximum value (LIC - 1), and minimum value 1) 
         assigned, the incoming channel range, the two-way 
         channel range, the outgoing channel range, 
         respectively.  The presence of each of the ranges shall 
         be optional.  Absence of a particular range shall 
         signify that there are no channels of that type 
         assigned.  Within each range, the low value shall be 
         less than or equal to the high value, and there shall 
         be no value in any set or range which is greater than 
         or equal to a value in a subsequent range when ordered 
         as above.  This attribute is subject to the rules for 
         logical assignments described in 3.7 of ISO/IEC 8208 or 
         ITU-T Rec. X.25."
    REFERENCE   
        "ITU-T Rec. X.283 (1997) | ISO/IEC 10733 : 1998, 
                logicalChannelAssignments ATTRIBUTE"
    ::= { nlmX25PLEIVMOEntry 13 }

nlmX25PLEIVMOSnServiceProvider OBJECT-TYPE
    SYNTAX      LocalDistinguishedName
    MAX-ACCESS  read-create
    STATUS      current
    DESCRIPTION 
        "Distinguished name of the SN service provider MO. This 
         attribute identifies the subnetwork entity to be used 
         to support the linkage, when enabled. The subnetwork 
         service provider may be in the Datalink Layer, or it 
         may be in the Network Layer (for example when operating 
         ITU-T Rec. X.233 | ISO/IEC 8473-1 over the ISO/IEC 8208 
         or ITU-T Rec. X.25 SNDCF)."
    REFERENCE   
        "ITU-T Rec. X.283 (1997) | ISO/IEC 10733 : 1998, 
                sN-ServiceProvider ATTRIBUTE"
    ::= { nlmX25PLEIVMOEntry 14 }

nlmX25PLEIVMOThroughputClassNegotiation OBJECT-TYPE
    SYNTAX      TruthValue
    MAX-ACCESS  read-create
    STATUS      current
    DESCRIPTION 
        "The subscription of the throughput class negotiation 
         facility as described in ITU-T Recommendation X.2. 
         Expressed as a boolean where a value of 'True' 
         indicates subscription and a value of 'False' indicates 
         non-subscription."
    REFERENCE   
        "ITU-T Rec. X.283 (1997) | ISO/IEC 10733 : 1998, 
                throughputClassNegotiation ATTRIBUTE"
    ::= { nlmX25PLEIVMOEntry 15 }

nlmX25PLEIVMOx25PLEMode OBJECT-TYPE
    SYNTAX      X25PLEMode
    MAX-ACCESS  read-create
    STATUS      current
    DESCRIPTION 
        "The DCE/DTE mode in which the X.25 PLE is currently 
         operating.  One of the following modes of operation may 
         be indicated.  dTE(0) DTE mode applying to both ITU-T 
         Rec.  X.25 and ISO/IEC 8208 operation, dCE(1) DCE mode 
         applying to ITU-T Rec.  X.25 operation only, and 
         dCEasDTE(2) DTE acting as a DCE applying to ISO/IEC 
         8208 operation only."
    REFERENCE   
        "ITU-T Rec. X.283 (1997) | ISO/IEC 10733 : 1998, 
                x25PLEMode ATTRIBUTE"
    ::= { nlmX25PLEIVMOEntry 16 }

-- ==========================================

nlmX25PLEdTETable OBJECT-TYPE
    SYNTAX      SEQUENCE OF NlmX25PLEdTEEntry
    MAX-ACCESS  not-accessible
    STATUS      current
    DESCRIPTION 
        ""
    REFERENCE   
        "ITU-T Rec. X.283 (1997) | ISO/IEC 10733 : 1998, 
               x25PLE-DTE MANAGED OBJECT CLASS"
    ::= { nlmX25PLE 3 }

nlmX25PLEdTEEntry OBJECT-TYPE
    SYNTAX      NlmX25PLEdTEEntry
    MAX-ACCESS  not-accessible
    STATUS      current
    DESCRIPTION 
        "5.10.3 The X.25 PLE DTE managed object
         
         There may be multiple instances of these MOs within 
         a system, corresponding to Multiple X.25 PLEs.
         
         The definition of this MO permits it to be created and 
         deleted explicitly by management operation or to be 
         created and deleted automatically as part of system 
         operation. When an instance of this MO is created 
         automatically, an instance of the x25PLEIVMO-DTE may be 
         used as the source of the initial values for attributes 
         of this MO.
         
         When the x25 PLE is operable, the operationalState 
         shall have the value 'enabled'; otherwise it shall have 
         the value 'disabled'.  Transitions of operationalState 
         shall be reported using the stateChange notification."
    REFERENCE   
        "ITU-T Rec. X.283 (1997) | ISO/IEC 10733 : 1998, 
               x25PLE-DTE MANAGED OBJECT"
    AUGMENTS    { nlmX25PLEEntry }
    ::= { nlmX25PLEdTETable 1 }

NlmX25PLEdTEEntry ::= SEQUENCE {
    nlmX25PLEdTECallDeflectionSubscription              TruthValue,
    nlmX25PLEdTECallRequestResponseTimer                MilliSeconds,
    nlmX25PLEdTEExtendedPacketSequenceNumbering         PacketSequencing,
    nlmX25PLEdTEMaxActiveCircuits                       Unsigned32,
    nlmX25PLEdTEMinimumRecallTimer                      MilliSeconds,
    nlmX25PLEdTEResetRequestResponseTimer               MilliSeconds,
    nlmX25PLEdTERestartRequestRetransmissionCount       Unsigned32,
    nlmX25PLEdTERestartRequestResponseTimer             MilliSeconds,
    nlmX25PLEdTEClearRequestResponseTimer               MilliSeconds,
    nlmX25PLEdTEInterruptResponseTimer                  MilliSeconds,
    nlmX25PLEdTEResetRequestRetransmissionCount         Unsigned32,
    nlmX25PLEdTEClearRequestRetransmissionCount         Unsigned32,
    nlmX25PLEdTECallAttempts                            Counter64,
    nlmX25PLEdTEProtocolErrorsDetectedLocally           Counter64,
    nlmX25PLEdTEProtocolErrorsAccusedOf                 Counter64,
    nlmX25PLEdTECallEstablishmentRetryCountsExceeded    Counter64,
-- dTEX25PLECounters-P PACKAGE
    nlmX25PLEdTEOctetsReceivedCounter                   Counter64,
    nlmX25PLEdTEOctetsSentCounter                       Counter64,
    nlmX25PLEdTECallTimeouts                            Counter64,
    nlmX25PLEdTECallsConnected                          Counter64,
    nlmX25PLEdTEClearCountsExceeded                     Counter64,
    nlmX25PLEdTEClearTimeouts                           Counter64,
    nlmX25PLEdTEDataPacketsReceived                     Counter64,
    nlmX25PLEdTEDataPacketsSent                         Counter64,
    nlmX25PLEdTEDataRetransmissionTimerExpiries         Counter64,
    nlmX25PLEdTEProviderInitiatedResets                 Counter64,
    nlmX25PLEdTEProviderInitiatedDisconnects            Counter64,
    nlmX25PLEdTERemotelyInitiatedResets                 Counter64,
    nlmX25PLEdTERemotelyInitiatedRestarts               Counter64,
    nlmX25PLEdTEResetTimeouts                           Counter64,
    nlmX25PLEdTERestartCountsExceeded                   Counter64,
-- receivingWindowRotationRecoveryProcedures-P PACKAGE
    nlmX25PLEdTEWindowStatusTransmissionTimer           MilliSeconds,
-- transmittingWindowRotationRecoveryProcedures-P PACKAGE
    nlmX25PLEdTEWindowRotationTimer                     MilliSeconds,
    nlmX25PLEdTEDataPacketRetransmissionCount           Unsigned32,
-- packetRetransmissionProcedures-P PACKAGE
    nlmX25PLEdTERejectResponseTimer                     MilliSeconds,
    nlmX25PLEdTERejectRetransmissionCount               Unsigned32,
-- onlineRegistration-P PACKAGE
    nlmX25PLEdTERegistrationRequestResponseTimer        MilliSeconds,
    nlmX25PLEdTERegistrationRequestRetransmissionCount  Unsigned32,
    nlmX25PLEdTERegistrationPermitted                   TruthValue,
--
    nlmX25PLEdTERowStatus                               RowStatus
}

nlmX25PLEdTECallDeflectionSubscription OBJECT-TYPE
    SYNTAX      TruthValue
    MAX-ACCESS  read-create
    STATUS      current
    DESCRIPTION 
        "The subscription of the call deflection facility as 
         described in ITU-T Recommendation X.2.  Expressed as 
         a boolean where a value of 'True' indicates 
         subscription and a value of 'False' indicates 
         non-subscription."
    REFERENCE   
        "ITU-T Rec. X.283 (1997) | ISO/IEC 10733 : 1998, 
               callDeflectionSubscription ATTRIBUTE"
    DEFVAL      { false }
    ::= { nlmX25PLEdTEEntry 1 }

nlmX25PLEdTECallRequestResponseTimer OBJECT-TYPE
    SYNTAX      MilliSeconds
    MAX-ACCESS  read-create
    STATUS      current
    DESCRIPTION 
        "Value for Timer T21 (Call Request Response Timer) in 
         seconds."
    REFERENCE   
        "ITU-T Rec. X.283 (1997) | ISO/IEC 10733 : 1998, 
               callRequestResponseTimer ATTRIBUTE"
    DEFVAL      { 200000 } -- 200 seconds
    ::= { nlmX25PLEdTEEntry 2 }

nlmX25PLEdTEExtendedPacketSequenceNumbering OBJECT-TYPE
    SYNTAX      PacketSequencing
    MAX-ACCESS  read-create
    STATUS      current
    DESCRIPTION 
        "The modulo of the packet sequence number space.  
         Expressed as an integer.  The ITU-T Recommendation 
         | International Standard only requires support for at 
         least one of the two values 8 and 128, but it is 
         possible that some future revision may extend the 
         range.  A system is only required to support the 
         setting of values which are also required by the 
         protocol standard.  A system shall return an error when 
         an attempt is made to set the value to a value which is 
         not supported by that system."
    REFERENCE   
        "ITU-T Rec. X.283 (1997) | ISO/IEC 10733 : 1998, 
               extendedPacketSequenceNumbering ATTRIBUTE"
    DEFVAL      { 128 }
    ::= { nlmX25PLEdTEEntry 3 }

nlmX25PLEdTEMaxActiveCircuits OBJECT-TYPE
    SYNTAX      Unsigned32
    MAX-ACCESS  read-create
    STATUS      current
    DESCRIPTION 
        "The maximum number of active circuits permitted on this 
         PLE. When the NULL value is specified, the maximum 
         number of active circuits shall be limited only by the 
         resources available to the entity."
    REFERENCE   
        "ITU-T Rec. X.283 (1997) | ISO/IEC 10733 : 1998, 
               maxActiveCircuits ATTRIBUTE"
    DEFVAL      { 0 }
    ::= { nlmX25PLEdTEEntry 4 }

nlmX25PLEdTEMinimumRecallTimer OBJECT-TYPE
    SYNTAX      MilliSeconds
    MAX-ACCESS  read-create
    STATUS      current
    DESCRIPTION 
        "Minimum time in seconds before recall permitted. This 
         timer determines the minimum interval (in seconds) 
         which shall elapse following an unsuccessful first call 
         attempt before a subsequent call attempt is permitted."
    REFERENCE   
        "ITU-T Rec. X.283 (1997) | ISO/IEC 10733 : 1998, 
               minimumRecallTimer ATTRIBUTE"
    DEFVAL      { 0 }
    ::= { nlmX25PLEdTEEntry 5 }

nlmX25PLEdTEResetRequestResponseTimer OBJECT-TYPE
    SYNTAX      MilliSeconds
    MAX-ACCESS  read-create
    STATUS      current
    DESCRIPTION 
        "Value for Timer T22 (Reset Request Response Timer) in 
         seconds."
    REFERENCE   
        "ITU-T Rec. X.283 (1997) | ISO/IEC 10733 : 1998, 
               resetRequestResponseTimer ATTRIBUTE"
    DEFVAL      { 180000 } -- 180 seconds
    ::= { nlmX25PLEdTEEntry 6 }

nlmX25PLEdTERestartRequestRetransmissionCount OBJECT-TYPE
    SYNTAX      Unsigned32
    MAX-ACCESS  read-create
    STATUS      current
    DESCRIPTION 
        "Value for count R20 (Restart Request Retransmission 
         Count)."
    REFERENCE   
        "ITU-T Rec. X.283 (1997) | ISO/IEC 10733 : 1998, 
               restartRequestRetransmissionCount ATTRIBUTE"
    DEFVAL      { 1 }
    ::= { nlmX25PLEdTEEntry 7 }

nlmX25PLEdTERestartRequestResponseTimer OBJECT-TYPE
    SYNTAX      MilliSeconds
    MAX-ACCESS  read-create
    STATUS      current
    DESCRIPTION 
        "Value for Timer T20 (Restart Request Response Timer) in 
         seconds."
    REFERENCE   
        "ITU-T Rec. X.283 (1997) | ISO/IEC 10733 : 1998, 
               restartRequestResponseTimer ATTRIBUTE"
    DEFVAL      { 180000 } -- 180 seconds
    ::= { nlmX25PLEdTEEntry 8 }

nlmX25PLEdTEClearRequestResponseTimer OBJECT-TYPE
    SYNTAX      MilliSeconds
    MAX-ACCESS  read-create
    STATUS      current
    DESCRIPTION 
        "Value for Timer T23 (Clear Request Response Timer) in 
         seconds."
    REFERENCE   
        "ITU-T Rec. X.283 (1997) | ISO/IEC 10733 : 1998, 
               clearRequestResponseTimer ATTRIBUTE"
    DEFVAL      { 180000 } -- 180 seconds
    ::= { nlmX25PLEdTEEntry 9 }

nlmX25PLEdTEInterruptResponseTimer OBJECT-TYPE
    SYNTAX      MilliSeconds
    MAX-ACCESS  read-create
    STATUS      current
    DESCRIPTION 
        "Value for Timer T26 (Interrupt Response Timer) in 
         seconds."
    REFERENCE   
        "ITU-T Rec. X.283 (1997) | ISO/IEC 10733 : 1998, 
               interruptResponseTimer ATTRIBUTE"
    DEFVAL      { 180000 } -- 180 seconds
    ::= { nlmX25PLEdTEEntry 10 }

nlmX25PLEdTEResetRequestRetransmissionCount OBJECT-TYPE
    SYNTAX      Unsigned32
    MAX-ACCESS  read-create
    STATUS      current
    DESCRIPTION 
        "Value for count R22 (Reset Request Retransmission 
         Count)."
    REFERENCE   
        "ITU-T Rec. X.283 (1997) | ISO/IEC 10733 : 1998, 
               resetRequestRetransmissionCount ATTRIBUTE"
    DEFVAL      { 1 }
    ::= { nlmX25PLEdTEEntry 11 }

nlmX25PLEdTEClearRequestRetransmissionCount OBJECT-TYPE
    SYNTAX      Unsigned32
    MAX-ACCESS  read-create
    STATUS      current
    DESCRIPTION 
        "Value for count R23 (Clear Request Retransmission 
         Count)."
    REFERENCE   
        "ITU-T Rec. X.283 (1997) | ISO/IEC 10733 : 1998, 
               clearRequestRetransmissionCount ATTRIBUTE"
    DEFVAL      { 1 }
    ::= { nlmX25PLEdTEEntry 12 }

nlmX25PLEdTECallAttempts OBJECT-TYPE
    SYNTAX      Counter64
    MAX-ACCESS  read-only
    STATUS      current
    DESCRIPTION 
        "Counter of the total number of calls attempted."
    REFERENCE   
        "ITU-T Rec. X.283 (1997) | ISO/IEC 10733 : 1998, 
               callAttempts ATTRIBUTE"
    ::= { nlmX25PLEdTEEntry 13 }

nlmX25PLEdTEProtocolErrorsDetectedLocally OBJECT-TYPE
    SYNTAX      Counter64
    MAX-ACCESS  read-only
    STATUS      current
    DESCRIPTION 
        "Counter associated with the 
         protocolErrorDetectedLocally event which generates 
         a communications alarm notification."
    REFERENCE   
        "ITU-T Rec. X.283 (1997) | ISO/IEC 10733 : 1998, 
               protocolErrorsDetectedLocally ATTRIBUTE"
    ::= { nlmX25PLEdTEEntry 14 }

nlmX25PLEdTEProtocolErrorsAccusedOf OBJECT-TYPE
    SYNTAX      Counter64
    MAX-ACCESS  read-only
    STATUS      current
    DESCRIPTION 
        "Counter associated with the accusedOfProtocolError 
         event which generates a communications alarm 
         notification."
    REFERENCE   
        "ITU-T Rec. X.283 (1997) | ISO/IEC 10733 : 1998, 
               protocolErrorsAccusedOf ATTRIBUTE"
    ::= { nlmX25PLEdTEEntry 15 }

nlmX25PLEdTECallEstablishmentRetryCountsExceeded OBJECT-TYPE
    SYNTAX      Counter64
    MAX-ACCESS  read-only
    STATUS      current
    DESCRIPTION 
        "Counter associated with the 
         callEstablishmentRetryCountExceeded event which 
         generates a communications alarm notification."
    REFERENCE   
        "ITU-T Rec. X.283 (1997) | ISO/IEC 10733 : 1998, 
               callEstablishmentRetryCountsExceeded ATTRIBUTE"
    ::= { nlmX25PLEdTEEntry 16 }

-- dTEX25PLECounters-P PACKAGE
nlmX25PLEdTEOctetsReceivedCounter OBJECT-TYPE
    SYNTAX      Counter64
    MAX-ACCESS  read-only
    STATUS      current
    DESCRIPTION 
        "Specifies the total number of user data octets received 
         by the connectionless network protocol state machine."
    REFERENCE   
        "ITU-T Rec. X.721 (1992) | ISO/IEC 10165-2 : 1992, 
               octetsReceivedCounter"
    ::= { nlmX25PLEdTEEntry 17 }

nlmX25PLEdTEOctetsSentCounter OBJECT-TYPE
    SYNTAX      Counter64
    MAX-ACCESS  read-only
    STATUS      current
    DESCRIPTION 
        "Specifies the total number of user data octets sent by 
         the connectionless network protocol state machine."
    REFERENCE   
        "ITU-T Rec. X.721 (1992) | ISO/IEC 10165-2 : 1992, 
               octetsSentCounter"
    ::= { nlmX25PLEdTEEntry 18 }

nlmX25PLEdTECallTimeouts OBJECT-TYPE
    SYNTAX      Counter64
    MAX-ACCESS  read-only
    STATUS      current
    DESCRIPTION 
        "Counter of the number of times timer T21 expiry is 
         experienced by the PLE."
    REFERENCE   
        "ITU-T Rec. X.283 (1997) | ISO/IEC 10733 : 1998, 
               callTimeouts ATTRIBUTE"
    ::= { nlmX25PLEdTEEntry 19 }

nlmX25PLEdTECallsConnected OBJECT-TYPE
    SYNTAX      Counter64
    MAX-ACCESS  read-only
    STATUS      current
    DESCRIPTION 
        "Counter of the total number of calls which have reached 
         the open state."
    REFERENCE   
        "ITU-T Rec. X.283 (1997) | ISO/IEC 10733 : 1998, 
               callsConnected ATTRIBUTE"
    ::= { nlmX25PLEdTEEntry 20 }

nlmX25PLEdTEClearCountsExceeded OBJECT-TYPE
    SYNTAX      Counter64
    MAX-ACCESS  read-only
    STATUS      current
    DESCRIPTION 
        "Counter associated with the clearCountExceeded event 
         which generates a communications alarm notification."
    REFERENCE   
        "ITU-T Rec. X.283 (1997) | ISO/IEC 10733 : 1998, 
               clearCountsExceeded ATTRIBUTE"
    ::= { nlmX25PLEdTEEntry 21 }

nlmX25PLEdTEClearTimeouts OBJECT-TYPE
    SYNTAX      Counter64
    MAX-ACCESS  read-only
    STATUS      current
    DESCRIPTION 
        "Counter of the number of times timer T23 expiry is 
         experienced by the PLE."
    REFERENCE   
        "ITU-T Rec. X.283 (1997) | ISO/IEC 10733 : 1998, 
               clearTimeouts ATTRIBUTE"
    ::= { nlmX25PLEdTEEntry 22 }

nlmX25PLEdTEDataPacketsReceived OBJECT-TYPE
    SYNTAX      Counter64
    MAX-ACCESS  read-only
    STATUS      current
    DESCRIPTION 
        "Counter of the total number of data packets received."
    REFERENCE   
        "ITU-T Rec. X.283 (1997) | ISO/IEC 10733 : 1998, 
               dataPacketsReceived ATTRIBUTE"
    ::= { nlmX25PLEdTEEntry 23 }

nlmX25PLEdTEDataPacketsSent OBJECT-TYPE
    SYNTAX      Counter64
    MAX-ACCESS  read-only
    STATUS      current
    DESCRIPTION 
        "Counter of the total number of data packets sent."
    REFERENCE   
        "ITU-T Rec. X.283 (1997) | ISO/IEC 10733 : 1998, 
               dataPacketsSent ATTRIBUTE"
    ::= { nlmX25PLEdTEEntry 24 }

nlmX25PLEdTEDataRetransmissionTimerExpiries OBJECT-TYPE
    SYNTAX      Counter64
    MAX-ACCESS  read-only
    STATUS      current
    DESCRIPTION 
        "Counter of the number of expiries of timer T25. Returns 
         zero if the option is not implemented."
    REFERENCE   
        "ITU-T Rec. X.283 (1997) | ISO/IEC 10733 : 1998, 
               dataRetransmissionTimerExpiries ATTRIBUTE"
    ::= { nlmX25PLEdTEEntry 25 }

nlmX25PLEdTEProviderInitiatedResets OBJECT-TYPE
    SYNTAX      Counter64
    MAX-ACCESS  read-only
    STATUS      current
    DESCRIPTION 
        "Counter associated with the providerInitiatedReset 
         event which generates a communication alarm 
         notification."
    REFERENCE   
        "ITU-T Rec. X.283 (1997) | ISO/IEC 10733 : 1998, 
               providerInitiatedResets ATTRIBUTE"
    ::= { nlmX25PLEdTEEntry 26 }

nlmX25PLEdTEProviderInitiatedDisconnects OBJECT-TYPE
    SYNTAX      Counter64
    MAX-ACCESS  read-only
    STATUS      current
    DESCRIPTION 
        "Counter for the providerInitiatedDisconnect events 
         which generate communication alarm notifications."
    REFERENCE   
        "ITU-T Rec. X.283 (1997) | ISO/IEC 10733 : 1998, 
               providerInitiatedDisconnects ATTRIBUTE"
    ::= { nlmX25PLEdTEEntry 27 }

nlmX25PLEdTERemotelyInitiatedResets OBJECT-TYPE
    SYNTAX      Counter64
    MAX-ACCESS  read-only
    STATUS      current
    DESCRIPTION 
        "Counter associated with the remotelyInitiatedReset 
         event which generates a communication alarm 
         notification."
    REFERENCE   
        "ITU-T Rec. X.283 (1997) | ISO/IEC 10733 : 1998, 
               remotelyInitiatedResets ATTRIBUTE"
    ::= { nlmX25PLEdTEEntry 28 }

nlmX25PLEdTERemotelyInitiatedRestarts OBJECT-TYPE
    SYNTAX      Counter64
    MAX-ACCESS  read-only
    STATUS      current
    DESCRIPTION 
        "Counter of the number of remotely initiated restarts. 
         This is the total number of remotely initiated 
         (including provider initiated) restarts experienced by 
         the PLE, excluding the restart associated with bringing 
         up the PLE interface."
    REFERENCE   
        "ITU-T Rec. X.283 (1997) | ISO/IEC 10733 : 1998, 
               remotelyInitiatedRestarts ATTRIBUTE"
    ::= { nlmX25PLEdTEEntry 29 }

nlmX25PLEdTEResetTimeouts OBJECT-TYPE
    SYNTAX      Counter64
    MAX-ACCESS  read-only
    STATUS      current
    DESCRIPTION 
        "Counter of the number of timer T22 expiries experienced 
         by the PLE."
    REFERENCE   
        "ITU-T Rec. X.283 (1997) | ISO/IEC 10733 : 1998, 
               resetTimeouts ATTRIBUTE"
    ::= { nlmX25PLEdTEEntry 30 }

nlmX25PLEdTERestartCountsExceeded OBJECT-TYPE
    SYNTAX      Counter64
    MAX-ACCESS  read-only
    STATUS      current
    DESCRIPTION 
        "Counter associated with the restartCountExceeded event 
         which generates a communication alarm notification."
    REFERENCE   
        "ITU-T Rec. X.283 (1997) | ISO/IEC 10733 : 1998, 
               restartCountsExceeded ATTRIBUTE"
    ::= { nlmX25PLEdTEEntry 31 }

-- receivingWindowRotationRecoveryProcedures-P PACKAGE
nlmX25PLEdTEWindowStatusTransmissionTimer OBJECT-TYPE
    SYNTAX      MilliSeconds
    MAX-ACCESS  read-create
    STATUS      current
    DESCRIPTION 
        "Value for Timer T24 (Window Status Transmission Timer) 
         in seconds."
    REFERENCE   
        "ITU-T Rec. X.283 (1997) | ISO/IEC 10733 : 1998, 
               windowStatusTransmissionTimer ATTRIBUTE"
    DEFVAL      { 60000 } -- 60 seconds
    ::= { nlmX25PLEdTEEntry 32 }

-- transmittingWindowRotationRecoveryProcedures-P PACKAGE
nlmX25PLEdTEWindowRotationTimer OBJECT-TYPE
    SYNTAX      MilliSeconds
    MAX-ACCESS  read-create
    STATUS      current
    DESCRIPTION 
        "Default for Timer T25 (Window Rotation Timer) in 
         seconds."
    REFERENCE   
        "ITU-T Rec. X.283 (1997) | ISO/IEC 10733 : 1998, 
               windowRotationTimer ATTRIBUTE"
    DEFVAL      { 200000 } -- 200 seconds
    ::= { nlmX25PLEdTEEntry 33 }

nlmX25PLEdTEDataPacketRetransmissionCount OBJECT-TYPE
    SYNTAX      Unsigned32
    MAX-ACCESS  read-create
    STATUS      current
    DESCRIPTION 
        "Value for count R25 (Data Packet Retransmission 
         Count)."
    REFERENCE   
        "ITU-T Rec. X.283 (1997) | ISO/IEC 10733 : 1998, 
               dataPacketRetransmissionCount ATTRIBUTE"
    DEFVAL      { 0 }
    ::= { nlmX25PLEdTEEntry 34 }

-- packetRetransmissionProcedures-P PACKAGE
nlmX25PLEdTERejectResponseTimer OBJECT-TYPE
    SYNTAX      MilliSeconds
    MAX-ACCESS  read-create
    STATUS      current
    DESCRIPTION 
        "Value for Timer T27 (Reject Response Timer) in 
         seconds."
    REFERENCE   
        "ITU-T Rec. X.283 (1997) | ISO/IEC 10733 : 1998, 
               rejectResponseTimer ATTRIBUTE"
    DEFVAL      { 60000 } -- 60 seconds
    ::= { nlmX25PLEdTEEntry 35 }

nlmX25PLEdTERejectRetransmissionCount OBJECT-TYPE
    SYNTAX      Unsigned32
    MAX-ACCESS  read-create
    STATUS      current
    DESCRIPTION 
        "Value for count R27 (Reject Retransmission Count)."
    REFERENCE   
        "ITU-T Rec. X.283 (1997) | ISO/IEC 10733 : 1998, 
               rejectRetransmissionCount ATTRIBUTE"
    DEFVAL      { 0 }
    ::= { nlmX25PLEdTEEntry 36 }

-- onlineRegistration-P PACKAGE
nlmX25PLEdTERegistrationRequestResponseTimer OBJECT-TYPE
    SYNTAX      MilliSeconds
    MAX-ACCESS  read-create
    STATUS      current
    DESCRIPTION 
        "Value for Timer T28 (Registration Request Response 
         Timer) in seconds."
    REFERENCE   
        "ITU-T Rec. X.283 (1997) | ISO/IEC 10733 : 1998, 
               registrationRequestResponseTimer ATTRIBUTE"
    DEFVAL      { 300000 } -- 300 seconds
    ::= { nlmX25PLEdTEEntry 37 }

nlmX25PLEdTERegistrationRequestRetransmissionCount OBJECT-TYPE
    SYNTAX      Unsigned32
    MAX-ACCESS  read-create
    STATUS      current
    DESCRIPTION 
        "Value for count R28 (Registration Request 
         Retransmission Count)."
    REFERENCE   
        "ITU-T Rec. X.283 (1997) | ISO/IEC 10733 : 1998, 
               registrationRequestRetransmissionCount ATTRIBUTE"
    DEFVAL      { 1 }
    ::= { nlmX25PLEdTEEntry 38 }

nlmX25PLEdTERegistrationPermitted OBJECT-TYPE
    SYNTAX      TruthValue
    MAX-ACCESS  read-create
    STATUS      current
    DESCRIPTION 
        "When true, the use of online facility registration is 
         permitted."
    REFERENCE   
        "ITU-T Rec. X.283 (1997) | ISO/IEC 10733 : 1998, 
               registrationPermitted ATTRIBUTE"
    DEFVAL      { false }
    ::= { nlmX25PLEdTEEntry 39 }

--
nlmX25PLEdTERowStatus OBJECT-TYPE
    SYNTAX      RowStatus
    MAX-ACCESS  read-create
    STATUS      current
    DESCRIPTION 
        ""
    REFERENCE   
        "ITU-T Rec. X.283 (1997) | ISO/IEC 10733 : 1998, 
               x25PLE-networkSubsystem-Management NAME BINDING"
    ::= { nlmX25PLEdTEEntry 40 }


-- ==========================================

nlmX25PLEdTEIVMOTable OBJECT-TYPE
    SYNTAX      SEQUENCE OF NlmX25PLEdTEIVMOEntry
    MAX-ACCESS  not-accessible
    STATUS      current
    DESCRIPTION 
        ""
    REFERENCE   
        "ITU-T Rec. X.283 (1997) | ISO/IEC 10733 : 1998, 
               x25PLEIVMO-DTE MANAGED OBJECT CLASS"
    ::= { nlmX25PLE 4 }

nlmX25PLEdTEIVMOEntry OBJECT-TYPE
    SYNTAX      NlmX25PLEdTEIVMOEntry
    MAX-ACCESS  not-accessible
    STATUS      current
    DESCRIPTION 
        "5.10.3 The X.25 PLE DTE managed object
         
         There may be multiple instances of these MOs within 
         a system, corresponding to Multiple X.25 PLEs.
         
         The definition of this MO permits it to be created and 
         deleted explicitly by management operation or to be 
         created and deleted automatically as part of system 
         operation. When an instance of this MO is created 
         automatically, an instance of the x25PLEIVMO-DTE may be 
         used as the source of the initial values for attributes 
         of this MO.
         
         When the x25 PLE is operable, the operationalState 
         shall have the value 'enabled'; otherwise it shall have 
         the value 'disabled'.  Transitions of operationalState 
         shall be reported using the stateChange notification."
    REFERENCE   
        "ITU-T Rec. X.283 (1997) | ISO/IEC 10733 : 1998, 
               x25PLEIVMO-DTE MANAGED OBJECT CLASS"
    AUGMENTS    { nlmX25PLEIVMOEntry }
    ::= { nlmX25PLEdTEIVMOTable 1 }

NlmX25PLEdTEIVMOEntry ::= SEQUENCE {
    nlmX25PLEdTEIVMOCallDeflectionSubscription              TruthValue,
    nlmX25PLEdTEIVMOCallRequestResponseTimer                MilliSeconds,
    nlmX25PLEdTEIVMOClearRequestResponseTimer               MilliSeconds,
    nlmX25PLEdTEIVMOClearRequestRetransmissionCount         Unsigned32,
    nlmX25PLEdTEIVMOExtendedPacketSequenceNumbering         PacketSequencing,
    nlmX25PLEdTEIVMOInterruptResponseTimer                  MilliSeconds,
    nlmX25PLEdTEIVMOMaxActiveCircuits                       Unsigned32,
    nlmX25PLEdTEIVMOMinimumRecallTimer                      MilliSeconds,
    nlmX25PLEdTEIVMOResetRequestResponseTimer               MilliSeconds,
    nlmX25PLEdTEIVMOResetRequestRetransmissionCount         Unsigned32,
    nlmX25PLEdTEIVMORestartRequestResponseTimer             MilliSeconds,
    nlmX25PLEdTEIVMORestartRequestRetransmissionCount       Unsigned32,
-- receivingWindowRotationRecoveryProcedures-P PACKAGE
    nlmX25PLEdTEIVMOWindowStatusTransmissionTimer           MilliSeconds,
-- transmittingWindowRotationRecoveryProcedures-P PACKAGE
    nlmX25PLEdTEIVMOWindowRotationTimer                     MilliSeconds,
    nlmX25PLEdTEIVMODataPacketRetransmissionCount           Unsigned32,
-- packetRetransmissionProcedures-P PACKAGE
    nlmX25PLEdTEIVMORejectResponseTimer                     MilliSeconds,
    nlmX25PLEdTEIVMORejectRetransmissionCount               Unsigned32,
-- onlineRegistration-P PACKAGE
    nlmX25PLEdTEIVMORegistrationRequestResponseTimer        MilliSeconds,
    nlmX25PLEdTEIVMORegistrationRequestRetransmissionCount  Unsigned32,
    nlmX25PLEdTEIVMORegistrationPermitted                   TruthValue,
    nlmX25PLEdTEIVMORowStatus                               RowStatus
}

nlmX25PLEdTEIVMOCallDeflectionSubscription OBJECT-TYPE
    SYNTAX      TruthValue
    MAX-ACCESS  read-create
    STATUS      current
    DESCRIPTION 
        "The subscription of the call deflection facility as 
         described in ITU-T Recommendation X.2.  Expressed as 
         a boolean where a value of 'True' indicates 
         subscription and a value of 'False' indicates 
         non-subscription."
    REFERENCE   
        "ITU-T Rec. X.283 (1997) | ISO/IEC 10733 : 1998, 
               callDeflectionSubscription ATTRIBUTE"
    DEFVAL      { false }
    ::= { nlmX25PLEdTEIVMOEntry 1 }

nlmX25PLEdTEIVMOCallRequestResponseTimer OBJECT-TYPE
    SYNTAX      MilliSeconds
    UNITS       "ms"
    MAX-ACCESS  read-create
    STATUS      current
    DESCRIPTION 
        "Value for Timer T21 (Call Request Response Timer) in 
         seconds."
    REFERENCE   
        "ITU-T Rec. X.283 (1997) | ISO/IEC 10733 : 1998, 
               callRequestResponseTimer ATTRIBUTE"
    DEFVAL      { 200000 } -- 200 seconds
    ::= { nlmX25PLEdTEIVMOEntry 2 }

nlmX25PLEdTEIVMOClearRequestResponseTimer OBJECT-TYPE
    SYNTAX      MilliSeconds
    UNITS       "ms"
    MAX-ACCESS  read-create
    STATUS      current
    DESCRIPTION 
        "Value for Timer T23 (Clear Request Response Timer) in 
         seconds."
    REFERENCE   
        "ITU-T Rec. X.283 (1997) | ISO/IEC 10733 : 1998, 
               clearRequestResponseTimer ATTRIBUTE"
    DEFVAL      { 180000 } -- 180 seconds
    ::= { nlmX25PLEdTEIVMOEntry 3 }

nlmX25PLEdTEIVMOClearRequestRetransmissionCount OBJECT-TYPE
    SYNTAX      Unsigned32
    MAX-ACCESS  read-create
    STATUS      current
    DESCRIPTION 
        "Value for count R23 (Clear Request Retransmission 
         Count)."
    REFERENCE   
        "ITU-T Rec. X.283 (1997) | ISO/IEC 10733 : 1998, 
               clearRequestRetransmissionCount ATTRIBUTE"
    DEFVAL      { 1 }
    ::= { nlmX25PLEdTEIVMOEntry 4 }

nlmX25PLEdTEIVMOExtendedPacketSequenceNumbering OBJECT-TYPE
    SYNTAX      PacketSequencing
    MAX-ACCESS  read-create
    STATUS      current
    DESCRIPTION 
        "The modulo of the packet sequence number space.  
         Expressed as an integer.  The ITU-T Recommendation 
         | International Standard only requires support for at 
         least one of the two values 8 and 128, but it is 
         possible that some future revision may extend the 
         range.  A system is only required to support the 
         setting of values which are also required by the 
         protocol standard.  A system shall return an error when 
         an attempt is made to set the value to a value which is 
         not supported by that system."
    REFERENCE   
        "ITU-T Rec. X.283 (1997) | ISO/IEC 10733 : 1998, 
               extendedPacketSequenceNumbering ATTRIBUTE"
    DEFVAL      { 128 }
    ::= { nlmX25PLEdTEIVMOEntry 5 }

nlmX25PLEdTEIVMOInterruptResponseTimer OBJECT-TYPE
    SYNTAX      MilliSeconds
    UNITS       "ms"
    MAX-ACCESS  read-create
    STATUS      current
    DESCRIPTION 
        "Value for Timer T26 (Interrupt Response Timer) in 
         seconds."
    REFERENCE   
        "ITU-T Rec. X.283 (1997) | ISO/IEC 10733 : 1998, 
               interruptResponseTimer ATTRIBUTE"
    DEFVAL      { 180000 } -- 180 seconds
    ::= { nlmX25PLEdTEIVMOEntry 6 }

nlmX25PLEdTEIVMOMaxActiveCircuits OBJECT-TYPE
    SYNTAX      Unsigned32
    MAX-ACCESS  read-create
    STATUS      current
    DESCRIPTION 
        "The maximum number of active circuits permitted on this 
         PLE. When the NULL value is specified, the maximum 
         number of active circuits shall be limited only by the 
         resources available to the entity."
    REFERENCE   
        "ITU-T Rec. X.283 (1997) | ISO/IEC 10733 : 1998, 
               maxActiveCircuits ATTRIBUTE"
    DEFVAL      { 0 }
    ::= { nlmX25PLEdTEIVMOEntry 7 }

nlmX25PLEdTEIVMOMinimumRecallTimer OBJECT-TYPE
    SYNTAX      MilliSeconds
    UNITS       "ms"
    MAX-ACCESS  read-create
    STATUS      current
    DESCRIPTION 
        "Minimum time in seconds before recall permitted. This 
         timer determines the minimum interval (in seconds) 
         which shall elapse following an unsuccessful first call 
         attempt before a subsequent call attempt is permitted."
    REFERENCE   
        "ITU-T Rec. X.283 (1997) | ISO/IEC 10733 : 1998, 
               minimumRecallTimer ATTRIBUTE"
    DEFVAL      { 0 }
    ::= { nlmX25PLEdTEIVMOEntry 8 }

nlmX25PLEdTEIVMOResetRequestResponseTimer OBJECT-TYPE
    SYNTAX      MilliSeconds
    UNITS       "ms"
    MAX-ACCESS  read-create
    STATUS      current
    DESCRIPTION 
        "Value for Timer T22 (Reset Request Response Timer) in 
         seconds."
    REFERENCE   
        "ITU-T Rec. X.283 (1997) | ISO/IEC 10733 : 1998, 
               resetRequestResponseTimer ATTRIBUTE"
    DEFVAL      { 180000 } -- 180 seconds
    ::= { nlmX25PLEdTEIVMOEntry 9 }

nlmX25PLEdTEIVMOResetRequestRetransmissionCount OBJECT-TYPE
    SYNTAX      Unsigned32
    MAX-ACCESS  read-create
    STATUS      current
    DESCRIPTION 
        "Value for count R22 (Reset Request Retransmission 
         Count)."
    REFERENCE   
        "ITU-T Rec. X.283 (1997) | ISO/IEC 10733 : 1998, 
               resetRequestRetransmissionCount ATTRIBUTE"
    DEFVAL      { 1 }
    ::= { nlmX25PLEdTEIVMOEntry 10 }

nlmX25PLEdTEIVMORestartRequestResponseTimer OBJECT-TYPE
    SYNTAX      MilliSeconds
    UNITS       "ms"
    MAX-ACCESS  read-create
    STATUS      current
    DESCRIPTION 
        "Value for Timer T20 (Restart Request Response Timer) in 
         seconds."
    REFERENCE   
        "ITU-T Rec. X.283 (1997) | ISO/IEC 10733 : 1998, 
               restartRequestResponseTimer ATTRIBUTE"
    DEFVAL      { 180000 } -- 180 seconds
    ::= { nlmX25PLEdTEIVMOEntry 11 }

nlmX25PLEdTEIVMORestartRequestRetransmissionCount OBJECT-TYPE
    SYNTAX      Unsigned32
    MAX-ACCESS  read-create
    STATUS      current
    DESCRIPTION 
        "Value for count R20 (Restart Request Retransmission 
         Count)."
    REFERENCE   
        "ITU-T Rec. X.283 (1997) | ISO/IEC 10733 : 1998, 
               restartRequestRetransmissionCount ATTRIBUTE"
    DEFVAL      { 1 }
    ::= { nlmX25PLEdTEIVMOEntry 12 }

-- receivingWindowRotationRecoveryProcedures-P PACKAGE
nlmX25PLEdTEIVMOWindowStatusTransmissionTimer OBJECT-TYPE
    SYNTAX      MilliSeconds
    UNITS       "ms"
    MAX-ACCESS  read-create
    STATUS      current
    DESCRIPTION 
        "Value for Timer T24 (Window Status Transmission Timer) 
         in seconds."
    REFERENCE   
        "ITU-T Rec. X.283 (1997) | ISO/IEC 10733 : 1998, 
               windowStatusTransmissionTimer ATTRIBUTE"
    DEFVAL      { 60000 } -- 60 seconds
    ::= { nlmX25PLEdTEIVMOEntry 13 }

-- transmittingWindowRotationRecoveryProcedures-P PACKAGE
nlmX25PLEdTEIVMOWindowRotationTimer OBJECT-TYPE
    SYNTAX      MilliSeconds
    UNITS       "ms"
    MAX-ACCESS  read-create
    STATUS      current
    DESCRIPTION 
        "Default for Timer T25 (Window Rotation Timer) in 
         seconds."
    REFERENCE   
        "ITU-T Rec. X.283 (1997) | ISO/IEC 10733 : 1998, 
               windowRotationTimer ATTRIBUTE"
    DEFVAL      { 200000 } -- 200 seconds
    ::= { nlmX25PLEdTEIVMOEntry 14 }

nlmX25PLEdTEIVMODataPacketRetransmissionCount OBJECT-TYPE
    SYNTAX      Unsigned32
    MAX-ACCESS  read-create
    STATUS      current
    DESCRIPTION 
        "Value for count R25 (Data Packet Retransmission 
         Count)."
    REFERENCE   
        "ITU-T Rec. X.283 (1997) | ISO/IEC 10733 : 1998, 
               dataPacketRetransmissionCount ATTRIBUTE"
    DEFVAL      { 0 }
    ::= { nlmX25PLEdTEIVMOEntry 15 }

-- packetRetransmissionProcedures-P PACKAGE
nlmX25PLEdTEIVMORejectResponseTimer OBJECT-TYPE
    SYNTAX      MilliSeconds
    UNITS       "ms"
    MAX-ACCESS  read-create
    STATUS      current
    DESCRIPTION 
        "Value for Timer T27 (Reject Response Timer) in 
         seconds."
    REFERENCE   
        "ITU-T Rec. X.283 (1997) | ISO/IEC 10733 : 1998, 
               rejectResponseTimer ATTRIBUTE"
    DEFVAL      { 60000 } -- 60 seconds
    ::= { nlmX25PLEdTEIVMOEntry 16 }

nlmX25PLEdTEIVMORejectRetransmissionCount OBJECT-TYPE
    SYNTAX      Unsigned32
    MAX-ACCESS  read-create
    STATUS      current
    DESCRIPTION 
        "Value for count R27 (Reject Retransmission Count)."
    REFERENCE   
        "ITU-T Rec. X.283 (1997) | ISO/IEC 10733 : 1998, 
               rejectRetransmissionCount ATTRIBUTE"
    DEFVAL      { 0 }
    ::= { nlmX25PLEdTEIVMOEntry 17 }

-- onlineRegistration-P PACKAGE
nlmX25PLEdTEIVMORegistrationRequestResponseTimer OBJECT-TYPE
    SYNTAX      MilliSeconds
    UNITS       "ms"
    MAX-ACCESS  read-create
    STATUS      current
    DESCRIPTION 
        "Value for Timer T28 (Registration Request Response 
         Timer) in seconds."
    REFERENCE   
        "ITU-T Rec. X.283 (1997) | ISO/IEC 10733 : 1998, 
               registrationRequestResponseTimer ATTRIBUTE"
    DEFVAL      { 300000 } -- 300 seconds
    ::= { nlmX25PLEdTEIVMOEntry 18 }

nlmX25PLEdTEIVMORegistrationRequestRetransmissionCount OBJECT-TYPE
    SYNTAX      Unsigned32
    MAX-ACCESS  read-create
    STATUS      current
    DESCRIPTION 
        "Value for count R28 (Registration Request 
         Retransmission Count)."
    REFERENCE   
        "ITU-T Rec. X.283 (1997) | ISO/IEC 10733 : 1998, 
               registrationRequestRetransmissionCount ATTRIBUTE"
    DEFVAL      { 1 }
    ::= { nlmX25PLEdTEIVMOEntry 19 }

nlmX25PLEdTEIVMORegistrationPermitted OBJECT-TYPE
    SYNTAX      TruthValue
    MAX-ACCESS  read-create
    STATUS      current
    DESCRIPTION 
        "When true, the use of online facility registration is 
         permitted."
    REFERENCE   
        "ITU-T Rec. X.283 (1997) | ISO/IEC 10733 : 1998, 
               registrationPermitted ATTRIBUTE"
    DEFVAL      { false }
    ::= { nlmX25PLEdTEIVMOEntry 20 }

nlmX25PLEdTEIVMORowStatus OBJECT-TYPE
    SYNTAX      RowStatus
    MAX-ACCESS  read-create
    STATUS      current
    DESCRIPTION 
        "Provides a mechanism whereby management stations can 
         create or delete conceptual rows in this table.  Table 
         contents must persist across management system 
         restart/reboot."
    REFERENCE   
        "ITU-T Rec. X.283 (1997) | ISO/IEC 10733 : 1998, 
               x25PLEIVMO-networkSubsystem NAME BINDING"
    ::= { nlmX25PLEdTEIVMOEntry 21 }

-- ==========================================

nlmX25PLEdCETable OBJECT-TYPE
    SYNTAX      SEQUENCE OF NlmX25PLEdCEEntry
    MAX-ACCESS  not-accessible
    STATUS      current
    DESCRIPTION 
        ""
    REFERENCE   
        "ITU-T Rec. X.283 (1997) | ISO/IEC 10733 : 1998, 
               x25PLE-DCE MANAGED OBJECT CLASS"
    ::= { nlmX25PLE 5 }

nlmX25PLEdCEEntry OBJECT-TYPE
    SYNTAX      NlmX25PLEdCEEntry
    MAX-ACCESS  not-accessible
    STATUS      current
    DESCRIPTION 
        "5.10.4 The X.25 PLE DCE managed object
         
         There may be multiple instances of these MOs within 
         a system, corresponding to Multiple X.25 PLEs.
         
         The definition of this MO permits it to be created and 
         deleted explicitly by management operation or to be 
         created and deleted automatically as part of system 
         operation. When an instance of this MO is created 
         automatically, an instance of the x25PLEIVMO-DCE may be 
         used as the source of the initial values for attributes 
         of this MO.
         
         When the x25 PLE is operable, the operationalState 
         shall have the value 'enabled'; otherwise it shall have 
         the value 'disabled'.  Transitions of operationalState 
         shall be reported using the stateChange notification."
    REFERENCE   
        "ITU-T Rec. X.283 (1997) | ISO/IEC 10733 : 1998, 
               x25PLE-DCE MANAGED OBJECT"
    AUGMENTS    { nlmX25PLEEntry }
    ::= { nlmX25PLEdCETable 1 }

NlmX25PLEdCEEntry ::= SEQUENCE {
-- x25PLE-DCE-P PACKAGE
    nlmX25PLEdCECallAttempts                        Counter64,
    nlmX25PLEdCECallsConnected                      Counter64,
    nlmX25PLEdCEcUG                                 TruthValue,
    nlmX25PLEdCEFastSelectAcceptance                TruthValue,
    nlmX25PLEdCEIncomingCallsBarred                 TruthValue,
    nlmX25PLEdCEOneWayLogicalChannelOutgoing        TruthValue,
    nlmX25PLEdCEOutgoingCallsBarred                 TruthValue,
-- dCECommonVirtualCircuitCounters-P PACKAGE
    nlmX25PLEdCEDataPacketsReceived                 Counter64,
    nlmX25PLEdCEDataPacketsSent                     Counter64,
    nlmX25PLEdCEInterruptPacketsReceived            Counter64,
    nlmX25PLEdCEInterruptPacketsSent                Counter64,
    nlmX25PLEdCEInterruptTimerExpiries              Counter64,
    nlmX25PLEdCEOctetsReceivedCounter               Counter64,
    nlmX25PLEdCEOctetsSentCounter                   Counter64,
    nlmX25PLEdCEProviderInitiatedDisconnects        Counter64,
    nlmX25PLEdCEProviderInitiatedResets             Counter64,
    nlmX25PLEdCERemotelyInitiatedRestarts           Counter64,
    nlmX25PLEdCERemotelyInitiatedResets             Counter64,
    nlmX25PLEdCEResetTimeouts                       Counter64,
    nlmX25PLEdCEx25SegmentsReceived                 Counter64,
    nlmX25PLEdCEx25SegmentsSent                     Counter64,
-- dCEX25PLEFacilities-P PACKAGE
    nlmX25PLEdCEBilateralCUG                        TruthValue,
    nlmX25PLEdCEBilateralCUGWithOutgoingAccess      TruthValue,
    nlmX25PLEdCECallDeflectionSubscription          TruthValue,
    nlmX25PLEdCECallRedirection                     TruthValue,
    nlmX25PLEdCEChargingInformation                 TruthValue,
    nlmX25PLEdCEcUGWithIncomingAccess               TruthValue,
    nlmX25PLEdCEcUGWithOutgoingAccess               TruthValue,
    nlmX25PLEdCEdBitModification                    TruthValue,
    nlmX25PLEdCEDefaultThroughputClassesAssignment  TruthValue,
    nlmX25PLEdCEExtendedPacketSequenceNumbering     PacketSequencing,
    nlmX25PLEdCEHuntGroup                           TruthValue,
    nlmX25PLEdCEIncomingCallBarredWithinCUG         TruthValue,
    nlmX25PLEdCELocalChargingPrevention             TruthValue,
    nlmX25PLEdCENonStandardDefaultPacketSizes       TruthValue,
    nlmX25PLEdCENonStandardDefaultWindowSizes       TruthValue,
    nlmX25PLEdCEnUIOverride                         TruthValue,
    nlmX25PLEdCEnUISubscription                     TruthValue,
    nlmX25PLEdCEOneWayLogicalChannelIncoming        TruthValue,
    nlmX25PLEdCEOnlineFacilityRegistration          TruthValue,
    nlmX25PLEdCEOutgoingCallBarredWithinCUG         TruthValue,
    nlmX25PLEdCEPacketRetransmission                TruthValue,
    nlmX25PLEdCEReverseChargingAcceptance           TruthValue,
    nlmX25PLEdCErOASubscription                     TruthValue,
-- dCEX25PLETimers-P PACKAGE
    nlmX25PLEdCEClearIndication                     MilliSeconds,
    nlmX25PLEdCEIncomingCall                        MilliSeconds,
    nlmX25PLEdCEResetIndication                     MilliSeconds,
    nlmX25PLEdCERestartIndication                   MilliSeconds,
--
    nlmX25PLEdCERowStatus                           RowStatus
}

-- x25PLE-DCE-P PACKAGE
nlmX25PLEdCECallAttempts OBJECT-TYPE
    SYNTAX      Counter64
    MAX-ACCESS  read-only
    STATUS      current
    DESCRIPTION 
        "Counter of the total number of calls attempted."
    REFERENCE   
        "ITU-T Rec. X.283 (1997) | ISO/IEC 10733 : 1998, 
               callAttempts ATTRIBUTE"
    ::= { nlmX25PLEdCEEntry 1 }

nlmX25PLEdCECallsConnected OBJECT-TYPE
    SYNTAX      Counter64
    MAX-ACCESS  read-only
    STATUS      current
    DESCRIPTION 
        "Counter of the total number of calls which have reached 
         the open state."
    REFERENCE   
        "ITU-T Rec. X.283 (1997) | ISO/IEC 10733 : 1998, 
               callsConnected ATTRIBUTE"
    ::= { nlmX25PLEdCEEntry 2 }

nlmX25PLEdCEcUG OBJECT-TYPE
    SYNTAX      TruthValue
    MAX-ACCESS  read-create
    STATUS      current
    DESCRIPTION 
        "The subscription of the closed user group facility as 
         described in ITU-T Recommendation X.2. Expressed as 
         a boolean where a value of 'True' indicates 
         subscription and a value of 'False' indicates 
         non-subscription."
    REFERENCE   
        "ITU-T Rec. X.283 (1997) | ISO/IEC 10733 : 1998, 
               cUG ATTRIBUTE"
    ::= { nlmX25PLEdCEEntry 3 }

nlmX25PLEdCEFastSelectAcceptance OBJECT-TYPE
    SYNTAX      TruthValue
    MAX-ACCESS  read-create
    STATUS      current
    DESCRIPTION 
        "The subscription of the fast select acceptance as 
         described in ITU-T Recommendation X.2. Expressed as 
         a boolean where a value of 'True' indicates 
         subscription and a value of 'False' indicates 
         non-subscription."
    REFERENCE   
        "ITU-T Rec. X.283 (1997) | ISO/IEC 10733 : 1998, 
               fastSelectAcceptance ATTRIBUTE"
    ::= { nlmX25PLEdCEEntry 4 }

nlmX25PLEdCEIncomingCallsBarred OBJECT-TYPE
    SYNTAX      TruthValue
    MAX-ACCESS  read-create
    STATUS      current
    DESCRIPTION 
        "The subscription of the incoming calls barred facility 
         as described in ITU-T Recommendation X.2. Expressed as 
         a boolean where a value of 'True' indicates 
         subscription and a value of 'False' indicates 
         non-subscription.!"
    REFERENCE   
        "ITU-T Rec. X.283 (1997) | ISO/IEC 10733 : 1998, 
               incomingCallsBarred ATTRIBUTE"
    ::= { nlmX25PLEdCEEntry 5 }

nlmX25PLEdCEOneWayLogicalChannelOutgoing OBJECT-TYPE
    SYNTAX      TruthValue
    MAX-ACCESS  read-create
    STATUS      current
    DESCRIPTION 
        "The subscription of the one way logical channel 
         outgoing facility as described in ITU-T Recommendation 
         X.2. Expressed as a boolean where a value of 'True' 
         indicates subscription and a value of 'False' indicates 
         non-subscription."
    REFERENCE   
        "ITU-T Rec. X.283 (1997) | ISO/IEC 10733 : 1998, 
               oneWayLogicalChannelOutgoing ATTRIBUTE"
    ::= { nlmX25PLEdCEEntry 6 }

nlmX25PLEdCEOutgoingCallsBarred OBJECT-TYPE
    SYNTAX      TruthValue
    MAX-ACCESS  read-create
    STATUS      current
    DESCRIPTION 
        "The subscription of the outgoing calls barred facility 
         as described in ITU-T Recommendation X.2. Expressed as 
         a boolean where a value of 'True' indicates 
         subscription and a value of 'False' indicates 
         non-subscription."
    REFERENCE   
        "ITU-T Rec. X.283 (1997) | ISO/IEC 10733 : 1998, 
               outgoingCallsBarred ATTRIBUTE"
    ::= { nlmX25PLEdCEEntry 7 }

-- dCECommonVirtualCircuitCounters-P PACKAGE
nlmX25PLEdCEDataPacketsReceived OBJECT-TYPE
    SYNTAX      Counter64
    MAX-ACCESS  read-only
    STATUS      current
    DESCRIPTION 
        "Counter of the total number of data packets received."
    REFERENCE   
        "ITU-T Rec. X.283 (1997) | ISO/IEC 10733 : 1998, 
               dataPacketsReceived ATTRIBUTE"
    ::= { nlmX25PLEdCEEntry 8 }

nlmX25PLEdCEDataPacketsSent OBJECT-TYPE
    SYNTAX      Counter64
    MAX-ACCESS  read-only
    STATUS      current
    DESCRIPTION 
        "Counter of the total number of data packets sent."
    REFERENCE   
        "ITU-T Rec. X.283 (1997) | ISO/IEC 10733 : 1998, 
               dataPacketsSent ATTRIBUTE"
    ::= { nlmX25PLEdCEEntry 9 }

nlmX25PLEdCEInterruptPacketsReceived OBJECT-TYPE
    SYNTAX      Counter64
    MAX-ACCESS  read-only
    STATUS      current
    DESCRIPTION 
        "Counter of the number of interrupt packets received by 
         the PLE or over the PVC/VC."
    REFERENCE   
        "ITU-T Rec. X.283 (1997) | ISO/IEC 10733 : 1998, 
               interruptPacketsReceived ATTRIBUTE"
    ::= { nlmX25PLEdCEEntry 10 }

nlmX25PLEdCEInterruptPacketsSent OBJECT-TYPE
    SYNTAX      Counter64
    MAX-ACCESS  read-only
    STATUS      current
    DESCRIPTION 
        "Counter of the number of interrupt packets sent by the 
         PLE or over the PVC/VC."
    REFERENCE   
        "ITU-T Rec. X.283 (1997) | ISO/IEC 10733 : 1998, 
               interruptPacketsSent ATTRIBUTE"
    ::= { nlmX25PLEdCEEntry 11 }

nlmX25PLEdCEInterruptTimerExpiries OBJECT-TYPE
    SYNTAX      Counter64
    MAX-ACCESS  read-only
    STATUS      current
    DESCRIPTION 
        "Counter of the number of expiries of timer T26 
         experienced by the PLE or over the PVC/VC."
    REFERENCE   
        "ITU-T Rec. X.283 (1997) | ISO/IEC 10733 : 1998, 
               interruptTimerExpiries ATTRIBUTE"
    ::= { nlmX25PLEdCEEntry 12 }

nlmX25PLEdCEOctetsReceivedCounter OBJECT-TYPE
    SYNTAX      Counter64
    MAX-ACCESS  read-only
    STATUS      current
    DESCRIPTION 
        "Specifies the total number of user data octets received 
         by the connectionless network protocol state machine."
    REFERENCE   
        "ITU-T Rec. X.721 (1992) | ISO/IEC 10165-2 : 1992, 
               octetsReceivedCounter"
    ::= { nlmX25PLEdCEEntry 13 }

nlmX25PLEdCEOctetsSentCounter OBJECT-TYPE
    SYNTAX      Counter64
    MAX-ACCESS  read-only
    STATUS      current
    DESCRIPTION 
        "Specifies the total number of user data octets sent by 
         the connectionless network protocol state machine."
    REFERENCE   
        "ITU-T Rec. X.721 (1992) | ISO/IEC 10165-2 : 1992, 
               octetsSentCounter"
    ::= { nlmX25PLEdCEEntry 14 }

nlmX25PLEdCEProviderInitiatedDisconnects OBJECT-TYPE
    SYNTAX      Counter64
    MAX-ACCESS  read-only
    STATUS      current
    DESCRIPTION 
        "Counter for the providerInitiatedDisconnect events 
         which generate communication alarm notifications."
    REFERENCE   
        "ITU-T Rec. X.283 (1997) | ISO/IEC 10733 : 1998, 
               providerInitiatedDisconnects ATTRIBUTE"
    ::= { nlmX25PLEdCEEntry 15 }

nlmX25PLEdCEProviderInitiatedResets OBJECT-TYPE
    SYNTAX      Counter64
    MAX-ACCESS  read-only
    STATUS      current
    DESCRIPTION 
        "Counter associated with the providerInitiatedReset 
         event which generates a communication alarm 
         notification."
    REFERENCE   
        "ITU-T Rec. X.283 (1997) | ISO/IEC 10733 : 1998, 
               providerInitiatedResets ATTRIBUTE"
    ::= { nlmX25PLEdCEEntry 16 }

nlmX25PLEdCERemotelyInitiatedRestarts OBJECT-TYPE
    SYNTAX      Counter64
    MAX-ACCESS  read-only
    STATUS      current
    DESCRIPTION 
        "Counter of the number of remotely initiated restarts. 
         This is the total number of remotely initiated 
         (including provider initiated) restarts experienced by 
         the PLE, excluding the restart associated with bringing 
         up the PLE interface."
    REFERENCE   
        "ITU-T Rec. X.283 (1997) | ISO/IEC 10733 : 1998, 
               remotelyInitiatedRestarts ATTRIBUTE"
    ::= { nlmX25PLEdCEEntry 17 }

nlmX25PLEdCERemotelyInitiatedResets OBJECT-TYPE
    SYNTAX      Counter64
    MAX-ACCESS  read-only
    STATUS      current
    DESCRIPTION 
        "Counter associated with the remotelyInitiatedReset 
         event which generates a communication alarm 
         notification."
    REFERENCE   
        "ITU-T Rec. X.283 (1997) | ISO/IEC 10733 : 1998, 
               remotelyInitiatedResets ATTRIBUTE"
    ::= { nlmX25PLEdCEEntry 18 }

nlmX25PLEdCEResetTimeouts OBJECT-TYPE
    SYNTAX      Counter64
    MAX-ACCESS  read-only
    STATUS      current
    DESCRIPTION 
        "Counter of the number of timer T22 expiries experienced 
         by the PLE."
    REFERENCE   
        "ITU-T Rec. X.283 (1997) | ISO/IEC 10733 : 1998, 
               resetTimeouts ATTRIBUTE"
    ::= { nlmX25PLEdCEEntry 19 }

nlmX25PLEdCEx25SegmentsReceived OBJECT-TYPE
    SYNTAX      Counter64
    MAX-ACCESS  read-only
    STATUS      current
    DESCRIPTION 
        "Value for count of X.25 Segments Received."
    REFERENCE   
        "ITU-T Rec. X.283 (1997) | ISO/IEC 10733 : 1998, 
               x25SegmentsReceived ATTRIBUTE"
    ::= { nlmX25PLEdCEEntry 20 }

nlmX25PLEdCEx25SegmentsSent OBJECT-TYPE
    SYNTAX      Counter64
    MAX-ACCESS  read-only
    STATUS      current
    DESCRIPTION 
        "Value for count of X.25 Segments Sent."
    REFERENCE   
        "ITU-T Rec. X.283 (1997) | ISO/IEC 10733 : 1998, 
               x25SegmentsSent ATTRIBUTE"
    ::= { nlmX25PLEdCEEntry 21 }

-- dCEX25PLEFacilities-P PACKAGE
nlmX25PLEdCEBilateralCUG OBJECT-TYPE
    SYNTAX      TruthValue
    MAX-ACCESS  read-create
    STATUS      current
    DESCRIPTION 
        "The subscription of the bilateral closed user group 
         facility as described in ITU-T Recommendation X.2. 
         Expressed as a boolean where a value of 'True' 
         indicates subscription and a value of 'False' indicates 
         non-subscription."
    REFERENCE   
        "ITU-T Rec. X.283 (1997) | ISO/IEC 10733 : 1998, 
               bilateralCUG ATTRIBUTE"
    ::= { nlmX25PLEdCEEntry 22 }

nlmX25PLEdCEBilateralCUGWithOutgoingAccess OBJECT-TYPE
    SYNTAX      TruthValue
    MAX-ACCESS  read-create
    STATUS      current
    DESCRIPTION 
        "The subscription of the bilateral CUG with outgoing 
         access facility as described in ITU-T Recommendation 
         X.2. Expressed as a boolean where a value of 'True' 
         indicates subscription and a value of 'False' indicates 
         non-subscription."
    REFERENCE   
        "ITU-T Rec. X.283 (1997) | ISO/IEC 10733 : 1998, 
               bilateralCUGWithOutgoingAccess ATTRIBUTE"
    ::= { nlmX25PLEdCEEntry 23 }

nlmX25PLEdCECallDeflectionSubscription OBJECT-TYPE
    SYNTAX      TruthValue
    MAX-ACCESS  read-create
    STATUS      current
    DESCRIPTION 
        "The subscription of the call deflection facility as 
         described in ITU-T Recommendation X.2.  Expressed as 
         a boolean where a value of 'True' indicates 
         subscription and a value of 'False' indicates 
         non-subscription."
    REFERENCE   
        "ITU-T Rec. X.283 (1997) | ISO/IEC 10733 : 1998, 
               callDeflectionSubscription ATTRIBUTE"
    ::= { nlmX25PLEdCEEntry 24 }

nlmX25PLEdCECallRedirection OBJECT-TYPE
    SYNTAX      TruthValue
    MAX-ACCESS  read-create
    STATUS      current
    DESCRIPTION 
        "The subscription of the call redirection facility as 
         described in ITU-T Recommendation X.2 Expressed as 
         a boolean where a value of 'True' indicates 
         subscription and a value of 'False' indicates 
         non-subscription."
    REFERENCE   
        "ITU-T Rec. X.283 (1997) | ISO/IEC 10733 : 1998, 
               callRedirection ATTRIBUTE"
    ::= { nlmX25PLEdCEEntry 25 }

nlmX25PLEdCEChargingInformation OBJECT-TYPE
    SYNTAX      TruthValue
    MAX-ACCESS  read-create
    STATUS      current
    DESCRIPTION 
        "The subscription of the charging information facility 
         as described in ITU-T Recommendation X.2. Expressed as 
         a boolean where a value of 'True' indicates 
         subscription and a value of 'False' indicates 
         non-subscription."
    REFERENCE   
        "ITU-T Rec. X.283 (1997) | ISO/IEC 10733 : 1998, 
               chargingInformation ATTRIBUTE"
    ::= { nlmX25PLEdCEEntry 26 }

nlmX25PLEdCEcUGWithIncomingAccess OBJECT-TYPE
    SYNTAX      TruthValue
    MAX-ACCESS  read-create
    STATUS      current
    DESCRIPTION 
        "The subscription of the closed user group with incoming 
         access facility as described in ITU-T Recommendation 
         X.2. Expressed as a boolean where a value of 'True' 
         indicates subscription and a value of 'False' indicates 
         non-subscription."
    REFERENCE   
        "ITU-T Rec. X.283 (1997) | ISO/IEC 10733 : 1998, 
               cUGWithIncomingAccess ATTRIBUTE"
    ::= { nlmX25PLEdCEEntry 27 }

nlmX25PLEdCEcUGWithOutgoingAccess OBJECT-TYPE
    SYNTAX      TruthValue
    MAX-ACCESS  read-create
    STATUS      current
    DESCRIPTION 
        "The subscription of the CUG with outgoing access 
         facility as described in ITU-T Recommendation X.2. 
         Expressed as a boolean where a value of 'True' 
         indicates subscription and a value of 'False' indicates 
         non-subscription."
    REFERENCE   
        "ITU-T Rec. X.283 (1997) | ISO/IEC 10733 : 1998, 
               cUGWithOutgoingAccess ATTRIBUTE"
    ::= { nlmX25PLEdCEEntry 28 }

nlmX25PLEdCEdBitModification OBJECT-TYPE
    SYNTAX      TruthValue
    MAX-ACCESS  read-create
    STATUS      current
    DESCRIPTION 
        "The subscription of the D bit modification facility as 
         described in ITU-T Recommendation X.2. Expressed as 
         a boolean where a value of 'True' indicates 
         subscription and a value of 'False' indicates 
         non-subscription."
    REFERENCE   
        "ITU-T Rec. X.283 (1997) | ISO/IEC 10733 : 1998, 
               dBitModification ATTRIBUTE"
    ::= { nlmX25PLEdCEEntry 29 }

nlmX25PLEdCEDefaultThroughputClassesAssignment OBJECT-TYPE
    SYNTAX      TruthValue
    MAX-ACCESS  read-create
    STATUS      current
    DESCRIPTION 
        "The subscription of the default throughput classes 
         assignment facility as described in ITU-T 
         Recommendation X.2. Expressed as a boolean where 
         a value of 'True' indicates subscription and a value of 
         'False' indicates non-subscription."
    REFERENCE   
        "ITU-T Rec. X.283 (1997) | ISO/IEC 10733 : 1998, 
               defaultThroughputClassesAssignment ATTRIBUTE"
    ::= { nlmX25PLEdCEEntry 30 }

nlmX25PLEdCEExtendedPacketSequenceNumbering OBJECT-TYPE
    SYNTAX      PacketSequencing
    MAX-ACCESS  read-create
    STATUS      current
    DESCRIPTION 
        "The modulo of the packet sequence number space.  
         Expressed as an integer.  The ITU-T Recommendation 
         | International Standard only requires support for at 
         least one of the two values 8 and 128, but it is 
         possible that some future revision may extend the 
         range.  A system is only required to support the 
         setting of values which are also required by the 
         protocol standard.  A system shall return an error when 
         an attempt is made to set the value to a value which is 
         not supported by that system."
    REFERENCE   
        "ITU-T Rec. X.283 (1997) | ISO/IEC 10733 : 1998, 
               extendedPacketSequenceNumbering ATTRIBUTE"
    ::= { nlmX25PLEdCEEntry 31 }

nlmX25PLEdCEHuntGroup OBJECT-TYPE
    SYNTAX      TruthValue
    MAX-ACCESS  read-create
    STATUS      current
    DESCRIPTION 
        "The subscription of the hunt group facility as 
         described in ITU-T Recommendation X.2. Expressed as 
         a boolean where a value of 'True' indicates 
         subscription and a value of 'False' indicates 
         non-subscription."
    REFERENCE   
        "ITU-T Rec. X.283 (1997) | ISO/IEC 10733 : 1998, 
               huntGroup ATTRIBUTE"
    ::= { nlmX25PLEdCEEntry 32 }

nlmX25PLEdCEIncomingCallBarredWithinCUG OBJECT-TYPE
    SYNTAX      TruthValue
    MAX-ACCESS  read-create
    STATUS      current
    DESCRIPTION 
        "The subscription of the incoming call barred within 
         a CUG facility as described in ITU-T Recommendation 
         X.2. Expressed as a boolean where a value of 'True' 
         indicates subscription and a value of 'False' indicates 
         non-subscription."
    REFERENCE   
        "ITU-T Rec. X.283 (1997) | ISO/IEC 10733 : 1998, 
               incomingCallBarredWithinCUG ATTRIBUTE"
    ::= { nlmX25PLEdCEEntry 33 }

nlmX25PLEdCELocalChargingPrevention OBJECT-TYPE
    SYNTAX      TruthValue
    MAX-ACCESS  read-create
    STATUS      current
    DESCRIPTION 
        "The subscription of the local charging prevention 
         facility as described in ITU-T Recommendation X.2. 
         Expressed as a boolean where a value of 'True' 
         indicates subscription and a value of 'False' indicates 
         non-subscription."
    REFERENCE   
        "ITU-T Rec. X.283 (1997) | ISO/IEC 10733 : 1998, 
               localChargingPrevention ATTRIBUTE"
    ::= { nlmX25PLEdCEEntry 34 }

nlmX25PLEdCENonStandardDefaultPacketSizes OBJECT-TYPE
    SYNTAX      TruthValue
    MAX-ACCESS  read-create
    STATUS      current
    DESCRIPTION 
        "The subscription of the non standard default packet 
         sizes facility as described in ITU-T Recommendation 
         X.2.  Expressed as a boolean where a value of 'True' 
         indicates subscription and a value of 'False' indicates 
         non-subscription."
    REFERENCE   
        "ITU-T Rec. X.283 (1997) | ISO/IEC 10733 : 1998, 
               nonStandardDefaultPacketSizes ATTRIBUTE"
    ::= { nlmX25PLEdCEEntry 35 }

nlmX25PLEdCENonStandardDefaultWindowSizes OBJECT-TYPE
    SYNTAX      TruthValue
    MAX-ACCESS  read-create
    STATUS      current
    DESCRIPTION 
        "The subscription of the non standard default window 
         sizes facility as described in ITU-T Recommendation 
         X.2. Expressed as a boolean where a value of 'True' 
         indicates subscription and a value of 'False' indicates 
         non-subscription."
    REFERENCE   
        "ITU-T Rec. X.283 (1997) | ISO/IEC 10733 : 1998, 
               nonStandardDefaultWindowSizes ATTRIBUTE"
    ::= { nlmX25PLEdCEEntry 36 }

nlmX25PLEdCEnUIOverride OBJECT-TYPE
    SYNTAX      TruthValue
    MAX-ACCESS  read-create
    STATUS      current
    DESCRIPTION 
        "The subscription of the NUI override facility as 
         described in ITU-T Recommendation X.2. Expressed as 
         a boolean where a value of 'True' indicates 
         subscription and a value of 'False' indicates 
         non-subscription."
    REFERENCE   
        "ITU-T Rec. X.283 (1997) | ISO/IEC 10733 : 1998, 
               nUIOverride ATTRIBUTE"
    ::= { nlmX25PLEdCEEntry 37 }

nlmX25PLEdCEnUISubscription OBJECT-TYPE
    SYNTAX      TruthValue
    MAX-ACCESS  read-create
    STATUS      current
    DESCRIPTION 
        "The subscription of the NUI subscription facility as 
         described in ITU-T Recommendation X.2. Expressed as 
         a boolean where a value of 'True' indicates 
         subscription and a value of 'False' indicates 
         non-subscription."
    REFERENCE   
        "ITU-T Rec. X.283 (1997) | ISO/IEC 10733 : 1998, 
               nUISubscription ATTRIBUTE"
    ::= { nlmX25PLEdCEEntry 38 }

nlmX25PLEdCEOneWayLogicalChannelIncoming OBJECT-TYPE
    SYNTAX      TruthValue
    MAX-ACCESS  read-create
    STATUS      current
    DESCRIPTION 
        "The subscription of the one way logical channel 
         incoming facility as described in ITU-T Recommendation 
         X.2. Expressed as a boolean where a value of 'True' 
         indicates subscription and a value of 'False' indicates 
         non-subscription."
    REFERENCE   
        "ITU-T Rec. X.283 (1997) | ISO/IEC 10733 : 1998, 
               oneWayLogicalChannelIncoming ATTRIBUTE"
    ::= { nlmX25PLEdCEEntry 39 }

nlmX25PLEdCEOnlineFacilityRegistration OBJECT-TYPE
    SYNTAX      TruthValue
    MAX-ACCESS  read-create
    STATUS      current
    DESCRIPTION 
        "The subscription of the on-line facility registration 
         facility as described in ITU-T Recommendation X.2. 
         Expressed as a boolean where a value of 'True' 
         indicates subscription and a value of 'False' indicates 
         non subscription."
    REFERENCE   
        "ITU-T Rec. X.283 (1997) | ISO/IEC 10733 : 1998, 
               onlineFacilityRegistration ATTRIBUTE"
    ::= { nlmX25PLEdCEEntry 40 }

nlmX25PLEdCEOutgoingCallBarredWithinCUG OBJECT-TYPE
    SYNTAX      TruthValue
    MAX-ACCESS  read-create
    STATUS      current
    DESCRIPTION 
        "The subscription of the outgoing call barred within 
         a CUG facility as described in ITU-T Recommendation 
         X.2. Expressed as a boolean where a value of 'True' 
         indicates subscription and a value of 'False' indicates 
         non-subscription."
    REFERENCE   
        "ITU-T Rec. X.283 (1997) | ISO/IEC 10733 : 1998, 
               outgoingCallBarredWithinCUG ATTRIBUTE"
    ::= { nlmX25PLEdCEEntry 41 }

nlmX25PLEdCEPacketRetransmission OBJECT-TYPE
    SYNTAX      TruthValue
    MAX-ACCESS  read-create
    STATUS      current
    DESCRIPTION 
        "The subscription of the packet retransmissions facility 
         as described in ITU-T Recommendation X.2. Expressed as 
         a boolean where a value of 'True' indicates 
         subscription and a value of 'False' indicates 
         non-subscription. If non-subscription, then the 
         attributes for rejectTimer and rejectCount will have 
         NULL values."
    REFERENCE   
        "ITU-T Rec. X.283 (1997) | ISO/IEC 10733 : 1998, 
               packetRetransmission ATTRIBUTE"
    ::= { nlmX25PLEdCEEntry 42 }

nlmX25PLEdCEReverseChargingAcceptance OBJECT-TYPE
    SYNTAX      TruthValue
    MAX-ACCESS  read-create
    STATUS      current
    DESCRIPTION 
        "The subscription of the reverse charging acceptance 
         facility as described in ITU-T Recommendation X.2. 
         Expressed as a boolean where a value of 'True' 
         indicates subscription and a value of 'False' indicates 
         non-subscription."
    REFERENCE   
        "ITU-T Rec. X.283 (1997) | ISO/IEC 10733 : 1998, 
               reverseChargingAcceptance ATTRIBUTE"
    ::= { nlmX25PLEdCEEntry 43 }

nlmX25PLEdCErOASubscription OBJECT-TYPE
    SYNTAX      TruthValue
    MAX-ACCESS  read-create
    STATUS      current
    DESCRIPTION 
        "The subscription of the ROA Subscription facility as 
         described in ITU-T Recommendation X.2. Expressed as 
         a boolean where a value of 'True' indicates 
         subscription and a value of 'False' indicates 
         non-subscription."
    REFERENCE   
        "ITU-T Rec. X.283 (1997) | ISO/IEC 10733 : 1998, 
               rOASubscription ATTRIBUTE"
    ::= { nlmX25PLEdCEEntry 44 }

-- dCEX25PLETimers-P PACKAGE
nlmX25PLEdCEClearIndication OBJECT-TYPE
    SYNTAX      MilliSeconds
    MAX-ACCESS  read-create
    STATUS      current
    DESCRIPTION 
        "Value for the Clear Indication, T13 timer, in seconds."
    REFERENCE   
        "ITU-T Rec. X.283 (1997) | ISO/IEC 10733 : 1998, 
               clearIndication ATTRIBUTE"
    ::= { nlmX25PLEdCEEntry 45 }

nlmX25PLEdCEIncomingCall OBJECT-TYPE
    SYNTAX      MilliSeconds
    MAX-ACCESS  read-create
    STATUS      current
    DESCRIPTION 
        "Value for the Incoming Call, T11 timer, in seconds."
    REFERENCE   
        "ITU-T Rec. X.283 (1997) | ISO/IEC 10733 : 1998, 
               incomingCall ATTRIBUTE"
    ::= { nlmX25PLEdCEEntry 46 }

nlmX25PLEdCEResetIndication OBJECT-TYPE
    SYNTAX      MilliSeconds
    MAX-ACCESS  read-create
    STATUS      current
    DESCRIPTION 
        "Value for the Reset Indication, T12 timer, in seconds."
    REFERENCE   
        "ITU-T Rec. X.283 (1997) | ISO/IEC 10733 : 1998, 
               resetIndication ATTRIBUTE"
    ::= { nlmX25PLEdCEEntry 47 }

nlmX25PLEdCERestartIndication OBJECT-TYPE
    SYNTAX      MilliSeconds
    MAX-ACCESS  read-create
    STATUS      current
    DESCRIPTION 
        "Value for the Restart Indication, T10 timer, in seconds."
    REFERENCE   
        "ITU-T Rec. X.283 (1997) | ISO/IEC 10733 : 1998, 
               restartIndication ATTRIBUTE"
    ::= { nlmX25PLEdCEEntry 48 }

--
nlmX25PLEdCERowStatus OBJECT-TYPE
    SYNTAX      RowStatus
    MAX-ACCESS  read-create
    STATUS      current
    DESCRIPTION 
        ""
    REFERENCE   
        "ITU-T Rec. X.283 (1997) | ISO/IEC 10733 : 1998, 
               x25PLE-networkSubsystem-Management NAME BINDING"
    ::= { nlmX25PLEdCEEntry 49 }


-- ==========================================

nlmX25PLEdCEIVMOTable OBJECT-TYPE
    SYNTAX      SEQUENCE OF NlmX25PLEdCEIVMOEntry
    MAX-ACCESS  not-accessible
    STATUS      current
    DESCRIPTION 
        ""
    REFERENCE   
        "ITU-T Rec. X.283 (1997) | ISO/IEC 10733 : 1998, 
               x25PLEIVMO-DCE MANAGED OBJECT CLASS"
    ::= { nlmX25PLE 6 }

nlmX25PLEdCEIVMOEntry OBJECT-TYPE
    SYNTAX      NlmX25PLEdCEIVMOEntry
    MAX-ACCESS  not-accessible
    STATUS      current
    DESCRIPTION 
        "5.10.4 The X.25 PLE DCE managed object
         
         There may be multiple instances of these MOs within 
         a system, corresponding to Multiple X.25 PLEs.
         
         The definition of this MO permits it to be created and 
         deleted explicitly by management operation or to be 
         created and deleted automatically as part of system 
         operation. When an instance of this MO is created 
         automatically, an instance of the x25PLEIVMO-DCE may be 
         used as the source of the initial values for attributes 
         of this MO.
         
         When the x25 PLE is operable, the operationalState 
         shall have the value 'enabled'; otherwise it shall have 
         the value 'disabled'.  Transitions of operationalState 
         shall be reported using the stateChange notification."
    REFERENCE   
        "ITU-T Rec. X.283 (1997) | ISO/IEC 10733 : 1998, 
               x25PLEIVMO-DCE MANAGED OBJECT"
    AUGMENTS    { nlmX25PLEIVMOEntry }
    ::= { nlmX25PLEdCEIVMOTable 1 }

NlmX25PLEdCEIVMOEntry ::= SEQUENCE {
    nlmX25PLEdCEIVMORowStatus   RowStatus
}

nlmX25PLEdCEIVMORowStatus OBJECT-TYPE
    SYNTAX      RowStatus
    MAX-ACCESS  read-create
    STATUS      current
    DESCRIPTION 
        ""
    REFERENCE   
        "ITU-T Rec. X.283 (1997) | ISO/IEC 10733 : 1998, 
               x25PLEIVMO-networkSubsystem NAME BINDING"
    ::= { nlmX25PLEdCEIVMOEntry 1 }

-- ==========================================

nlmVirtualCircuit OBJECT IDENTIFIER
    ::= { nlmTables 9 }

nlmVirtualCircuitTable OBJECT-TYPE
    SYNTAX      SEQUENCE OF NlmVirtualCircuitEntry
    MAX-ACCESS  not-accessible
    STATUS      current
    DESCRIPTION 
        ""
    REFERENCE   
        "ITU-T Rec. X.283 (1997) | ISO/IEC 10733 : 1998, 
               virtualCircuit MANAGED OBJECT CLASS"
    ::= { nlmVirtualCircuit 1 }

nlmVirtualCircuitEntry OBJECT-TYPE
    SYNTAX      NlmVirtualCircuitEntry
    MAX-ACCESS  not-accessible
    STATUS      current
    DESCRIPTION 
        "5.11 The virtual circuit and related managed objects
         
         5.11.1 The virtual managed object
         
         This MO Class is never instantiated. It serves as 
         a generic Virtual Circuit MO from which both the 
         Virtual Circuit DTE and Virtual Circuit DCE MOs are 
         derived.  Note that the values of the virtualCircuitId 
         naming attribute are required to be unique across all 
         instances of MOs derived from this which have a common 
         superior."
    REFERENCE   
        "ITU-T Rec. X.283 (1997) | ISO/IEC 10733 : 1998, 
               virtualCircuit MANAGED OBJECT"
    INDEX       { nlmX25PLEId, nlmVirtualCircuitId }
    ::= { nlmVirtualCircuitTable 1 }

NlmVirtualCircuitEntry ::= SEQUENCE {
    nlmVirtualCircuitId                         SimpleNameType,
    nlmVirtualCircuitLogicalChannel             LogicalChannelId,
    nlmVirtualCircuitPacketSizeIncoming         Unsigned32,
    nlmVirtualCircuitPacketSizeOutgoing         Unsigned32,
    nlmVirtualCircuitThroughputClassIncoming    Unsigned32,
    nlmVirtualCircuitThroughputClassOutgoing    Unsigned32,
    nlmVirtualCircuitWindowSizeIncoming         Unsigned32,
    nlmVirtualCircuitWindowSizeOutgoing         Unsigned32
}

nlmVirtualCircuitId OBJECT-TYPE
    SYNTAX      SimpleNameType
    MAX-ACCESS  not-accessible
    STATUS      current
    DESCRIPTION 
        ""
    REFERENCE   
        "ITU-T Rec. X.283 (1997) | ISO/IEC 10733 : 1998, 
               virtualCircuitId ATTRIBUTE"
    ::= { nlmVirtualCircuitEntry 1 }

nlmVirtualCircuitLogicalChannel OBJECT-TYPE
    SYNTAX      LogicalChannelId
    MAX-ACCESS  read-only
    STATUS      current
    DESCRIPTION 
        "The actual Logical Channel ID used for the call."
    REFERENCE   
        "ITU-T Rec. X.283 (1997) | ISO/IEC 10733 : 1998, 
               logicalChannel ATTRIBUTE"
    ::= { nlmVirtualCircuitEntry 2 }

nlmVirtualCircuitPacketSizeIncoming OBJECT-TYPE
    SYNTAX      Unsigned32
    MAX-ACCESS  read-only
    STATUS      current
    DESCRIPTION 
        "The packet sizes for this VC. In the case of an IVMO MO 
         it is the proposed value of the packet sizes (incoming 
         and outgoing) to be used when establishing the virtual 
         call, expressed in octets. The value of NULL indicates 
         that the default packet size for that direction (as 
         indicated by the defaultPacketSizes attribute of the 
         containing X.25 PLE MO), is to be used. In the case of 
         a non-IVMO MO it is the actual packet sizes in use for 
         this VC."
    REFERENCE   
        "ITU-T Rec. X.283 (1997) | ISO/IEC 10733 : 1998, 
               packetSizes ATTRIBUTE"
    ::= { nlmVirtualCircuitEntry 3 }

nlmVirtualCircuitPacketSizeOutgoing OBJECT-TYPE
    SYNTAX      Unsigned32
    MAX-ACCESS  read-only
    STATUS      current
    DESCRIPTION 
        "The packet sizes for this VC. In the case of an IVMO MO 
         it is the proposed value of the packet sizes (incoming 
         and outgoing) to be used when establishing the virtual 
         call, expressed in octets. The value of NULL indicates 
         that the default packet size for that direction (as 
         indicated by the defaultPacketSizes attribute of the 
         containing X.25 PLE MO), is to be used. In the case of 
         a non-IVMO MO it is the actual packet sizes in use for 
         this VC."
    REFERENCE   
        "ITU-T Rec. X.283 (1997) | ISO/IEC 10733 : 1998, 
               packetSizes ATTRIBUTE"
    ::= { nlmVirtualCircuitEntry 4 }

nlmVirtualCircuitThroughputClassIncoming OBJECT-TYPE
    SYNTAX      Unsigned32
    MAX-ACCESS  read-only
    STATUS      current
    DESCRIPTION 
        "The throughput classes in use or to be used. For an 
         IVMO, this is the throughput classes to be proposed. 
         For a non-IVMO it is the actual throughput classes in 
         use. For Virtual Calls this is the result of 
         negotiation."
    REFERENCE   
        "ITU-T Rec. X.283 (1997) | ISO/IEC 10733 : 1998, 
               throughputClasses ATTRIBUTE"
    ::= { nlmVirtualCircuitEntry 5 }

nlmVirtualCircuitThroughputClassOutgoing OBJECT-TYPE
    SYNTAX      Unsigned32
    MAX-ACCESS  read-only
    STATUS      current
    DESCRIPTION 
        "The throughput classes in use or to be used. For an 
         IVMO, this is the throughput classes to be proposed. 
         For a non-IVMO it is the actual throughput classes in 
         use. For Virtual Calls this is the result of 
         negotiation."
    REFERENCE   
        "ITU-T Rec. X.283 (1997) | ISO/IEC 10733 : 1998, 
               throughputClasses ATTRIBUTE"
    ::= { nlmVirtualCircuitEntry 6 }

nlmVirtualCircuitWindowSizeIncoming OBJECT-TYPE
    SYNTAX      Unsigned32
    MAX-ACCESS  read-only
    STATUS      current
    DESCRIPTION 
        "The actual window sizes in use for this VC."
    REFERENCE   
        "ITU-T Rec. X.283 (1997) | ISO/IEC 10733 : 1998, 
               windowSizes ATTRIBUTE"
    ::= { nlmVirtualCircuitEntry 7 }

nlmVirtualCircuitWindowSizeOutgoing OBJECT-TYPE
    SYNTAX      Unsigned32
    MAX-ACCESS  read-only
    STATUS      current
    DESCRIPTION 
        "The actual window sizes in use for this VC."
    REFERENCE   
        "ITU-T Rec. X.283 (1997) | ISO/IEC 10733 : 1998, 
               windowSizes ATTRIBUTE"
    ::= { nlmVirtualCircuitEntry 8 }


-- ==========================================

nlmVirtualCircuitDTETable OBJECT-TYPE
    SYNTAX      SEQUENCE OF NlmVirtualCircuitDTEEntry
    MAX-ACCESS  not-accessible
    STATUS      current
    DESCRIPTION 
        ""
    REFERENCE   
        "ITU-T Rec. X.283 (1997) | ISO/IEC 10733 : 1998, 
               virtualCircuit-DTE MANAGED OBJECT CLASS"
    ::= { nlmVirtualCircuit 2 }

nlmVirtualCircuitDTEEntry OBJECT-TYPE
    SYNTAX      NlmVirtualCircuitDTEEntry
    MAX-ACCESS  not-accessible
    STATUS      current
    DESCRIPTION 
        "5.11.2 The virtual circuit DTE managed object
         
         This MO Class is never instantiated. It serves as 
         a generic Virtual Circuit DTE MO from which both the 
         Virtual Call DTE and the Permanent Virtual Circuit DTE 
         MOs are derived.  Note that the values of the 
         virtualCircuitId naming attribute are required to be 
         unique across all instances of MOs derived from this 
         which have a common superior."
    REFERENCE   
        "ITU-T Rec. X.283 (1997) | ISO/IEC 10733 : 1998, 
               virtualCircuit-DTE MANAGED OBJECT"
    AUGMENTS    { nlmVirtualCircuitEntry }
    ::= { nlmVirtualCircuitDTETable 1 }

NlmVirtualCircuitDTEEntry ::= SEQUENCE {
-- dTEVirtualCircuitCounters-P PACKAGE
    nlmVirtualCircuitDTEOctetsSentCounter           Counter64,
    nlmVirtualCircuitDTEOctetsReceivedCounter       Counter64,
    nlmVirtualCircuitDTEDataPacketsReceived         Counter64,
    nlmVirtualCircuitDTEDataPacketsSent             Counter64,
    nlmVirtualCircuitDTEInterruptTimerExpiries      Counter64,
    nlmVirtualCircuitDTEProviderInitiatedResets     Counter64,
    nlmVirtualCircuitDTERemotelyInitiatedResets     Counter64,
    nlmVirtualCircuitDTEResetTimeouts               Counter64
}

nlmVirtualCircuitDTEOctetsSentCounter OBJECT-TYPE
    SYNTAX      Counter64
    MAX-ACCESS  read-only
    STATUS      current
    DESCRIPTION 
        "Specifies the total number of user data octets sent by 
         the connectionless network protocol state machine."
    REFERENCE   
        "ITU-T Rec. X.721 (1992) | ISO/IEC 10165-2 : 1992, 
               octetsSentCounter"
    ::= { nlmVirtualCircuitDTEEntry 1 }

nlmVirtualCircuitDTEOctetsReceivedCounter OBJECT-TYPE
    SYNTAX      Counter64
    MAX-ACCESS  read-only
    STATUS      current
    DESCRIPTION 
        "Specifies the total number of user data octets received 
         by the connectionless network protocol state machine."
    REFERENCE   
        "ITU-T Rec. X.721 (1992) | ISO/IEC 10165-2 : 1992, 
               octetsReceivedCounter"
    ::= { nlmVirtualCircuitDTEEntry 2 }

nlmVirtualCircuitDTEDataPacketsReceived OBJECT-TYPE
    SYNTAX      Counter64
    MAX-ACCESS  read-only
    STATUS      current
    DESCRIPTION 
        "Counter of the total number of data packets received."
    REFERENCE   
        "ITU-T Rec. X.283 (1997) | ISO/IEC 10733 : 1998, 
               dataPacketsReceived ATTRIBUTE"
    ::= { nlmVirtualCircuitDTEEntry 3 }

nlmVirtualCircuitDTEDataPacketsSent OBJECT-TYPE
    SYNTAX      Counter64
    MAX-ACCESS  read-only
    STATUS      current
    DESCRIPTION 
        "Counter of the total number of data packets sent."
    REFERENCE   
        "ITU-T Rec. X.283 (1997) | ISO/IEC 10733 : 1998, 
               dataPacketsSent ATTRIBUTE"
    ::= { nlmVirtualCircuitDTEEntry 4 }

nlmVirtualCircuitDTEInterruptTimerExpiries OBJECT-TYPE
    SYNTAX      Counter64
    MAX-ACCESS  read-only
    STATUS      current
    DESCRIPTION 
        "Counter of the number of expiries of timer T26 
         experienced by the PLE or over the PVC/VC."
    REFERENCE   
        "ITU-T Rec. X.283 (1997) | ISO/IEC 10733 : 1998, 
               interruptTimerExpiries ATTRIBUTE"
    ::= { nlmVirtualCircuitDTEEntry 5 }

nlmVirtualCircuitDTEProviderInitiatedResets OBJECT-TYPE
    SYNTAX      Counter64
    MAX-ACCESS  read-only
    STATUS      current
    DESCRIPTION 
        "Counter associated with the providerInitiatedReset 
         event which generates a communication alarm 
         notification."
    REFERENCE   
        "ITU-T Rec. X.283 (1997) | ISO/IEC 10733 : 1998, 
               providerInitiatedResets ATTRIBUTE"
    ::= { nlmVirtualCircuitDTEEntry 6 }

nlmVirtualCircuitDTERemotelyInitiatedResets OBJECT-TYPE
    SYNTAX      Counter64
    MAX-ACCESS  read-only
    STATUS      current
    DESCRIPTION 
        "Counter associated with the remotelyInitiatedReset 
         event which generates a communication alarm 
         notification."
    REFERENCE   
        "ITU-T Rec. X.283 (1997) | ISO/IEC 10733 : 1998, 
               remotelyInitiatedResets ATTRIBUTE"
    ::= { nlmVirtualCircuitDTEEntry 7 }

nlmVirtualCircuitDTEResetTimeouts OBJECT-TYPE
    SYNTAX      Counter64
    MAX-ACCESS  read-only
    STATUS      current
    DESCRIPTION 
        "Counter of the number of timer T22 expiries experienced 
         by the PLE."
    REFERENCE   
        "ITU-T Rec. X.283 (1997) | ISO/IEC 10733 : 1998, 
               resetTimeouts ATTRIBUTE"
    ::= { nlmVirtualCircuitDTEEntry 8 }


-- ==========================================

nlmVirtualCircuitDCETable OBJECT-TYPE
    SYNTAX      SEQUENCE OF NlmVirtualCircuitDCEEntry
    MAX-ACCESS  not-accessible
    STATUS      current
    DESCRIPTION 
        ""
    REFERENCE   
        "ITU-T Rec. X.283 (1997) | ISO/IEC 10733 : 1998, 
               virtualCircuit-DCE MANAGED OBJECT CLASS"
    ::= { nlmVirtualCircuit 3 }

nlmVirtualCircuitDCEEntry OBJECT-TYPE
    SYNTAX      NlmVirtualCircuitDCEEntry
    MAX-ACCESS  not-accessible
    STATUS      current
    DESCRIPTION 
        ""
    REFERENCE   
        "ITU-T Rec. X.283 (1997) | ISO/IEC 10733 : 1998, 
               virtualCircuit-DCE MANAGED OBJECT"
    AUGMENTS    { nlmVirtualCircuitEntry }
    ::= { nlmVirtualCircuitDCETable 1 }

NlmVirtualCircuitDCEEntry ::= SEQUENCE {
-- dCECommonVirtualCircuitCounters-P PACKAGE
    nlmVirtualCircuitDCEDataPacketsReceived             Counter64,
    nlmVirtualCircuitDCEDataPacketsSent                 Counter64,
    nlmVirtualCircuitDCEInterruptPacketsReceived        Counter64,
    nlmVirtualCircuitDCEInterruptPacketsSent            Counter64,
    nlmVirtualCircuitDCEInterruptTimerExpiries          Counter64,
    nlmVirtualCircuitDCEOctetsReceivedCounter           Counter64,
    nlmVirtualCircuitDCEOctetsSentCounter               Counter64,
    nlmVirtualCircuitDCEProviderInitiatedDisconnects    Counter64,
    nlmVirtualCircuitDCEProviderInitiatedResets         Counter64,
    nlmVirtualCircuitDCERemotelyInitiatedRestarts       Counter64,
    nlmVirtualCircuitDCERemotelyInitiatedResets         Counter64,
    nlmVirtualCircuitDCEResetTimeouts                   Counter64,
    nlmVirtualCircuitDCEx25SegmentsReceived             Counter64,
    nlmVirtualCircuitDCEx25SegmentsSent                 Counter64
}

nlmVirtualCircuitDCEDataPacketsReceived OBJECT-TYPE
    SYNTAX      Counter64
    MAX-ACCESS  read-only
    STATUS      current
    DESCRIPTION 
        "Counter of the total number of data packets received."
    REFERENCE   
        "ITU-T Rec. X.283 (1997) | ISO/IEC 10733 : 1998, 
               dataPacketsReceived ATTRIBUTE"
    ::= { nlmVirtualCircuitDCEEntry 1 }

nlmVirtualCircuitDCEDataPacketsSent OBJECT-TYPE
    SYNTAX      Counter64
    MAX-ACCESS  read-only
    STATUS      current
    DESCRIPTION 
        "Counter of the total number of data packets sent."
    REFERENCE   
        "ITU-T Rec. X.283 (1997) | ISO/IEC 10733 : 1998, 
               dataPacketsSent ATTRIBUTE"
    ::= { nlmVirtualCircuitDCEEntry 2 }

nlmVirtualCircuitDCEInterruptPacketsReceived OBJECT-TYPE
    SYNTAX      Counter64
    MAX-ACCESS  read-only
    STATUS      current
    DESCRIPTION 
        "Counter of the number of interrupt packets received by 
         the PLE or over the PVC/VC."
    REFERENCE   
        "ITU-T Rec. X.283 (1997) | ISO/IEC 10733 : 1998, 
               interruptPacketsReceived ATTRIBUTE"
    ::= { nlmVirtualCircuitDCEEntry 3 }

nlmVirtualCircuitDCEInterruptPacketsSent OBJECT-TYPE
    SYNTAX      Counter64
    MAX-ACCESS  read-only
    STATUS      current
    DESCRIPTION 
        "Counter of the number of interrupt packets sent by the 
         PLE or over the PVC/VC."
    REFERENCE   
        "ITU-T Rec. X.283 (1997) | ISO/IEC 10733 : 1998, 
               interruptPacketsSent ATTRIBUTE"
    ::= { nlmVirtualCircuitDCEEntry 4 }

nlmVirtualCircuitDCEInterruptTimerExpiries OBJECT-TYPE
    SYNTAX      Counter64
    MAX-ACCESS  read-only
    STATUS      current
    DESCRIPTION 
        "Counter of the number of expiries of timer T26 
         experienced by the PLE or over the PVC/VC."
    REFERENCE   
        "ITU-T Rec. X.283 (1997) | ISO/IEC 10733 : 1998, 
               interruptTimerExpiries ATTRIBUTE"
    ::= { nlmVirtualCircuitDCEEntry 5 }

nlmVirtualCircuitDCEOctetsReceivedCounter OBJECT-TYPE
    SYNTAX      Counter64
    MAX-ACCESS  read-only
    STATUS      current
    DESCRIPTION 
        "Specifies the total number of user data octets received 
         by the connectionless network protocol state machine."
    REFERENCE   
        "ITU-T Rec. X.721 (1992) | ISO/IEC 10165-2 : 1992, 
               octetsReceivedCounter"
    ::= { nlmVirtualCircuitDCEEntry 6 }

nlmVirtualCircuitDCEOctetsSentCounter OBJECT-TYPE
    SYNTAX      Counter64
    MAX-ACCESS  read-only
    STATUS      current
    DESCRIPTION 
        "Specifies the total number of user data octets sent by 
         the connectionless network protocol state machine."
    REFERENCE   
        "ITU-T Rec. X.721 (1992) | ISO/IEC 10165-2 : 1992, 
               octetsSentCounter"
    ::= { nlmVirtualCircuitDCEEntry 7 }

nlmVirtualCircuitDCEProviderInitiatedDisconnects OBJECT-TYPE
    SYNTAX      Counter64
    MAX-ACCESS  read-only
    STATUS      current
    DESCRIPTION 
        "Counter for the providerInitiatedDisconnect events 
         which generate communication alarm notifications."
    REFERENCE   
        "ITU-T Rec. X.283 (1997) | ISO/IEC 10733 : 1998, 
               providerInitiatedDisconnects ATTRIBUTE"
    ::= { nlmVirtualCircuitDCEEntry 8 }

nlmVirtualCircuitDCEProviderInitiatedResets OBJECT-TYPE
    SYNTAX      Counter64
    MAX-ACCESS  read-only
    STATUS      current
    DESCRIPTION 
        "Counter associated with the providerInitiatedReset 
         event which generates a communication alarm 
         notification."
    REFERENCE   
        "ITU-T Rec. X.283 (1997) | ISO/IEC 10733 : 1998, 
               providerInitiatedResets ATTRIBUTE"
    ::= { nlmVirtualCircuitDCEEntry 9 }

nlmVirtualCircuitDCERemotelyInitiatedRestarts OBJECT-TYPE
    SYNTAX      Counter64
    MAX-ACCESS  read-only
    STATUS      current
    DESCRIPTION 
        "Counter of the number of remotely initiated restarts. 
         This is the total number of remotely initiated 
         (including provider initiated) restarts experienced by 
         the PLE, excluding the restart associated with bringing 
         up the PLE interface."
    REFERENCE   
        "ITU-T Rec. X.283 (1997) | ISO/IEC 10733 : 1998, 
               remotelyInitiatedRestarts ATTRIBUTE"
    ::= { nlmVirtualCircuitDCEEntry 10 }

nlmVirtualCircuitDCERemotelyInitiatedResets OBJECT-TYPE
    SYNTAX      Counter64
    MAX-ACCESS  read-only
    STATUS      current
    DESCRIPTION 
        "Counter associated with the remotelyInitiatedReset 
         event which generates a communication alarm 
         notification."
    REFERENCE   
        "ITU-T Rec. X.283 (1997) | ISO/IEC 10733 : 1998, 
               remotelyInitiatedResets ATTRIBUTE"
    ::= { nlmVirtualCircuitDCEEntry 11 }

nlmVirtualCircuitDCEResetTimeouts OBJECT-TYPE
    SYNTAX      Counter64
    MAX-ACCESS  read-only
    STATUS      current
    DESCRIPTION 
        "Counter of the number of timer T22 expiries experienced 
         by the PLE."
    REFERENCE   
        "ITU-T Rec. X.283 (1997) | ISO/IEC 10733 : 1998, 
               resetTimeouts ATTRIBUTE"
    ::= { nlmVirtualCircuitDCEEntry 12 }

nlmVirtualCircuitDCEx25SegmentsReceived OBJECT-TYPE
    SYNTAX      Counter64
    MAX-ACCESS  read-only
    STATUS      current
    DESCRIPTION 
        "Value for count of X.25 Segments Received."
    REFERENCE   
        "ITU-T Rec. X.283 (1997) | ISO/IEC 10733 : 1998, 
               x25SegmentsReceived ATTRIBUTE"
    ::= { nlmVirtualCircuitDCEEntry 13 }

nlmVirtualCircuitDCEx25SegmentsSent OBJECT-TYPE
    SYNTAX      Counter64
    MAX-ACCESS  read-only
    STATUS      current
    DESCRIPTION 
        "Value for count of X.25 Segments Sent."
    REFERENCE   
        "ITU-T Rec. X.283 (1997) | ISO/IEC 10733 : 1998, 
               x25SegmentsSent ATTRIBUTE"
    ::= { nlmVirtualCircuitDCEEntry 14 }


-- ==========================================

nlmPermanentVirtualCircuitDTETable OBJECT-TYPE
    SYNTAX      SEQUENCE OF NlmPermanentVirtualCircuitDTEEntry
    MAX-ACCESS  not-accessible
    STATUS      current
    DESCRIPTION 
        ""
    REFERENCE   
        "ITU-T Rec. X.283 (1997) | ISO/IEC 10733 : 1998, 
               permanentVirtualCircuit-DTE MANAGED OBJECT CLASS"
    ::= { nlmVirtualCircuit 4 }

nlmPermanentVirtualCircuitDTEEntry OBJECT-TYPE
    SYNTAX      NlmPermanentVirtualCircuitDTEEntry
    MAX-ACCESS  not-accessible
    STATUS      current
    DESCRIPTION 
        "5.11.4 The permanent virtual circuit DTE managed object
         
         An instance of this MO exists for each Permanent 
         Virtual Circuit.  It may be both created and deleted by 
         management.
         
         When the MO is created, the protocol machine shall be 
         reinitialized and a reset PDU with a cause code of DTE 
         originated (encoded as 00000000) and a diagnostic code 
         of DTE operational (161) shall be transmitted. When the 
         MO is deleted, the protocol machine shall be 
         reinitialized and a reset PDU with a cause code of DTE 
         originated (encoded as 00000000) and a diagnostic code 
         of DTE not operational (162) shall be transmitted."
    REFERENCE   
        "ITU-T Rec. X.283 (1997) | ISO/IEC 10733 : 1998, 
               permanentVirtualCircuit-DTE MANAGED OBJECT"
    AUGMENTS    { nlmVirtualCircuitEntry }
    ::= { nlmPermanentVirtualCircuitDTETable 1 }

NlmPermanentVirtualCircuitDTEEntry ::= SEQUENCE {
    nlmPermanentVirtualCircuitDTERowStatus      RowStatus
}

nlmPermanentVirtualCircuitDTERowStatus OBJECT-TYPE
    SYNTAX      RowStatus
    MAX-ACCESS  read-create
    STATUS      current
    DESCRIPTION 
        ""
    REFERENCE   
        "ITU-T Rec. X.283 (1997) | ISO/IEC 10733 : 1998, 
               permanentVirtualCircuit-DTE-x25PLE-DTE NAME 
               BINDING"
    ::= { nlmPermanentVirtualCircuitDTEEntry 1 }

-- ==========================================

nlmPermanentVirtualCircuitDCETable OBJECT-TYPE
    SYNTAX      SEQUENCE OF NlmPermanentVirtualCircuitDCEEntry
    MAX-ACCESS  not-accessible
    STATUS      current
    DESCRIPTION 
        ""
    REFERENCE   
        "ITU-T Rec. X.283 (1997) | ISO/IEC 10733 : 1998, 
               permanentVirtualCircuit-DCE MANAGED OBJECT CLASS"
    ::= { nlmVirtualCircuit 5 }

nlmPermanentVirtualCircuitDCEEntry OBJECT-TYPE
    SYNTAX      NlmPermanentVirtualCircuitDCEEntry
    MAX-ACCESS  not-accessible
    STATUS      current
    DESCRIPTION 
        "5.11.5 The permanent virtual circuit DCE managed object
         
         An instance of this MO exists for each Permanent 
         Virtual Circuit. It may be both created and deleted by 
         management.
         
         When the MO is created, the protocol machine shall be 
         re-initialized and a reset PDU shall be transmitted. 
         A cause code of remote DTE Operational (encoded as X000 
         1001) or Network Operational (encoded as X000 1111) 
         may, for example, be included. When the MO is deleted 
         the protocol machine shall be reinitialized and a reset 
         PDU shall be transmitted. A cause code of Out of Order 
         (encoded as X000 0001) or Network Out of Order (encoded 
         as X001 1101) may, for example, be included."
    REFERENCE   
        "ITU-T Rec. X.283 (1997) | ISO/IEC 10733 : 1998, 
               permanentVirtualCircuit-DCE MANAGED OBJECT"
    AUGMENTS    { nlmVirtualCircuitEntry }
    ::= { nlmPermanentVirtualCircuitDCETable 1 }

NlmPermanentVirtualCircuitDCEEntry ::= SEQUENCE {
    nlmPermanentVirtualCircuitDCEChargingDirection      TruthValue,
    nlmPermanentVirtualCircuitDCEOperationalState       OperationalState,
    nlmPermanentVirtualCircuitDCERemoteDTEAddress       DTEAddress,
    nlmPermanentVirtualCircuitDCERemoteLogicalChannel   LogicalChannelId,
    nlmPermanentVirtualCircuitDCERowStatus              RowStatus
}

nlmPermanentVirtualCircuitDCEChargingDirection OBJECT-TYPE
    SYNTAX      TruthValue
    MAX-ACCESS  read-create
    STATUS      current
    DESCRIPTION 
        "Indicates the use of the charging direction facility 
         for that call."
    REFERENCE   
        "ITU-T Rec. X.283 (1997) | ISO/IEC 10733 : 1998, 
               chargingDirection ATTRIBUTE"
    ::= { nlmPermanentVirtualCircuitDCEEntry 1 }

nlmPermanentVirtualCircuitDCEOperationalState OBJECT-TYPE
    SYNTAX      OperationalState
    MAX-ACCESS  read-create
    STATUS      current
    DESCRIPTION 
        "Provides the operational state of the PVC in accordance 
         with the OperationalState textual convention of the 
         OPENSS7-SMI-MIB and ITU-T Rec. X.721 (1992) | ISO/IEC 
         10165-2 : 1992."
    REFERENCE   
        "ITU-T Rec. X.721 (1992) | ISO/IEC 10165-2 : 1992, 
               operationalState"
    ::= { nlmPermanentVirtualCircuitDCEEntry 2 }

nlmPermanentVirtualCircuitDCERemoteDTEAddress OBJECT-TYPE
    SYNTAX      DTEAddress
    MAX-ACCESS  read-create
    STATUS      current
    DESCRIPTION 
        "The DTE Address of the remote DTE. In the case of an 
         outgoing call, this is the remote DTE address from the 
         called address of the transmitted call request packet. 
         In the case of an incoming call, it is the calling 
         address from the received call request packet."
    REFERENCE   
        "ITU-T Rec. X.283 (1997) | ISO/IEC 10733 : 1998, 
               remoteDTEAddress ATTRIBUTE"
    ::= { nlmPermanentVirtualCircuitDCEEntry 3 }

nlmPermanentVirtualCircuitDCERemoteLogicalChannel OBJECT-TYPE
    SYNTAX      LogicalChannelId
    MAX-ACCESS  read-create
    STATUS      current
    DESCRIPTION 
        "The Remote Logical Channel ID for the Permanent Virtual 
         Circuit."
    REFERENCE   
        "ITU-T Rec. X.283 (1997) | ISO/IEC 10733 : 1998, 
               remoteLogicalChannel ATTRIBUTE"
    ::= { nlmPermanentVirtualCircuitDCEEntry 4 }

nlmPermanentVirtualCircuitDCERowStatus OBJECT-TYPE
    SYNTAX      RowStatus
    MAX-ACCESS  read-create
    STATUS      current
    DESCRIPTION 
        ""
    REFERENCE   
        "ITU-T Rec. X.283 (1997) | ISO/IEC 10733 : 1998, 
               permanentVirtualCircuit-DCE-x25PLE-DCE NAME 
               BINDING"
    ::= { nlmPermanentVirtualCircuitDCEEntry 5 }


-- ==========================================

nlmVirtualCallIVMOTable OBJECT-TYPE
    SYNTAX      SEQUENCE OF NlmVirtualCallIVMOEntry
    MAX-ACCESS  not-accessible
    STATUS      current
    DESCRIPTION 
        ""
    REFERENCE   
        "ITU-T Rec. X.283 (1997) | ISO/IEC 10733 : 1998, 
               virtualCallIVMO MANAGED OBJECT CLASS"
    ::= { nlmVirtualCircuit 6 }

nlmVirtualCallIVMOEntry OBJECT-TYPE
    SYNTAX      NlmVirtualCallIVMOEntry
    MAX-ACCESS  not-accessible
    STATUS      current
    DESCRIPTION 
        "5.11.6 The virtual call initial values managed object
         
         There may be multiple instances of the virtualCallIVMO 
         in a system.  A virtualCallIVMO may be used to supply 
         initial values for the attributes of the 
         virtualCall-DTE or virtualCall-DCE MO.  Different 
         instances of virtualCallIVMO may contain different 
         initial values.
         
         Its definition permits it to be created and deleted 
         explicitly by management operation."
    REFERENCE   
        "ITU-T Rec. X.283 (1997) | ISO/IEC 10733 : 1998, 
               virtualCallIVMO MANAGED OBJECT"
    INDEX       { nlmX25PLEId, nlmVirtualCallIVMOId }
    ::= { nlmVirtualCallIVMOTable 1 }

NlmVirtualCallIVMOEntry ::= SEQUENCE {
    nlmVirtualCallIVMOId                        SimpleNameType,
    nlmVirtualCallIVMOFastSelect                FastSelect,
    nlmVirtualCallIVMOPacketSizeIncoming        Unsigned32,
    nlmVirtualCallIVMOPacketSizeOutgoing        Unsigned32,
    nlmVirtualCallIVMOReverseCharging           TruthValue,
    nlmVirtualCallIVMOThroughputClassIncoming   Integer32,
    nlmVirtualCallIVMOThroughputClassOutgoing   Integer32,
    nlmVirtualCallIVMOWindowSizeIncoming        Unsigned32,
    nlmVirtualCallIVMOWindowSizeOutgoing        Unsigned32,
    nlmVirtualCallIVMORowStatus                 RowStatus
}

nlmVirtualCallIVMOId OBJECT-TYPE
    SYNTAX      SimpleNameType
    MAX-ACCESS  not-accessible
    STATUS      current
    DESCRIPTION 
        "The name of this instance of virtualCallIVMO."
    REFERENCE   
        "ITU-T Rec. X.283 (1997) | ISO/IEC 10733 : 1998, 
               virtualCallIVMOId ATTRIBUTE"
    ::= { nlmVirtualCallIVMOEntry 1 }

nlmVirtualCallIVMOFastSelect OBJECT-TYPE
    SYNTAX      FastSelect
    MAX-ACCESS  read-create
    STATUS      current
    DESCRIPTION 
        "Type of fast select used or to be used for call. In the 
         case of an IVMO, this specifies that one of 'fast 
         select', 'fast select with restricted response', or no 
         fast select facility is to be used for the call. It 
         includes a value 'not specified' which indicates that 
         no preference is expressed in the IVMO. In the case of 
         a non-IVMO MO, this specifies that one of 'fast select' 
         or 'no fast select' was used for the call."
    REFERENCE   
        "ITU-T Rec. X.283 (1997) | ISO/IEC 10733 : 1998, 
               fastSelect ATTRIBUTE"
    ::= { nlmVirtualCallIVMOEntry 2 }

nlmVirtualCallIVMOPacketSizeIncoming OBJECT-TYPE
    SYNTAX      Unsigned32
    MAX-ACCESS  read-create
    STATUS      current
    DESCRIPTION 
        "The packet sizes for this VC. In the case of an IVMO MO 
         it is the proposed value of the packet sizes (incoming 
         and outgoing) to be used when establishing the virtual 
         call, expressed in octets. The value of NULL indicates 
         that the default packet size for that direction (as 
         indicated by the defaultPacketSizes attribute of the 
         containing X.25 PLE MO), is to be used. In the case of 
         a non-IVMO MO it is the actual packet sizes in use for 
         this VC."
    REFERENCE   
        "ITU-T Rec. X.283 (1997) | ISO/IEC 10733 : 1998, 
               packetSizes ATTRIBUTE"
    ::= { nlmVirtualCallIVMOEntry 3 }

nlmVirtualCallIVMOPacketSizeOutgoing OBJECT-TYPE
    SYNTAX      Unsigned32
    MAX-ACCESS  read-create
    STATUS      current
    DESCRIPTION 
        "The packet sizes for this VC. In the case of an IVMO MO 
         it is the proposed value of the packet sizes (incoming 
         and outgoing) to be used when establishing the virtual 
         call, expressed in octets. The value of NULL indicates 
         that the default packet size for that direction (as 
         indicated by the defaultPacketSizes attribute of the 
         containing X.25 PLE MO), is to be used. In the case of 
         a non-IVMO MO it is the actual packet sizes in use for 
         this VC."
    REFERENCE   
        "ITU-T Rec. X.283 (1997) | ISO/IEC 10733 : 1998, 
               packetSizes ATTRIBUTE"
    ::= { nlmVirtualCallIVMOEntry 4 }

nlmVirtualCallIVMOReverseCharging OBJECT-TYPE
    SYNTAX      TruthValue
    MAX-ACCESS  read-create
    STATUS      current
    DESCRIPTION 
        "Use of reverse charging. When 'True' for an outgoing 
         call, it shall be (for an IVMO), or was (for 
         a non-IVMO), initiated requesting reverse charging. 
         When 'True' for an incoming call associated with 
         a virtualCall MO, it indicates that reverse charging 
         was accepted."
    REFERENCE   
        "ITU-T Rec. X.283 (1997) | ISO/IEC 10733 : 1998, 
               reverseCharging ATTRIBUTE"
    ::= { nlmVirtualCallIVMOEntry 5 }

nlmVirtualCallIVMOThroughputClassIncoming OBJECT-TYPE
    SYNTAX      Integer32
    MAX-ACCESS  read-create
    STATUS      current
    DESCRIPTION 
        "The throughput classes in use or to be used. For an 
         IVMO, this is the throughput classes to be proposed. 
         For a non-IVMO it is the actual throughput classes in 
         use. For Virtual Calls this is the result of 
         negotiation."
    REFERENCE   
        "ITU-T Rec. X.283 (1997) | ISO/IEC 10733 : 1998, 
               throughputClasses ATTRIBUTE"
    ::= { nlmVirtualCallIVMOEntry 6 }

nlmVirtualCallIVMOThroughputClassOutgoing OBJECT-TYPE
    SYNTAX      Integer32
    MAX-ACCESS  read-create
    STATUS      current
    DESCRIPTION 
        "The throughput classes in use or to be used. For an 
         IVMO, this is the throughput classes to be proposed. 
         For a non-IVMO it is the actual throughput classes in 
         use. For Virtual Calls this is the result of 
         negotiation."
    REFERENCE   
        "ITU-T Rec. X.283 (1997) | ISO/IEC 10733 : 1998, 
               throughputClasses ATTRIBUTE"
    ::= { nlmVirtualCallIVMOEntry 7 }

nlmVirtualCallIVMOWindowSizeIncoming OBJECT-TYPE
    SYNTAX      Unsigned32
    MAX-ACCESS  read-create
    STATUS      current
    DESCRIPTION 
        "The actual window sizes in use for this VC."
    REFERENCE   
        "ITU-T Rec. X.283 (1997) | ISO/IEC 10733 : 1998, 
               windowSizes ATTRIBUTE"
    ::= { nlmVirtualCallIVMOEntry 8 }

nlmVirtualCallIVMOWindowSizeOutgoing OBJECT-TYPE
    SYNTAX      Unsigned32
    MAX-ACCESS  read-create
    STATUS      current
    DESCRIPTION 
        "The actual window sizes in use for this VC."
    REFERENCE   
        "ITU-T Rec. X.283 (1997) | ISO/IEC 10733 : 1998, 
               windowSizes ATTRIBUTE"
    ::= { nlmVirtualCallIVMOEntry 9 }

nlmVirtualCallIVMORowStatus OBJECT-TYPE
    SYNTAX      RowStatus
    MAX-ACCESS  read-create
    STATUS      current
    DESCRIPTION 
        ""
    REFERENCE   
        "ITU-T Rec. X.283 (1997) | ISO/IEC 10733 : 1998, 
               virtualCallIVMO-x25PLE NAME BINDING"
    ::= { nlmVirtualCallIVMOEntry 10 }


-- ==========================================

nlmVirtualCallDTETable OBJECT-TYPE
    SYNTAX      SEQUENCE OF NlmVirtualCallDTEEntry
    MAX-ACCESS  not-accessible
    STATUS      current
    DESCRIPTION 
        ""
    REFERENCE   
        "ITU-T Rec. X.283 (1997) | ISO/IEC 10733 : 1998, 
               virtualCall-DTE MANAGED OBJECT CLASS"
    ::= { nlmVirtualCircuit 7 }

nlmVirtualCallDTEEntry OBJECT-TYPE
    SYNTAX      NlmVirtualCallDTEEntry
    MAX-ACCESS  not-accessible
    STATUS      current
    DESCRIPTION 
        "5.11.7 The virtual call DTE managed object
         
         An instance of this MO exists for each Virtual Call. It 
         is not created by management, but by the operation of 
         the protocol state machine.  An existing instance may, 
         however, be deactivated by management action, which 
         will cause the associated VC to be cleared.
         
         An instance of this MO is created and exists as long as 
         real resources are consumed by the existence of the 
         virtual call. It is an implementation matter to 
         determine the point during call establishment when real 
         resources are consumed, and conversely, when during 
         call clearing, when they are released.
         
         The Deactivate action causes the connection to be 
         terminated. The termination should occur as rapidly as 
         practical, but no particular time constraints are 
         implied. Typically, this action simulates a disconnect 
         request received across the service interface. If 
         a more rapid means for terminating the connection 
         exists, then this should be used. The termination shall 
         occur in conformance to the protocol standard. The 
         Managed Object remains in existence after completion of 
         the Deactivate action. It is subsequently deleted when 
         the connection is terminated, in the same way as if the 
         connection has been terminated by other means. 
         A deactivate action may fail (with the ProcessingError 
         response) if it is temporarily not possible to 
         terminate the connection.
         
         This Package imports the communicationsInformation 
         notification from 'GMI'. It is used to report the 
         following events. successfulConnectionEstablishment: 
         Generated when a connection is successfully 
         established. However, the precise synchronization 
         between the notification and the corresponding protocol 
         and service interface interactions is not defined by 
         this Specification. The value 
         NLM.successfulConnectionEstablishment shall be reported 
         in the informationType field."
    REFERENCE   
        "ITU-T Rec. X.283 (1997) | ISO/IEC 10733 : 1998, 
               virtualCall-DTE MANAGED OBJECT"
    AUGMENTS    { nlmVirtualCircuitEntry }
    ::= { nlmVirtualCallDTETable 1 }

NlmVirtualCallDTEEntry ::= SEQUENCE {
    nlmVirtualCallDTECallingAddressExtension    NAddress,
    nlmVirtualCallDTECalledAddressExtension     NAddress,
    nlmVirtualCallDTEDirection                  Direction,
    nlmVirtualCallDTEFastSelect                 FastSelect,
    nlmVirtualCallDTEOriginallyCalledAddress    DTEAddress,
    nlmVirtualCallDTERedirectReason             RedirectReason,
    nlmVirtualCallDTERemoteDTEAddress           DTEAddress,
    nlmVirtualCallDTEReverseCharging            TruthValue
}

nlmVirtualCallDTECallingAddressExtension OBJECT-TYPE
    SYNTAX      NAddress
    MAX-ACCESS  read-only
    STATUS      current
    DESCRIPTION 
        "The contents of the calling address extension field.
         
         In the OSI context this will always be an NSAP address 
         but in other uses it may not. In any case it may be 
         null, for example, when used by ITU-T Rec. X.233 
         | ISO/IEC 8473-1."
    REFERENCE   
        "ITU-T Rec. X.283 (1997) | ISO/IEC 10733 : 1998, 
               callingAddressExtension ATTRIBUTE"
    ::= { nlmVirtualCallDTEEntry 1 }

nlmVirtualCallDTECalledAddressExtension OBJECT-TYPE
    SYNTAX      NAddress
    MAX-ACCESS  read-only
    STATUS      current
    DESCRIPTION 
        "The contents of the called address extension field.
         
         In the OSI context this will always be an NSAP address 
         but in other uses it may not. In any case it may be 
         null, for example, when used by ITU-T Rec. X.233 
         | ISO/IEC 8473-1."
    REFERENCE   
        "ITU-T Rec. X.283 (1997) | ISO/IEC 10733 : 1998, 
               calledAddressExtension ATTRIBUTE"
    ::= { nlmVirtualCallDTEEntry 2 }

nlmVirtualCallDTEDirection OBJECT-TYPE
    SYNTAX      Direction
    MAX-ACCESS  read-only
    STATUS      current
    DESCRIPTION 
        "The direction (incoming or outgoing) of the call."
    REFERENCE   
        "ITU-T Rec. X.283 (1997) | ISO/IEC 10733 : 1998, 
               direction ATTRIBUTE"
    ::= { nlmVirtualCallDTEEntry 3 }

nlmVirtualCallDTEFastSelect OBJECT-TYPE
    SYNTAX      FastSelect
    MAX-ACCESS  read-only
    STATUS      current
    DESCRIPTION 
        "Type of fast select used or to be used for call. In the 
         case of an IVMO, this specifies that one of 'fast 
         select', 'fast select with restricted response', or no 
         fast select facility is to be used for the call. It 
         includes a value 'not specified' which indicates that 
         no preference is expressed in the IVMO. In the case of 
         a non-IVMO MO, this specifies that one of 'fast select' 
         or 'no fast select' was used for the call."
    REFERENCE   
        "ITU-T Rec. X.283 (1997) | ISO/IEC 10733 : 1998, 
               fastSelect ATTRIBUTE"
    ::= { nlmVirtualCallDTEEntry 4 }

nlmVirtualCallDTEOriginallyCalledAddress OBJECT-TYPE
    SYNTAX      DTEAddress
    MAX-ACCESS  read-only
    STATUS      current
    DESCRIPTION 
        "The originally called address."
    REFERENCE   
        "ITU-T Rec. X.283 (1997) | ISO/IEC 10733 : 1998, 
               originallyCalledAddress ATTRIBUTE"
    ::= { nlmVirtualCallDTEEntry 5 }

nlmVirtualCallDTERedirectReason OBJECT-TYPE
    SYNTAX      RedirectReason
    MAX-ACCESS  read-only
    STATUS      current
    DESCRIPTION 
        "The reason why the call has been redirected. This is 
         the reason why the call has been offered or has been 
         connected to an address different from the originally 
         called address. That is, the value of the first octet 
         of the Facility Parameter Field of the CRCDN or CLAMN 
         facility, indicating the reason for call redirection or 
         call deflection. The zero value indicates that the call 
         was not redirected."
    REFERENCE   
        "ITU-T Rec. X.283 (1997) | ISO/IEC 10733 : 1998, 
               redirectReason ATTRIBUTE"
    ::= { nlmVirtualCallDTEEntry 6 }

nlmVirtualCallDTERemoteDTEAddress OBJECT-TYPE
    SYNTAX      DTEAddress
    MAX-ACCESS  read-only
    STATUS      current
    DESCRIPTION 
        "The DTE Address of the remote DTE. In the case of an 
         outgoing call, this is the remote DTE address from the 
         called address of the transmitted call request packet. 
         In the case of an incoming call, it is the calling 
         address from the received call request packet."
    REFERENCE   
        "ITU-T Rec. X.283 (1997) | ISO/IEC 10733 : 1998, 
               remoteDTEAddress ATTRIBUTE"
    ::= { nlmVirtualCallDTEEntry 7 }

nlmVirtualCallDTEReverseCharging OBJECT-TYPE
    SYNTAX      TruthValue
    MAX-ACCESS  read-only
    STATUS      current
    DESCRIPTION 
        "Use of reverse charging. When 'True' for an outgoing 
         call, it shall be (for an IVMO), or was (for 
         a non-IVMO), initiated requesting reverse charging. 
         When 'True' for an incoming call associated with 
         a virtualCall MO, it indicates that reverse charging 
         was accepted."
    REFERENCE   
        "ITU-T Rec. X.283 (1997) | ISO/IEC 10733 : 1998, 
               reverseCharging ATTRIBUTE"
    ::= { nlmVirtualCallDTEEntry 8 }


-- ==========================================

nlmVirtualCallDCETable OBJECT-TYPE
    SYNTAX      SEQUENCE OF NlmVirtualCallDCEEntry
    MAX-ACCESS  not-accessible
    STATUS      current
    DESCRIPTION 
        ""
    REFERENCE   
        "ITU-T Rec. X.283 (1997) | ISO/IEC 10733 : 1998, 
               virtualCall-DCE MANAGED OBJECT CLASS"
    ::= { nlmVirtualCircuit 8 }

nlmVirtualCallDCEEntry OBJECT-TYPE
    SYNTAX      NlmVirtualCallDCEEntry
    MAX-ACCESS  not-accessible
    STATUS      current
    DESCRIPTION 
        "5.11.8 The virtual call DCE managed object
         
         An instance of this MO is created and exists as long as 
         real resources are consumed by the existence of the 
         Virtual Call. It is an implementation matter to 
         determine the point during a call establishment when 
         real resources are consumed, and conversely, when 
         during call clearing, when they are released.
         
         An instance of this MO is created and exists as long as 
         real resources are consumed by the existence of the 
         virtual call. It is an implementation matter to 
         determine the point during call establishment when real 
         resources are consumed, and conversely, when during 
         call clearing, when they are released.

         The Deactivate action causes the connection to be 
         terminated. The termination should occur as rapidly as 
         practical, but no particular time constraints are 
         implied. Typically, this action simulates a disconnect 
         request received across the service interface. If 
         a more rapid means for terminating the connection 
         exists, then this should be used. The termination shall 
         occur in conformance to the protocol standard. The 
         Managed Object remains in existence after completion of 
         the Deactivate action. It is subsequently deleted when 
         the connection is terminated, in the same way as if the 
         connection has been terminated by other means. 
         A deactivate action may fail (with the ProcessingError 
         response) if it is temporarily not possible to 
         terminate the connection.
         
         This Package imports the communicationsInformation 
         notification from 'GMI'. It is used to report the 
         following events. successfulConnectionEstablishment: 
         Generated when a connection is successfully 
         established. However, the precise synchronization 
         between the notification and the corresponding protocol 
         and service interface interactions is not defined by 
         this Specification. The value 
         NLM.successfulConnectionEstablishment shall be reported 
         in the informationType field."
    REFERENCE   
        "ITU-T Rec. X.283 (1997) | ISO/IEC 10733 : 1998, 
               virtualCall-DCE MANAGED OBJECT"
    AUGMENTS    { nlmVirtualCircuitEntry }
    ::= { nlmVirtualCallDCETable 1 }

NlmVirtualCallDCEEntry ::= SEQUENCE {
    nlmVirtualCallDCEChargingDirection                      TruthValue,
    nlmVirtualCallDCEcUGSelection                           TruthValue,
    nlmVirtualCallDCEDirection                              Direction,
    nlmVirtualCallDCEFastSelect                             FastSelect,
    nlmVirtualCallDCERemoteDTEAddress                       DTEAddress,
    nlmVirtualCallDCETransitDelaySelectionAndIndication     TruthValue,
-- dCEVirtualCallFacilities-P PACKAGE
    nlmVirtualCallDCEBilateralCUGSelection                  TruthValue,
    nlmVirtualCallDCECallRedirectionDeflectionNotification  TruthValue,
    nlmVirtualCallDCECalledLineAdressModifiedNotification   TruthValue,
    nlmVirtualCallDCEcUGWithOutgoingAccessSelection         TruthValue,
    nlmVirtualCallDCEnUISelection                           TruthValue,
    nlmVirtualCallDCEReverseCharging                        TruthValue,
    nlmVirtualCallDCErOASelection                           TruthValue,
--
    nlmVirtualCallDCERowStatus                              RowStatus
}

nlmVirtualCallDCEChargingDirection OBJECT-TYPE
    SYNTAX      TruthValue
    MAX-ACCESS  read-create
    STATUS      current
    DESCRIPTION 
        "Indicates the use of the charging direction facility 
         for that call."
    REFERENCE   
        "ITU-T Rec. X.283 (1997) | ISO/IEC 10733 : 1998, 
               chargingDirection ATTRIBUTE"
    ::= { nlmVirtualCallDCEEntry 1 }

nlmVirtualCallDCEcUGSelection OBJECT-TYPE
    SYNTAX      TruthValue
    MAX-ACCESS  read-create
    STATUS      current
    DESCRIPTION 
        "Indicates the use of the closed user group selection 
         facility for that call."
    REFERENCE   
        "ITU-T Rec. X.283 (1997) | ISO/IEC 10733 : 1998, 
               cUGSelection ATTRIBUTE"
    ::= { nlmVirtualCallDCEEntry 2 }

nlmVirtualCallDCEDirection OBJECT-TYPE
    SYNTAX      Direction
    MAX-ACCESS  read-create
    STATUS      current
    DESCRIPTION 
        "The direction (incoming or outgoing) of the call."
    REFERENCE   
        "ITU-T Rec. X.283 (1997) | ISO/IEC 10733 : 1998, 
               direction ATTRIBUTE"
    ::= { nlmVirtualCallDCEEntry 3 }

nlmVirtualCallDCEFastSelect OBJECT-TYPE
    SYNTAX      FastSelect
    MAX-ACCESS  read-create
    STATUS      current
    DESCRIPTION 
        "Type of fast select used or to be used for call. In the 
         case of an IVMO, this specifies that one of 'fast 
         select', 'fast select with restricted response', or no 
         fast select facility is to be used for the call. It 
         includes a value 'not specified' which indicates that 
         no preference is expressed in the IVMO. In the case of 
         a non-IVMO MO, this specifies that one of 'fast select' 
         or 'no fast select' was used for the call."
    REFERENCE   
        "ITU-T Rec. X.283 (1997) | ISO/IEC 10733 : 1998, 
               fastSelect ATTRIBUTE"
    ::= { nlmVirtualCallDCEEntry 4 }

nlmVirtualCallDCERemoteDTEAddress OBJECT-TYPE
    SYNTAX      DTEAddress
    MAX-ACCESS  read-create
    STATUS      current
    DESCRIPTION 
        "The DTE Address of the remote DTE. In the case of an 
         outgoing call, this is the remote DTE address from the 
         called address of the transmitted call request packet. 
         In the case of an incoming call, it is the calling 
         address from the received call request packet."
    REFERENCE   
        "ITU-T Rec. X.283 (1997) | ISO/IEC 10733 : 1998, 
               remoteDTEAddress ATTRIBUTE"
    ::= { nlmVirtualCallDCEEntry 5 }

nlmVirtualCallDCETransitDelaySelectionAndIndication OBJECT-TYPE
    SYNTAX      TruthValue
    MAX-ACCESS  read-create
    STATUS      current
    DESCRIPTION 
        "Indicates the use of the transit delay selection and 
         indication facility for that call."
    REFERENCE   
        "ITU-T Rec. X.283 (1997) | ISO/IEC 10733 : 1998, 
               transitDelaySelectionAndIndication ATTRIBUTE"
    ::= { nlmVirtualCallDCEEntry 6 }

-- dCEVirtualCallFacilities-P PACKAGE

nlmVirtualCallDCEBilateralCUGSelection OBJECT-TYPE
    SYNTAX      TruthValue
    MAX-ACCESS  read-create
    STATUS      current
    DESCRIPTION 
        "Indicates the use of the bilateral closed user group 
         selection facility for that call."
    REFERENCE   
        "ITU-T Rec. X.283 (1997) | ISO/IEC 10733 : 1998, 
               bilateralCUGSelection ATTRIBUTE"
    ::= { nlmVirtualCallDCEEntry 7 }

nlmVirtualCallDCECallRedirectionDeflectionNotification OBJECT-TYPE
    SYNTAX      TruthValue
    MAX-ACCESS  read-create
    STATUS      current
    DESCRIPTION 
        "Indicates the use of the call redirection deflection 
         notification facility for that call."
    REFERENCE   
        "ITU-T Rec. X.283 (1997) | ISO/IEC 10733 : 1998, 
               callRedirectionDeflectionNotification ATTRIBUTE"
    ::= { nlmVirtualCallDCEEntry 8 }

nlmVirtualCallDCECalledLineAdressModifiedNotification OBJECT-TYPE
    SYNTAX      TruthValue
    MAX-ACCESS  read-create
    STATUS      current
    DESCRIPTION 
        "Indicates the use of the called line address modified 
         notification facility for that call."
    REFERENCE   
        "ITU-T Rec. X.283 (1997) | ISO/IEC 10733 : 1998, 
               calledLineAddressModifiedNotification ATTRIBUTE"
    ::= { nlmVirtualCallDCEEntry 9 }

nlmVirtualCallDCEcUGWithOutgoingAccessSelection OBJECT-TYPE
    SYNTAX      TruthValue
    MAX-ACCESS  read-create
    STATUS      current
    DESCRIPTION 
        "Indicates the use of the Closed User Group With 
         Outgoing Access Selection facility for that call. It 
         may only take the value 'True' if the DTE does not have 
         a preferential closed user group, as described in ITU-T 
         Recommendation X.25 and ISO/IEC 8208."
    REFERENCE   
        "ITU-T Rec. X.283 (1997) | ISO/IEC 10733 : 1998, 
               cUGWithOutgoingAccessSelection ATTRIBUTE"
    ::= { nlmVirtualCallDCEEntry 10 }

nlmVirtualCallDCEnUISelection OBJECT-TYPE
    SYNTAX      TruthValue
    MAX-ACCESS  read-create
    STATUS      current
    DESCRIPTION 
        "Indicates the use of the network user identification 
         selection facility for that call."
    REFERENCE   
        "ITU-T Rec. X.283 (1997) | ISO/IEC 10733 : 1998, 
               nUISelection ATTRIBUTE"
    ::= { nlmVirtualCallDCEEntry 11 }

nlmVirtualCallDCEReverseCharging OBJECT-TYPE
    SYNTAX      TruthValue
    MAX-ACCESS  read-create
    STATUS      current
    DESCRIPTION 
        "Use of reverse charging. When 'True' for an outgoing 
         call, it shall be (for an IVMO), or was (for 
         a non-IVMO), initiated requesting reverse charging. 
         When 'True' for an incoming call associated with 
         a virtualCall MO, it indicates that reverse charging 
         was accepted."
    REFERENCE   
        "ITU-T Rec. X.283 (1997) | ISO/IEC 10733 : 1998, 
               reverseCharging ATTRIBUTE"
    ::= { nlmVirtualCallDCEEntry 12 }

nlmVirtualCallDCErOASelection OBJECT-TYPE
    SYNTAX      TruthValue
    MAX-ACCESS  read-create
    STATUS      current
    DESCRIPTION 
        "Indicates the use of the registered operating agency 
         selection facility for that call."
    REFERENCE   
        "ITU-T Rec. X.283 (1997) | ISO/IEC 10733 : 1998, 
               rOASelection ATTRIBUTE"
    ::= { nlmVirtualCallDCEEntry 13 }

--
nlmVirtualCallDCERowStatus OBJECT-TYPE
    SYNTAX      RowStatus
    MAX-ACCESS  read-create
    STATUS      current
    DESCRIPTION 
        "The name binding that applies when the virtualCall-DCE 
         Managed Object is created automatically by the 
         operation of the system. The instance name is derived 
         automatically (as for CREATE 
         WITH-AUTOMATIC-INSTANCE-NAMING). The creation of an 
         instance of the virtualCall-DCE MO using this name 
         binding may reference an instance of the 
         virtualCallIVMO. The means by which such an instance 
         (if any) of the virtualCallIVMO is identified is 
         a local matter. When this occurs, some of the initial 
         values of the attributes of the instance of the 
         virtualCall-DCE MO may be supplied by the values of the 
         attributes in the specified instance of the 
         virtualCallIVMO. However, any such value may be 
         overridden by a value supplied by local means (for 
         example, across an internal interface). Where values 
         are supplied by the IVMO, the initial value of an 
         attribute of the virtualCall-DCE MO shall be the value 
         of the corresponding attribute in the virtualCallIVMO 
         (that is, which has the same attribute template label). 
         The naming attribute of the virtualCall-DCE is assigned 
         a value according to local mechanisms."
    REFERENCE   
        "ITU-T Rec. X.283 (1997) | ISO/IEC 10733 : 1998, 
               virtualCall-DCE-x25PLE-DCE-Management NAME 
               BINDING"
    ::= { nlmVirtualCallDCEEntry 14 }


-- ==========================================

nlmDSeriesCounts OBJECT IDENTIFIER
    ::= { nlmTables 10 }

nlmDSeriesCountsTable OBJECT-TYPE
    SYNTAX      SEQUENCE OF NlmDSeriesCountsEntry
    MAX-ACCESS  not-accessible
    STATUS      current
    DESCRIPTION 
        ""
    REFERENCE   
        "ITU-T Rec. X.283 (1997) | ISO/IEC 10733 : 1998, 
               dSeriesCounts MANAGED OBJECT CLASS"
    ::= { nlmDSeriesCounts 1 }

nlmDSeriesCountsEntry OBJECT-TYPE
    SYNTAX      NlmDSeriesCountsEntry
    MAX-ACCESS  not-accessible
    STATUS      current
    DESCRIPTION 
        "5.11.9 The Recommendation D Series counts managed object
         
         There is one instance of this MO created by management 
         action or automatically for each instance of a virtual 
         call where the Tariff Principles applying to Data 
         Communications Services over dedicated Public Data 
         Networks are applicable. The provisions of the tariff 
         principles are defined in Recommendations D.10, D.11 
         and D.12.
         
         provides the set of packet and segment counts required 
         to collect the charges levied according to the tariff 
         principles contained in Recommendations D.10, D.11 and 
         D.12 for international packet switched public data 
         communications services. The values collected are 
         reported at object deletion."
    REFERENCE   
        "ITU-T Rec. X.283 (1997) | ISO/IEC 10733 : 1998, 
               dSeriesCounts MANAGED OBJECT"
    INDEX       { nlmX25PLEId, nlmVirtualCircuitId, nlmDSeriesCountsId }
    ::= { nlmDSeriesCountsTable 1 }

NlmDSeriesCountsEntry ::= SEQUENCE {
    nlmDSeriesCountsId                              SimpleNameType,
    nlmDSeriesCountsResetRequestIndicationPackets   Counter64,
    nlmDSeriesCountsSegmentsSent                    Counter64,
    nlmDSeriesCountsSegmentsReceived                Counter64,
    nlmDSeriesCountsRowStatus                       RowStatus
}

nlmDSeriesCountsId OBJECT-TYPE
    SYNTAX      SimpleNameType
    MAX-ACCESS  not-accessible
    STATUS      current
    DESCRIPTION 
        "The name of this instance of the dSeriesCounts MO."
    REFERENCE   
        "ITU-T Rec. X.283 (1997) | ISO/IEC 10733 : 1998, 
               dSeriesId ATTRIBUTE"
    ::= { nlmDSeriesCountsEntry 1 }

nlmDSeriesCountsResetRequestIndicationPackets OBJECT-TYPE
    SYNTAX      Counter64
    MAX-ACCESS  read-only
    STATUS      current
    DESCRIPTION 
        "Value for count of Reset Request or Indication Packets 
         with restrictions defined in Recommendation D.11."
    REFERENCE   
        "ITU-T Rec. X.283 (1997) | ISO/IEC 10733 : 1998, 
               dSeriesResetRequestIndicationPackets ATTRIBUTE"
    ::= { nlmDSeriesCountsEntry 2 }

nlmDSeriesCountsSegmentsSent OBJECT-TYPE
    SYNTAX      Counter64
    MAX-ACCESS  read-only
    STATUS      current
    DESCRIPTION 
        "Value for count of Segments Sent, in 64 octets, as per 
         Recommendation D.12."
    REFERENCE   
        "ITU-T Rec. X.283 (1997) | ISO/IEC 10733 : 1998, 
               dSeriesSegmentsSent ATTRIBUTE"
    ::= { nlmDSeriesCountsEntry 3 }

nlmDSeriesCountsSegmentsReceived OBJECT-TYPE
    SYNTAX      Counter64
    MAX-ACCESS  read-only
    STATUS      current
    DESCRIPTION 
        "Value for count of Segments Received, in 64 octets, as 
         per Recommendation D.12."
    REFERENCE   
        "ITU-T Rec. X.283 (1997) | ISO/IEC 10733 : 1998, 
               dSeriesSegmentsReceived ATTRIBUTE"
    ::= { nlmDSeriesCountsEntry 4 }

nlmDSeriesCountsRowStatus OBJECT-TYPE
    SYNTAX      RowStatus
    MAX-ACCESS  read-create
    STATUS      current
    DESCRIPTION 
        "The name binding that applies when the dSeriesCounts 
         Managed Object is created by management operation."
    REFERENCE   
        "ITU-T Rec. X.283 (1997) | ISO/IEC 10733 : 1998, 
               dSeriesCounts-virtualCall-DCE-Management NAME 
               BINDING"
    ::= { nlmDSeriesCountsEntry 5 }

-- ==========================================

nlmScalars OBJECT IDENTIFIER
    ::= { nlmObjects 2 }

nlmNotifs OBJECT IDENTIFIER
    ::= { nlmObjects 3 }

nlmOids OBJECT IDENTIFIER
    ::= { nlmObjects 4 }

nlmConformance OBJECT IDENTIFIER
    ::= { nlmMIB 2 }

nlmCompliances OBJECT IDENTIFIER
    ::= { nlmConformance 1 }

nlmGroups OBJECT IDENTIFIER
    ::= { nlmConformance 2 }

pDUDiscard OBJECT-IDENTITY
    STATUS      current
    DESCRIPTION 
        ""
    REFERENCE   
        "ITU-T Rec. X.283 (1997) | ISO/IEC 10733 : 1998, 
               NLM.pDUDiscard"
    ::= { 2 13 0 2 0 3 1 }
--  ::= { nlmOids 3 1 }

-- pDUDiscard OBJECT IDENTIFIER ::=
--    ::= { joint-iso-ccitt(2) network-layer(13) management(0) 
--          nLM(2) standardSpecificExtensions(0) specificProblems(3) 
--          pDUDiscard(1) }

iSO9542PDUDiscard OBJECT-IDENTITY
    STATUS      current
    DESCRIPTION 
        ""
    REFERENCE   
        "ITU-T Rec. X.283 (1997) | ISO/IEC 10733 : 1998, 
               NLM.iSO9542PDUDiscard"
--  ::= { nlmOids 3 2 }
    ::= { 2 13 0 2 0 3 2 }

-- iSO9542PDUDiscard OBJECT IDENTIFIER ::=
--    ::= { joint-iso-ccitt(2) network-layer(13) management(0) 
--          nLM(2) standardSpecificExtensions(0) specificProblems(3) 
--          iSO9542PDUDiscard(2) }

iSReachabilityChange OBJECT-IDENTITY
    STATUS      current
    DESCRIPTION 
        ""
    REFERENCE   
        ""
--  ::= { nlmOids 4 1 }
    ::= { 2 13 0 2 0 4 1 }

-- iSReachabilityChange OBJECT IDENTIFIER ::=
--    ::= { joint-iso-ccitt(2) network-layer(13) management(0) 
--          nLM(2) standardSpecificExtensions(0) informationType(4) 
--          isReachabilityChange(1) }

eSReachabilityChange OBJECT-IDENTITY
    STATUS      current
    DESCRIPTION 
        ""
    REFERENCE   
        ""
--  ::= { nlmOids 4 2 }
    ::= { 2 13 0 2 0 4 2 }

-- eSReachabilityChange OBJECT IDENTIFIER ::=
--    ::= { joint-iso-ccitt(2) network-layer(13) management(0) 
--          nLM(2) standardSpecificExtensions(0) informationType(4) 
--          esReachabilityChange(2) }

successfulConnectionEstablishment OBJECT-IDENTITY
    STATUS      current
    DESCRIPTION 
        ""
    REFERENCE   
        ""
--  ::= { nlmOids 4 3 }
    ::= { 2 13 0 2 0 4 3 }

-- successfulConnectionEstablishment OBJECT IDENTIFIER ::=
--    ::= { joint-iso-ccitt(2) network-layer(13) management(0) 
--          nLM(2) standardSpecificExtensions(0) informationType(4) 
--          successfulConnectionEstablishment(3) }

sNPADTEAddress OBJECT-IDENTITY
    STATUS      current
    DESCRIPTION 
        ""
    REFERENCE   
        "ITU-T Rec. X.283 (1997) | ISO/IEC 10733 : 1998, 
               NLM.sNPADTEAddress"
--  ::= { nlmOids 5 1 }
    ::= { 2 13 0 2 0 5 1 }

-- sNPADTEAddress OBJECT IDENTIFIER ::=
--    ::= { joint-iso-ccitt(2) network-layer(13) management(0) 
--          nLM(2) standardSpecificExtensions(0) sNPAAddressType(5) 
--          dTEAddress(1) }

sNPAMACAddress OBJECT-IDENTITY
    STATUS      current
    DESCRIPTION 
        ""
    REFERENCE   
        "ITU-T Rec. X.283 (1997) | ISO/IEC 10733 : 1998, 
               NLM.sNPAMACAddress"
--  ::= { nlmOids 5 2 }
    ::= { 2 13 0 2 0 5 2 }

-- sNPAMACAddress OBJECT IDENTIFIER ::=
--    ::= { joint-iso-ccitt(2) network-layer(13) management(0) 
--          nLM(2) standardSpecificExtensions(0) sNPAAddressType(5) 
--          mACAddress(1) }


END -- end of module OPENSS7-NLM-MIB.
-- vim: ft=mib comments=\f\b\:\"ITU\-T,\f\b\:ITU\-T,\f\:\",\b\:\-\-,\:\-\-,\f\b\:\-,\f\b\:\· fo+=tcqlornw12 tw=64 ai nocin nosi sts=4 sw=4 et
