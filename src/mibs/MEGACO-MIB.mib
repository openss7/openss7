-- vim: ft=mib comments=\f\:\",\b\:\-\-,\:\-\-,\f\b\:- fo+=tcqlornw tw=72 nocin nosi sts=4 sw=4
--*********************************************************************
-- MEGACO-MIB
--    Media Gateway Control MIB
--
--*********************************************************************

MEGACO-MIB DEFINITIONS ::= BEGIN

IMPORTS
    InterfaceIndex
        FROM IF-MIB
    SnmpAdminString
        FROM SNMP-FRAMEWORK-MIB
    MODULE-COMPLIANCE, NOTIFICATION-GROUP, OBJECT-GROUP
        FROM SNMPv2-CONF
    Integer32, IpAddress, MODULE-IDENTITY, NOTIFICATION-TYPE, 
    OBJECT-TYPE, Unsigned32, mib-2
        FROM SNMPv2-SMI
    AutonomousType, RowStatus, TEXTUAL-CONVENTION, TestAndIncr, 
    TimeStamp
        FROM SNMPv2-TC;

megacoMIB MODULE-IDENTITY
    LAST-UPDATED "200304181200Z"
    ORGANIZATION 
        "IETF"
    CONTACT-INFO 
        "Postal:
         Bala Pitchandi
         UTStarcom Inc
         33 Wood Avenue South
         Iselin, NJ 08830
         
         Phone:
         +1 (732)452-4457
         
         Email:
         bs@utstar.com"
    DESCRIPTION 
        "Media Gateway Control (Megaco) Management Information Base 
         (MIB)"
    REVISION    "200304181200Z"
    DESCRIPTION 
        "Corrected syntactical errors and some MIB errors"
    REVISION    "200209301200Z"
    DESCRIPTION 
        "Reworked the entire MIB to add the missing objects and 
         eliminate the ambiguities"
    REVISION    "200003201200Z"
    DESCRIPTION 
        "Initial Version by Holdridge et al"
    ::= { mib-2 1000 }


-- *****************************************************************
--
-- Textual conventions for the Media Gateway MIB
--
-- *****************************************************************

MediaGatewayId ::= TEXTUAL-CONVENTION
    DISPLAY-HINT "d"
    STATUS      current
    DESCRIPTION 
        "Possible Media Gateway Id that can be used to identify 
         any media gateway uniquely"
    SYNTAX      Unsigned32 (1..2147483647)

MediaGatewayLinkId ::= TEXTUAL-CONVENTION
    DISPLAY-HINT "d"
    STATUS      current
    DESCRIPTION 
        "Possible Media Gateway Link Id that can be used to identify 
         any media gateway link uniquely"
    SYNTAX      Unsigned32 (1..2147483647)

MediaGatewayTermId ::= TEXTUAL-CONVENTION
    DISPLAY-HINT "d"
    STATUS      current
    DESCRIPTION 
        "Possible Termination Id that can be used to identify 
         any media gateway termination uniquely"
    SYNTAX      Unsigned32 (1..2147483647)

-- *****************************************************************
--
-- OID For the MIB
--
-- *****************************************************************

mediaGatewayMIBObjects OBJECT IDENTIFIER
    ::= { megacoMIB 1 }

-- *****************************************************************
--
-- MEGACO-MIB
--
-- The Media Gateway MIB contains 4 (object) groups
-- medGwyConfiguration
--    This group consists of all the configuration related information
--    pertained with the Media Gateways and Media Gateway Controllers
--    in the network being managed. This group contains the following
--    three tables:
--    medGwyLinkIdTable - Table used to provide the linkId to create
--                        new entries in the gateway table
--    medGwyGatewayConfigTable - Table provides the list of gateways
--                               in the network and their configuration
--    medGwyGatewayControllerTable - Table provides the list of media
--                                   gateway controllers in the network
--                                   and their configuration
-- medGwyStatistics
--    This group consists of all the statistics related information
--    pertained with the gateways. This group contains the following table:
--    medGwyGatewayStatsTable - Table provides the gateway statistics
--                              and related information
--
-- medGwyConnections
--    This group consists of the connections, terminations and their
--    properties related information for the gateways being managed
--    This group contains the following three tables:
--    medGwyTermIdTable - Table used to provide the manager the next
--                        available termination Id.
--    medGwyTerminationsTable - Table provides the list of terminations
--                              and their configuration & status
--    medGwyPropertyProfileTable - Table provides the list of profiles
--                                 that are being supported by the
--                                 gateway
--
-- medGwyProperties
--    For Future Extension
--
--
-- *****************************************************************

-- *****************************************************************
--
-- Group Objects
--
-- *****************************************************************

medGwyConfiguration OBJECT IDENTIFIER
    ::= { mediaGatewayMIBObjects 1 }

-- *****************************************************************
--
-- medGwyLinkIdTable
--   Media Gateway LinkId Table...
--
--   Provides the manager with the nextId for use in creating a
--   LinkId. There is one entry in this table for each MediaGateway.
--
--   Link represents the signalling link between the media gateway
--   and the media gateway controller. The following rules guide
--   the creation of the LinkId
--
--   (1) There could be more than one media gateways (medGwyGatewayId)
--       sharing the same signalling link (medGwyLinkId).
--
--   (2) A gateway may have many links (interfaces) towards the Media
--       Gateway Controller but only the active link that is currently
--       being used to communicate with the controller would be accounted
--       in this table
--
--   If this table isn't implemented, the manager would be
--   responsible for providing the (unique) nextId (via retaining
--   used id's, hashing, etc.)
--
-- *****************************************************************


medGwyLinkIdTable OBJECT-TYPE
    SYNTAX      SEQUENCE OF MedGwyLinkIdEntry
    MAX-ACCESS  not-accessible
    STATUS      current
    DESCRIPTION 
        "This table contains a nextLinkId for each Gateway.  
         It provides the manager with the nextLinkId for use 
         in creating new Gateway Table Entries."
    ::= { medGwyConfiguration 1 }

medGwyLinkIdEntry OBJECT-TYPE
    SYNTAX      MedGwyLinkIdEntry
    MAX-ACCESS  not-accessible
    STATUS      current
    DESCRIPTION 
        "This table contains the NextLinkId for this Gateway 
         and is indexed by mediaGatewayId."
    INDEX       { medGwyGatewayId }
    ::= { medGwyLinkIdTable 1 }

MedGwyLinkIdEntry ::= SEQUENCE {
    medGwyNextLinkId    TestAndIncr
}

medGwyNextLinkId OBJECT-TYPE
    SYNTAX      TestAndIncr
    MAX-ACCESS  read-write
    STATUS      current
    DESCRIPTION 
        "The Next Value for a MediaGateway LinkId.  Assists the 
         manager in selecting a value for medGwyGatewayLinkId.  
         Using the TestAndIncr syntax, A Manager will 'lock' this 
         variable, ensuring single access."
    ::= { medGwyLinkIdEntry 1 }

-- *****************************************************************
--
-- medGwyGatewayConfigTable
--
--   The Media Gateway Configuration Table...
--
--   There would be one entry in this table and is indexed by
--   (medGwyGatewayId, medGwyGatewayLinkId). The table is guided by
--   the following rules:
--
--   (1) There is one entry in this table for each MediaGateway
--       SignallingLink.
--
--   (2) Even though gateways could share the signalling link, they
--       could have different IP Address and/or Port Number. In order
--       to accomodate that, the table is indexed by both medGwyGatewayId
--       and medGwyGatewayLinkId.
--
--   (3) Virtual MGs must be represented as a separate entry
--       in this table
--
--   (4) Statistics can be reset to zero by managers when necessary using
--       medGwyGatewayResetStatistics.
--
-- *****************************************************************

medGwyGatewayConfigTable OBJECT-TYPE
    SYNTAX      SEQUENCE OF MedGwyGatewayConfigEntry
    MAX-ACCESS  not-accessible
    STATUS      current
    DESCRIPTION 
        "A list of medGwyGatewayConfigEntry objects."
    ::= { medGwyConfiguration 2 }

medGwyGatewayConfigEntry OBJECT-TYPE
    SYNTAX      MedGwyGatewayConfigEntry
    MAX-ACCESS  not-accessible
    STATUS      current
    DESCRIPTION 
        "Entry holding configuration information about a 
         group of Media Gateway Controllers sharing the same 
         signaling link."
    INDEX       { medGwyGatewayId, medGwyGatewayLinkId }
    ::= { medGwyGatewayConfigTable 1 }

MedGwyGatewayConfigEntry ::= SEQUENCE {
    medGwyGatewayId                     MediaGatewayId,
    medGwyGatewayLinkId                 MediaGatewayLinkId,
    medGwyGatewayLinkName               OCTET STRING,
    medGwyGatewayIPAddress              IpAddress,
    medGwyGatewayPort                   Integer32,
    medGwyGatewayEncodingScheme         INTEGER,
    medGwyGatewayProtocol               INTEGER,
    medGwyGatewaySignalingTptProtocol   INTEGER,
    medGwyGatewayAdminStatus            INTEGER,
    medGwyGatewayOperStatus             INTEGER,
    medGwyGatewayLastStatusChange       TimeStamp,
    medGwyGatewayResetStatistics        INTEGER,
    medGwyGatewayRowStatus              RowStatus
}

medGwyGatewayId OBJECT-TYPE
    SYNTAX      MediaGatewayId
    MAX-ACCESS  accessible-for-notify
    STATUS      current
    DESCRIPTION 
        "The unique Media Gateway Id which identifies this 
         media gateway"
    ::= { medGwyGatewayConfigEntry 1 }

medGwyGatewayLinkId OBJECT-TYPE
    SYNTAX      MediaGatewayLinkId
    MAX-ACCESS  not-accessible
    STATUS      current
    DESCRIPTION 
        "The unique link id which identifies the signalling 
         link that this gateway uses to communicate with the 
         Gateway Controllers."
    ::= { medGwyGatewayConfigEntry 2 }

medGwyGatewayLinkName OBJECT-TYPE
    SYNTAX      OCTET STRING (SIZE(0..255))
    MAX-ACCESS  read-create
    STATUS      current
    DESCRIPTION 
        "A descriptive name of this signalling link / media 
         gateway combination"
    ::= { medGwyGatewayConfigEntry 3 }

medGwyGatewayIPAddress OBJECT-TYPE
    SYNTAX      IpAddress
    MAX-ACCESS  read-create
    STATUS      current
    DESCRIPTION 
        "The IP address that the Media Gateway Controller 
         will use to communicate with the Media Gateway.  
         The value 0.0.0.0 is returned if the entry is 
         invalid."
    ::= { medGwyGatewayConfigEntry 4 }

medGwyGatewayPort OBJECT-TYPE
    SYNTAX      Integer32 (0..65535)
    MAX-ACCESS  read-create
    STATUS      current
    DESCRIPTION 
        "TCP/UDP port number that the Media Gateway Controller will 
         use to communicate with the Media Gateway. The value 
         0 is returned if the entry is invalid."
    DEFVAL      { 2944 }
    ::= { medGwyGatewayConfigEntry 5 }

medGwyGatewayEncodingScheme OBJECT-TYPE
    SYNTAX      INTEGER { text(1), binary(2) }
    MAX-ACCESS  read-create
    STATUS      current
    DESCRIPTION 
        "The encoding scheme that would be used to encode the Megaco 
         messages that are sent/received to/from the gateway 
         controller"
    DEFVAL      { text }
    ::= { medGwyGatewayConfigEntry 6 }

medGwyGatewayProtocol OBJECT-TYPE
    SYNTAX      INTEGER { notApplicable(1), other(2), dss1Ip(3), ipdc(4), 
			  megacov1(5), megacov2(6), mgcp(7) }
    MAX-ACCESS  read-create
    STATUS      current
    DESCRIPTION 
        "Type of the control protocol in use.
         
         - notApplicable(1), not applicable
         - other(2), Other (none from the list below)
         - dss1Ip(3), Q931+
         - ipdc(4), IPDC
         - megacov1(5), MEGACO/H.248 Version 1
         - megacov2(6), MEGACO/H.248 Version 2
         - mgcp(7) MGCP"
    ::= { medGwyGatewayConfigEntry 7 }

medGwyGatewaySignalingTptProtocol OBJECT-TYPE
    SYNTAX      INTEGER { tcp(1), udp(2), sctp(3), other(4) }
    MAX-ACCESS  read-create
    STATUS      current
    DESCRIPTION 
        "Type of the transport protocol that is being used to 
         transport the megaco signalling traffic"
    ::= { medGwyGatewayConfigEntry 8 }

medGwyGatewayAdminStatus OBJECT-TYPE
    SYNTAX      INTEGER { up(1), down(2), testing(3) }
    MAX-ACCESS  read-create
    STATUS      current
    DESCRIPTION 
        "The desired state of the gateway.  The testing(3) state 
         indicates that no signalling packets can be passed.  When 
         a managed system initializes, all gateways start with 
         medGwyGatewayAdminStatus in the down(2) state.  As a result 
         of either explicit management action or per configuration 
         information retained by the managed system, 
         medGwyGatewayAdminStatus is then changed to either the 
         up(1) or testing(3) states (or remains in the down(2) 
         state)."
    ::= { medGwyGatewayConfigEntry 9 }

medGwyGatewayOperStatus OBJECT-TYPE
    SYNTAX      INTEGER { up(1), down(2), testing(3), unknown(4) }
    MAX-ACCESS  read-only
    STATUS      current
    DESCRIPTION 
        "The current operational state of the gateway.
         
         - up(1), ready to communicate with MGC.
         - down(2),
         - testing(3), in some test mode.
         - unknown(4) status can not be determined for some 
           reason.
         
         The testing(3) state indicates that no signalling 
         packets can be passed.  If medGwyGatewayAdminStatus 
         is down(2) then medGwyGatewayOperStatus should be 
         down(2).  If medGwyGatewayAdminStatus is changed to 
         up(1) then medGwyGatewayOperStatus should change to 
         up(1) if the gateway is ready to transmit and receive 
         signalling traffic; it should remain in the down(2) 
         state if and only if there is a fault that prevents 
         it from going to the up(1) state"
    ::= { medGwyGatewayConfigEntry 10 }

medGwyGatewayLastStatusChange OBJECT-TYPE
    SYNTAX      TimeStamp
    MAX-ACCESS  read-only
    STATUS      current
    DESCRIPTION 
        "The value of sysUpTime at the time the associated 
         link entered its current operational status. If 
         the current status was entered prior to the last 
         re-initialization of the local network management 
         subsystem, then this object contains a zero value."
    ::= { medGwyGatewayConfigEntry 11 }

medGwyGatewayResetStatistics OBJECT-TYPE
    SYNTAX      INTEGER { notApplicable(1), other(2), reset(3) }
    MAX-ACCESS  read-create
    STATUS      current
    DESCRIPTION 
        "This object can be used to reset all statistics 
         collected for this media gateway link so far.  
         
         - notApplicable(1), Invalid/unknown.
         - other(2), None from the list below.
         - reset(3)  Reset all statistics now.
         
         Statistics will be reset when the object is SET 
         to 'reset'.  Upon reset, the agent changes the value 
         of this object to 'notApplicable'."
    ::= { medGwyGatewayConfigEntry 12 }

medGwyGatewayRowStatus OBJECT-TYPE
    SYNTAX      RowStatus
    MAX-ACCESS  read-create
    STATUS      current
    DESCRIPTION 
        "This is used to create new rows in this table, 
         Modify existing rows, and to delete existing rows."
    ::= { medGwyGatewayConfigEntry 13 }

-- *****************************************************************
--
-- medGwyGatewayControllerTable
--
--   The Media Gateway Controller Table...
--
--   This table would provide information about the media gateway
--   controllers in the network and their configuration. The rules
--   that guide this table are:
--
--   (1) This table consists a 'List' of Media Gateway Controllers
--       (on a media gateway), and Configuration Information for these
--       Controllers.
--
--   (2) An Entry in this Table is automatically created when a manager
--       creates an entry in the medGwyGatewayConfigTable because even
--       though the same MGC could manage many gateways, they could have
--       different logical IP address/Port number towards each of the
--       gateway
--
--   (3) There can be many logical gateways inside a physical gateway
--       (MediaGatewayId) and there can me multiple media gateway
--       controllers (medGwyGatewayControllerId) and there can be many
--       links between "m" number of gateways and "n" number of controllers
--       (medGwyGatewayLinkId).
--
--       The relationship can be, for example, as follows:
--
--      MediaGatewayId                       medGwyGatewayControllerId
--       + - - - - -+   medGwyGatewayLinkId   + - - - - -+
--       |      mg1 |- - - - - -> - - - - - ->|     mgc1 |
--       | + - - - - -+          |            | + - - - - -+
--       | |      mg2 |          +- - - - - - ->|     mgc2 |
--       | | + - - - - -+                     | | + - - - - -+
--       +-| |      mg3 |- - - - - -> - - - - ->| |    mgc3  |
--         | |          |            |          | |          |
--         +-|          |            +- - - - - ->|          |
--           |          |                         |          |
--           + - - - - -+                         + - - - - -+
--
-- *****************************************************************

medGwyGatewayControllerTable OBJECT-TYPE
    SYNTAX      SEQUENCE OF MedGwyGatewayControllerEntry
    MAX-ACCESS  not-accessible
    STATUS      current
    DESCRIPTION 
        "List of the Media Gateway Controllers that are managed 
         in the network"
    ::= { medGwyConfiguration 3 }

medGwyGatewayControllerEntry OBJECT-TYPE
    SYNTAX      MedGwyGatewayControllerEntry
    MAX-ACCESS  not-accessible
    STATUS      current
    DESCRIPTION 
        "Entry holding information about an individual 
         Media Gateway Controller."
    INDEX       { medGwyGatewayId, medGwyGatewayLinkId, 
                  medGwyGatewayControllerId }
    ::= { medGwyGatewayControllerTable 1 }

MedGwyGatewayControllerEntry ::= SEQUENCE {
    medGwyGatewayControllerId           Unsigned32,
    medGwyGatewayControllerIPAddress    IpAddress,
    medGwyGatewayControllerPort         Integer32,
    medGwyGatewayControllerAdminStatus  INTEGER,
    medGwyGatewayControllerOperStatus   INTEGER
}

medGwyGatewayControllerId OBJECT-TYPE
    SYNTAX      Unsigned32 (1..2147483647)
    MAX-ACCESS  accessible-for-notify
    STATUS      current
    DESCRIPTION 
        "An unique identification number that is assigned to 
         the gateway controller by the manager"
    ::= { medGwyGatewayControllerEntry 1 }

medGwyGatewayControllerIPAddress OBJECT-TYPE
    SYNTAX      IpAddress
    MAX-ACCESS  read-create
    STATUS      current
    DESCRIPTION 
        "The IP address of the Media Gateway Controller. The 
         value 0.0.0.0 is returned if the entry is invalid."
    ::= { medGwyGatewayControllerEntry 2 }

medGwyGatewayControllerPort OBJECT-TYPE
    SYNTAX      Integer32 (0..65535)
    MAX-ACCESS  read-create
    STATUS      current
    DESCRIPTION 
        "TCP port of the Media Gateway Controller. The value 
         0 is returned if the entry is invalid."
    ::= { medGwyGatewayControllerEntry 3 }

medGwyGatewayControllerAdminStatus OBJECT-TYPE
    SYNTAX      INTEGER { up(1), down(2), testing(3) }
    MAX-ACCESS  read-create
    STATUS      current
    DESCRIPTION 
        "The desired state of the gateway.  The testing(3) state 
         indicates that no signalling packets can be passed.  When 
         a managed system initializes, all gateways start with 
         medGwyGatewayControllerAdminStatus in the down(2) state.  
         As a result of either explicit management action or per 
         configuration information retained by the managed system, 
         medGwyGatewayControllerAdminStatus is then changed to 
         either the up(1) or testing(3) states (or remains in the 
         down(2) state)."
    ::= { medGwyGatewayControllerEntry 4 }

medGwyGatewayControllerOperStatus OBJECT-TYPE
    SYNTAX      INTEGER { up(1), down(2), standby(3) }
    MAX-ACCESS  read-only
    STATUS      current
    DESCRIPTION 
        "The current operational state of the gateway controller.  
         
         - up(1), Up/active.
         - down(2), Down.
         - standby(3)  Standby mode.
         
         The standby(3) state indicates that it is in the standby 
         mode and no signalling packets can be passed. If 
         medGwyGatewayControllerAdminStatus is down(2) then 
         medGwyGatewayControllerOperStatus should be down(2). If 
         medGwyGatewayControllerAdminStatus is changed to up(1) then 
         medGwyGatewayControllerOperStatus should change to up(1) 
         if the gateway controller is ready to transmit and receive 
         signalling traffic; it should remain in the down(2) state if 
         and only if there is a fault that prevents it from going to 
         the up(1) state"
    ::= { medGwyGatewayControllerEntry 5 }

medGwyStatistics OBJECT IDENTIFIER
    ::= { mediaGatewayMIBObjects 2 }

-- *****************************************************************
--
-- medGwyGatewayStatsTable
--
--   The Media Gateway Stats Table...
--
--   This table provides the control protocol related statistics for
--   the gateways that are being managed in the network. The rules
--   that guide this table are:
--
--   (1) There is one entry in this table for each
--       MediaGateway/SignallingLink.
--   (2) The Agent creates this table, when a GatewayConfigTable
--       Entry is created.
--
-- *****************************************************************

medGwyGatewayStatsTable OBJECT-TYPE
    SYNTAX      SEQUENCE OF MedGwyGatewayStatsEntry
    MAX-ACCESS  not-accessible
    STATUS      current
    DESCRIPTION 
        "A list of mediaGatewayTableEntry objects."
    ::= { medGwyStatistics 1 }

medGwyGatewayStatsEntry OBJECT-TYPE
    SYNTAX      MedGwyGatewayStatsEntry
    MAX-ACCESS  not-accessible
    STATUS      current
    DESCRIPTION 
        "Entry holding statistics about a group of 
         media Gateway/signalling link pair."
    INDEX       { medGwyGatewayId, medGwyGatewayLinkId }
    ::= { medGwyGatewayStatsTable 1 }

MedGwyGatewayStatsEntry ::= SEQUENCE {
    medGwyGatewayNumInMessages              Unsigned32,
    medGwyGatewayNumInOctets                Unsigned32,
    medGwyGatewayNumOutMessages             Unsigned32,
    medGwyGatewayNumOutOctets               Unsigned32,
    medGwyGatewayNumErrors                  Unsigned32,
    medGwyGatewayNumTimerRecovery           Unsigned32,
    medGwyGatewayTransportNumLosses         Unsigned32,
    medGwyGatewayTransportNumSwitchover     Unsigned32,
    medGwyGatewayTransportTotalNumAlarms    Unsigned32,
    medGwyGatewayTransportLastEvent         INTEGER,
    medGwyGatewayTransportLastEventTime     TimeStamp,
    medGwyGatewayLastStatisticsReset        TimeStamp
}

medGwyGatewayNumInMessages OBJECT-TYPE
    SYNTAX      Unsigned32
    MAX-ACCESS  read-only
    STATUS      current
    DESCRIPTION 
        "Total number of messages received on the link."
    ::= { medGwyGatewayStatsEntry 1 }

medGwyGatewayNumInOctets OBJECT-TYPE
    SYNTAX      Unsigned32
    MAX-ACCESS  read-only
    STATUS      current
    DESCRIPTION 
        "Total number of octets received on the link."
    ::= { medGwyGatewayStatsEntry 2 }

medGwyGatewayNumOutMessages OBJECT-TYPE
    SYNTAX      Unsigned32
    MAX-ACCESS  read-only
    STATUS      current
    DESCRIPTION 
        "Total number of messages sent on the link."
    ::= { medGwyGatewayStatsEntry 3 }

medGwyGatewayNumOutOctets OBJECT-TYPE
    SYNTAX      Unsigned32
    MAX-ACCESS  read-only
    STATUS      current
    DESCRIPTION 
        "Total number of octets sent on the link."
    ::= { medGwyGatewayStatsEntry 4 }

medGwyGatewayNumErrors OBJECT-TYPE
    SYNTAX      Unsigned32
    MAX-ACCESS  read-only
    STATUS      current
    DESCRIPTION 
        "Total number of signaling-level errors encountered.  
         Includes, but is not limited to, number of bad 
         messages received, number of failures to sent a 
         message and number of other errors."
    ::= { medGwyGatewayStatsEntry 5 }

medGwyGatewayNumTimerRecovery OBJECT-TYPE
    SYNTAX      Unsigned32
    MAX-ACCESS  read-only
    STATUS      current
    DESCRIPTION 
        "Total Number of timer recovery events since the 
         statistics was last reset. This reflects all protocol 
         timers that are supported (For Megaco, T - start timer, 
         S - short timer, L - long timer, and Z - long duration 
         timer, etc.)"
    ::= { medGwyGatewayStatsEntry 6 }

medGwyGatewayTransportNumLosses OBJECT-TYPE
    SYNTAX      Unsigned32
    MAX-ACCESS  read-only
    STATUS      current
    DESCRIPTION 
        "Number of times a transport link was lost 
         (excluding switch-over cases). A link loss is defined 
         as loss of communication with the entity (MGC) due to 
         hardware/transient problems in the interface or other 
         related hardware/software"
    ::= { medGwyGatewayStatsEntry 7 }

medGwyGatewayTransportNumSwitchover OBJECT-TYPE
    SYNTAX      Unsigned32
    MAX-ACCESS  read-only
    STATUS      current
    DESCRIPTION 
        "Number of times when the signaling was switched 
         over to an alternative link. This includes 
         switchover due to the Handoffs initiated by the 
         gateway controllers"
    ::= { medGwyGatewayStatsEntry 8 }

medGwyGatewayTransportTotalNumAlarms OBJECT-TYPE
    SYNTAX      Unsigned32
    MAX-ACCESS  read-only
    STATUS      current
    DESCRIPTION 
        "Total number of all alarms issued for the transport 
         layer."
    ::= { medGwyGatewayStatsEntry 9 }

medGwyGatewayTransportLastEvent OBJECT-TYPE
    SYNTAX      INTEGER { notApplicable(1), other(2), linkUp(3), 
                    linkLoss(4), persistentError(5), linkShutdown(6), 
                    switchOver(7) }
    MAX-ACCESS  read-only
    STATUS      current
    DESCRIPTION 
        "Last event reported by the transport layer.
         
         - notApplicable(1), Invalid/unknown.
         - other(2), None from the list below.
         - linkUp(3), Transport link is up.
         - linkLoss(4), Transport link loss.
         - persistentError(5), No link - persistent error.
         - linkShutdown(6), Link is shut down.
         - switchOver(7), Fail-over."
    ::= { medGwyGatewayStatsEntry 10 }

medGwyGatewayTransportLastEventTime OBJECT-TYPE
    SYNTAX      TimeStamp
    MAX-ACCESS  read-write
    STATUS      current
    DESCRIPTION 
        "The value of sysUpTime at the time when the event 
         specified by mediaGatewayTransportLastEvent occured. 
         If the last event occured prior to the last 
         re-initialization of the local network management 
         subsystem, then this object contains a zero value."
    ::= { medGwyGatewayStatsEntry 11 }

medGwyGatewayLastStatisticsReset OBJECT-TYPE
    SYNTAX      TimeStamp
    MAX-ACCESS  read-only
    STATUS      current
    DESCRIPTION 
        "The value of sysUpTime at the time when the 
         statistics were reset. If the reset occurred prior to 
         the last re-initialization of the local network 
         management subsystem, this object contains a zero 
         value."
    ::= { medGwyGatewayStatsEntry 12 }

medGwyConnections OBJECT IDENTIFIER
    ::= { mediaGatewayMIBObjects 3 }

-- *****************************************************************
--
-- medGwyTermIdTable
--
--   TerminationId Table...
--
--   This table provides unique TerminationId for the creation of
--   an entry into the TerminationsTable. The following rules guide
--   this table:
--
--   (1) This table provides the manager with the nextId for use in
--       creating a Termination. There is one entry in this table for each
--       MediaGateway.
--   (2) If this table isn't implemented, the manager would be
--       responsible for providing the (unique) nextId (via retaining
--       used id's, hashing, etc.)
--
-- *****************************************************************

medGwyTermIdTable OBJECT-TYPE
    SYNTAX      SEQUENCE OF MedGwyTermIdEntry
    MAX-ACCESS  not-accessible
    STATUS      current
    DESCRIPTION 
        "This table contains a nextTerminationId for each 
         Gateway. It provides the manager with the 
         nextTerminationId for use in creating a new 
         TerminationsTable Entry."
    ::= { medGwyConnections 1 }

medGwyTermIdEntry OBJECT-TYPE
    SYNTAX      MedGwyTermIdEntry
    MAX-ACCESS  not-accessible
    STATUS      current
    DESCRIPTION 
        "This table contains a nextTerminationId for each 
         Gateway, and is indexed by mediaGatewayId."
    INDEX       { medGwyGatewayId }
    ::= { medGwyTermIdTable 1 }

MedGwyTermIdEntry ::= SEQUENCE {
    medGwyNextTerminationId     TestAndIncr
}

medGwyNextTerminationId OBJECT-TYPE
    SYNTAX      TestAndIncr
    MAX-ACCESS  read-write
    STATUS      current
    DESCRIPTION 
        "The Next Value for a MediaGateway TerminationId.  Assists 
         the manager in selecting a value for medGwyTerminationId.  
         Using the TestAndIncr syntax, A Manager will 'lock' this 
         variable, ensuring single access."
    ::= { medGwyTermIdEntry 1 }

-- *****************************************************************
--
-- medGwyTerminationsTable
--
--   The Terminations Table...
--
--   This table provides the list of terminations available in the gateway
--   and their corresponding profile information and related configuration
--   information. The following rules guide this table:
--
--   (1) There is one entry in this table for each Termination in a
--       MediaGateway.
--   (2) The list of terminations include terminations that are present
--       for all the contexts that are present in the gateway (excluding
--       the NULL context) (Subject to Discussion)
--
-- *****************************************************************

medGwyTerminationsTable OBJECT-TYPE
    SYNTAX      SEQUENCE OF MedGwyTerminationsEntry
    MAX-ACCESS  not-accessible
    STATUS      current
    DESCRIPTION 
        "This table contains information about terminations 
         in a media gateway. It is a list of terminations.  
         The number of entries equals to the total number of 
         terminations for all contexts in a gateway."
    ::= { medGwyConnections 2 }

medGwyTerminationsEntry OBJECT-TYPE
    SYNTAX      MedGwyTerminationsEntry
    MAX-ACCESS  not-accessible
    STATUS      current
    DESCRIPTION 
        "It contains objects that describe a termination."
    INDEX       { medGwyGatewayId, medGwyTerminationId }
    ::= { medGwyTerminationsTable 1 }

MedGwyTerminationsEntry ::= SEQUENCE {
    medGwyTerminationId                     MediaGatewayTermId,
    medGwyTerminationName                   SnmpAdminString,
    medGwyTerminationAdminStatus            INTEGER,
    medGwyTerminationOperStatus             INTEGER,
    medGwyTerminationInterfaceIdentifier    InterfaceIndex,
    medGwyTerminationPropertyProfileId      Unsigned32,
    medGwyTerminationRowStatus              RowStatus
}

medGwyTerminationId OBJECT-TYPE
    SYNTAX      MediaGatewayTermId
    MAX-ACCESS  accessible-for-notify
    STATUS      current
    DESCRIPTION 
        "An unique identification number that is assigned to 
         the termination by a media gateway. This is the 
         TerminationId that would be used in the protocol 
         messages that are sent from the gateway"
    ::= { medGwyTerminationsEntry 1 }

medGwyTerminationName OBJECT-TYPE
    SYNTAX      SnmpAdminString (SIZE(0..64))
    MAX-ACCESS  read-create
    STATUS      current
    DESCRIPTION 
        "A descriptive name that would describe this termination 
         and its use. For example, 'emergency-ds0-1' indicating 
         that this termination is reserved as an emergency DS0 
         channel"
    ::= { medGwyTerminationsEntry 2 }

medGwyTerminationAdminStatus OBJECT-TYPE
    SYNTAX      INTEGER { inService(1), outOfService(2), testing(3) }
    MAX-ACCESS  read-create
    STATUS      current
    DESCRIPTION 
        "The desired state of the termination.  The testing(3) state 
         indicates that no connections can be created for this 
         termination.  When a managed system initializes, all 
         terminations start with medGwyTerminationAdminStatus in the 
         out-of-service(2) state.  As a result of either 
         explicit management action or per configuration information 
         retained by the managed system, 
         medGwyTerminationAdminStatus is then changed to either the 
         inService(1) or testing(3) states (or remains in the 
         outOfService(2) state)."
    ::= { medGwyTerminationsEntry 3 }

medGwyTerminationOperStatus OBJECT-TYPE
    SYNTAX      INTEGER { up(1), down(2), testing(3) }
    MAX-ACCESS  read-create
    STATUS      current
    DESCRIPTION 
        "The current operational state of the termination.  
         The testing(3) state indicates that it is in the testing 
         mode and no connections can be created on it. If 
         medGwyTerminationAdminStatus is out-of-service(2) then 
         medGwyTerminationOperStatus should be down(2). If 
         medGwyTerminationAdminStatus is changed to up(1) then 
         medGwyTerminationOperStatus should change to up(1) if the 
         termination is ready to accept connections; it should remain 
         in the down(2) state if and only if there is a fault that 
         prevents it from going to the up(1) state"
    ::= { medGwyTerminationsEntry 4 }

medGwyTerminationInterfaceIdentifier OBJECT-TYPE
    SYNTAX      InterfaceIndex
    MAX-ACCESS  read-create
    STATUS      current
    DESCRIPTION 
        "A number that uniquely identifies the interface in 
         the physical gateway. This is the ifIndex in the ifTable, 
         that this termination would be using to communicate to 
         other gateways"
    ::= { medGwyTerminationsEntry 5 }

medGwyTerminationPropertyProfileId OBJECT-TYPE
    SYNTAX      Unsigned32 (1..2147483647)
    MAX-ACCESS  read-create
    STATUS      current
    DESCRIPTION 
        "This determines the profile of the termination which 
         determines what kind of capabilities this termination has.  
         This is an index into the medGwyPropertyProfileTable 
         which identifies all the profile that are available"
    ::= { medGwyTerminationsEntry 6 }

medGwyTerminationRowStatus OBJECT-TYPE
    SYNTAX      RowStatus
    MAX-ACCESS  read-create
    STATUS      current
    DESCRIPTION 
        "This is used to create new rows in this table, 
         Modify existing rows, and to delete existing rows."
    ::= { medGwyTerminationsEntry 7 }

-- *****************************************************************
--
-- medGwyPropertyProfileTable
--
--   The Media Gateway Property Profile Table...
--
--   This table describes different profiles and the properties supported
--   by each profile. The rules that guide this table are:
--
--   (1) There are 'N' entries for each Gateway-PropertyProfile
--   (2) Each entry is a supported property, thus this table gives a list
--       of supported properties for each specified Profile.
--   (3) Each Property is defined as an Object Identifier in the various
--       Package Mibs (like MEGACO-TONES-MIB, etc.).
--   (4) That OID is used to identify the particular Package, and if the
--       Termination supports the property, this Package OID is included
--       in its list.
--   (5) Terminations (in the TerminationsTable) will have a
--       PropertyProfileId that indicates which PropertyProfile this
--       Termination supports.
--   (6) A Manager builds a Profile of properties, then ties each
--       termination to a defined profile, via the PropertyProfileId
--   (7) Vendors are encouraged to come up with different profiles
--       for different scenarios in order to ensure inter-operability
--       among different implementations
--
-- *****************************************************************

medGwyPropertyProfileTable OBJECT-TYPE
    SYNTAX      SEQUENCE OF MedGwyPropertyProfileEntry
    MAX-ACCESS  not-accessible
    STATUS      current
    DESCRIPTION 
        "This table contains a list of the properties 
         supported in a Profile.  A Manager builds a Profile 
         of properties, then ties each termination to a 
         defined profile"
    ::= { medGwyConnections 3 }

medGwyPropertyProfileEntry OBJECT-TYPE
    SYNTAX      MedGwyPropertyProfileEntry
    MAX-ACCESS  not-accessible
    STATUS      current
    DESCRIPTION 
        "Each row represents a default property of the 
         Property Profile N-entries per 
         mediaGatewayId/PropertyId, one entry per property."
    INDEX       { medGwyGatewayId, medGwyPropertyProfileId, 
                  medGwyPropertyProfileIndex }
    ::= { medGwyPropertyProfileTable 1 }

MedGwyPropertyProfileEntry ::= SEQUENCE {
    medGwyPropertyProfileId             Unsigned32,
    medGwyPropertyProfileIndex          Unsigned32,
    medGwyPropertyProfileProperty       AutonomousType,
    medGwyTermPropertyProfileStatus     RowStatus
}

medGwyPropertyProfileId OBJECT-TYPE
    SYNTAX      Unsigned32 (1..2147483647)
    MAX-ACCESS  not-accessible
    STATUS      current
    DESCRIPTION 
        "This PropertyProfile Identifier uniquelyidentifies this 
         set of properties.  This is the value each termination 
         would refer, when they would like to support all the 
         properties in this profile"
    ::= { medGwyPropertyProfileEntry 1 }

medGwyPropertyProfileIndex OBJECT-TYPE
    SYNTAX      Unsigned32 (1..2147483647)
    MAX-ACCESS  not-accessible
    STATUS      current
    DESCRIPTION 
        "This is the index to the PropertyProfile This is just 
         a 'counter' through the medGwyPropertyProfile Table.  
         ie, property=1 property=2, etc."
    ::= { medGwyPropertyProfileEntry 2 }

medGwyPropertyProfileProperty OBJECT-TYPE
    SYNTAX      AutonomousType
    MAX-ACCESS  read-create
    STATUS      current
    DESCRIPTION 
        "The Property supported by this Profile.  
         This is an Object ID (OID) defined in a package MIB 
         to identify a Particular property (such as AnalogLines, 
         Tones, etc.)."
    ::= { medGwyPropertyProfileEntry 3 }

medGwyTermPropertyProfileStatus OBJECT-TYPE
    SYNTAX      RowStatus
    MAX-ACCESS  read-create
    STATUS      current
    DESCRIPTION 
        "used to create new rows in this table, modify 
         existing rows, and to delete existing rows."
    ::= { medGwyPropertyProfileEntry 4 }

medGwyProperties OBJECT IDENTIFIER
    ::= { mediaGatewayMIBObjects 4 }

-- *****************************************************************
--
-- MEGACO-MIB Notification Definitions
--
-- There are seven traps currently supported by the MEGACO-MIB. They are
--
-- o medGwyLinkStatusChange
--    This trap is sent whenever there is a change in the link status
--    that the media gateway is communicating
--
-- o medGwyInvalidControllerAddress
--    This trap is sent whenever a gateway receives a protocol message
--    from a controller that was not present in the configured list
--    of media gateway controllers
--
-- o meGwyInvalidTerminationId
--    This trap is sent whenever a gateway receives a protocol message
--    for a termination that is not recognized by the gateway
--
-- o medGwyInvalidPackageElement
--    This trap is sent whenever a gateway receives an invalid
--    event/signal or any other descriptor for the package specified
--    along with it.
--
-- o medGwyTerminationStatusChange
--    This trap is sent whenever the status of the termination
--    changes from inService to out-of-Service or to testing.
--
-- o medGwyGatewayHandoff
--    This trap is sent whenever there is a hand-off (due to a failure of
--    the MGC or enforced by the MGC) in a gateway
--
-- o medGwyProtocolError
--    This trap is sent whenever there is a protocol error detected
--    in the messages that the gateway receives from the gateway
--    controllers that are configured
--
-- *****************************************************************

mediaGatewayMIBNotifications OBJECT IDENTIFIER
    ::= { megacoMIB 2 }

medGwyNotifPrefix OBJECT IDENTIFIER
    ::= { mediaGatewayMIBNotifications 0 }

medGwyNotifObjects OBJECT IDENTIFIER
    ::= { mediaGatewayMIBNotifications 1 }

--
-- Objects necessary for these Notifications
--
medGwyReceivedElement OBJECT-TYPE
    SYNTAX      OCTET STRING (SIZE(0..255))
    MAX-ACCESS  accessible-for-notify
    STATUS      current
    DESCRIPTION 
        "The element name received in a megaco message. For 
         example, 'eventDescriptor' is one such element that 
         could be sent with the notifications"
    ::= { medGwyNotifObjects 1 }

mediaGatewayConformance OBJECT IDENTIFIER
    ::= { megacoMIB 3 }

-- *****************************************************************
--
-- Conformance Object Groups
--
-- There are two object groups
--
-- medGwyCompliances
--   This group includes all the compliance statements (both mandatory
--   and optional statements.
--
-- medGwyConfGroups
--   This group includes all the different groups that form the compliance
--   statements
--
-- *****************************************************************

medGwyCompliances OBJECT IDENTIFIER
    ::= { mediaGatewayConformance 1 }

medGwyConfGroups OBJECT IDENTIFIER
    ::= { mediaGatewayConformance 2 }

medGwyLinkStatusChange NOTIFICATION-TYPE
    OBJECTS     { medGwyGatewayLinkName, medGwyGatewayOperStatus }
    STATUS      current
    DESCRIPTION 
        "This notification indicates that operational status 
         of a media gateway control link has changed."
    ::= { medGwyNotifPrefix 1 }

medGwyInvalidControllerAddress NOTIFICATION-TYPE
    OBJECTS     { medGwyGatewayControllerIPAddress }
    STATUS      current
    DESCRIPTION 
        "This notification indicates that a message was received 
         from a controller that did not match any of the valid 
         controller IPAddress-es configured in 
         medGwyGatewayControllerTable"
    ::= { medGwyNotifPrefix 2 }

medGwyInvalidTerminationId NOTIFICATION-TYPE
    OBJECTS     { medGwyTerminationId }
    STATUS      current
    DESCRIPTION 
        "This notification indicates that a message was received 
         from a controller that contained a TerminationId that did 
         not match any TerminationId in the TerminationsTable.  
         TerminationId is found in the OID of the 
         medGwyTerminationName Object."
    ::= { medGwyNotifPrefix 3 }

medGwyInvalidPackageElement NOTIFICATION-TYPE
    OBJECTS     { medGwyReceivedElement }
    STATUS      current
    DESCRIPTION 
        "This notification indicates that a message was received 
         from a controller that contained an event, signal, 
         or descriptor that was not recognized for the 
         package."
    ::= { medGwyNotifPrefix 4 }

medGwyTerminationStatusChange NOTIFICATION-TYPE
    OBJECTS     { medGwyTerminationAdminStatus, 
		  medGwyTerminationOperStatus }
    STATUS      current
    DESCRIPTION 
        "This notification is sent when a termination changes 
         status."
    ::= { medGwyNotifPrefix 5 }

medGwyGatewayHandoff NOTIFICATION-TYPE
    OBJECTS     { medGwyGatewayId, medGwyGatewayControllerId }
    STATUS      current
    DESCRIPTION 
        "This notification is sent when a gateway is handed off 
         to a different gateway controller either due to a apparent 
         MGC failure or due to a MGC-enforced condition"
    ::= { medGwyNotifPrefix 6 }

medGwyProtocolError NOTIFICATION-TYPE
    OBJECTS     { medGwyTerminationId }
    STATUS      current
    DESCRIPTION 
        "This notification is sent when a protocol error is detected 
         in the messages received from the 'configured' gateway 
         controllers"
    ::= { medGwyNotifPrefix 7 }

-- *****************************************************************
--
-- Conformance for the MEGACO-MIB
--
-- This object group provides list of groups to be conformed when
-- managing different types of gateways, gateway controllers individually
-- and both simultaneously from one single management entity.
--
-- *****************************************************************

-- Units of Conformance

medGwyConfigGroup OBJECT-GROUP
    OBJECTS     { medGwyGatewayLinkName, medGwyGatewayIPAddress, 
                  medGwyGatewayPort, medGwyGatewayEncodingScheme, 
                  medGwyGatewayProtocol, 
                  medGwyGatewaySignalingTptProtocol, 
                  medGwyGatewayAdminStatus, medGwyGatewayOperStatus, 
                  medGwyGatewayLastStatusChange, 
                  medGwyGatewayResetStatistics }
    STATUS      current
    DESCRIPTION 
        "This group contains of all the configuration Information for a 
         Media Gateway. This group is mandatory for any implementation 
         managing a media gateway or a group of media gateways"
    ::= { medGwyConfGroups 1 }

medGwyStatsGroup OBJECT-GROUP
    OBJECTS     { medGwyGatewayNumInMessages, medGwyGatewayNumInOctets, 
                  medGwyGatewayNumOutMessages, medGwyGatewayNumOutOctets, 
                  medGwyGatewayNumErrors, medGwyGatewayNumTimerRecovery, 
                  medGwyGatewayTransportNumLosses, 
                  medGwyGatewayTransportNumSwitchover, 
                  medGwyGatewayTransportTotalNumAlarms, 
                  medGwyGatewayTransportLastEvent, 
                  medGwyGatewayTransportLastEventTime, 
                  medGwyGatewayLastStatisticsReset }
    STATUS      current
    DESCRIPTION 
        "This group contains of all the statistics Information for a 
         Media Gateway. This group is mandatory for any implementation 
         managing a media gateway or a group of media gateways"
    ::= { medGwyConfGroups 2 }

medGwyGWControllerGroup OBJECT-GROUP
    OBJECTS     { medGwyGatewayControllerIPAddress, 
                  medGwyGatewayControllerPort, 
                  medGwyGatewayControllerAdminStatus, 
                  medGwyGatewayControllerOperStatus }
    STATUS      current
    DESCRIPTION 
        "This group contains of all the configuration Information for a 
         Media Gateway Controller. This group is mandatory for any 
         implementation managing a media gateway controller or a group of 
         media gateway controllers. It is also mandatory for implementations 
         managing media gateways"
    ::= { medGwyConfGroups 3 }

medGwyNextIdGroup OBJECT-GROUP
    OBJECTS     { medGwyNextTerminationId, medGwyNextLinkId }
    STATUS      current
    DESCRIPTION 
        "Agent provides NextId's to the Manager to assist in selecting 
         and creating new table entries. This group is optional for 
         all the implementations. But when it is not implemented, it is 
         the manager's responsibility to uniquely determine these ids"
    ::= { medGwyConfGroups 4 }

medGwyNotificationsGroup NOTIFICATION-GROUP
    NOTIFICATIONS { medGwyLinkStatusChange, 
                  medGwyInvalidControllerAddress, 
                  medGwyInvalidTerminationId, 
                  medGwyInvalidPackageElement, 
                  medGwyTerminationStatusChange, medGwyGatewayHandoff, 
                  medGwyProtocolError }
    STATUS      current
    DESCRIPTION 
        "This group contains notifications that an entity implementing 
         the Media Gateways will send. This group is mandatory for 
         all implementations that are managing a media gateway or a group 
         of media gateways"
    ::= { medGwyConfGroups 5 }

medGwyTerminationGroup OBJECT-GROUP
    OBJECTS	{ medGwyGatewayRowStatus, medGwyTerminationName, 
		  medGwyTerminationAdminStatus, 
		  medGwyTerminationOperStatus, 
		  medGwyTerminationInterfaceIdentifier, 
		  medGwyTerminationPropertyProfileId, 
		  medGwyTerminationRowStatus, 
		  medGwyPropertyProfileProperty, 
		  medGwyTermPropertyProfileStatus, medGwyReceivedElement }
    STATUS	current
    DESCRIPTION
	"This group contains all of the statistics and information for 
	 the termination points in a Media Gateway."
    ::= { medGwyConfGroups 6 }

medGwyCompliance MODULE-COMPLIANCE
    STATUS      current
    DESCRIPTION 
        "Compliance statement for entities which implement 
         the MEGACO-MIB."

    MODULE      -- this module

        MANDATORY-GROUPS        { medGwyConfigGroup, medGwyStatsGroup }

        GROUP   medGwyGWControllerGroup
        DESCRIPTION   
              "This group is mandatory for all Systems that are 
               gateway controllers and are being managed over a 
               distributed environment"

        GROUP   medGwyNextIdGroup
        DESCRIPTION   
              "This group is not mandatory for all the agent 
               implementations.  But if this group is not 
               implemented, then the manager is responsible for 
               uniquely determining the nextId to be used in 
               various listed objects."

        GROUP   medGwyNotificationsGroup
        DESCRIPTION   
	      "This group is mandatory for all the implementations, 
	       which are fault tolerant.  This group contains all the 
	       notifications"

	GROUP	medGwyTerminationGroup
	DESCRIPTION   
	      "This group is mandatory for all implementations that have 
	       terminations."

    ::= { medGwyCompliances 1 }

END -- end of module MEGACO-MIB.
