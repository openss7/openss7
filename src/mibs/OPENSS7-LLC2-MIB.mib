-- vim: ft=mib comments=\f\b\:\"ITU\-T,\f\b\:ITU\-T,\f\:\",\b\:\-\-,\:\-\-,\f\b\:\-,\f\b\:\· fo+=tcqlornw12 tw=64 ai nocin nosi sts=4 sw=4 et
-- =============================================================================
-- 
-- @(#) src/mibs/OPENSS7-LLC2-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-LLC2-MIB DEFINITIONS ::= BEGIN

IMPORTS
    openss7Modules
        FROM OPENSS7-SMI
    tmnObjectInstance
        FROM OPENSS7-SMI-MIB
    AdministrativeState, AlarmStatus, OperationalState, ProceduralStatus, 
    SimpleNameType, UsageState
        FROM OPENSS7-TMN-TC
    MODULE-COMPLIANCE, NOTIFICATION-GROUP, OBJECT-GROUP
        FROM SNMPv2-CONF
    Counter32, Gauge32, Integer32, MODULE-IDENTITY, NOTIFICATION-TYPE, 
    OBJECT-TYPE, Unsigned32, zeroDotZero
        FROM SNMPv2-SMI
    DisplayString, RowPointer, RowStatus, TEXTUAL-CONVENTION, 
    TimeInterval, TimeStamp, TruthValue
        FROM SNMPv2-TC;

llcMIB MODULE-IDENTITY
    LAST-UPDATED "201112101120Z"
    ORGANIZATION 
        "The OpenSS7 Project"
    CONTACT-INFO 
        "Brian Bidulock
         OpenSS7 Corporation
         1469 Jefferys Crescent
         Edmonton, Alberta  T6L 6T1
         CANADA
         Tel: +1 780 490 1141
         Fax: +1 780 490 1241
         Mob: +1 780 953 0557
         mailto:bidulock@openss7.org"
    DESCRIPTION 
        "This MIB provides configuration and status information 
         for an ISO/IEC 8802 LLC1/LLC2 subsystem.
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201112101120Z"
    DESCRIPTION 
        "Corrections an smilint workup."
    REVISION    "200712170903Z"
    DESCRIPTION 
        "Initial release of this mib."
    ::= { openss7Modules 23 }

-- =====================================================================
--
-- Textual Conventions

LLCServices ::= TEXTUAL-CONVENTION
    STATUS      current
    DESCRIPTION 
        "This textual convention represents the LLC services the 
         are available or selected.  Per ISO/IEC 8802-2, the 
         services are type1(0), type2(1), type3Initiate(2), 
         type3ReceiveData(3) and type3ReturnData(4)."
    REFERENCE   
        "IEEE 802.2 | ISO/IEC 8802-2 ASN.1, LLCServices."
    SYNTAX      BITS { type1(0), type2(1), type3Initiate(2), 
                    type3ReceiveData(3), type3ReturnData(4) }

LLCStationStatus ::= TEXTUAL-CONVENTION
    STATUS      current
    DESCRIPTION 
        "This textual convetion represents the status of an LLC 
         station.  Per ISO/IEC 8802-2, the status can be up(0), 
         down(1), or other (2)."
    REFERENCE   
        "IEEE 802.2 | ISO/IEC 8802-2 ASN.1, Status."
    SYNTAX      INTEGER { up(0), down(1), other(2) }

STRIndicator ::= TEXTUAL-CONVENTION
    STATUS      current
    DESCRIPTION 
        "This textual convention indicates the type of source 
         routed MAC bridging per ISO/IEC 8802-2 (IEEE 802.2), 
         the types are nsr(0) or ste(1)."
    SYNTAX      BITS { nsr(0), ste(1) }

MACAddress ::= TEXTUAL-CONVENTION
    DISPLAY-HINT    "1x-"
    STATUS      current
    DESCRIPTION 
        "This textual convention represents a MAC Address.  The 
         minmum length is 6 octets.  If the MAC address is a 
         48-bit address, the length of the octet string shall be 
         6 octets.  If the MAC address is a 60-bit address, the 
         length of the octet string shall be 8 octets.  The 
         octet encoding is derived from the hexadecimal 
         representation order for the MAC address.  
         AB-CD-EF-GH-IJ-KL for the 48-bit address format; 
         AB-CD-EF-GH-IJ-KL-MN-OP ofr the 60-bit address format.  
         The octets are encoded as follows: the first pari of 
         hexadecimal digits, AB, are encoded in the first octet.  
         The second pair, CD, is encoded in the second octet, 
         etc.  (See ISO/IEC 8802-2 6.2, MAC address attribute, 
         for definition of 60-bit hexadecimal display format.)"
    SYNTAX      OCTET STRING (SIZE(0 | 6 | 8))

DLSAP ::= TEXTUAL-CONVENTION
    DISPLAY-HINT    "1x-"
    STATUS      current
    DESCRIPTION 
        "This texutal convention represents a fully qualified 
         DLSAP which consistes of a 6 or 8 octet MACAddress (as 
         described for the MACAddress texutal convention) 
         followed by a one octet DSAP.  When null (zero length 
         octet string) the value represents no specific address."
    SYNTAX      OCTET STRING (SIZE(0 | 7 | 9))

LSAP ::= TEXTUAL-CONVENTION
    DISPLAY-HINT    "1x"
    STATUS      current
    DESCRIPTION 
        "This textual convention represents an LLC LSAP which 
         consists of a 1-octet value which contains the LLC 
         LSAP.  Note that technically the LSAP could be 
         continued into subsequent octets, however, this is not 
         normally necessary for X.25/ISO 8208 and CLNS."
    REFERENCE   
        "IEEE 802.2 (ISO/IEC 8802-2) ASN.1, LSAP."
    SYNTAX      OCTET STRING (SIZE(1))

LSAPPairId ::= TEXTUAL-CONVENTION
    DISPLAY-HINT    "1x-"
    STATUS      current
    DESCRIPTION 
        "This textual convention represents an RDE Pair ID whcih 
         consists of a 1-octet value which contains the LLC 
         SSAP, followed by the 6 or 8 octet MACAddress (the 
         combination as described in the DLSAP textual 
         convention), following by anoth 1-octet value which 
         contains the LLC DSAP, followed by the 6 or 8 octet 
         MACAddress."
    REFERENCE   
        "IEEE 802.2 (ISO/IEC 8802-2) ASN.1, LSAPPairID."
    SYNTAX      OCTET STRING (SIZE(0 | 14 | 18))

RoutingInformationField ::= TEXTUAL-CONVENTION
    DISPLAY-HINT    "1x"
    STATUS      current
    DESCRIPTION 
        "The routing information field varies in length up to 30 
         octets.  When source routing is not used the RIF is 
         said to be NULL and contains no information.  The first 
         bit of the MAC source address is defined as the Routing 
         Information Indicator (RII). When the RIF is null, the 
         RII is set to zero (0).  When the RIF is not null, the 
         RII is set to 1.  The first two octets are the Routing 
         Control field (RC) and the remainder of the RIF 
         contains Routing Descriptors (RD).  Each RD is two 
         octets in length, therefore a maximum of 14 RDs can 
         exist in a RIF."
    REFERENCE   
        "IEEE 802.2 (ISO/IEC 8802-2) ASN.1, RIF."
    SYNTAX      OCTET STRING (SIZE(0..30))

llcNotifications OBJECT IDENTIFIER
    ::= { llcMIB 0 }

llcObjects OBJECT IDENTIFIER
    ::= { llcMIB 1 }

llcTables OBJECT IDENTIFIER
    ::= { llcObjects 1 }

-- =====================================================================

mACDLE OBJECT IDENTIFIER
    ::= { llcTables 1 }

mACDLETable OBJECT-TYPE
    SYNTAX      SEQUENCE OF MACDLEEntry
    MAX-ACCESS  not-accessible
    STATUS      current
    DESCRIPTION 
        "The MAC Data Link Entity managed object class.  There 
         may be multiple instances of the mACDLE managed object 
         in a system.  Systems not supported connections to LAN 
         media are not required to support the mACDLE and 
         contained managed objects.
         
         A mACDLE managed object may contain at modes on 
         instance of a mac-specific MO derived from the generic 
         mAC MO.  A mACDLE MO may contain at most one dLSAP MO.  
         The value of the sap1Address attribute is of no 
         significance.  The cardinality of the userEntityNames 
         attribute is limited to one.
         
         A mACDLE MO may be created and deleted explicitly by 
         management operation or created and deleted 
         automatically as part of system operation.
         
         When the mACDLE MO is operable, the operationalState 
         shall have the value 'enabled'; otherwise, it shall 
         have the value 'disabled'.  Transitions of 
         operationalState shall be reported using the 
         stateChange notification.
         
         The mACDLE MOC is derived from the datalinkEntity MOC.  
         The mACDLE MO contains mAC MOs.
         
         An instance of the mACDLE MO represents an instance of 
         the IEEE 802.2 MAC sublayer.  The MAC data link entity 
         can contain mAC MOs.  Each mAC MO instance contained 
         represents a MAC address that belongs to the mACDLE."
    REFERENCE   
        "ITU-T Rec. X.272 | ISO/IEC 10742, mACDLE MOC."
    ::= { mACDLE 1 }

mACDLEEntry OBJECT-TYPE
    SYNTAX      MACDLEEntry
    MAX-ACCESS  not-accessible
    STATUS      current
    DESCRIPTION 
        "Each row in this table is indexed by the MAC DLE 
         communications entity identifier.  Each row contains 
         the linkage and operational status of the 
         communications entity."
    REFERENCE   
        "ITU-T Rec. X.272 | ISO/IEC 10742, mACDLE MO."
    INDEX       { mACDLECommunicationsEntityId }
    ::= { mACDLETable 1 }

MACDLEEntry ::= SEQUENCE {
    -- X.723 communicationsEntity
    mACDLECommunicationsEntityId    SimpleNameType,
    mACDLELocalSapNames             RowPointer,
    mACDLEOperationalState          OperationalState,
    -- X.282 datalinkEntity
    mACDLEProviderEntityNames       RowPointer,
    --
    mACDLERowStatus                 RowStatus
}

mACDLECommunicationsEntityId OBJECT-TYPE
    SYNTAX      SimpleNameType
    MAX-ACCESS  not-accessible
    STATUS      current
    DESCRIPTION 
        "Provides an index into this table used for naming 
         instances of MAC data link equipment."
    REFERENCE   
        "ITU-T Rec. X.282 | ISO/IEC 10742, mACDLE."
    ::= { mACDLEEntry 1 }

mACDLELocalSapNames OBJECT-TYPE
    SYNTAX      RowPointer
    MAX-ACCESS  read-create
    STATUS      current
    DESCRIPTION 
        "The localSapNames attribute identifies the providing 
         entity's SAP objects.  In this case, the providing 
         entity is a Ph-Entity and the Ph-SAP is indicated by 
         the name."
    REFERENCE   
        "ITU-T Rec. X.282 | ISO/IEC 10742, mACDLE."
    ::= { mACDLEEntry 2 }

mACDLEOperationalState OBJECT-TYPE
    SYNTAX      OperationalState
    MAX-ACCESS  read-only
    STATUS      current
    DESCRIPTION 
        "Provides the operational state of the MAC data link 
         entity following the OperationalState textual 
         convention and ITU-T Rec. X.721 | ISO/IEC 10165-2."
    REFERENCE   
        "ITU-T Rec. X.282 | ISO/IEC 10742, mACDLE."
    ::= { mACDLEEntry 3 }

mACDLEProviderEntityNames OBJECT-TYPE
    SYNTAX      RowPointer
    MAX-ACCESS  read-create
    STATUS      current
    DESCRIPTION 
        "Provides a pointer to a side-table that contains the 
         list of provider entity names that provide for the MAC 
         data link equipment."
    REFERENCE   
        "ITU-T Rec. X.282 | ISO/IEC 10742, mACDLE."
    ::= { mACDLEEntry 4 }

mACDLERowStatus OBJECT-TYPE
    SYNTAX      RowStatus
    MAX-ACCESS  read-create
    STATUS      current
    DESCRIPTION 
        "Provides a mechanism whereby management stations may 
         create and destroy entries in this table.  Entries in 
         this table must persist across an agent reboot."
    REFERENCE   
        "ITU-T Rec. X.282 | ISO/IEC 10742, mACDLE."
    ::= { mACDLEEntry 5 }

-- =====================================================================

mAC OBJECT IDENTIFIER
    ::= { llcTables 2 }

mACTable OBJECT-TYPE
    SYNTAX      SEQUENCE OF MACEntry
    MAX-ACCESS  not-accessible
    STATUS      current
    DESCRIPTION 
        "Provides a table of MAC ids that belong to a MAC data 
         link equipment."
    REFERENCE   
        "ITU-T Rec. X.282 | ISO/IEC 10742 mAC MOC."
    ::= { mAC 1 }

mACEntry OBJECT-TYPE
    SYNTAX      MACEntry
    MAX-ACCESS  not-accessible
    STATUS      current
    DESCRIPTION 
        "Each row in this table is indexed by the MAC DLE 
         communications entity id and defines the MAC id.  Each 
         row contains the operational status of the MAC."
    REFERENCE   
        "ITU-T Rec. X.282 | ISO/IEC 10742 mAC MO."
    INDEX       { mACDLECommunicationsEntityId, mACId }
    ::= { mACTable 1 }

MACEntry ::= SEQUENCE {
    mACOperationalState     OperationalState,
    mACId                   SimpleNameType,
    mACRowStatus            RowStatus
}

mACOperationalState OBJECT-TYPE
    SYNTAX      OperationalState
    MAX-ACCESS  read-only
    STATUS      current
    DESCRIPTION 
        "Provides the X.721 operationalState of the mAC 
         according to the OperationalState textual convention 
         from the OPENSS7-TMN-TC module.  The state is 'enabled' 
         when the mAC is operational; 'disabled' otherwise."
    REFERENCE   
        "ITU-T Rec. X.721 | ISO/IEC 10165-2 operationalState."
    ::= { mACEntry 1 }

mACId OBJECT-TYPE
    SYNTAX      SimpleNameType
    MAX-ACCESS  not-accessible
    STATUS      current
    DESCRIPTION 
        "Provides a naming attribute for the mAC MO."
    REFERENCE   
        "ITU-T Rec. X.282 | ISO/IEC 10742 mACId."
    ::= { mACEntry 2 }

mACRowStatus OBJECT-TYPE
    SYNTAX      RowStatus
    MAX-ACCESS  read-create
    STATUS      current
    DESCRIPTION 
        "
         The mACId-mACDLE-Automatic name binding applies when a 
         mAC managed object (or an instance of a subclass of the 
         mAC MO class) is created automatically by the operation 
         of the system as a subordinate object of a mACDLE 
         managed object (or subclass), and deleted 
         automatically.
         
         The mACId-mACDLE-Management name binding applies when a 
         mAC managed object (or an instance of a subclass or the 
         mAC MO class) can be created by management as a 
         subordiante object of a mACDLE managed object (or 
         subclass), and deleted by management."
    REFERENCE   
        "ITU-T Rec. X.282 | ISO/IEC 10742 
         mACId-mACDLE-Automatic, mACId-mACDLE-Management, STD 
         58, SNMPv2-TC RowStatus."
    ::= { mACEntry 3 }

-- =====================================================================

resourceTypeId OBJECT IDENTIFIER
    ::= { llcTables 3 }

resourceTypeIdTable OBJECT-TYPE
    SYNTAX      SEQUENCE OF ResourceTypeIdEntry
    MAX-ACCESS  not-accessible
    STATUS      current
    DESCRIPTION 
        "Provides a table of resource types.  Resource types are 
         characteristics that belong to the provider of the MAC 
         DLE."
    REFERENCE   
        "ISO/IEC 10742 but not ITU-T Rec. X.282"
    ::= { resourceTypeId 1 }

resourceTypeIdEntry OBJECT-TYPE
    SYNTAX      ResourceTypeIdEntry
    MAX-ACCESS  not-accessible
    STATUS      current
    DESCRIPTION 
        "Each row in this table is indexed by the MAC DLE 
         communications entity identifier to which the resources 
         apply.  Each row contains the resources associated with 
         the MAC DLE."
    REFERENCE   
        "ISO/IEC 10742 but not ITU-T Rec. X.282"
    INDEX       { mACDLECommunicationsEntityId }
    ::= { resourceTypeIdTable 1 }

ResourceTypeIdEntry ::= SEQUENCE {
    resourceTypeIdName                      SimpleNameType,
    resourceInfoManufacturerOUI             OCTET STRING,
    resourceInfoManufacturerName            DisplayString,
    resourceInfoManufacturerProductName     DisplayString,
    resourceInfoManufacturerProductVersion  DisplayString
}

resourceTypeIdName OBJECT-TYPE
    SYNTAX      SimpleNameType
    MAX-ACCESS  read-only
    STATUS      current
    DESCRIPTION 
        "Provides a index into the resource type table that is 
         used to name the entry.  The index is not significant, 
         but can be chosen in such a way as it is convenient: 
         for example: eth0."
    REFERENCE   
        "ISO/IEC 10742 but not ITU-T Rec. X.282"
    DEFVAL      { "RTID" }
    ::= { resourceTypeIdEntry 1 }

resourceInfoManufacturerOUI OBJECT-TYPE
    SYNTAX      OCTET STRING
    MAX-ACCESS  read-only
    STATUS      current
    DESCRIPTION 
        "ManufacturerOUI takes the value of an Organizationally 
         Unique Identifier, as defined in secion 5.1 of IEEE 
         802.1 Overview and Architecture.  When encoded as an 
         OCTET STRING, the encoding of the value field of the 
         OCTET STRING shall comply with the representation 
         defined in sections 5.1.2 of the Overview and 
         Architecture.  Inasmcuh as multiple OUI assignements 
         are possible for a given manufacturer and no public 
         registry of such assigments exists, methods for 
         application of the OUI as a globally unique 
         manufacturer identifier is outside the scope of this 
         standard."
    REFERENCE   
        "ISO/IEC 10742 but not ITU-T Rec. X.282"
    ::= { resourceTypeIdEntry 2 }

resourceInfoManufacturerName OBJECT-TYPE
    SYNTAX      DisplayString (SIZE(0..128))
    MAX-ACCESS  read-only
    STATUS      current
    DESCRIPTION 
        "ManufactererName is a printable string used to identify 
         the manufacturer of the resource.  Global assignment of 
         unique name strngs is outside the scope of this 
         standard.  Maximum string length is 128 octets."
    REFERENCE   
        "ISO/IEC 10742 but not ITU-T Rec. X.282"
    ::= { resourceTypeIdEntry 3 }

resourceInfoManufacturerProductName OBJECT-TYPE
    SYNTAX      DisplayString (SIZE(0..128))
    MAX-ACCESS  read-only
    STATUS      current
    DESCRIPTION 
        "ManufactererProductName is a printable string used to 
         identify the manufacturer's product name of the 
         resource.  Maximum string length is 128 octets."
    REFERENCE   
        "ISO/IEC 10742 but not ITU-T Rec. X.282"
    ::= { resourceTypeIdEntry 4 }

resourceInfoManufacturerProductVersion OBJECT-TYPE
    SYNTAX      DisplayString (SIZE(0..128))
    MAX-ACCESS  read-only
    STATUS      current
    DESCRIPTION 
        "ManufacturerProductVersion is a printable string used 
         to identify the manufacturer's product version of the 
         resource.  Maximum string length is 128."
    REFERENCE   
        "ISO/IEC 10742 but not ITU-T Rec. X.282"
    ::= { resourceTypeIdEntry 5 }


-- =====================================================================

dLSAP OBJECT IDENTIFIER
    ::= { llcTables 4 }

dLSAPTable OBJECT-TYPE
    SYNTAX      SEQUENCE OF DLSAPEntry
    MAX-ACCESS  not-accessible
    STATUS      current
    DESCRIPTION 
        "The data link service access point managed object 
         class.  The dLSAP maanged object class is used to 
         represent a service access point at which services are 
         provided by a data link entity to the user entity.  
         Instances of dLSAP managed object class are contained 
         within instances of subclasses derived from the 
         datalinkEntity managed object class.  Constraints on 
         the number of contained dLSAP MOs and any specific 
         semantics of the attreibutes are given as part of the 
         definition of the containing DLE managed object class.
         
         A dLSAP managed object may be created and deleted 
         explicitly by management operation or created and 
         deleted automatically as part of system operation, e.g. 
         when a user of the data link layer service requests and 
         is granted user of the service.  The mechanism by which 
         this happens is a local matter and not subject to OSI 
         standardization."
    REFERENCE   
        "ITU-T Rec. X.282 | ISO/IEC 10742 dLSAP MOC."
    ::= { dLSAP 1 }

dLSAPEntry OBJECT-TYPE
    SYNTAX      DLSAPEntry
    MAX-ACCESS  not-accessible
    STATUS      current
    DESCRIPTION 
        "Each row in the data link SAP table is index by the MAC 
         DLE communications entity identifier and defines the 
         DLSAP identifier."
    REFERENCE   
        "ITU-T Rec. X.282 | ISO/IEC 10742 dLSAP MO."
    INDEX       { mACDLECommunicationsEntityId, dLSAPSapId }
    ::= { dLSAPTable 1 }

DLSAPEntry ::= SEQUENCE {
    dLSAPSapId              SimpleNameType,
    dLSAPSap1Address        Integer32,
    dLSAPUserEntityNames    RowPointer,
    dLSAPRowStatus          RowStatus
}

dLSAPSapId OBJECT-TYPE
    SYNTAX      SimpleNameType
    MAX-ACCESS  not-accessible
    STATUS      current
    DESCRIPTION 
        "Provides a naming attribute for the dLSAP object."
    REFERENCE   
        "ITU-T Rec. X.723 | ISO/IEC 10165-5, sapId."
    ::= { dLSAPEntry 1 }

dLSAPSap1Address OBJECT-TYPE
    SYNTAX      Integer32
    MAX-ACCESS  read-create
    STATUS      current
    DESCRIPTION 
        "Provides the address of the dLSAP which is only of 
         local significance.  It can be the Physical Point of 
         Attachment attached to the dLSAP or the interface index 
         of the entity to which the dLSAP is attached."
    REFERENCE   
        "ITU-T Rec. X.723 | ISO/IEC 10165-5, sap1Address."
    DEFVAL      { 0 }
    ::= { dLSAPEntry 2 }

dLSAPUserEntityNames OBJECT-TYPE
    SYNTAX      RowPointer
    MAX-ACCESS  read-create
    STATUS      current
    DESCRIPTION 
        "Provides the distinguished names of the entities using 
         this dLSAP.  For data links this is a single user 
         entity name formatted as a RowPointer to the entry in 
         the table at which the user entity exists.  This is 
         likely the network entity.  If the user entity is 
         detached or unknown, the value will be zeroDotZero."
    REFERENCE   
        "ITU-T Rec. X.723 | ISO/IEC 10165-5, userEntityNames."
    DEFVAL      { zeroDotZero }
    ::= { dLSAPEntry 3 }

dLSAPRowStatus OBJECT-TYPE
    SYNTAX      RowStatus
    MAX-ACCESS  read-create
    STATUS      current
    DESCRIPTION 
        "Provides a mechanism whereby management stations, 
         following the RowStatus textual convention of the 
         SNMPv2-TC module, may create or delete conceptual rows 
         from this table.
         
         The dLSAP-datalinkEntity-Management name binding 
         applies when a dLSAP managed object (or an instance of 
         a subclass of the dLSAP MO class) can be created by 
         management as a subordinate object of a datalinkEntity 
         maanged object (or subclasses), and deleted by 
         management."
    REFERENCE   
        "ITU-T Rec. X.282 | ISO/IEC 10742, 
         dLSAP-datalinkEntity-Management, STD 58, SNMPv2-TC 
         RowStatus."
    ::= { dLSAPEntry 4 }

-- =====================================================================

lLCDLE OBJECT IDENTIFIER
    ::= { llcTables 5 }

lLCDLETable OBJECT-TYPE
    SYNTAX      SEQUENCE OF LLCDLEEntry
    MAX-ACCESS  not-accessible
    STATUS      current
    DESCRIPTION 
        "The LLC Data Link Entity managed object.  There may be 
         multiple instances of the lLCDLE managed object in a 
         system.  Systems not supporting LLC procedures are not 
         required to support the lLCDLE and contained managed 
         objects.
         
         An lLCDLE managed object may contain instances of 
         llc-specific connectionless and connection-mode 
         protocol machine MOs derived form the generic lLCCOPM 
         and lLCCLPM MO.  An lLCDLE MO may contain multiple 
         dLSAP MOs.  The cardinality of the userEntityNames 
         attribute is limited to one.
         
         An lLCDLE MO may be created and deleted explicity by 
         management operation or created and deleted 
         automatically as part of ssytem operation.
         
         When the lLCDLE MO is operable, the operationalState 
         shall have the value 'enabled'; otherwise it shall have 
         the value 'disabled'.  Transitions of operationalState 
         shall be reported using the stateChange notification.
         
         The lLCDLE MOC is derived from the datalinkEntity MOC.  
         The lLCDLE contains connectionless and connection 
         oriented protocol machines representing LLC1, and LLC2 
         and/or LLC3 operation.  The lLCDLE also contains an LLC 
         station and one or more lLCSAP service access points.
         
         Each lLCDLE MO uses the services of a mACDLE.  The 
         mACDLE provides service to an lLCDLE.  (Note that 
         Ethernet II accesses the MAC sublayer directly, via a 
         dlSAP MO contained by the mACDLE.)
         
         An instance of the lLCDLE MO represents an instance of 
         the IEEE 802.2 LLC sublayer.  The LLC data link entity 
         can contain lLCCLPM and lLCCOPM protocol machines MOs, 
         an lLCstation MO, and one or more lLCSAP MOs."
    REFERENCE   
        "ITU-T Rec. X.282 | ISO/IEC 10742, lLCDLE MOC."
    ::= { lLCDLE 1 }

lLCDLEEntry OBJECT-TYPE
    SYNTAX      LLCDLEEntry
    MAX-ACCESS  not-accessible
    STATUS      current
    DESCRIPTION 
        "Each row in the LLC DLE table is indexed by and defines 
         the LLC DLE communication entity identifier.  Each row 
         contains the local SAP names, provider entity names, 
         and the operational state of the LLC DLE."
    REFERENCE   
        "ITU-T Rec. X.282 | ISO/IEC 10742, lLCDLE MO."
    INDEX       { lLCDLECommunicationsEntityId }
    ::= { lLCDLETable 1 }

LLCDLEEntry ::= SEQUENCE {
    -- X.723 communicationsEntity
    lLCDLECommunicationsEntityId    SimpleNameType,
    lLCDLELocalSapNames             RowPointer,
    lLCDLEOperationalState          OperationalState,
    -- X.282 datalinkEntity
    lLCDLEProviderEntityNames       RowPointer,
    --
    lLCDLERowStatus                 RowStatus
}

lLCDLECommunicationsEntityId OBJECT-TYPE
    SYNTAX      SimpleNameType
    MAX-ACCESS  not-accessible
    STATUS      current
    DESCRIPTION 
        "Provides an index for the lLCDLE entries in this table."
    REFERENCE   
        "ITU-T Rec. X.723 | ISO/IEC 10165-5 
         communicationsEntityId."
    ::= { lLCDLEEntry 1 }

lLCDLELocalSapNames OBJECT-TYPE
    SYNTAX      RowPointer
    MAX-ACCESS  read-create
    STATUS      current
    DESCRIPTION 
        "The localSapNames attribute identifies the providing 
         entity's SAP objects.  In the case of the lLCDLE, the 
         localSapNames identifies the dLSAP of the mACDLE object 
         which is providing service to the lLCDLE."
    REFERENCE   
        "ITU-T Rec. X.723 | ISO/IEC 10165-5 localSapNames."
    ::= { lLCDLEEntry 2 }

lLCDLEOperationalState OBJECT-TYPE
    SYNTAX      OperationalState
    MAX-ACCESS  read-only
    STATUS      current
    DESCRIPTION 
        "Provides the operational state of the logical link 
         control data link entity following the OperationalState 
         textual convention of the OPENSS7-TMN-TC module.
         
         When the lLCDLE MO is operable, the operationalState 
         shall have the value 'enabled'; otherwise it shall have 
         the value 'disabled'.  Transitions of operationalState 
         shall be reported using the stateChange notification."
    REFERENCE   
        "ITU-T Rec. X.721 | ISO/IEC 10165-2 operationalState."
    ::= { lLCDLEEntry 3 }

lLCDLEProviderEntityNames OBJECT-TYPE
    SYNTAX      RowPointer
    MAX-ACCESS  read-create
    STATUS      current
    DESCRIPTION 
        "The providerEntityNames attribute identifies the 
         entities providing service to this datalinkEntity.  In 
         the case of the LLC data link entity, lLCDLE, the 
         provider entity is a MAC data link entity, mACDLE.  
         At most one mACDLE can provide service to an lLCDLE, 
         and at most one lLCDLE can be provided service by a 
         mACDLE.
         
         When there is no mACDLE providing service to the 
         lLCDLE, this attribute will contain zeroDotZero.  When 
         there is a mACDLE associated with this lLCDLE, the 
         value of this attribute will be the RowPointer to the 
         entry in the mACDLE table at which the corresponding 
         mACDLE entry occurs.
         
         When there is a mACDLE providing service to this 
         lLCDLE, the mACDLECommunicationsEntityId will be the 
         same as the lLCDLECommunicationsEntityId and this entry 
         will contain the RowPointer of the corresponding row in 
         the mACDLE table.  "
    REFERENCE   
        "ITU-T Rec. X.282 | ISO/IEC 10742."
    ::= { lLCDLEEntry 4 }

lLCDLERowStatus OBJECT-TYPE
    SYNTAX      RowStatus
    MAX-ACCESS  read-create
    STATUS      current
    DESCRIPTION 
        "Provides a mechanism whereby management stations, 
         following the RowStatus textual convention of the 
         SNMPv2-TC module, may create and destroy conceptual 
         rows in this table.
         
         Rows must have been created by a management station to 
         be deleted by a management station.  Rows created by 
         system operation must be deleted by system operation."
    REFERENCE   
        "STD 58, SNMPv2-TC RowStatus."
    ::= { lLCDLEEntry 5 }

-- =====================================================================

lLCStation OBJECT IDENTIFIER
    ::= { llcTables 6 }

lLCStationTable OBJECT-TYPE
    SYNTAX      SEQUENCE OF LLCStationEntry
    MAX-ACCESS  not-accessible
    STATUS      current
    DESCRIPTION 
        "The station component is responsible for processing the 
         events that affect the entire LLC entity.  The station 
         component handles PDUs addressed to the null DSAP 
         address and processes the duplicate address check, if 
         implemented.  One station component shall exist for 
         each MAC service access point present on the local 
         area network.
         
         Provides a table of LLC Stations.  There is in entry in 
         this table for each MAC service access point present on 
         the local area network.
         
         Provides a table of statistics for LLC stations.  There 
         is an entry in this table for each MAC service access 
         point present on a local area network attached to this 
         system."
    REFERENCE   
        "IEEE 802.2 | ISO/IEC 8802-2, lLCStation MOC."
    ::= { lLCStation 1 }

lLCStationEntry OBJECT-TYPE
    SYNTAX      LLCStationEntry
    MAX-ACCESS  not-accessible
    STATUS      current
    DESCRIPTION 
        "The station component is responsible for handling all 
         events that are directed to the LLC as a whole (i.e, 
         events affecting all SAPs and connections serviced by 
         that LLC).  The station component shall begin in the 
         DOWN state, optionally check for a duplicate station 
         address, and potentially enter the UP state; see figure 
         24 and table 1 of IEEE 802.2 (ISO/IEC 8802-2).  The UP 
         state of the LLC station component provides the 
         enabling conditions for the operation of the service 
         access point (SAP) components.
         
         The station component shall be capable of receiving and 
         responding to XID and TEST command PDUs.  It shall 
         optionally be capable of initiating the XID commend 
         PDU, if duplicate address checking is performed by the 
         LLC entity in a particular implementation; see table 2 
         of IEEE 802.2 (ISO/IEC 8802-2).  These PDUs shall used 
         the null DSAP address to denote that the station 
         component is being referenced.
         
         The performance of the duplicate address check requires 
         that the station component be prepared to received its 
         own XID PDUs.  The definition of the MAC operation 
         provides for the ability to simultaneously transmit and 
         receive.  Since the DA = SA in the XID PDUs can be used 
         for duplicate address check, the MAC will recognize its 
         own address and pass the PDU to the station component.  
         The station component will respond to an XID command 
         PDU with an XID responose PDU, regardless of whether it 
         originated from itself or a remote LLC.  The station 
         component provides the duplicate address check by 
         maintaining a count of received XID response PDUs.  If 
         more than one XID response PDU is received, then at 
         least one other identical MAC DA exists on the LAN.  
         See figure 24 and table 1 in IEEE 802.2 (ISO/IEC 
         8802-2) for details.
         
         Provides an entry in the X.25 LLC2 Station table for 
         one LLC2 connection to the media (MAC Access).  Each 
         MAC is indexed by its ifIndex into the interface 
         table.
         
         Provides an enty in the X.25 LLC Station table for one 
         LLC connection to the media (MAC Access).  Each MAC is 
         indexed by its ifIndex into the interface table."
    REFERENCE   
        "IEEE 802.2 | ISO/IEC 8802-2, lLCStation MO."
    INDEX       { lLCDLECommunicationsEntityId, dLSAPSapId }
    ::= { lLCStationTable 1 }

LLCStationEntry ::= SEQUENCE {
    -- lLCStation-P mandatory package
    lLCStationLLCName                           SimpleNameType,
    lLCStationMaximumLSAPsConfigured            Integer32,
    lLCStationNumberOfActiveLSAPs               Gauge32,
    lLCStationSupportedServicesTypes            LLCServices,
    lLCStationStatus                            LLCStationStatus,
    -- need reinitialize action
    -- lLCDupAddress-P conditional package
    lLCStationType1AcknowledgeTimeoutValue      TimeInterval,
    lLCStationType1MaximumRetryCount            Integer32,
    -- lLCType3-P conditional package
    lLCStationMaximumPDUN3                      Integer32,
    lLCStationMaximumRetransmissions4           Integer32,
    lLCStationReceiveVariableLifetime           TimeInterval,
    lLCStationTransmitVariableLifetime          TimeInterval,
    lLCStationType3AcknowledgeTimeoutValue      TimeInterval,
    lLCStationType3Retransmissions              Counter32,
    -- need lLC3StationEvent notification
    -- lLCBuffer-P conditional package
    lLCStationAvgBufferUseSize                  Gauge32,
    lLCStationBufferProblems                    Counter32,
    lLCStationBufferSize                        Integer32,
    lLCStationMaxBufferUseSize                  Gauge32,
    -- need lLCStationEvent notification
    -- pDUsDiscarded-P conditional package
    lLCStationInactiveLSAP                      Counter32,
    lLCStationPDUsDiscard                       Counter32,
    -- need lLCStationEvent notification
    -- rDE-P conditional package
    lLCStationSTRIndicator                      STRIndicator,
    lLCStationVersionNumber                     Integer32,
    -- type1AcknowledgmentTimerTimeouts-P conditional package
    lLCStationType1AcknowledgmentTimerTimeouts  Counter32
}

-- lLCStation-P mandatory package
--
-- The lLCStation package contains the definition of all attributes and 
-- all actions that are common to the LLC station as a whole, regardless 
-- of which LLC operations are supported.
--
lLCStationLLCName OBJECT-TYPE
    SYNTAX      SimpleNameType
    MAX-ACCESS  read-write
    STATUS      current
    DESCRIPTION 
        "This attriute is used to name the instance of the 
         lLCStation managed object."
    REFERENCE   
        "IEEE 802.2 | ISO/IEC 8802-2, lLCName"
    ::= { lLCStationEntry 1 }

lLCStationMaximumLSAPsConfigured OBJECT-TYPE
    SYNTAX      Integer32 (1..128)
    UNITS       "LSAPs"
    MAX-ACCESS  read-only
    STATUS      current
    DESCRIPTION 
        "The maximum number of LSAPs that can be supported by 
         this station at any moment in time.  All LLC stations 
         must support at least one LSAP (the null LSAP used for 
         duplicate address detection and station-wide XID and 
         TEST commands).  Station numbers (LSAP IDs) range from 
         0 to 127.  Therefore, the range of this value is from 1 
         to 128.  IEEE 802.2F (ISO/IEC 8802-2) does not 
         constrain the range of this attribute.  The number 
         reported is implementation dependent.  This is a 
         read-only column."
    REFERENCE   
        "IEEE 802.2 | ISO/IEC 8802-2, maximumLSAPsConfigured"
    ::= { lLCStationEntry 2 }

lLCStationNumberOfActiveLSAPs OBJECT-TYPE
    SYNTAX      Gauge32 (1..128)
    UNITS       "LSAPs"
    MAX-ACCESS  read-only
    STATUS      current
    DESCRIPTION 
        "The number of active LSAPs that the station currently 
         supports."
    REFERENCE   
        "IEEE 802.2 | ISO/IEC 8802-2, numberOfActiveLSAPs"
    ::= { lLCStationEntry 3 }

lLCStationSupportedServicesTypes OBJECT-TYPE
    SYNTAX      LLCServices
    MAX-ACCESS  read-write
    STATUS      current
    DESCRIPTION 
        "The type or types of service supported (i.e., Type 1, 
         Type 2, Type 3.) The type or types of service supported 
         by this station.  The type are a combination of 
         
         - type1(0),
         - type2(1),
         - type3Initiate(2),
         - kype3ReceiveData(3),
         - type3ReturnData(4).
         
         Implementations supporting this MIB must support at 
         least type1(0) and should support type2(1) if at all 
         possible."
    REFERENCE   
        "IEEE 802.2 | ISO/IEC 8802-2, supportedServicesTypes"
    ::= { lLCStationEntry 4 }

lLCStationStatus OBJECT-TYPE
    SYNTAX      LLCStationStatus
    MAX-ACCESS  read-only
    STATUS      current
    DESCRIPTION 
        "Provides the status of the station.  This attribute 
         allows a manager to determine what state (UP, DOWN, 
         etc.) the LLC Station entity is in.  Note that the only 
         reason that the integer values start at zero (0) here 
         instead of one (1) is that the values are already 
         defined in the GDMO MIBs of IEEE 802.2 (ISO/IEC 
         8802-2)."
    REFERENCE   
        "IEEE 802.2 | ISO/IEC 8802-2, status"
    ::= { lLCStationEntry 5 }

lLCStationType1AcknowledgeTimeoutValue OBJECT-TYPE
    SYNTAX      TimeInterval
    MAX-ACCESS  read-write
    STATUS      current
    DESCRIPTION 
        "The timeout value of the Ack timer, which is measured 
         in centiseconds, displayed in seconds.  THe Ack timer 
         is described in IEEE 802.2 (ISO/IEC 8802-2) 6.9.2.2 and 
         6.9.2.3.  It is used by the station to supervise the 
         acknowledgement of an XID message sent to detect 
         duplicate MAC addresses.  If no XID response message is 
         received within this time period, the XID message will 
         be reattempted up to the maximum retry count."
    REFERENCE   
        "IEEE 802.2 (ISO/IEC 8802-2), 
         type1AcknowledgeTimeoutValue, 6.9.2.2 and 6.9.2.3."
    ::= { lLCStationEntry 6 }

lLCStationType1MaximumRetryCount OBJECT-TYPE
    SYNTAX      Integer32
    UNITS       "retries"
    MAX-ACCESS  read-write
    STATUS      current
    DESCRIPTION 
        "The maximum number of retries during duplicate address 
         checking.  If the acknowledgement timer expires after 
         sending an XID message for duplicate address checking, 
         the XID message will be retransmitted this number of 
         times, before moving to the UP state."
    REFERENCE   
        "ISO/IEC 8802-2 (IEEE 802.2), type1MaximumRetryCount, 
         6.9.2.2 and 6.9.2.3."
    ::= { lLCStationEntry 7 }

-- lLCType3-P conditional package
--
-- This is a conditional part of the lLCStation component object.  It 
-- exists if the LLC object supports LLC Type 3 service.

lLCStationMaximumPDUN3 OBJECT-TYPE
    SYNTAX      Integer32
    UNITS       "octets"
    MAX-ACCESS  read-write
    STATUS      current
    DESCRIPTION 
        "The maximum size of a Type 3 command PDU.
         
         Unless Type 3 service is supported on the LLC station, 
         this value is of no significance."
    REFERENCE   
        "IEEE 802.2 | ISO/IEC 8802-2, maximumPDUN3"
    ::= { lLCStationEntry 8 }

lLCStationMaximumRetransmissions4 OBJECT-TYPE
    SYNTAX      Integer32
    UNITS       "retransmissions"
    MAX-ACCESS  read-write
    STATUS      current
    DESCRIPTION 
        "The number of retransmissions of a Type 3 PDU due to 
         error conditions preventing receive of an 
         acknowledgement.
         
         Unless Type 3 service is supported on the LLC station, 
         this value is of no significance."
    REFERENCE   
        "IEEE 802.2 | ISO/IEC 8802-2, maximumRetransmissions4"
    ::= { lLCStationEntry 9 }

lLCStationReceiveVariableLifetime OBJECT-TYPE
    SYNTAX      TimeInterval
    MAX-ACCESS  read-write
    STATUS      current
    DESCRIPTION 
        "The amount of time the Type 3 LLC receive state 
         variables are maintained.
         
         Unless Type 3 service is suported on the LLC station, 
         this value is of no significance."
    REFERENCE   
        "IEEE 802.2 | ISO/IEC 8802-2, receiveVariableLifetime"
    ::= { lLCStationEntry 10 }

lLCStationTransmitVariableLifetime OBJECT-TYPE
    SYNTAX      TimeInterval
    MAX-ACCESS  read-write
    STATUS      current
    DESCRIPTION 
        "The amout of time the Type 3 LLC transmit state 
         variables are maintained.
         
         Unless Type 3 service is supported on the LLC station, 
         this value is of no significance."
    REFERENCE   
        "IEEE 802.2 | ISO/IEC 8802-2, transmitVariableLifetime"
    ::= { lLCStationEntry 11 }

lLCStationType3AcknowledgeTimeoutValue OBJECT-TYPE
    SYNTAX      TimeInterval
    MAX-ACCESS  read-write
    STATUS      current
    DESCRIPTION 
        "Specifies the time interval during which the LLC 
         expects to receive a response to an acknowledged 
         connectionless request.
         
         Unless Type 3 service is supported by the LLC station, 
         this value is of no significance."
    REFERENCE   
        "IEEE 802.2 | ISO/IEC 8802-2, 
         type3AcknowledgeTimeoutValue"
    ::= { lLCStationEntry 12 }

lLCStationType3Retransmissions OBJECT-TYPE
    SYNTAX      Counter32
    UNITS       "octets"
    MAX-ACCESS  read-only
    STATUS      current
    DESCRIPTION 
        "Provides a count of the number of PDUs which were 
         retrasmitted (at least once) by the Type 3 LLC service.
         
         Provides a count of the number of PDUs which were 
         retransmitted (at least once) by the Type 3 LLC 
         service.  This value is of no significance unless the 
         LLC station supports Type 3 operation."
    REFERENCE   
        "IEEE 802.2 | ISO/IEC 8802-2, type3Retransmissions"
    ::= { lLCStationEntry 13 }

-- need lLC3StationEvent notification

-- lLCBuffer-P conditional package
--
-- This package provides the total amount of buffer space available for 
-- this station, the amount of buffer space in use and the average 
-- buffer space in use by this station.

lLCStationAvgBufferUseSize OBJECT-TYPE
    SYNTAX      Gauge32
    UNITS       "octets"
    MAX-ACCESS  read-only
    STATUS      current
    DESCRIPTION 
        "Specifies the average amount of buffer space (in 
         octets) in use at the same time by LLC for this 
         station."
    REFERENCE   
        "IEEE 802.2 | ISO/IEC 8802-2, avgBufferUseSize"
    ::= { lLCStationEntry 14 }

lLCStationBufferProblems OBJECT-TYPE
    SYNTAX      Counter32
    UNITS       "PDUs"
    MAX-ACCESS  read-only
    STATUS      current
    DESCRIPTION 
        "This counter provides a count of PDUs discarded due to 
         buffer limitations."
    REFERENCE   
        "IEEE 802.2 | ISO/IEC 8802-2, bufferProblems"
    ::= { lLCStationEntry 15 }

lLCStationBufferSize OBJECT-TYPE
    SYNTAX      Integer32
    UNITS       "octets"
    MAX-ACCESS  read-write
    STATUS      current
    DESCRIPTION 
        "THe amount of buffer space (in octets) for use by LLC."
    REFERENCE   
        "IEEE 802.2 | ISO/IEC 8802-2, bufferSize"
    ::= { lLCStationEntry 16 }

lLCStationMaxBufferUseSize OBJECT-TYPE
    SYNTAX      Gauge32
    UNITS       "octets"
    MAX-ACCESS  read-only
    STATUS      current
    DESCRIPTION 
        "Specifies the maximum amount of buffer space (in 
         octets) in use at the same time by LLC for this 
         station."
    REFERENCE   
        "IEEE 802.2 | ISO/IEC 8802-2, maxBufferUseSize"
    ::= { lLCStationEntry 17 }

-- need lLCStationEvent notification

-- pDUsDiscarded-P conditional package
--
-- This package is present if the implementation supports the counting 
-- of the number of invalid PDUs discarded also if implementation 
-- supports the counting of PDUs discarded due to the specification of 
-- an inactive DSAP.

lLCStationInactiveLSAP OBJECT-TYPE
    SYNTAX      Counter32
    UNITS       "PDUs"
    MAX-ACCESS  read-only
    STATUS      current
    DESCRIPTION 
        "This counts the number of PDUs discarded due to the 
         specification of an inactive DSAP."
    REFERENCE   
        "IEEE 802.2 | ISO/IEC 8802-2, inactiveLSAP"
    ::= { lLCStationEntry 18 }

lLCStationPDUsDiscard OBJECT-TYPE
    SYNTAX      Counter32
    UNITS       "invalid PDUs"
    MAX-ACCESS  read-only
    STATUS      current
    DESCRIPTION 
        "Provides a total count of invalid PDUs that are 
         discarded.  A discarded (invalid) PDU shall be defined 
         as one that meets at least one of the following 
         coniditions:
         
         1. It is identified by such by the PHY or the MAC 
            sublayer;
         2. It is not an integral number of octets in length;
         3. It does not contain two properly formatted address 
            fields, one control field, and optionally an 
            information field in their proper order.
         4. Its length is less that 3 octets (one-octet control 
            field) or 4 octets (two-octet control field)."
    REFERENCE   
        "IEEE 802.2 | ISO/IEC 8802-2, pDUsDiscard"
    ::= { lLCStationEntry 19 }

-- need lLCStationEvent notification

-- rDE-P conditional package
--
-- If RDE is suppored by this station, then two attributes will be 
-- present at the Station level.

lLCStationSTRIndicator OBJECT-TYPE
    SYNTAX      STRIndicator
    MAX-ACCESS  read-write
    STATUS      current
    DESCRIPTION 
        "A value that indicates if the spanning tree will be 
         traversed by a NSR or STE routing."
    REFERENCE   
        "IEEE 802.2 | ISO/IEC 8802-2, sTRIndicator"
    ::= { lLCStationEntry 20 }

lLCStationVersionNumber OBJECT-TYPE
    SYNTAX      Integer32
    MAX-ACCESS  read-write
    STATUS      current
    DESCRIPTION 
        "The version of sap RDE protocol implemented at this 
         station.  The value of 1 will be used to represent the 
         current version.  The special value zero (0) indicates 
         that RDE is not support at this station."
    REFERENCE   
        "IEEE 802.2 | ISO/IEC 8802-2, versionNumber"
    ::= { lLCStationEntry 21 }

-- type1AcknowledgmentTimerTimeouts-P conditional package
--
-- This package is present if the implementation supports the 
-- Acknolwedgment Timer attribute.

lLCStationType1AcknowledgmentTimerTimeouts OBJECT-TYPE
    SYNTAX      Counter32
    UNITS       "ACK timer expiries"
    MAX-ACCESS  read-only
    STATUS      current
    DESCRIPTION 
        "Specifies the number of times the ACK timer has 
         expired."
    REFERENCE   
        "ISO/IEC 8802-2 (IEEE 802.2), 
         type1AcknowledgmentTimerTimeouts, 6.9.2.2 and 6.9.2.3."
    ::= { lLCStationEntry 22 }


-- =====================================================================

lLCSAP OBJECT IDENTIFIER
    ::= { llcTables 7 }

lLCSAPTable OBJECT-TYPE
    SYNTAX      SEQUENCE OF LLCSAPEntry
    MAX-ACCESS  not-accessible
    STATUS      current
    DESCRIPTION 
        "The Link Service Access Point (SAP) component  is 
         responsible for processing the events that affect a 
         specific operating service access point.  One SAP 
         component shall exist for each SAP within the LLC 
         entity.
         
         lLCSAP managed object.  This managed object contains 
         attributes associated wtih an LLC SAP that are 
         independent of any paticular type of Operation."
    REFERENCE   
        "IEEE 802.2 (ISO/IEC 8802-2)."
    ::= { lLCSAP 1 }

lLCSAPEntry OBJECT-TYPE
    SYNTAX      LLCSAPEntry
    MAX-ACCESS  not-accessible
    STATUS      current
    DESCRIPTION 
        "The lLCDLECommunicationsEntityId index is because this 
         MOC is contained by the
         lLCDLE MOC.
         The dLSAPSapId index is used because this MOC is 
         derived from the dLSAP MOC."
    REFERENCE   
        "IEEE 802.2 (ISO/IEC 8802-2)."
    INDEX       { lLCDLECommunicationsEntityId, dLSAPSapId }
    ::= { lLCSAPTable 1 }

LLCSAPEntry ::= SEQUENCE {
    -- lLCSAP-P mandatory package
    lLCSAPName      SimpleNameType,
    lLCSAPAddress   LSAP,
    lLCSAPRDE       TruthValue
}

-- lLCSAP-P mandatory package
--
-- The lLCSAP package contains the definitions of all attributes and 
-- actions aassociatedw ith an LLC SAP that are independent of what LLC 
-- types of operation are supported.

lLCSAPName OBJECT-TYPE
    SYNTAX      SimpleNameType
    MAX-ACCESS  not-accessible
    STATUS      current
    DESCRIPTION 
        "Used to name the instance of this lLCSAP managed object 
         within the scope of a containing lLCDLE managed object."
    REFERENCE   
        "IEEE 802.2 (ISO/IEC 8802-2), lLCSAPName."
    ::= { lLCSAPEntry 1 }

lLCSAPAddress OBJECT-TYPE
    SYNTAX      LSAP
    MAX-ACCESS  read-only
    STATUS      current
    DESCRIPTION 
        "The individual LLC address identifying this LSAP."
    REFERENCE   
        "IEEE 802.2 (ISO/IEC 8802-2), lLCAddress."
    ::= { lLCSAPEntry 2 }

lLCSAPRDE OBJECT-TYPE
    SYNTAX      TruthValue
    MAX-ACCESS  read-only
    STATUS      current
    DESCRIPTION 
        "A boolean value that, if set to true, means that RDE 
         is supported by this SAP."
    REFERENCE   
        "IEEE 802.2 (ISO/IEC 8802-2), rDE."
    ::= { lLCSAPEntry 3 }


-- =====================================================================

rDESetup OBJECT IDENTIFIER
    ::= { llcTables 8 }

rDESetupTable OBJECT-TYPE
    SYNTAX      SEQUENCE OF RDESetupEntry
    MAX-ACCESS  not-accessible
    STATUS      current
    DESCRIPTION 
        "
         RDE setup managed object.  A rDESetup managed object 
         instance is instaniated if an instance of the lLCSAP 
         object enables RDE.  RDE setup managed objects are not 
         created nor deleted explicitly by management operation."
    ::= { rDESetup 1 }

rDESetupEntry OBJECT-TYPE
    SYNTAX      RDESetupEntry
    MAX-ACCESS  not-accessible
    STATUS      current
    DESCRIPTION 
        "The lLCDLECommunicationsEntityId index is used because 
         this MOC is contained by the lLCDLE MOC.
         The dLSAPSapId index is because this MOC is derived 
         from the dLSAP MOC."
    INDEX       { lLCDLECommunicationsEntityId, dLSAPSapId }
    ::= { rDESetupTable 1 }

RDESetupEntry ::= SEQUENCE {
    rDESetupAgingEnabled                TruthValue,
    rDESetupAgingValue                  Integer32,
    rDESetupEnableType2Reset            Integer32,
    rDESetupMaximumRouteDescriptors     Integer32,
    rDESetupMaximumResponseTime         TimeInterval,
    rDESetupMinimumPDUSize              Integer32,
    rDESetupRDEHold                     TruthValue,
    rDESetupRDEReplace                  TruthValue,
    rDESetupName                        Integer32,
    rDESetupResetOnTestEnabled          TruthValue
}

rDESetupAgingEnabled OBJECT-TYPE
    SYNTAX      TruthValue
    MAX-ACCESS  read-write
    STATUS      current
    DESCRIPTION 
        "A boolean value representing the policy that, when true, 
         allows a manager to age a route."
    REFERENCE   
        "IEEE 802.2 (ISO/IEC 8802-2), agingEnabled."
    ::= { rDESetupEntry 1 }

rDESetupAgingValue OBJECT-TYPE
    SYNTAX      Integer32
    MAX-ACCESS  read-write
    STATUS      current
    DESCRIPTION 
        "A value used to determine if a route should be flushed 
         due to inactivity for a specified time period."
    REFERENCE   
        "IEEE 802.2 (ISO/IEC 8802-2), agingValue."
    ::= { rDESetupEntry 2 }

rDESetupEnableType2Reset OBJECT-TYPE
    SYNTAX      Integer32
    MAX-ACCESS  read-write
    STATUS      current
    DESCRIPTION 
        "A value used to determine if a type 2 reset is to be 
         enabled."
    REFERENCE   
        "IEEE 802.2 (ISO/IEC 8802-2), enableType2Reset."
    ::= { rDESetupEntry 3 }

rDESetupMaximumRouteDescriptors OBJECT-TYPE
    SYNTAX      Integer32
    MAX-ACCESS  read-write
    STATUS      current
    DESCRIPTION 
        "The maximum number or route descriptors that an 
         acceptable route may contain."
    REFERENCE   
        "IEEE 802.2 (ISO/IEC 8802-2), maximumRouteDescriptors."
    ::= { rDESetupEntry 4 }

rDESetupMaximumResponseTime OBJECT-TYPE
    SYNTAX      TimeInterval
    MAX-ACCESS  read-write
    STATUS      current
    DESCRIPTION 
        "The timer value used to limit the maximum route trip 
         response time allowed for route discovery and 
         consequently the maximum time a PDU can reamin in the 
         system."
    REFERENCE   
        "IEEE 802.2 (ISO/IEC 8802-2), maximumResponseTime."
    ::= { rDESetupEntry 5 }

rDESetupMinimumPDUSize OBJECT-TYPE
    SYNTAX      Integer32
    MAX-ACCESS  read-write
    STATUS      current
    DESCRIPTION 
        "The minimum number of octets that must be supported by 
         an acceptable route as indicated by the LF bits of the 
         routing information field."
    REFERENCE   
        "IEEE 802.2 (ISO/IEC 8802-2), minimumPDUSize."
    ::= { rDESetupEntry 6 }

rDESetupRDEHold OBJECT-TYPE
    SYNTAX      TruthValue
    MAX-ACCESS  read-write
    STATUS      current
    DESCRIPTION 
        "A boolean value representing the policy that, when 
         true, requires RDE to withhold sending PDUs while 
         changing routes."
    REFERENCE   
        "IEEE 802.2 (ISO/IEC 8802-2), rDEHold."
    ::= { rDESetupEntry 7 }

rDESetupRDEReplace OBJECT-TYPE
    SYNTAX      TruthValue
    MAX-ACCESS  read-write
    STATUS      current
    DESCRIPTION 
        "A boolean value representing the policy that, when 
         true, enables the RDE to use the route selected by the 
         remote station."
    REFERENCE   
        "IEEE 802.2 (ISO/IEC 8802-2), rDEReplace."
    ::= { rDESetupEntry 8 }

rDESetupName OBJECT-TYPE
    SYNTAX      Integer32
    MAX-ACCESS  read-only
    STATUS      current
    DESCRIPTION 
        "Naming attribute for the rDESetup managed object."
    REFERENCE   
        "IEEE 802.2 (ISO/IEC 8802-2), rDESetupName."
    ::= { rDESetupEntry 9 }

rDESetupResetOnTestEnabled OBJECT-TYPE
    SYNTAX      TruthValue
    MAX-ACCESS  read-write
    STATUS      current
    DESCRIPTION 
        "This attribute is a boolean value.  If the attribute is 
         true, then if a test frame is rceieved the source route 
         is reset."
    REFERENCE   
        "IEEE 802.2 (ISO/IEC 8802-2), resetOnTestEnabled."
    ::= { rDESetupEntry 10 }

-- =====================================================================

rDEPair OBJECT IDENTIFIER
    ::= { llcTables 9 }

rDEPairTable OBJECT-TYPE
    SYNTAX      SEQUENCE OF RDEPairEntry
    MAX-ACCESS  not-accessible
    STATUS      current
    DESCRIPTION 
        "
         RDE pair managed object.  An instance of this managed 
         object will exist for each RDE pair used by any type of 
         LLC service provided.  This managed object contains the 
         local MAC address and local SAP and the remote MAC 
         address and remote SAP, plus counters.
         
         An instance of this managed object will exist for each 
         RDE pair used by any type of LLC service provided. This 
         managed object contains the local MAC address and local 
         SAP and the remote MAC address and remote SAP, plus 
         counters.
         
         Provides a table that lists the pairing of local LSAP 
         and MAC with remote LSAP Id and MAC, as a pair for use 
         by the route determination entity (RDE)."
    ::= { rDEPair 1 }

rDEPairEntry OBJECT-TYPE
    SYNTAX      RDEPairEntry
    MAX-ACCESS  not-accessible
    STATUS      current
    DESCRIPTION 
        "Provides an entry into the rDEPairTable which 
         represets the route determination entity routing 
         information for one local LSAP/MAC and remote 
         LSAPId/MAC pair.  The pair is indexed by the 
         rDEPairIndex which indicates the local LLC station 
         and the rDEPairName which indicates the remote LLC 
         station.
         
         Each entry can have the flushRoute action performed on 
         it.  The flushRoute action takes no parameters.  This 
         action will be sent when management requests an RDE 
         Parit o flush its route.  This does not cause the RDE 
         to discover a new route.
         
         Each entry can have the the readCounters action 
         performed on it.  The readCounters action will be sent 
         when management requests information concerning RDE 
         counters."
    INDEX       { lLCDLECommunicationsEntityId, dLSAPSapId, rDEPairName }
                -- lLCDLECommunicationsEntityId - contained by lLCDLE
                -- dLSAPSapId - derived from dLSAP
                -- rDEPairName - index
    ::= { rDEPairTable 1 }

RDEPairEntry ::= SEQUENCE {
    rDEPairName                 LSAPPairId,
    rDEPairDiscardCounter       Counter32,
    rDEPairNSRPDUCounter        Counter32,
    rDEPairNSRSelectedCounter   Counter32,
    rDEPairRIF                  RoutingInformationField,
    rDEPairSRFPDUCounter        Counter32,
    rDEPairQueryCounter         Counter32
}

rDEPairName OBJECT-TYPE
    SYNTAX      LSAPPairId
    MAX-ACCESS  not-accessible
    STATUS      current
    DESCRIPTION 
        "The local LSAP and remote LSAPId and the local and 
         remote MAC Addresses.  Because the local LSAP and local 
         MAC address are implied by this LAN station, only the 
         remote LSAPId and remote MAC are provided in this 
         attribute.  The field is encoded as a MACAddress 
         textual convenstion (6 octet or 8 octet MAC address) 
         except that it is also followed by a single octet 
         inicating the remote LSAPId and can have values between 
         0 and 127."
    REFERENCE   
        "IEEE 802.2 (ISO/IEC 8802-2) rDEPairName."
    ::= { rDEPairEntry 1 }

rDEPairDiscardCounter OBJECT-TYPE
    SYNTAX      Counter32
    MAX-ACCESS  read-only
    STATUS      current
    DESCRIPTION 
        "A value that represents the number of times a new 
         selection has been made."
    REFERENCE   
        "IEEE 802.2 (ISO/IEC 8802-2) discardCounter."
    ::= { rDEPairEntry 2 }

rDEPairNSRPDUCounter OBJECT-TYPE
    SYNTAX      Counter32
    UNITS       "frames"
    MAX-ACCESS  read-only
    STATUS      current
    DESCRIPTION 
        "A value that represents the number of frames without a 
         routing field."
    REFERENCE   
        "IEEE 802.2 (ISO/IEC 8802-2) nSRPDUCounter."
    ::= { rDEPairEntry 3 }

rDEPairNSRSelectedCounter OBJECT-TYPE
    SYNTAX      Counter32
    MAX-ACCESS  read-only
    STATUS      current
    DESCRIPTION 
        "A value that represents the number of times that 
         acceptable SRF route existed resulting in the selection 
         of the NSR path."
    REFERENCE   
        "IEEE 802.2 (ISO/IEC 8802-2) nSRSelectedCounter."
    ::= { rDEPairEntry 4 }

rDEPairRIF OBJECT-TYPE
    SYNTAX      RoutingInformationField
                -- OCTET STRING(SIZE(0..30))
    MAX-ACCESS  read-only
    STATUS      current
    DESCRIPTION 
        "The routing information field varies in length up to 30 
         octets.  When source routing is not used the RIF is 
         said to be NULL and contains no information.  The first 
         bit of the MAC source address is defined as the Routing 
         Information Indicator (RII). When the RIF is null, the 
         RII is set to zero (0).  When the RIF is not null, the 
         RII is set to 1.  The first two octets are the Routing 
         Control field (RC) and the remainder of the RIF 
         contains Routing Descriptors (RD).  Each RD is two 
         octets in length, therefore a maximum of 14 RDs can 
         exists in a RIF."
    REFERENCE   
        "IEEE 802.2 (ISO/IEC 8802-2) rIF."
    ::= { rDEPairEntry 5 }

rDEPairSRFPDUCounter OBJECT-TYPE
    SYNTAX      Counter32
    UNITS       "frames"
    MAX-ACCESS  read-only
    STATUS      current
    DESCRIPTION 
        "A value that represents the number of frames with 
         routing field."
    REFERENCE   
        "IEEE 802.2 (ISO/IEC 8802-2) sRFPDUCounter."
    ::= { rDEPairEntry 6 }

rDEPairQueryCounter OBJECT-TYPE
    SYNTAX      Counter32
    UNITS       "RQ commands"
    MAX-ACCESS  read-only
    STATUS      current
    DESCRIPTION 
        "A value that represents the numer of Route Query 
         commands generated."
    REFERENCE   
        "IEEE 802.2 (ISO/IEC 8802-2) queryCounter."
    ::= { rDEPairEntry 7 }


-- =====================================================================

lLCCLPM OBJECT IDENTIFIER
    ::= { llcTables 10 }

lLCCLPMTable OBJECT-TYPE
    SYNTAX      SEQUENCE OF LLCCLPMEntry
    MAX-ACCESS  not-accessible
    STATUS      current
    DESCRIPTION 
        "The LLC Connectionless Protocol Machine managed object.  
         The generic LLC Connectionless PM MO from which 
         protocol-specific LLC PM MOs bay be derived."
    REFERENCE   
        "ITU-T Rec. X.282 | ISO/IEC 10742"
    ::= { lLCCLPM 1 }

lLCCLPMEntry OBJECT-TYPE
    SYNTAX      LLCCLPMEntry
    MAX-ACCESS  not-accessible
    STATUS      current
    DESCRIPTION 
        "The CL PM is contaned by a datalinkEntity, in this case 
         a lLCDLE.
         
         
         Each entry supports an activation and deactivation 
         action.
         
         Whenever an entry is created, the objectCreation 
         notification is issued.  Whenever an entry is deleted, 
         the objectDeletion notification is issued.  Whenever 
         the operational state changes a stateChange 
         notification is issued.  Objects may be created and 
         deleted by explicity management operation.  Deletion 
         and deactivation have a similar effect, as does 
         creation and activation."
    REFERENCE   
        "ITU-T Rec. X.282 | ISO/IEC 10742"
    INDEX       { lLCCLPMClProtocolMachineId }
    ::= { lLCCLPMTable 1 }

LLCCLPMEntry ::= SEQUENCE {
    -- derived from clProtocolMachine
    lLCCLPMClProtocolMachineId  SimpleNameType,
    lLCCLPMOperationalState     OperationalState,
    -- clProtocolMachineP2 package
    lLCCLPMTotalRemoteSAPs      Counter32,
    lLCCLPMRowStatus            RowStatus
}

-- derived from clProtocolMachine
lLCCLPMClProtocolMachineId OBJECT-TYPE
    SYNTAX      SimpleNameType
    MAX-ACCESS  not-accessible
    STATUS      current
    DESCRIPTION 
        "Provides a naming attribute for the logical link 
         control connectionless protocol machine."
    REFERENCE   
        "ITU-T Rec. X.723 | ISO/IEC 10165-5, clProtocolMachineId."
    ::= { lLCCLPMEntry 1 }

lLCCLPMOperationalState OBJECT-TYPE
    SYNTAX      OperationalState
    MAX-ACCESS  read-only
    STATUS      current
    DESCRIPTION 
        "Provides the operational state of the logical link 
         control connectionless protocol machine."
    REFERENCE   
        "ITU-T Rec. X.721 | ISO/IEC 10165-2, operationalState."
    ::= { lLCCLPMEntry 2 }

-- clProtocolMachineP2 package
lLCCLPMTotalRemoteSAPs OBJECT-TYPE
    SYNTAX      Counter32
    UNITS       "remote SAPs"
    MAX-ACCESS  read-only
    STATUS      current
    DESCRIPTION 
        "Counts the number of remote (N) SAPs that the 
         containing clProtocolMachine has communicated with.  
         incremented by 1 every time communication with a remote 
         (N) SAP is acheived."
    REFERENCE   
        "ITU-T Rec. X.723 | ISO/IEC 10165-5, totalRemoteSAPs."
    ::= { lLCCLPMEntry 3 }

lLCCLPMRowStatus OBJECT-TYPE
    SYNTAX      RowStatus
    MAX-ACCESS  read-create
    STATUS      current
    DESCRIPTION 
        "Provides a mechanism whereby management stations, 
         following the RowStatus textual convention of the 
         SNMPv2-TC module, may create or delete conceptual rows 
         from this table.
         
         The lLCCLPM-lLCDLE-Management name binding applies when 
         an lLCCLPM managed object (or an instance of a subclass 
         of the lLCCLPM MO class) can be created by management 
         as a subordinate object of a lLCDLE managed object (or 
         subclasses), and deleted by mangement."
    REFERENCE   
        "ITU-T Rec. X.282 | ISO/IEC 10742, 
         lLCCLPM-lLCDLE-Management, STD 58, SNMPv2-TC 
         RowStatus."
    ::= { lLCCLPMEntry 4 }


-- =====================================================================

lLCConnectionLess OBJECT IDENTIFIER
    ::= { llcTables 11 }

lLCConnectionLessTable OBJECT-TYPE
    SYNTAX      SEQUENCE OF LLCConnectionLessEntry
    MAX-ACCESS  not-accessible
    STATUS      current
    DESCRIPTION 
        "lLCConnectionless MOC. This clause contains those 
         attributes, actions, and event notifications associated 
         with an LLC connectionless environment.  This managed 
         object class is responsible for processing the 
         attributes, actions and notifications that are 
         associated with the LLC connectionless service.
         
         The managed object class is derived from the lLCCLPM 
         LLC connectionless protocol machine managed object 
         class, and is also contained by an instance of the 
         lLCCLPM with the lLCClessName as the relative name."
    REFERENCE   
        "IEEE 802.2 (ISO/IEC 8802-2), lLCConnectionless MOC."
    ::= { lLCConnectionLess 1 }

lLCConnectionLessEntry OBJECT-TYPE
    SYNTAX      LLCConnectionLessEntry
    MAX-ACCESS  not-accessible
    STATUS      current
    DESCRIPTION 
        "Each row in the LLC connection-less protocol machine 
         table is indexed by the LLC connection-less protocol 
         machine identifier in which it is contained and the 
         LLC connection-less protocol machine from which it is 
         derived.  Each row contains protocol parameters and 
         operational measurements associated with the LLC 
         connection-less protocol machine."
    REFERENCE   
        "IEEE 802.2 (ISO/IEC 8802-2), lLCConnectionless MO."
    INDEX       { lLCCLPMClProtocolMachineId, lLCCLPMClProtocolMachineId }
                -- lLCCLPMClProtocolMachineId - contained by lLCCLPM
                -- lLCCLPMClProtocolMachineId - derived from lLCCLPM
    ::= { lLCConnectionLessTable 1 }

LLCConnectionLessEntry ::= SEQUENCE {
    -- lLCConnectionless-P mandatory package
    lLCConnectionlessName                               SimpleNameType,
    lLCConnectionlessMaximumLLCInformationFieldSize     Integer32,
    lLCConnectionlessTESTReceivedABBResponse            Counter32,
    lLCConnectionlessTESTReceivedCommand                Counter32,
    lLCConnectionlessTESTReceivedResponse               Counter32,
    lLCConnectionlessTESTSentABBResponse                Counter32,
    lLCConnectionlessTESTSentCommand                    Counter32,
    lLCConnectionlessTESTSentResponse                   Counter32,
    lLCConnectionlessUIReceived                         Counter32,
    lLCConnectionlessUISent                             Counter32,
    lLCConnectionlessXIDReceivedCommand                 Counter32,
    lLCConnectionlessXIDReceivedResponse                Counter32,
    lLCConnectionlessXIDSentCommand                     Counter32,
    lLCConnectionlessXIDSentResponse                    Counter32
    -- need action tESTSendCommand
    -- need action xIDSendCommand
}

-- lLCConnectionless-P mandatory package
lLCConnectionlessName OBJECT-TYPE
    SYNTAX      SimpleNameType
    MAX-ACCESS  read-write
    STATUS      current
    DESCRIPTION 
        "Provides the name of the higher level entity associated 
         with this object class.
         
         Because the lLCConnectionlessName is used as a relative name 
         within the containing lLCCLPM table entry, all 
         lLCConnectionless entries with the same indexed lLCCLPM 
         table entry must have unique names."
    REFERENCE   
        "IEEE 802.2 (ISO/IEC 8802-2) lLCClessName."
    ::= { lLCConnectionLessEntry 1 }

lLCConnectionlessMaximumLLCInformationFieldSize OBJECT-TYPE
    SYNTAX      Integer32
    MAX-ACCESS  read-write
    STATUS      current
    DESCRIPTION 
        "The maximum length SDU that the LSAP will accomodate.  
         For Ethernet 10baseT and 100baseT LANs this is 
         typically the 1500 byte MTU minus the SNAP header, 
         minus the address fields and command field, or 1492 
         bytes."
    REFERENCE   
        "IEEE 802.2 (ISO/IEC 8802-2) 
         maximumLLCInformationFieldSize."
    ::= { lLCConnectionLessEntry 2 }

lLCConnectionlessTESTReceivedABBResponse OBJECT-TYPE
    SYNTAX      Counter32
    UNITS       "TEST ABB responses received"
    MAX-ACCESS  read-only
    STATUS      current
    DESCRIPTION 
        "Provides a count of TEST responses received by this 
         LSAP without the LSDU due to limited resources at the 
         remote station."
    REFERENCE   
        "IEEE 802.2 (ISO/IEC 8802-2) tESTReceivedABBResponse."
    ::= { lLCConnectionLessEntry 3 }

lLCConnectionlessTESTReceivedCommand OBJECT-TYPE
    SYNTAX      Counter32
    UNITS       "TEST commands received"
    MAX-ACCESS  read-only
    STATUS      current
    DESCRIPTION 
        "Provides a count of TEST commands received from the MAC 
         sublayer by this LSAP.  This includes commands recieved 
         with any group address recognized by this LSAP."
    REFERENCE   
        "IEEE 802.2 (ISO/IEC 8802-2) tESTReceivedCommand."
    ::= { lLCConnectionLessEntry 4 }

lLCConnectionlessTESTReceivedResponse OBJECT-TYPE
    SYNTAX      Counter32
    UNITS       "TEST responses received"
    MAX-ACCESS  read-only
    STATUS      current
    DESCRIPTION 
        "Provides a count of TEST responses received from the 
         MAC sublayer by this LSAP."
    REFERENCE   
        "IEEE 802.2 (ISO/IEC 8802-2) tESTReceivedResponse."
    ::= { lLCConnectionLessEntry 5 }

lLCConnectionlessTESTSentABBResponse OBJECT-TYPE
    SYNTAX      Counter32
    UNITS       "TEST ABB response sent"
    MAX-ACCESS  read-only
    STATUS      current
    DESCRIPTION 
        "Provides a count of TEST responses that were delivered 
         to the MAC without the LSDU data due to limited 
         resources."
    REFERENCE   
        "IEEE 802.2 (ISO/IEC 8802-2) tESTSentABBResponse."
    ::= { lLCConnectionLessEntry 6 }

lLCConnectionlessTESTSentCommand OBJECT-TYPE
    SYNTAX      Counter32
    UNITS       "TEST commands sent"
    MAX-ACCESS  read-only
    STATUS      current
    DESCRIPTION 
        "Provides a count of TEST command set to the MAC 
         sublayer by this LSAP."
    REFERENCE   
        "IEEE 802.2 (ISO/IEC 8802-2) tESTSentCommand."
    ::= { lLCConnectionLessEntry 7 }

lLCConnectionlessTESTSentResponse OBJECT-TYPE
    SYNTAX      Counter32
    UNITS       "TEST responses sent"
    MAX-ACCESS  read-only
    STATUS      current
    DESCRIPTION 
        "Provides a count of TEST responses sent to the MAC 
         sublayer by this LSAP."
    REFERENCE   
        "IEEE 802.2 (ISO/IEC 8802-2) tESTSentResponse."
    ::= { lLCConnectionLessEntry 8 }

lLCConnectionlessUIReceived OBJECT-TYPE
    SYNTAX      Counter32
    UNITS       "UI frames received"
    MAX-ACCESS  read-only
    STATUS      current
    DESCRIPTION 
        "Provides a count of user data PDUs that were received 
         by the LSAP from the MAC sublayer and passed to the 
         user layer.  This includes commands received with group 
         addresses of which the LSAP is a member."
    REFERENCE   
        "IEEE 802.2 (ISO/IEC 8802-2) uIReceived."
    ::= { lLCConnectionLessEntry 9 }

lLCConnectionlessUISent OBJECT-TYPE
    SYNTAX      Counter32
    UNITS       "UI frames sent"
    MAX-ACCESS  read-only
    STATUS      current
    DESCRIPTION 
        "Provides a count of user data PDUs that were accepted 
         by the LSAP from the user layer and delivered to the 
         MAC sublayer."
    REFERENCE   
        "IEEE 802.2 (ISO/IEC 8802-2) uISent."
    ::= { lLCConnectionLessEntry 10 }

lLCConnectionlessXIDReceivedCommand OBJECT-TYPE
    SYNTAX      Counter32
    UNITS       "XID commands received"
    MAX-ACCESS  read-only
    STATUS      current
    DESCRIPTION 
        "Proivdes a count of XID commands received from the MAC 
         sublayer by this LSAP.  This includes commands received 
         with any group address recognized by this LSAP."
    REFERENCE   
        "IEEE 802.2 (ISO/IEC 8802-2) xIDReceivedCommand."
    ::= { lLCConnectionLessEntry 11 }

lLCConnectionlessXIDReceivedResponse OBJECT-TYPE
    SYNTAX      Counter32
    UNITS       "XID responses received"
    MAX-ACCESS  read-only
    STATUS      current
    DESCRIPTION 
        "Provides a count of XID responses received from the MAC 
         sublayer by this LSAP."
    REFERENCE   
        "IEEE 802.2 (ISO/IEC 8802-2) xIDReceivedResponse."
    ::= { lLCConnectionLessEntry 12 }

lLCConnectionlessXIDSentCommand OBJECT-TYPE
    SYNTAX      Counter32
    UNITS       "XID commands sent"
    MAX-ACCESS  read-only
    STATUS      current
    DESCRIPTION 
        "Provides a count of XID commands sent to the MAC 
         sublayer by this LSAP."
    REFERENCE   
        "IEEE 802.2 (ISO/IEC 8802-2) xIDSentCommand."
    ::= { lLCConnectionLessEntry 13 }

lLCConnectionlessXIDSentResponse OBJECT-TYPE
    SYNTAX      Counter32
    UNITS       "XID responses sent"
    MAX-ACCESS  read-only
    STATUS      current
    DESCRIPTION 
        "Provides a count of the XID responses sent to the MAC 
         sublayer by this LSAP."
    REFERENCE   
        "IEEE 802.2 (ISO/IEC 8802-2) xIDSentResponse."
    ::= { lLCConnectionLessEntry 14 }

-- need action tESTSendCommand
--
-- This action causes the LLCSAP Component to send a TEST command PDU to 
-- a specified remote LSAP.

-- need action xIDSendCommand
--
-- This action causes the LLCSAP component to send an XID command PDU to 
-- a specified remote LSAP.  The information in the XID PDU (supported 
-- LLC types and send window size value) is determined by the current 
-- configuration of the LSAP and LSAP pair.


-- =====================================================================

lLCCOPM OBJECT IDENTIFIER
    ::= { llcTables 12 }

lLCCOPMTable OBJECT-TYPE
    SYNTAX      SEQUENCE OF LLCCOPMEntry
    MAX-ACCESS  not-accessible
    STATUS      current
    DESCRIPTION 
        "The LLC Connection-mode Protocol Machine managed 
         object.  The generic LLC Connection-mode PM MO from 
         which protocol specific LLC PM MOs may be derived."
    ::= { lLCCOPM 1 }

lLCCOPMEntry OBJECT-TYPE
    SYNTAX      LLCCOPMEntry
    MAX-ACCESS  not-accessible
    STATUS      current
    DESCRIPTION 
        "Each row in the LLC connection-oriented protocol 
         machine table is defined by the connection-oriented 
         protocol machine identifier.  Each row contains the 
         operational status of the connection-oriented protocol 
         machine.."
    INDEX       { lLCCOPMCoProtocolMachineId }
    ::= { lLCCOPMTable 1 }

LLCCOPMEntry ::= SEQUENCE {
    -- derived from coProtooclMachine
    lLCCOPMCoProtocolMachineId  SimpleNameType,
    lLCCOPMOperationalState     OperationalState,
    --
    lLCCOPMRowStatus            RowStatus
}

-- derived from coProtooclMachine
lLCCOPMCoProtocolMachineId OBJECT-TYPE
    SYNTAX      SimpleNameType
    MAX-ACCESS  not-accessible
    STATUS      current
    DESCRIPTION 
        "Provides a naming attribute for the logical link 
         control connection-oriented protocol machine."
    REFERENCE   
        "ITU-T Rec. X.723 | ISO/IEC 10165-5, coProtocolMachineId."
    ::= { lLCCOPMEntry 1 }

lLCCOPMOperationalState OBJECT-TYPE
    SYNTAX      OperationalState
    MAX-ACCESS  read-only
    STATUS      current
    DESCRIPTION 
        "Provides the operational state of the logical link 
         contorl connection-oriented protocol machine."
    REFERENCE   
        "ITU-T Rec. X.721 | ISO/IEC 10165-2, operationalState."
    ::= { lLCCOPMEntry 2 }

--
lLCCOPMRowStatus OBJECT-TYPE
    SYNTAX      RowStatus
    MAX-ACCESS  read-create
    STATUS      current
    DESCRIPTION 
        "Provides a mechanism whereby management stations, 
         following the RowStatus textual convention of the 
         SNMPv2-TC module, may create or delete conceptual rows 
         from this table.
         
         The lLCCOPM-lLCDLE-Management name binding applies when 
         an lLCCOPM managed object (or an instance of a subclass 
         of the lLCCOPM MO class) can be created by management 
         as a subordinate object of a lLCDLE managed object (or 
         subclasses), and deleted by mangement."
    REFERENCE   
        "ITU-T Rec. X.282 | ISO/IEC 10742, 
         lLCCOPM-lLCDLE-Management, STD 58, SNMPv2-TC 
         RowStatus."
    ::= { lLCCOPMEntry 3 }


-- =====================================================================

lLCConnection2 OBJECT IDENTIFIER
    ::= { llcTables 13 }

lLCConnection2Table OBJECT-TYPE
    SYNTAX      SEQUENCE OF LLCConnection2Entry
    MAX-ACCESS  not-accessible
    STATUS      current
    DESCRIPTION 
        "The Connection component is responsible for processing 
         the events that affect a specific data link connection 
         for Type 2 procedures only.  One connection component 
         shall exist for each data link connection supported in 
         the LLC entity.
         
         LLCConnection2 managed object.  This clause contains 
         those attributes, actions, and event notifications 
         associated with an LLC Type 2 (connection) environment. 
         This managed object is responsible for processing the 
         events that affect the current data link connection 
         during its lifetime (i.e., timeframe of link 
         established until link disconnect).  One LLC Connection 
         managed object shall exist for each data link (LLC Type 
         2) connection supported in the LLC entity.
         
         The managed object is derived from the iLLCCOPM LLC 
         connection-oriented protocol machine managed object 
         lcass, and is also contained by an instance of the 
         lLCCOPM with the lLCConnection2Name as the relative 
         name.
         
         Provides a table of statistics for each LLC2 connection 
         to a remote LLC2 station.
         
         Provides a table of configuration for each LLC2 
         connection to a remote LLC2 station.  This table 
         provides the configuration (non-statistical) atribtues 
         for the lLCConnection2 managed object from ISO/IEC 
         8802-2 (IEEE 802.2).  It includes attributes from both 
         mandatory and conditional packages.  Attributes that 
         belong to conditional packages in the GDMOs have a 
         default value that reperesents the feature being 
         disabled.
         
         The table is indexed by the ifIndex into the ifTable 
         that represents the local MAC coupled with the Remote 
         MAC Address and LSAP that represents the specific 
         connection."
    REFERENCE   
        "IEEE 802.2 (ISO/IEC 8802-2), lLCConnection2 MOC."
    ::= { lLCConnection2 1 }

lLCConnection2Entry OBJECT-TYPE
    SYNTAX      LLCConnection2Entry
    MAX-ACCESS  not-accessible
    STATUS      current
    DESCRIPTION 
        "Each entry in this table represents an instance of the 
         lLCConnection2 managed object class.  Each instance oft 
         the lLCConnection2 managed object lcass is responsible  
         for processing the events that affect the current data 
         link connection during its lifetime (i.e., timeframe of 
         link established until link disconnect).  One 
         lLCConnection2 manged object instance shall exist for 
         each data link (LLC Type 2) conenction supported in the 
         LLC entity.
         
         Provides an entry in the X.25 LLC2 Connection table for 
         one LLC2 connection to a remote station.  Each 
         connection is indexed by its ifIndex into the interface 
         table plus a connection identifier.  Each connection is 
         associated with a unique remote DLSAP (MAC address and 
         LSAP), used as a secondary index into this table.
         
         Provides an entry in the X.25 LLC2 Connection table for 
         one LLC connection to a remote station.  Each 
         connection is indexed by its ifIndex into the interface 
         table plus a connection identifier.  Each connection is 
         associated with a unique remote DLSAP (MAC addres and 
         LSAP).
         
         Entries support a correlatorExchange action.  The 
         action is used when two ends or a link cnnection report 
         errors relating tot he same problem.  A correlator is 
         reported in the events so that the managing process can 
         assume that the errors are related to the same failure.  
         This section describes the function that uses the CMIP 
         protoocl verb Confirmed Action to facilitate a 
         correlator exchange between the two ends of the link 
         connection.  At the end of the link connection set-up 
         (when the LSAP Pair has initially entered into 
         LINK-OPENED state), a Manager will send a confirmed 
         Correlator Exchange CAction to the Manager of the 
         adjacent link station.  Upon receipt of this Action, 
         the Manager will compute a correlator.  Once this 
         correlator is generated, it is returned to the 
         initiating Manager.  This correlator will be sent in 
         events relating to the link connection.  If the 
         response is not received, no correlator is send in the 
         events.  If the MAC address of the two ends of the link 
         connection are the same, the link station that 
         initiated the connection (sent SABME) should intiiate 
         the Correlator Exchange Action.
         
         Entries support the communicationsAlarm notification 
         and the lLCConnection2Event notification."
    REFERENCE   
        "IEEE 802.2 (ISO/IEC 8802-2), lLCConnection2 MO."
    INDEX       { lLCCOPMCoProtocolMachineId, lLCCOPMCoProtocolMachineId }
                -- lLCCOPMCoProtocolMachineId - contained by lLCCOPM
                -- lLCCOPMCoProtocolMachineId - derived from lLCCOPM
    ::= { lLCConnection2Table 1 }

LLCConnection2Entry ::= SEQUENCE {
    -- lLCConnection2-P mandatory package
    lLCConnection2Name                      SimpleNameType,
    lLCConnection2MaximumRetransmissions    Integer32,
    lLCConnection2ReceivedWindowSize        Integer32,
    lLCConnection2SendWindowSize            Integer32,
    lLCConnection2AcknowledgeTimeoutValue   TimeInterval,
    lLCConnection2BusyStateTimeoutValue     TimeInterval,
    lLCConnection2PBitTimeoutValue          TimeInterval,
    lLCConnection2RejectTimeoutValue        TimeInterval,
    -- need action correlatorExchange
    -- need notification communicationsAlarm
    -- need notification lLCConnection2Event
    -- connectionBusy-P conditional package
    lLCConnection2LocalBusy                 Counter32,
    lLCConnection2RemoteBusy                Counter32,
    -- connectionReset-P conditioanl package
    lLCConnection2RemoteReset               Counter32,
    lLCConnection2LocalReset                Counter32,
    lLCConnection2ProviderReset             Counter32,
    -- connectionRoute-P conditional package
    lLCConnection2Route                     OCTET STRING,
    -- type2FlowControl-P conditional package
    lLCConnection2KStep                     Integer32,
    lLCConnection2MaxSendWindowSize         Integer32,
    -- type2I-P conditional package
    lLCConnection2ReceivedI                 Counter32,
    lLCConnection2SentI                     Counter32,
    -- type2Iack-P conditional package
    lLCConnection2SentAcks                  Counter32,
    lLCConnection2ReceivedAcks              Counter32,
    -- type2FRMR-P conditional package
    lLCConnection2ReceivedFRMR              Counter32,
    lLCConnection2SentFRMR                  Counter32,
    -- type2RR-P conditional package
    lLCConnection2ReceivedRR                Counter32,
    lLCConnection2SentRR                    Counter32,
    -- type2RNR-P conditional package
    lLCConnection2ReceivedRNR               Counter32,
    lLCConnection2SentRNR                   Counter32,
    -- type2REJ-P conditional package
    lLCConnection2ReceivedREJ               Counter32,
    lLCConnection2SentREJ                   Counter32,
    -- type2SABME-P conditional package
    lLCConnection2ReceivedSABME             Counter32,
    lLCConnection2SentSABME                 Counter32,
    -- type2UA-P conditional package
    lLCConnection2ReceivedUA                Counter32,
    lLCConnection2SentUA                    Counter32,
    -- type2DISC-P conditional package
    lLCConnection2ReceivedDISC              Counter32,
    lLCConnection2SentDISC                  Counter32,
    -- type2DM-P conditional package
    lLCConnection2ReceivedDM                Counter32,
    lLCConnection2SentDM                    Counter32,
    -- type2PDUs-P conditional package
    lLCConnection2PDUsDiscarded1            Counter32,
    lLCConnection2PDUsDiscarded2            Counter32,
    lLCConnection2PDURetransmissions        Counter32,
    -- need lLCCoEvent notification
    -- type2OptTolIPDUs-P conditional package
    lLCConnection2OptionalTolerationIPDUs   TruthValue,
    lLCConnection2DuplicateIPDUsReceived    Counter32,
    -- need lLCCoEvent notification
    -- type2Violation-P conditional package
    lLCConnection2Violation                 Counter32,
    -- need lLCConnection2Event notification
    lLCConnection2ProtocolState             INTEGER,
    lLCConnection2AdministrativeState       AdministrativeState,
    lLCConnection2OperationalState          OperationalState,
    lLCConnection2UsageState                UsageState,
    lLCConnection2ProceduralStatus          ProceduralStatus,
    lLCConnection2AlarmStatus               AlarmStatus
}

-- lLCConnection2-P mandatory package
--
-- The LLC Connection object is responsible for processing the 
-- attributes, actions and notifications that affect a specific data 
-- link connection (for LLC Type 2 connections).  One data connection 
-- shall exist for each data link connection supported.

lLCConnection2Name OBJECT-TYPE
    SYNTAX      SimpleNameType
    MAX-ACCESS  read-write
    STATUS      current
    DESCRIPTION 
        "The localLSAP and remoteLSAPId and the local and remote 
         MACAddress.
         
         Because the lLCConnection2Name is used as a relative name 
         within the containing lLCCOPM table entry, all 
         lLCConnection2 entries with the same indexed lLCCOPM 
         table entry must have unique names.
         
         Provides an index in to the ifTable that identifies the 
         primary MAC interface through which multilple LLC2 
         connections are established.
         
         Provides a connection identifier that identifies the 
         explicit connection made via the MAC device identified 
         by the lLCConnection2StatsIndex above.  These two 
         fields form the index and identify the specific LLC2 
         connection within this host."
    REFERENCE   
        "IEEE 802.2 (ISO/IEC 8802-2) lLCConnection2Name."
    ::= { lLCConnection2Entry 1 }

lLCConnection2MaximumRetransmissions OBJECT-TYPE
    SYNTAX      Integer32
    MAX-ACCESS  read-write
    STATUS      current
    DESCRIPTION 
        "The number of times that the LLC Type 2 should attempt 
         to realize a successful PDU transfer."
    REFERENCE   
        "IEEE 802.2 (ISO/IEC 8802-2) maximumRetransmissions."
    ::= { lLCConnection2Entry 2 }

lLCConnection2ReceivedWindowSize OBJECT-TYPE
    SYNTAX      Integer32
    MAX-ACCESS  read-write
    STATUS      current
    DESCRIPTION 
        "The value of the receive window."
    REFERENCE   
        "IEEE 802.2 (ISO/IEC 8802-2) receivedWindowSize."
    ::= { lLCConnection2Entry 3 }

lLCConnection2SendWindowSize OBJECT-TYPE
    SYNTAX      Integer32
    MAX-ACCESS  read-write
    STATUS      current
    DESCRIPTION 
        "The value of the send window."
    REFERENCE   
        "IEEE 802.2 (ISO/IEC 8802-2) sendWindowSize."
    ::= { lLCConnection2Entry 4 }

lLCConnection2AcknowledgeTimeoutValue OBJECT-TYPE
    SYNTAX      TimeInterval
    MAX-ACCESS  read-write
    STATUS      current
    DESCRIPTION 
        "This attribute defines the time interval during which 
         the LLC shall expect to receive an acknowledgment to 
         one or more outstanding I PDUs or an expected response 
         PDU to a sent unnumbered command PDU.  This value is 
         measured in centiseconds and displayed in seconds."
    REFERENCE   
        "IEEE 802.2 (ISO/IEC 8802-2), 
         type2AcknowledgeTimeoutValue, 7.4.1, 7.4.3, 7.4.5, 7.5, 
         7.5.5, 7.5.9, 7.6, 7.8.1.1, 7.9.2, 7.9.2.2, and 
         7.9.2.3."
    ::= { lLCConnection2Entry 5 }

lLCConnection2BusyStateTimeoutValue OBJECT-TYPE
    SYNTAX      TimeInterval
    MAX-ACCESS  read-write
    STATUS      current
    DESCRIPTION 
        "This attribute defines the time interval during which 
         the LLC shall wait for an indication of the clearance 
         of a busy condition at the other LLC.  This time value 
         is measured in centiseconds and displayed in seconds."
    REFERENCE   
        "IEEE 802.2 (ISO/IEC 8802-2), 
         type2BusyStateTimeoutValue, 7.5.7, 7.5.9, 7.8.1.4, 
         7.9.2, 7.9.2.2, and 7.9.2.3."
    ::= { lLCConnection2Entry 6 }

lLCConnection2PBitTimeoutValue OBJECT-TYPE
    SYNTAX      TimeInterval
    MAX-ACCESS  read-write
    STATUS      current
    DESCRIPTION 
        "The P-bit timer defines the time interval during which 
         the LLC shall expect to receive a PDU with the F bit 
         set to '1' in response to a sent Type 2 command with 
         the P bit set to '1'. This value is measured in 
         centiseconds and dsiplayed in seconds."
    REFERENCE   
        "IEEE 802.2 (ISO/IEC 8802-2), type2BitTimeoutValue, 
         7.5.9, 7.8.1.2, 7.9.2, 7.9.2.2, and 7.9.2.3."
    ::= { lLCConnection2Entry 7 }

lLCConnection2RejectTimeoutValue OBJECT-TYPE
    SYNTAX      TimeInterval
    MAX-ACCESS  read-write
    STATUS      current
    DESCRIPTION 
        "The Reject timer defines the time interval during which 
         the LLC shall expect to receive a reply to a sent REJ 
         PDU. This value is measured in centiseconds and 
         displayed in seconds."
    REFERENCE   
        "IEEE 802.2 (ISO/IEC 8802-2), type2RejectTimeoutValue, 
         7.5.4, 7.8.1.3, 7.9.2, 7.9.2.2, and 7.9.2.3."
    ::= { lLCConnection2Entry 8 }

-- need action correlatorExchange
-- need notification communicationsAlarm
-- need notification lLCConnection2Event

-- connectionBusy-P conditional package
--
-- Contains attributes that count instances of local or remote busy 
-- conditions.

lLCConnection2LocalBusy OBJECT-TYPE
    SYNTAX      Counter32
    MAX-ACCESS  read-only
    STATUS      current
    DESCRIPTION 
        "Provides a count of the occurences of entry into the 
         busy condition."
    REFERENCE   
        "IEEE 802.2 (ISO/IEC 8802-2) localBusy."
    ::= { lLCConnection2Entry 9 }

lLCConnection2RemoteBusy OBJECT-TYPE
    SYNTAX      Counter32
    UNITS       "PDUs"
    MAX-ACCESS  read-only
    STATUS      current
    DESCRIPTION 
        "Provides a count of the RNR PDUs received when the 
         remote busy condition is not already set."
    REFERENCE   
        "IEEE 802.2 (ISO/IEC 8802-2) remoteBusy."
    ::= { lLCConnection2Entry 10 }

-- connectionReset-P conditioanl package
--
-- Contains attributes that count instances of particular types of 
-- reset.

lLCConnection2RemoteReset OBJECT-TYPE
    SYNTAX      Counter32
    UNITS       "PDUs"
    MAX-ACCESS  read-only
    STATUS      current
    DESCRIPTION 
        "Provides a count of instances of partner-initiated 
         reset (SABME PDU received in a connected state)."
    REFERENCE   
        "IEEE 802.2 (ISO/IEC 8802-2) remoteReset."
    ::= { lLCConnection2Entry 11 }

lLCConnection2LocalReset OBJECT-TYPE
    SYNTAX      Counter32
    UNITS       "requests"
    MAX-ACCESS  read-only
    STATUS      current
    DESCRIPTION 
        "Provides a count of the instances of user request for 
         reset while in the connected state."
    REFERENCE   
        "IEEE 802.2 (ISO/IEC 8802-2) localReset."
    ::= { lLCConnection2Entry 12 }

lLCConnection2ProviderReset OBJECT-TYPE
    SYNTAX      Counter32
    UNITS       "resets"
    MAX-ACCESS  read-only
    STATUS      current
    DESCRIPTION 
        "Provides a count of the instances of provider-initiated 
         reset due to FRMR PDU sent, FRMR received, or retry 
         exhaustion."
    REFERENCE   
        "IEEE 802.2 (ISO/IEC 8802-2) providerReset."
    ::= { lLCConnection2Entry 13 }

-- connectionRoute-P conditional package
--
-- This is a conditional part of the LLC Connection Object. It is 
-- present if source routing is used and the connection is cognizant of 
-- its route.  This conditional package contains one attribute, the 
-- source route that the LSAP Pair uses to communicate. Source Routing 
-- is described in ISO/IEC 10038 : 1993.

lLCConnection2Route OBJECT-TYPE
    SYNTAX      OCTET STRING (SIZE(4))
    MAX-ACCESS  read-write
    STATUS      current
    DESCRIPTION 
        "This is a conditional part of the LSAP Pair Object. It 
         is present if source routing is used and the LSAP Pair 
         is cognizant of its route. This attribute is used by 
         the LSAP Pair to communicate. Source Routing is 
         described in ISO/IEC 10038 : 1993 (IEEE 802.1D 1993).
         
         The syntax of the octet string is as follows:
         
         RoutingControl ::= OCTET STRING(SIZE(2))
         RoutingDescriptors ::= OCTET STRING(SIZE(2))
         Route ::= SEQUENCE {
         	 routingControl [0] IMPLICIT RoutingControl,
         	 routingDescriptors [1] IMPLICIT RoutingDescriptors }"
    REFERENCE   
        "IEEE 802.2 (ISO/IEC 8802-2), route, IEEE 802.2D 1993 
         (ISO/IEC 10038 : 1993)."
    ::= { lLCConnection2Entry 14 }

-- type2FlowControl-P conditional package
--
-- This conditional package contains two attributes that are used to 
-- provide flow control.

lLCConnection2KStep OBJECT-TYPE
    SYNTAX      Integer32
    MAX-ACCESS  read-write
    STATUS      current
    DESCRIPTION 
        "The value of the flow control parameter."
    REFERENCE   
        "IEEE 802.2 (ISO/IEC 8802-2) kStep."
    ::= { lLCConnection2Entry 15 }

lLCConnection2MaxSendWindowSize OBJECT-TYPE
    SYNTAX      Integer32
    MAX-ACCESS  read-write
    STATUS      current
    DESCRIPTION 
        "The maximum size of the send window."
    REFERENCE   
        "IEEE 802.2 (ISO/IEC 8802-2) sendWindowSize."
    ::= { lLCConnection2Entry 16 }

-- type2I-P conditional package
--
-- This conditional package counts the number of I PDUs received and 
-- sent (see 7.5.1, 7.5.6, 7.5.8, 7.5.9, and 7.8.4).

lLCConnection2ReceivedI OBJECT-TYPE
    SYNTAX      Counter32
    MAX-ACCESS  read-only
    STATUS      current
    DESCRIPTION 
        "Provides a count of the number of I PDUs received from 
         the MAC and passed to the LLC user on this connection."
    REFERENCE   
        "IEEE 802.2 (ISO/IEC 8802-2) type2ReceivedI."
    ::= { lLCConnection2Entry 17 }

lLCConnection2SentI OBJECT-TYPE
    SYNTAX      Counter32
    MAX-ACCESS  read-only
    STATUS      current
    DESCRIPTION 
        "Provides a count of the number of I PDUs delivered to 
         the MAC on this connection."
    REFERENCE   
        "IEEE 802.2 (ISO/IEC 8802-2) type2SentI."
    ::= { lLCConnection2Entry 18 }

-- type2Iack-P conditional package
--
-- Contains attributes that count acknowledgments sent and received.

lLCConnection2SentAcks OBJECT-TYPE
    SYNTAX      Counter32
    MAX-ACCESS  read-only
    STATUS      current
    DESCRIPTION 
        "Provides a count of the number of acknowledgments sent 
         for received I PDUs on this connection."
    REFERENCE   
        "IEEE 802.2 (ISO/IEC 8802-2) sentAcks."
    ::= { lLCConnection2Entry 19 }

lLCConnection2ReceivedAcks OBJECT-TYPE
    SYNTAX      Counter32
    MAX-ACCESS  read-only
    STATUS      current
    DESCRIPTION 
        "Provides a count of the number of I PDUs acknowledged 
         by connection partner on this connection."
    REFERENCE   
        "IEEE 802.2 (ISO/IEC 8802-2) receivedAcks."
    ::= { lLCConnection2Entry 20 }

-- type2FRMR-P conditional package
--
-- Specifies a count of FRMR PDUs delivered to the MAC and a count of 
-- FRMR PDUs received from the MAC and not discarded.

lLCConnection2ReceivedFRMR OBJECT-TYPE
    SYNTAX      Counter32
    MAX-ACCESS  read-only
    STATUS      current
    DESCRIPTION 
        "Provides a count of the number of FRMR PDUs received 
         from the MAC and not discarded on this connection."
    REFERENCE   
        "IEEE 802.2 (ISO/IEC 8802-2) type2ReceivedFRMR."
    ::= { lLCConnection2Entry 21 }

lLCConnection2SentFRMR OBJECT-TYPE
    SYNTAX      Counter32
    MAX-ACCESS  read-only
    STATUS      current
    DESCRIPTION 
        "Provides a count of the number of FRMR PDUs delivered 
         to the MAC on this connection."
    REFERENCE   
        "IEEE 802.2 (ISO/IEC 8802-2) type2SentFRMR."
    ::= { lLCConnection2Entry 22 }

-- type2RR-P conditional package
--
-- Specifies a count of RR PDUs either delivered or received from the 
-- MAC.

lLCConnection2ReceivedRR OBJECT-TYPE
    SYNTAX      Counter32
    MAX-ACCESS  read-only
    STATUS      current
    DESCRIPTION 
        "Provides a count of the number of RR PDUs received from 
         the MAC and not discarded on this connection."
    REFERENCE   
        "IEEE 802.2 (ISO/IEC 8802-2) type2ReceivedRR."
    ::= { lLCConnection2Entry 23 }

lLCConnection2SentRR OBJECT-TYPE
    SYNTAX      Counter32
    MAX-ACCESS  read-only
    STATUS      current
    DESCRIPTION 
        "Provides a count of the number of RR PDUs delivered to  
         the MAC on this connection."
    REFERENCE   
        "IEEE 802.2 (ISO/IEC 8802-2) type2SentRR."
    ::= { lLCConnection2Entry 24 }

-- type2RNR-P conditional package
--
-- This conditional package contains attributes that specify the count 
-- of RNR PDUs either delivered or received from the MAC.

lLCConnection2ReceivedRNR OBJECT-TYPE
    SYNTAX      Counter32
    MAX-ACCESS  read-only
    STATUS      current
    DESCRIPTION 
        "Provides a count of the number of RNR PDUs received 
         from the MAC and not discarded on this connection."
    REFERENCE   
        "IEEE 802.2 (ISO/IEC 8802-2) type2ReceivedRNR."
    ::= { lLCConnection2Entry 25 }

lLCConnection2SentRNR OBJECT-TYPE
    SYNTAX      Counter32
    MAX-ACCESS  read-only
    STATUS      current
    DESCRIPTION 
        "Provides a count of the number of RNR PDUs delivered to  
         the MAC on this connection."
    REFERENCE   
        "IEEE 802.2 (ISO/IEC 8802-2) type2SentRNR."
    ::= { lLCConnection2Entry 26 }

-- type2REJ-P conditional package
--
-- This conditional package contains two attributes to count sent and 
-- received REJ PDUs (see Clause 7.5.9).

lLCConnection2ReceivedREJ OBJECT-TYPE
    SYNTAX      Counter32
    MAX-ACCESS  read-only
    STATUS      current
    DESCRIPTION 
        "Provides a count of the number of REJ PDUs received 
         from the MAC and not discarded on this connection."
    REFERENCE   
        "IEEE 802.2 (ISO/IEC 8802-2) type2ReceivedREJ."
    ::= { lLCConnection2Entry 27 }

lLCConnection2SentREJ OBJECT-TYPE
    SYNTAX      Counter32
    MAX-ACCESS  read-only
    STATUS      current
    DESCRIPTION 
        "Provides a count of the number of REJ PDUs delivered to  
         the MAC on this connection."
    REFERENCE   
        "IEEE 802.2 (ISO/IEC 8802-2) type2SentREJ."
    ::= { lLCConnection2Entry 28 }

-- type2SABME-P conditional package
--
-- This conditional package contains attributes that specify the count 
-- of SABME PDUs either delivered or received.

lLCConnection2ReceivedSABME OBJECT-TYPE
    SYNTAX      Counter32
    MAX-ACCESS  read-only
    STATUS      current
    DESCRIPTION 
        "Provides a count of the number of SABME PDUs received 
         from the MAC and not discarded on this connection."
    REFERENCE   
        "IEEE 802.2 (ISO/IEC 8802-2) type2ReceivedSABME."
    ::= { lLCConnection2Entry 29 }

lLCConnection2SentSABME OBJECT-TYPE
    SYNTAX      Counter32
    MAX-ACCESS  read-only
    STATUS      current
    DESCRIPTION 
        "Provides a count of the number of SABME PDUs delivered 
         to the MAC  on this connection."
    REFERENCE   
        "IEEE 802.2 (ISO/IEC 8802-2) type2SentSABME."
    ::= { lLCConnection2Entry 30 }

-- type2UA-P conditional package
--
-- Specifies a count of UA PDUs either delivered or received from the 
-- MAC.

lLCConnection2ReceivedUA OBJECT-TYPE
    SYNTAX      Counter32
    MAX-ACCESS  read-only
    STATUS      current
    DESCRIPTION 
        "Provides a count of the number of UA PDUs received from 
         the MAC and not discarded on this connection."
    REFERENCE   
        "IEEE 802.2 (ISO/IEC 8802-2) type2ReceivedUA."
    ::= { lLCConnection2Entry 31 }

lLCConnection2SentUA OBJECT-TYPE
    SYNTAX      Counter32
    MAX-ACCESS  read-only
    STATUS      current
    DESCRIPTION 
        "Provides a count of the number of UA PDUs delivered to  
         the MAC on this connection."
    REFERENCE   
        "IEEE 802.2 (ISO/IEC 8802-2) type2SentUA."
    ::= { lLCConnection2Entry 32 }

-- type2DISC-P conditional package
--
-- Specifies a count of DISC PDUs either delivered or received from the 
-- MAC.

lLCConnection2ReceivedDISC OBJECT-TYPE
    SYNTAX      Counter32
    MAX-ACCESS  read-only
    STATUS      current
    DESCRIPTION 
        "Provides a count of the number of DISC PDUs received 
         from the MAC and not discarded on this connection."
    REFERENCE   
        "IEEE 802.2 (ISO/IEC 8802-2) type2ReceivedDISC."
    ::= { lLCConnection2Entry 33 }

lLCConnection2SentDISC OBJECT-TYPE
    SYNTAX      Counter32
    MAX-ACCESS  read-only
    STATUS      current
    DESCRIPTION 
        "Provides a count of the number of DISC PDUs delivered 
         to the MAC  on this connection."
    REFERENCE   
        "IEEE 802.2 (ISO/IEC 8802-2) type2SentDISC."
    ::= { lLCConnection2Entry 34 }

-- type2DM-P conditional package
--
-- Specifies a count of DM PDUs either delivered or received from the 
-- MAC.

lLCConnection2ReceivedDM OBJECT-TYPE
    SYNTAX      Counter32
    MAX-ACCESS  read-only
    STATUS      current
    DESCRIPTION 
        "Provides a count of the number of DM PDUs received from 
         the MAC and not discarded on this connection."
    REFERENCE   
        "IEEE 802.2 (ISO/IEC 8802-2) type2ReceivedDM."
    ::= { lLCConnection2Entry 35 }

lLCConnection2SentDM OBJECT-TYPE
    SYNTAX      Counter32
    MAX-ACCESS  read-only
    STATUS      current
    DESCRIPTION 
        "Provides a count of the number of DM PDUs delivered to  
         the MAC on this connection."
    REFERENCE   
        "IEEE 802.2 (ISO/IEC 8802-2) type2SentDM."
    ::= { lLCConnection2Entry 36 }

-- type2PDUs-P conditional package
--
-- This conditional package contains attributes that count a number of 
-- different types of discarded PDUs.

lLCConnection2PDUsDiscarded1 OBJECT-TYPE
    SYNTAX      Counter32
    MAX-ACCESS  read-only
    STATUS      current
    DESCRIPTION 
        "Provides a count of the number of PDUs discarded due to 
         insufficient resources for this connection."
    REFERENCE   
        "IEEE 802.2 (ISO/IEC 8802-2) pDUsDiscarded1."
    ::= { lLCConnection2Entry 37 }

lLCConnection2PDUsDiscarded2 OBJECT-TYPE
    SYNTAX      Counter32
    MAX-ACCESS  read-only
    STATUS      current
    DESCRIPTION 
        "Provides a count of the number of PDUs discarded due to 
         unexpected or invalid sequence numberfor this 
         connection."
    REFERENCE   
        "IEEE 802.2 (ISO/IEC 8802-2) pDUsDiscarded2."
    ::= { lLCConnection2Entry 38 }

lLCConnection2PDURetransmissions OBJECT-TYPE
    SYNTAX      Counter32
    MAX-ACCESS  read-only
    STATUS      current
    DESCRIPTION 
        "Provides a count of the number of times the Type 2 LLC 
         service retransmitted PDUs for this connection."
    REFERENCE   
        "IEEE 802.2 (ISO/IEC 8802-2) pDURetransmissions."
    ::= { lLCConnection2Entry 39 }

-- need lLCConnection2Event notification
-- type2OptTolIPDUs-P conditional package
--
-- This optional package contains two attributes: a Boolean to indicate 
-- support for the Optional Toleration of Duplicate I PDUs function and 
-- an event counter to count the number of Duplicate I PDUs received.

lLCConnection2OptionalTolerationIPDUs OBJECT-TYPE
    SYNTAX      TruthValue
    MAX-ACCESS  read-write
    STATUS      current
    DESCRIPTION 
        "Indicates if the Toleration of Duplicate I PDUs is on 
         or off."
    REFERENCE   
        "IEEE 802.2 (ISO/IEC 8802-2) optionalTolerationIPDUs."
    ::= { lLCConnection2Entry 40 }

lLCConnection2DuplicateIPDUsReceived OBJECT-TYPE
    SYNTAX      Counter32
    MAX-ACCESS  read-only
    STATUS      current
    DESCRIPTION 
        "Provides a count of the number of duplicated I PDUs 
         received on this connection.  Duplication I PDUs are 
         those that have a sequence number within the current 
         window and which have already been received."
    REFERENCE   
        "IEEE 802.2 (ISO/IEC 8802-2) duplicatePDUsReceived, 
         (also dupIPDUsReceived)."
    ::= { lLCConnection2Entry 41 }

-- need lLCConnection2Event notification
-- type2Violation-P conditional package
--
-- This conditional package provides an attribute and notification for 
-- type 2 violations.

lLCConnection2Violation OBJECT-TYPE
    SYNTAX      Counter32
    MAX-ACCESS  read-only
    STATUS      current
    DESCRIPTION 
        "Provides a count of the number of LLC Type 2 protocol 
         violations detected by this connection. Protocol 
         violations include the following:
         1. those that result in the LLC entity sending an FRMR 
            frame;
         2. those that result in a data link resetting action to 
            be initiated by the receiving LLC entity itself."
    REFERENCE   
        "IEEE 802.2 (ISO/IEC 8802-2) type2Violation."
    ::= { lLCConnection2Entry 42 }

-- need lLCConnection2Event notification

lLCConnection2ProtocolState OBJECT-TYPE
    SYNTAX      INTEGER { disconnectedPhase(0), linkdiconnectionPhase(1), 
                    linkSetUpPhase(2), informationTransferPhase(3), 
                    frameRejectCondition(4), busyCondition(5), 
                    sentRejectCondition(6), 
                    systemParametersAndErrorRecovery(7) }
    MAX-ACCESS  read-only
    STATUS      current
    DESCRIPTION 
        "Local state of an LLC2 connection."
    ::= { lLCConnection2Entry 43 }

lLCConnection2AdministrativeState OBJECT-TYPE
    SYNTAX      AdministrativeState
    MAX-ACCESS  read-write
    STATUS      current
    DESCRIPTION 
        "Provides the X.731 administrative status of the LLC2 
         connection.  When locked(0), the LLC2 connection is 
         administratively prohibitted from forming and when 
         set to locked(0) will be abruptly disconnected if 
         already formed.  When unlocked(1) the LLC2 connection 
         is administratively permitted to form.  When set to
         shuttingDown(2), the LLC2 connection will be gracefully 
         withdrawn from service and will enter the locked(0) 
         state when shut down."
    ::= { lLCConnection2Entry 44 }

lLCConnection2OperationalState OBJECT-TYPE
    SYNTAX      OperationalState
    MAX-ACCESS  read-only
    STATUS      current
    DESCRIPTION 
        "Provides the X.731 operational state of this LAPB 
         connection."
    ::= { lLCConnection2Entry 45 }

lLCConnection2UsageState OBJECT-TYPE
    SYNTAX      UsageState
    MAX-ACCESS  read-only
    STATUS      current
    DESCRIPTION 
        "Provides the X.731 usage state of this LLC2 connection.  
         When idle(0), the LLC2 connection is not currently in 
         use (although it may still be formed).  When active(1), 
         the resource is being used and has sufficient spare 
         operating capacity to provide for additional users 
         simultaneously.  When busy(2), the resource is in use, 
         but it has no spare capacity to provide additional 
         users at this instant."
    ::= { lLCConnection2Entry 46 }

lLCConnection2ProceduralStatus OBJECT-TYPE
    SYNTAX      ProceduralStatus
    MAX-ACCESS  read-only
    STATUS      current
    DESCRIPTION 
        "Provides the X.731 procedural status of this LLC2 
         connection.  The procedural status contains 
         initializationRequired(0) when the LLC2 requires 
         initiation action to form or reform a connection.  It 
         contains notInitialized(1) when the LLC2 connection is 
         in disconnected mode (ADM); initializing(2) when 
         forming connection (SABM) and terminating(3) when 
         disconnecting (DISC)."
    ::= { lLCConnection2Entry 47 }

lLCConnection2AlarmStatus OBJECT-TYPE
    SYNTAX      AlarmStatus
    MAX-ACCESS  read-write
    STATUS      current
    DESCRIPTION 
        "Provides the alarm status of this LLC2 connection.
         
         The lLCConnection2f entry may issue a 
         communicationsAlarm notification using the RowPointer 
         of the corresponding entry in the objectIsntance 
         parameter of the communicationsAlarm.
         
         The probableCause is fRMRReceived.  The 
         specificProblems is one of:
         
         - fRMRReasonsControlFieldUndefinedOrUnimplemented,
         - fRMRReasonsFormatError,
         - fRMRReasonsInfoFieldLengthGreaterThanMaximum,
         - fRMRReasonsInvalidNR,
         - fRMRReasonsNonSpecific.
         
         The perceivedSeverity parameter is set to the value 
         Minor.  A subsequent communicationsAlarm with a 
         perceivedSeverity of Cleared is not generated.  Alarms 
         must be cleared by management stations using the 
         lLCConnection2AlarmStatus or locally.
         
         The fRMR parameter containing the received frame is 
         included in the additionalInformation.  No other 
         parameters are used."
    ::= { lLCConnection2Entry 48 }


-- =====================================================================

lLCConnection2IVMO OBJECT IDENTIFIER
    ::= { llcTables 14 }

lLCConnection2IVMOTable OBJECT-TYPE
    SYNTAX      SEQUENCE OF LLCConnection2IVMOEntry
    MAX-ACCESS  not-accessible
    STATUS      current
    DESCRIPTION 
        "lLCConnection2IVMO managed object.  A 
         lLCConnection2IVMO may be used to supply initial values 
         for the attributes of lLCConnection2 MOs.  Different 
         instances of lLCConnection2IVMO may contain different 
         initial values.
         
         Provides a table of configuration defaults for LLC2 
         connections to remote LLC2 stations from this LLC 
         station.
         
         This table provides initial values for connection 
         associated with the MAC/LLC stations indicated by the 
         index into the table.  Note that if the management 
         station does not assign values ot a MAC/LLC station, 
         the agent or implementation will assign default values 
         or values specified by local configuration.  These are 
         only default values for new connections formed to or 
         from the LLC station.  The management station can alter 
         the operational values via the 
         lLCConnection2Table.  The agent or 
         implementation may also alter operational values.  
         
         Changes made to values in this table will not 
         necessarily affect operational connections, but will be 
         used as default values for new connection formed 
         subsequent to the change.  Note that managements 
         stations may not add rows to or delete rows from this 
         table.  Rows are allocated by the implementation and 
         correspond each to available LLC stations."
    REFERENCE   
        "IEEE 802.2 (ISO/IEC 8802-2), lLCConenction2IVMO MOC."
    ::= { lLCConnection2IVMO 1 }

lLCConnection2IVMOEntry OBJECT-TYPE
    SYNTAX      LLCConnection2IVMOEntry
    MAX-ACCESS  not-accessible
    STATUS      current
    DESCRIPTION 
        "Each row in this table is indexed by the initial value 
         managed object (IVMO) name.  Each row contains initial 
         values for use in initializing LLC2 connections."
    REFERENCE   
        "IEEE 802.2 (ISO/IEC 8802-2), lLCConenction2IVMO MO."
    INDEX       { lLCConnection2IVMOName }
    ::= { lLCConnection2IVMOTable 1 }

LLCConnection2IVMOEntry ::= SEQUENCE {
    -- lLCConnection2IVMO-P mandatory package
    lLCConnection2IVMOName                      SimpleNameType,
    -- lLCConnection2-P mandatory package
    lLCConnection2IVMOMaximumRetransmissions    Unsigned32,
    lLCConnection2IVMOReceivedWindowSize        Unsigned32,
    lLCConnection2IVMOSendWindowSize            Unsigned32,
    lLCConnection2IVMOAcknowledgeTimeoutValue   TimeInterval,
    lLCConnection2IVMOBusyStateTimeoutValue     TimeInterval,
    lLCConnection2IVMOBitTimeoutValue           TimeInterval,
    lLCConnection2IVMORejectTimeoutValue        TimeInterval,
    -- connectionRoute-P conditional package
    lLCConnection2IVMORoute                     OCTET STRING,
    -- type2FlowControl-P conditional package
    lLCConnection2IVMOKStep                     Unsigned32,
    lLCConnection2IVMOMaxSendWindowSize         Unsigned32,
    -- type2I-P conditional package
    -- type2FRMR-P conditional package
    -- type2RR-P conditional package
    -- type2RNR-P conditional package
    -- type2REJ-P conditional package
    -- type2SABME-P conditional package
    -- type2UA-P conditional package
    -- type2DISC-P conditional package
    -- type2DM-P conditional package
    -- type2PDUs-P conditional package
    -- type2OptTolPDUs-P conditional package
    lLCConnection2IVMOOptionalTolerationIPDUs   TruthValue
    -- type2Violation-P conditional package
}

lLCConnection2IVMOName OBJECT-TYPE
    SYNTAX      SimpleNameType
    MAX-ACCESS  not-accessible
    STATUS      current
    DESCRIPTION 
        "Provides a name for the initial value managed object 
         (IVMO) instance that can be used when initializing LLC 
         connections."
    REFERENCE   
        "IEEE 802.2 (ISO/IEC 8802-2)."
    ::= { lLCConnection2IVMOEntry 1 }

lLCConnection2IVMOMaximumRetransmissions OBJECT-TYPE
    SYNTAX      Unsigned32
    MAX-ACCESS  read-write
    STATUS      current
    DESCRIPTION 
        "The default value, when not explicity specified by a 
         management station, is derived from the 
         lLCConnection2DefaultMaximumRetransmissions scalar."
    REFERENCE   
        "IEEE 802.2 (ISO/IEC 8802-2)."
    ::= { lLCConnection2IVMOEntry 2 }

lLCConnection2IVMOReceivedWindowSize OBJECT-TYPE
    SYNTAX      Unsigned32
    MAX-ACCESS  read-write
    STATUS      current
    DESCRIPTION 
        "The default value, when not explicity specified by a 
         management station, is derived from the 
         lLCConnection2DefaultReceivedWindowSize scalar."
    REFERENCE   
        "IEEE 802.2 (ISO/IEC 8802-2)."
    ::= { lLCConnection2IVMOEntry 3 }

lLCConnection2IVMOSendWindowSize OBJECT-TYPE
    SYNTAX      Unsigned32
    MAX-ACCESS  read-write
    STATUS      current
    DESCRIPTION 
        "The default value, when not explicity specified by a 
         management station, is derived from the 
         lLCConnection2DefaultSendWindowSize scalar."
    REFERENCE   
        "IEEE 802.2 (ISO/IEC 8802-2)."
    ::= { lLCConnection2IVMOEntry 4 }

lLCConnection2IVMOAcknowledgeTimeoutValue OBJECT-TYPE
    SYNTAX      TimeInterval
    MAX-ACCESS  read-write
    STATUS      current
    DESCRIPTION 
        "The default value, when not explicity specified by a 
         management station, is derived from the 
         lLCConnection2DefaultAcknowledgeTimeoutValue scalar."
    REFERENCE   
        "IEEE 802.2 (ISO/IEC 8802-2)."
    ::= { lLCConnection2IVMOEntry 5 }

lLCConnection2IVMOBusyStateTimeoutValue OBJECT-TYPE
    SYNTAX      TimeInterval
    MAX-ACCESS  read-write
    STATUS      current
    DESCRIPTION 
        "The default value, when not explicity specified by a 
         management station, is derived from the 
         lLCConnection2DefaultBusyStateTimeoutValue scalar."
    REFERENCE   
        "IEEE 802.2 (ISO/IEC 8802-2)."
    ::= { lLCConnection2IVMOEntry 6 }

lLCConnection2IVMOBitTimeoutValue OBJECT-TYPE
    SYNTAX      TimeInterval
    MAX-ACCESS  read-write
    STATUS      current
    DESCRIPTION 
        "The default value, when not explicity specified by a 
         management station, is derived from the 
         lLCConnection2DefaultPBitTimeoutValue scalar."
    REFERENCE   
        "IEEE 802.2 (ISO/IEC 8802-2)."
    ::= { lLCConnection2IVMOEntry 7 }

lLCConnection2IVMORejectTimeoutValue OBJECT-TYPE
    SYNTAX      TimeInterval
    MAX-ACCESS  read-write
    STATUS      current
    DESCRIPTION 
        "The default value, when not explicity specified by a 
         management station, is derived from the 
         lLCConnection2DefaultRejectTimeoutValue scalar."
    REFERENCE   
        "IEEE 802.2 (ISO/IEC 8802-2)."
    ::= { lLCConnection2IVMOEntry 8 }

lLCConnection2IVMORoute OBJECT-TYPE
    SYNTAX      OCTET STRING
    MAX-ACCESS  read-write
    STATUS      current
    DESCRIPTION 
        "The default value, when not explicity specified by a 
         management station, is derived from the 
         lLCConnection2DefaultRoute scalar."
    REFERENCE   
        "IEEE 802.2 (ISO/IEC 8802-2)."
    ::= { lLCConnection2IVMOEntry 9 }

lLCConnection2IVMOKStep OBJECT-TYPE
    SYNTAX      Unsigned32
    MAX-ACCESS  read-write
    STATUS      current
    DESCRIPTION 
        "The default value, when not explicity specified by a 
         management station, is derived from the 
         lLCConnection2DefaultKStep scalar."
    REFERENCE   
        "IEEE 802.2 (ISO/IEC 8802-2)."
    ::= { lLCConnection2IVMOEntry 10 }

lLCConnection2IVMOMaxSendWindowSize OBJECT-TYPE
    SYNTAX      Unsigned32
    MAX-ACCESS  read-write
    STATUS      current
    DESCRIPTION 
        "The default value, when not explicity specified by a 
         management station, is derived from the 
         lLCConnection2DefaultMaxSendWindowSize scalar."
    REFERENCE   
        "IEEE 802.2 (ISO/IEC 8802-2)."
    ::= { lLCConnection2IVMOEntry 11 }

lLCConnection2IVMOOptionalTolerationIPDUs OBJECT-TYPE
    SYNTAX      TruthValue
    MAX-ACCESS  read-write
    STATUS      current
    DESCRIPTION 
        "The default value, when not explicity specified by a 
         management station, is derived from the 
         lLCConnection2DefaultOptionalTolerationIPDUs scalar."
    REFERENCE   
        "IEEE 802.2 (ISO/IEC 8802-2)."
    ::= { lLCConnection2IVMOEntry 12 }


-- =====================================================================

lLCConnectionlessAck OBJECT IDENTIFIER
    ::= { llcTables 15 }

lLCConnectionlessAckTable OBJECT-TYPE
    SYNTAX      SEQUENCE OF LLCConnectionlessAckEntry
    MAX-ACCESS  not-accessible
    STATUS      current
    DESCRIPTION 
        "The Type 3 Received component is responsible for 
         processing Type 3 commands as they are received from 
         the medium access control sublayer, and for returning 
         Type 3 responses to the originators of the commands.  
         At a given station there is potentially a separate Type 
         3 Receiver component for each possible combination of 
         remote address (SA and SSAP), and MAC priority.  In 
         most applications, however, only a subset of the 
         possible Receiver components will exist, since a 
         component is needed only for those address and priority 
         combinations for which Type 3 commands are actually 
         received.
         
         The Type 3 Sender component is responsible for sending 
         Type 3 commands upon request of the network layer, and 
         for processing of Type 3 responses when they are 
         received from the medium access control sublayer.  At 
         any given station there is potentially a spearate Type 
         3 Sender component for each possible combination of 
         local LSAP, DA portion of the remote address, and MAC 
         priority.  In most applications, however, only a subset 
         of the possible Sender components will exist, since a 
         component is needed only for those address and priority 
         combinations for which Type 3 commands are actually 
         sent."
    REFERENCE   
        "IEEE 802.2 (ISO/IEC 8802-2), lLCConnectionlessAck MOC."
    ::= { lLCConnectionlessAck 1 }

lLCConnectionlessAckEntry OBJECT-TYPE
    SYNTAX      LLCConnectionlessAckEntry
    MAX-ACCESS  not-accessible
    STATUS      current
    DESCRIPTION 
        "Each row in the acknowledged connectionless table is 
         indexed by as well as defined with the connection 
         oriented protocol machine identifier to which it 
         belongs as well as the connection-oriented protocol 
         machine identifier that defines it.  Each row contains 
         the characteristics and operational status and 
         measurements for the acknoweldged connectionless 
         protocol machine."
    REFERENCE   
        "IEEE 802.2 (ISO/IEC 8802-2), lLCConnectionlessAck MO."
    INDEX       { lLCCOPMCoProtocolMachineId, lLCCOPMCoProtocolMachineId }
                -- lLCCOPMCoProtocolMachineId - contained by lLCCOPM
                -- lLCCOPMCoProtocolMachineId - derived from lLCCOPM
    ::= { lLCConnectionlessAckTable 1 }

LLCConnectionlessAckEntry ::= SEQUENCE {
    -- lLCConnectionlessAck-P mandatory package
    lLCConnectionlessAckName                            SimpleNameType,
    lLCConnectionlessAckMaximumLLCInformationFieldSize  Integer32,
    lLCConnectionlessAckMaximumRetransmissions          Integer32,
    lLCConnectionlessAckTESTReceivedABBResponse         Counter32,
    lLCConnectionlessAckTESTReceivedCommand             Counter32,
    lLCConnectionlessAckTESTReceivedResponse            Counter32,
    lLCConnectionlessAckTESTSentABBResponse             Counter32,
    lLCConnectionlessAckTESTSentCommand                 Counter32,
    lLCConnectionlessAckTESTSentResponse                Counter32,
    lLCConnectionlessAckReceiveResources                TruthValue,
    lLCConnectionlessAckUIReceived                      Counter32,
    lLCConnectionlessAckUISent                          Counter32,
    lLCConnectionlessAckXIDReceivedCommand              Counter32,
    lLCConnectionlessAckXIDReceivedResponse             Counter32,
    lLCConnectionlessAckXIDSentCommand                  Counter32,
    lLCConnectionlessAckXIDSentResponse                 Counter32,
    -- type3Retranmissions-P conditional package
    lLCConnectionlessAckRetransmissions                 Counter32,
    -- type3NoResponse-P conditional package
    lLCConnectionlessAckNoResponse                      Counter32,
    -- type3Command-P conditional package
    lLCConnectionlessAckCommandIP                       Counter32,
    lLCConnectionlessAckCommandIT                       Counter32,
    lLCConnectionlessAckCommandOK                       Counter32,
    lLCConnectionlessAckCommandPE                       Counter32,
    lLCConnectionlessAckCommandRS                       Counter32,
    lLCConnectionlessAckCommandUE                       Counter32,
    lLCConnectionlessAckCommandUN                       Counter32,
    lLCConnectionlessAckReceivedACCommand               Counter32,
    lLCConnectionlessAckSentACCommand                   Counter32,
    -- type3Response-P conditional package
    lLCConnectionlessAckResponseIP                      Counter32,
    lLCConnectionlessAckResponseIT                      Counter32,
    lLCConnectionlessAckResponseNE                      Counter32,
    lLCConnectionlessAckResponseNR                      Counter32,
    lLCConnectionlessAckResponseOK                      Counter32,
    lLCConnectionlessAckResponseRS                      Counter32,
    lLCConnectionlessAckResponseUE                      Counter32,
    lLCConnectionlessAckResponseUN                      Counter32,
    -- type3Violation-P conditional package
    lLCConnectionlessAckViolation                       Counter32
}

-- lLCConnectionlessAck-P mandatory package
--
-- The LLC Connectionless Ack object is responsible for processing the 
-- attributes, actions and notifications which affect a specific data 
-- link connection (for LLC Type 3 connections). One data connection 
-- shall exist for each data link connection supported.

lLCConnectionlessAckName OBJECT-TYPE
    SYNTAX      SimpleNameType
    MAX-ACCESS  read-only
    STATUS      current
    DESCRIPTION 
        "The localLSAP and remoteLSAPId and the local and remote 
         MAC Address."
    REFERENCE   
        "IEEE 802.2 (ISO/IEC 8802-2), lLCConnectionlessAckName."
    ::= { lLCConnectionlessAckEntry 1 }

lLCConnectionlessAckMaximumLLCInformationFieldSize OBJECT-TYPE
    SYNTAX      Integer32
    MAX-ACCESS  read-write
    STATUS      current
    DESCRIPTION 
        "The maximum length SDU that the LSAP will accomodate."
    REFERENCE   
        "IEEE 802.2 (ISO/IEC 8802-2), 
         maximumLLCInformationFieldSize."
    ::= { lLCConnectionlessAckEntry 2 }

lLCConnectionlessAckMaximumRetransmissions OBJECT-TYPE
    SYNTAX      Integer32
    MAX-ACCESS  read-write
    STATUS      current
    DESCRIPTION 
        "The number of times that the LLC Type 2 should attempt 
         to realize a successful PDU transfer."
    REFERENCE   
        "IEEE 802.2 (ISO/IEC 8802-2), maximumRetransmissions."
    ::= { lLCConnectionlessAckEntry 3 }

lLCConnectionlessAckTESTReceivedABBResponse OBJECT-TYPE
    SYNTAX      Counter32
    UNITS       "TEST ABB responses received"
    MAX-ACCESS  read-only
    STATUS      current
    DESCRIPTION 
        "Provides a count of TEST responses received by this 
         LSAP without the LSDU due to limited resources at the 
         remote station."
    REFERENCE   
        "IEEE 802.2 (ISO/IEC 8802-2), tESTReceivedABBResponse."
    ::= { lLCConnectionlessAckEntry 4 }

lLCConnectionlessAckTESTReceivedCommand OBJECT-TYPE
    SYNTAX      Counter32
    UNITS       "TEST commands received"
    MAX-ACCESS  read-only
    STATUS      current
    DESCRIPTION 
        "Provides a count of TEST commands received from the MAC 
         sublayer by this LSAP.  This includes commands recieved 
         with any group address recognized by this LSAP."
    REFERENCE   
        "IEEE 802.2 (ISO/IEC 8802-2), tESTReceivedCommand."
    ::= { lLCConnectionlessAckEntry 5 }

lLCConnectionlessAckTESTReceivedResponse OBJECT-TYPE
    SYNTAX      Counter32
    UNITS       "TEST responses received"
    MAX-ACCESS  read-only
    STATUS      current
    DESCRIPTION 
        "Provides a count of TEST responses received from the 
         MAC sublayer by this LSAP."
    REFERENCE   
        "IEEE 802.2 (ISO/IEC 8802-2), tESTReceivedResponse."
    ::= { lLCConnectionlessAckEntry 6 }

lLCConnectionlessAckTESTSentABBResponse OBJECT-TYPE
    SYNTAX      Counter32
    UNITS       "TEST ABB responses sent"
    MAX-ACCESS  read-only
    STATUS      current
    DESCRIPTION 
        "Provides a count of TEST responses that were delivered 
         to the MAC without the LSDU data due to limited 
         resources."
    REFERENCE   
        "IEEE 802.2 (ISO/IEC 8802-2), tESTSentABBResponse."
    ::= { lLCConnectionlessAckEntry 7 }

lLCConnectionlessAckTESTSentCommand OBJECT-TYPE
    SYNTAX      Counter32
    UNITS       "TEST commands sent"
    MAX-ACCESS  read-only
    STATUS      current
    DESCRIPTION 
        "Provides a count of TEST command set to the MAC 
         sublayer by this LSAP."
    REFERENCE   
        "IEEE 802.2 (ISO/IEC 8802-2), tESTSentCommand."
    ::= { lLCConnectionlessAckEntry 8 }

lLCConnectionlessAckTESTSentResponse OBJECT-TYPE
    SYNTAX      Counter32
    UNITS       "TEST responses sent"
    MAX-ACCESS  read-only
    STATUS      current
    DESCRIPTION 
        "Provides a count of TEST responses sent to the MAC 
         sublayer by this LSAP."
    REFERENCE   
        "IEEE 802.2 (ISO/IEC 8802-2), tESTSentResponse."
    ::= { lLCConnectionlessAckEntry 9 }

lLCConnectionlessAckReceiveResources OBJECT-TYPE
    SYNTAX      TruthValue
    MAX-ACCESS  read-write
    STATUS      current
    DESCRIPTION 
        "Causes the LSAP entity to either enable or disable the 
         resources for reception of the data field of Type 3 
         command PDUs sent to this LSAP.  If a Type 3 PDU 
         containing data is received while disabled, the UN 
         status code is returned in the CCCC field of the 
         response PDU."
    REFERENCE   
        "IEEE 802.2 (ISO/IEC 8802-2), type3ReceiveResources."
    ::= { lLCConnectionlessAckEntry 10 }

lLCConnectionlessAckUIReceived OBJECT-TYPE
    SYNTAX      Counter32
    UNITS       "UI frames received"
    MAX-ACCESS  read-only
    STATUS      current
    DESCRIPTION 
        "Provides a count of user data PDUs that were received 
         by the LSAP from the MAC sublayer and passed to the 
         user layer.  This includes commands received with group 
         addresses of which the LSAP is a member."
    REFERENCE   
        "IEEE 802.2 (ISO/IEC 8802-2), uIReceived."
    ::= { lLCConnectionlessAckEntry 11 }

lLCConnectionlessAckUISent OBJECT-TYPE
    SYNTAX      Counter32
    UNITS       "UI frames sent"
    MAX-ACCESS  read-only
    STATUS      current
    DESCRIPTION 
        "Provides a count of user data PDUs that were accepted 
         by the LSAP from the user layer and delivered to the 
         MAC sublayer."
    REFERENCE   
        "IEEE 802.2 (ISO/IEC 8802-2), uISent."
    ::= { lLCConnectionlessAckEntry 12 }

lLCConnectionlessAckXIDReceivedCommand OBJECT-TYPE
    SYNTAX      Counter32
    UNITS       "XID commands received"
    MAX-ACCESS  read-only
    STATUS      current
    DESCRIPTION 
        "Proivdes a count of XID commands received from the MAC 
         sublayer by this LSAP.  This includes commands received 
         with any group address recognized by this LSAP."
    REFERENCE   
        "IEEE 802.2 (ISO/IEC 8802-2), xIDReceivedCommand."
    ::= { lLCConnectionlessAckEntry 13 }

lLCConnectionlessAckXIDReceivedResponse OBJECT-TYPE
    SYNTAX      Counter32
    UNITS       "XID responses received"
    MAX-ACCESS  read-only
    STATUS      current
    DESCRIPTION 
        "Provides a count of XID responses received from the MAC 
         sublayer by this LSAP."
    REFERENCE   
        "IEEE 802.2 (ISO/IEC 8802-2), xIDReceivedResponse."
    ::= { lLCConnectionlessAckEntry 14 }

lLCConnectionlessAckXIDSentCommand OBJECT-TYPE
    SYNTAX      Counter32
    UNITS       "XID commands sent"
    MAX-ACCESS  read-only
    STATUS      current
    DESCRIPTION 
        "Provides a count of XID commands sent to the MAC 
         sublayer by this LSAP."
    REFERENCE   
        "IEEE 802.2 (ISO/IEC 8802-2), xIDSentCommand."
    ::= { lLCConnectionlessAckEntry 15 }

lLCConnectionlessAckXIDSentResponse OBJECT-TYPE
    SYNTAX      Counter32
    UNITS       "XID responses sent"
    MAX-ACCESS  read-only
    STATUS      current
    DESCRIPTION 
        "Provides a count of the XID responses sent to the MAC 
         sublayer by this LSAP."
    REFERENCE   
        "IEEE 802.2 (ISO/IEC 8802-2), xIDSentResponse."
    ::= { lLCConnectionlessAckEntry 16 }

-- type3Retranmissions-P conditional package
--
-- Provides a count of retransmissions that have occurred to the 
-- destination associated with this LSAP pair.

lLCConnectionlessAckRetransmissions OBJECT-TYPE
    SYNTAX      Counter32
    UNITS       "retransmissions"
    MAX-ACCESS  read-only
    STATUS      current
    DESCRIPTION 
        "Provides a count of the number of PDUs which were 
         retrasmitted (at least once) by the Type 3 LLC service."
    REFERENCE   
        "IEEE 802.2 (ISO/IEC 8802-2), type3Retransmissions."
    ::= { lLCConnectionlessAckEntry 17 }

-- type3NoResponse-P conditional package
--
-- Provides a count of failures to obtain a response from the 
-- destination associated with an LSAPPairComponent, after exhausting 
-- the retry counter Retransmission4. When this counter is updated an 
-- event notification is forwarded.

lLCConnectionlessAckNoResponse OBJECT-TYPE
    SYNTAX      Counter32
    UNITS       "failures"
    MAX-ACCESS  read-only
    STATUS      current
    DESCRIPTION 
        "Provides a count of failures to obtain a response from 
         the destination associated with this LSAP pair, after 
         exhausting the retry counter MaximumRetransmissions4."
    REFERENCE   
        "IEEE 802.2 (ISO/IEC 8802-2), type3NoResponse."
    ::= { lLCConnectionlessAckEntry 18 }

-- type3Command-P conditional package
--
-- This conditional packages contains attributes (counters) that count 
-- received responses with the command status field set.

lLCConnectionlessAckCommandIP OBJECT-TYPE
    SYNTAX      Counter32
    UNITS       "responses"
    MAX-ACCESS  read-only
    STATUS      current
    DESCRIPTION 
        "Provides a count of the received responses with the 
         command status field set to indicate 'Permanent 
         implementation dependent error,' as defined in 
         5.4.3.2."
    REFERENCE   
        "IEEE 802.2 (ISO/IEC 8802-2), type3CommandIP."
    ::= { lLCConnectionlessAckEntry 19 }

lLCConnectionlessAckCommandIT OBJECT-TYPE
    SYNTAX      Counter32
    UNITS       "responses"
    MAX-ACCESS  read-only
    STATUS      current
    DESCRIPTION 
        "Provides a count of the received responses with the 
         command status field set to indicate 'Temporarily 
         implementation dependent error,' as defined in 
         5.4.3.2."
    REFERENCE   
        "IEEE 802.2 (ISO/IEC 8802-2), type3CommandIT."
    ::= { lLCConnectionlessAckEntry 20 }

lLCConnectionlessAckCommandOK OBJECT-TYPE
    SYNTAX      Counter32
    UNITS       "responses"
    MAX-ACCESS  read-only
    STATUS      current
    DESCRIPTION 
        "Provides a count of the received responses with the 
         command status field set to indicate 'Command 
         accepted,' as defined in 5.4.3.2."
    REFERENCE   
        "IEEE 802.2 (ISO/IEC 8802-2), type3CommandOK."
    ::= { lLCConnectionlessAckEntry 21 }

lLCConnectionlessAckCommandPE OBJECT-TYPE
    SYNTAX      Counter32
    UNITS       "responses"
    MAX-ACCESS  read-only
    STATUS      current
    DESCRIPTION 
        "Provides a count of the received responses with the 
         command status field set to indicate 'Protocol error,' 
         as defined in 5.4.3.2."
    REFERENCE   
        "IEEE 802.2 (ISO/IEC 8802-2), type3CommandPE."
    ::= { lLCConnectionlessAckEntry 22 }

lLCConnectionlessAckCommandRS OBJECT-TYPE
    SYNTAX      Counter32
    UNITS       "responses"
    MAX-ACCESS  read-only
    STATUS      current
    DESCRIPTION 
        "Provides a count of the received responses with the 
         command status field set to indicate 'Unimplemented or 
         inactivated service,' as defined in 5.4.3.2."
    REFERENCE   
        "IEEE 802.2 (ISO/IEC 8802-2), type3CommandRS."
    ::= { lLCConnectionlessAckEntry 23 }

lLCConnectionlessAckCommandUE OBJECT-TYPE
    SYNTAX      Counter32
    UNITS       "responses"
    MAX-ACCESS  read-only
    STATUS      current
    DESCRIPTION 
        "Provides a count of the received responses with the 
         command status field set to indicate 'LLC user 
         interface error,' as defined in 5.4.3.2."
    REFERENCE   
        "IEEE 802.2 (ISO/IEC 8802-2), type3CommandUE."
    ::= { lLCConnectionlessAckEntry 24 }

lLCConnectionlessAckCommandUN OBJECT-TYPE
    SYNTAX      Counter32
    UNITS       "responses"
    MAX-ACCESS  read-only
    STATUS      current
    DESCRIPTION 
        "Provides a count of the received responses with the 
         command status field set to indicate 'Resources 
         temporarily unavailable,' as defined in 5.4.3.2."
    REFERENCE   
        "IEEE 802.2 (ISO/IEC 8802-2), type3CommandUN."
    ::= { lLCConnectionlessAckEntry 25 }

lLCConnectionlessAckReceivedACCommand OBJECT-TYPE
    SYNTAX      Counter32
    UNITS       "AC command PDUs received"
    MAX-ACCESS  read-only
    STATUS      current
    DESCRIPTION 
        "Provides a count of AC command PDUs received from the 
         other LSAP of the connection (LSAP PAIR)."
    REFERENCE   
        "IEEE 802.2 (ISO/IEC 8802-2), type3ReceivedACCommand."
    ::= { lLCConnectionlessAckEntry 26 }

lLCConnectionlessAckSentACCommand OBJECT-TYPE
    SYNTAX      Counter32
    UNITS       "AC command PDUs sent"
    MAX-ACCESS  read-only
    STATUS      current
    DESCRIPTION 
        "Provides a count of AC command PDUs sent to the other 
         LSAP of the connection (LSAP PAIR)."
    REFERENCE   
        "IEEE 802.2 (ISO/IEC 8802-2), type3SentACCommand."
    ::= { lLCConnectionlessAckEntry 27 }

-- type3Response-P conditional package
--
-- This conditional packages contains attributes (counters) that count 
-- received responses with the response status field set.

lLCConnectionlessAckResponseIP OBJECT-TYPE
    SYNTAX      Counter32
    UNITS       "responses"
    MAX-ACCESS  read-only
    STATUS      current
    DESCRIPTION 
        "Provides a count of the received responses with the 
         response status field set to indicate 'Permanent 
         implementation dependent error,' as defined in 
         5.4.3.2."
    REFERENCE   
        "IEEE 802.2 (ISO/IEC 8802-2), type3ResponseIP."
    ::= { lLCConnectionlessAckEntry 28 }

lLCConnectionlessAckResponseIT OBJECT-TYPE
    SYNTAX      Counter32
    UNITS       "responses"
    MAX-ACCESS  read-only
    STATUS      current
    DESCRIPTION 
        "Provides a count of the received responses with the 
         response status field set to indicate 'Temporary 
         implementation dependent error,' as defined in 
         5.4.3.2."
    REFERENCE   
        "IEEE 802.2 (ISO/IEC 8802-2), type3ResponseIT."
    ::= { lLCConnectionlessAckEntry 29 }

lLCConnectionlessAckResponseNE OBJECT-TYPE
    SYNTAX      Counter32
    UNITS       "responses"
    MAX-ACCESS  read-only
    STATUS      current
    DESCRIPTION 
        "Provides a count of the received responses with the 
         response status field set to indicate 'Response LSDU 
         never submitted,' as defined in 5.4.3.2."
    REFERENCE   
        "IEEE 802.2 (ISO/IEC 8802-2), type3ResponseNE."
    ::= { lLCConnectionlessAckEntry 30 }

lLCConnectionlessAckResponseNR OBJECT-TYPE
    SYNTAX      Counter32
    UNITS       "responses"
    MAX-ACCESS  read-only
    STATUS      current
    DESCRIPTION 
        "Provides a count of the received responses with the 
         response status field set to indicate 'Response LSDU 
         not requested,' as defined in 5.4.3.2."
    REFERENCE   
        "IEEE 802.2 (ISO/IEC 8802-2), type3ResponseNR."
    ::= { lLCConnectionlessAckEntry 31 }

lLCConnectionlessAckResponseOK OBJECT-TYPE
    SYNTAX      Counter32
    UNITS       "responses"
    MAX-ACCESS  read-only
    STATUS      current
    DESCRIPTION 
        "Provides a count of the received responses with the 
         response status field set to indicate 'Response LSDU 
         present,' as defined in 5.4.3.2."
    REFERENCE   
        "IEEE 802.2 (ISO/IEC 8802-2), type3ResponseOK."
    ::= { lLCConnectionlessAckEntry 32 }

lLCConnectionlessAckResponseRS OBJECT-TYPE
    SYNTAX      Counter32
    UNITS       "responses"
    MAX-ACCESS  read-only
    STATUS      current
    DESCRIPTION 
        "Provides a count of the received responses with the 
         response status field set to indicate 'Unimplemented or 
         inactivated service,' as defined in 5.4.3.2."
    REFERENCE   
        "IEEE 802.2 (ISO/IEC 8802-2), type3ResponseRS."
    ::= { lLCConnectionlessAckEntry 33 }

lLCConnectionlessAckResponseUE OBJECT-TYPE
    SYNTAX      Counter32
    UNITS       "responses"
    MAX-ACCESS  read-only
    STATUS      current
    DESCRIPTION 
        "Provides a count of the received responses with the 
         response status field set to indicate 'LLC user 
         interface error,' as defined in 5.4.3.2."
    REFERENCE   
        "IEEE 802.2 (ISO/IEC 8802-2), type3ResponseUE."
    ::= { lLCConnectionlessAckEntry 34 }

lLCConnectionlessAckResponseUN OBJECT-TYPE
    SYNTAX      Counter32
    UNITS       "responses"
    MAX-ACCESS  read-only
    STATUS      current
    DESCRIPTION 
        "Provides a count of the received responses with the 
         response status field set to indicate 'Resources 
         temporarily unavailable,' as defined in 5.4.3.2."
    REFERENCE   
        "IEEE 802.2 (ISO/IEC 8802-2), type3ResponseUN."
    ::= { lLCConnectionlessAckEntry 35 }

-- type3Violation-P conditional package
--
-- Provides a count of the number of protocol violations detected by 
-- this connection.

lLCConnectionlessAckViolation OBJECT-TYPE
    SYNTAX      Counter32
    UNITS       "protocol violations"
    MAX-ACCESS  read-only
    STATUS      current
    DESCRIPTION 
        "Provides a count of the number of protocol violations 
         detected by this connection."
    REFERENCE   
        "IEEE 802.2 (ISO/IEC 8802-2), type3Violation."
    ::= { lLCConnectionlessAckEntry 36 }


-- =====================================================================

lLCConnectionlessAckIVMO OBJECT IDENTIFIER
    ::= { llcTables 16 }

lLCConnectionlessAckIVMOTable OBJECT-TYPE
    SYNTAX      SEQUENCE OF LLCConnectionlessAckIVMOEntry
    MAX-ACCESS  not-accessible
    STATUS      current
    DESCRIPTION 
        "lLCConnectionlessAckIVMOmanaged object.  
         An lLCConnectionlessAckIVMO may be used to supply 
         initial values for the attributes of 
         lLCConnectionlessAck managed objects.  Different 
         instances of lLCConnectionlessAckIVMO may contain 
         different initial values.
         
         This table provides intial values for acknowledged 
         connectionless associations associated with the MAC/LLC 
         stations indicated by the index into the table.  Note 
         that if the management station does not assign valuds 
         to a MAC/LLC station, the agent or implementation will 
         assign default values or values specified by local 
         configuration.  These are from the LLC station.  The 
         management station can alter the operational values via 
         the lLCConnectionlessAckTable.  The agent or 
         implementation may also alter operational values.
         
         Changes made to values in this table will not 
         necessarily affect operational connections, but will be 
         used as default values for new acknowledged 
         connectionless associations formed subsequent to the 
         change.  Note that management stations may not add rows 
         to or delete rows from this table.  Rows are allocated 
         by the implementation and correspond to each to 
         available LLC stations. "
    REFERENCE   
        "IEEE 802.2 (ISO/IEC 8802-2), lLCCOnnectionlessAckIVMO 
         MOC."
    ::= { lLCConnectionlessAckIVMO 1 }

lLCConnectionlessAckIVMOEntry OBJECT-TYPE
    SYNTAX      LLCConnectionlessAckIVMOEntry
    MAX-ACCESS  not-accessible
    STATUS      current
    DESCRIPTION 
        "Each row in this table is indexed by the initial value 
         managed object (IVMO) name.  Each row contains initial 
         values for use in initializing LLC3 associations."
    REFERENCE   
        "IEEE 802.2 (ISO/IEC 8802-2), lLCCOnnectionlessAckIVMO 
         MO."
    INDEX       { lLCConnectionlessAckIVMOName }
    ::= { lLCConnectionlessAckIVMOTable 1 }

LLCConnectionlessAckIVMOEntry ::= SEQUENCE {
    -- lLCConnectionlessAckIVMO-P mandatory package
    lLCConnectionlessAckIVMOName                            SimpleNameType,
    -- lLCConnectionlessAck-P mandatory package
    lLCConnectionlessAckIVMOMaximumLLCInformationFieldSize  Integer32,
    lLCConnectionlessAckIVMOMaximumRetransmissions          Integer32,
    -- type3Retranmissions-P conditional package
    -- type3NoResponse-P conditional package
    -- type3Command-P conditional package
    -- type3Response-P conditional package
    -- type3Violation-P conditional package
    lLCConnectionlessAckIVMORowStatus                       RowStatus
}

-- lLCConnectionlessAckIVMO-P mandatory package
lLCConnectionlessAckIVMOName OBJECT-TYPE
    SYNTAX      SimpleNameType
    MAX-ACCESS  not-accessible
    STATUS      current
    DESCRIPTION 
        "Provides a name for the initial value managed object 
         (IVMO) instance that can be used when initializing LLC 
         associations."
    REFERENCE   
        "IEEE 802.2 (ISO/IEC 8802-2), 
         lLCConnecionlessAckIVMOName."
    ::= { lLCConnectionlessAckIVMOEntry 1 }

-- lLCConnectionlessAck-P mandatory package
lLCConnectionlessAckIVMOMaximumLLCInformationFieldSize OBJECT-TYPE
    SYNTAX      Integer32
    MAX-ACCESS  read-create
    STATUS      current
    DESCRIPTION 
        "The maximum length SDU that the LSAP will accomodate."
    REFERENCE   
        "IEEE 802.2 (ISO/IEC 8802-2), 
         maximumLLCInformationFieldSize."
    ::= { lLCConnectionlessAckIVMOEntry 2 }

lLCConnectionlessAckIVMOMaximumRetransmissions OBJECT-TYPE
    SYNTAX      Integer32
    MAX-ACCESS  read-create
    STATUS      current
    DESCRIPTION 
        "The number of times that the LLC Type 3 should attempt 
         to realize a successful PDU transfer."
    REFERENCE   
        "IEEE 802.2 (ISO/IEC 8802-2), 
         maximumRetransmissions."
    ::= { lLCConnectionlessAckIVMOEntry 3 }

-- type3Retranmissions-P conditional package
-- type3NoResponse-P conditional package
-- type3Command-P conditional package
-- type3Response-P conditional package
-- type3Violation-P conditional package

lLCConnectionlessAckIVMORowStatus OBJECT-TYPE
    SYNTAX      RowStatus
    MAX-ACCESS  read-create
    STATUS      current
    DESCRIPTION 
        "Provides a mechanism whereby management stations may 
         create or delete rows in this table.  Entries must 
         persist across an agent reboot."
    REFERENCE   
        "STD 58, SNMPv2-TC RowStatus."
    ::= { lLCConnectionlessAckIVMOEntry 4 }

-- =====================================================================
--
-- Scalars

llcScalars OBJECT IDENTIFIER
    ::= { llcObjects 2 }

llcGlobals OBJECT IDENTIFIER
    ::= { llcScalars 1 }

llcDiscontinuityTime OBJECT-TYPE
    SYNTAX      TimeStamp
    MAX-ACCESS  read-only
    STATUS      current
    DESCRIPTION 
        "Provides the time since the last reboot at which a 
         discontinuity in counters and gauges occurred possibly 
         resulting in the reset of counters and gauges to zero."
    REFERENCE   
        "SMIv2"
    ::= { llcGlobals 1 }

-- lLCConnection2IVMO defaults
--
-- The following are default values for connection profiles for LLC 
-- stations.  These values will be used as the default values when an 
-- LLC station profile is created in the lLCConnection2IVMOTable.

llcDefaults OBJECT IDENTIFIER
    ::= { llcScalars 2 }

lLCConnection2Defaults OBJECT IDENTIFIER
    ::= { llcDefaults 1 }

lLCConnection2DefaultMaximumRetransmissions OBJECT-TYPE
    SYNTAX      Integer32
    MAX-ACCESS  read-write
    STATUS      current
    DESCRIPTION 
        "Sets the default value for the 
         lLCConnection2MaximumRetransmissions element of the 
         lLCConnection2Table.  When set by a management 
         station, the value set should persist across agent and 
         system reboots.  The DEFVAL, therefore, is only 
         applicable when this default has never been set by a  
         managements station."
    REFERENCE   
        "IEEE 802.2 (ISO/IEC 8802-2)."
    ::= { lLCConnection2Defaults 1 }

lLCConnection2DefaultReceivedWindowSize OBJECT-TYPE
    SYNTAX      Integer32
    MAX-ACCESS  read-write
    STATUS      current
    DESCRIPTION 
        "Sets the default value for the 
         lLCConnection2ReceivedWindowSize element of the 
         lLCConnection2Table.  When set by a management 
         station, the value set should persist across agent and 
         system reboots.  The DEFVAL, therefore, is only 
         applicable when this default has never been set by a  
         managements station."
    REFERENCE   
        "IEEE 802.2 (ISO/IEC 8802-2)."
    ::= { lLCConnection2Defaults 2 }

lLCConnection2DefaultSendWindowSize OBJECT-TYPE
    SYNTAX      Integer32
    MAX-ACCESS  read-write
    STATUS      current
    DESCRIPTION 
        "Sets the default value for the 
         lLCConnection2SendWindowSize element of the 
         lLCConnection2Table.  When set by a management 
         station, the value set should persist across agent and 
         system reboots.  The DEFVAL, therefore, is only 
         applicable when this default has never been set by a  
         managements station."
    REFERENCE   
        "IEEE 802.2 (ISO/IEC 8802-2)."
    ::= { lLCConnection2Defaults 3 }

lLCConnection2DefaultAcknowledgeTimeoutValue OBJECT-TYPE
    SYNTAX      TimeInterval
    MAX-ACCESS  read-write
    STATUS      current
    DESCRIPTION 
        "Sets the default value for the 
         lLCConnection2AcknowleTimeoutValue element of 
         the lLCConnection2Table.  When set by a management 
         station, the value set should persist across agent and 
         system reboots.  The DEFVAL, therefore, is only 
         applicable when this default has never been set by a  
         managements station."
    REFERENCE   
        "IEEE 802.2 (ISO/IEC 8802-2)."
    ::= { lLCConnection2Defaults 4 }

lLCConnection2DefaultBusyStateTimeoutValue OBJECT-TYPE
    SYNTAX      TimeInterval
    MAX-ACCESS  read-write
    STATUS      current
    DESCRIPTION 
        "Sets the default value for the 
         lLCConnection2BusyStateTimeoutValue element of 
         the lLCConnection2Table.  When set by a management 
         station, the value set should persist across agent and 
         system reboots.  The DEFVAL, therefore, is only 
         applicable when this default has never been set by a  
         managements station."
    REFERENCE   
        "IEEE 802.2 (ISO/IEC 8802-2)."
    ::= { lLCConnection2Defaults 5 }

lLCConnection2DefaultPBitTimeoutValue OBJECT-TYPE
    SYNTAX      TimeInterval
    MAX-ACCESS  read-write
    STATUS      current
    DESCRIPTION 
        "Sets the default value for the 
         lLCConnection2BitTImeoutValue element of the 
         lLCConnection2Table.  When set by a management 
         station, the value set should persist across agent and 
         system reboots.  The DEFVAL, therefore, is only 
         applicable when this default has never been set by a  
         managements station."
    REFERENCE   
        "IEEE 802.2 (ISO/IEC 8802-2)."
    ::= { lLCConnection2Defaults 6 }

lLCConnection2DefaultRejectTimeoutValue OBJECT-TYPE
    SYNTAX      TimeInterval
    MAX-ACCESS  read-write
    STATUS      current
    DESCRIPTION 
        "Sets the default value for the 
         lLCConnection2RejectTimeoutValue element of the 
         lLCConnection2Table.  When set by a management 
         station, the value set should persist across agent and 
         system reboots.  The DEFVAL, therefore, is only 
         applicable when this default has never been set by a  
         managements station."
    REFERENCE   
        "IEEE 802.2 (ISO/IEC 8802-2)."
    ::= { lLCConnection2Defaults 7 }

lLCConnection2DefaultRoute OBJECT-TYPE
    SYNTAX      OCTET STRING
    MAX-ACCESS  read-write
    STATUS      current
    DESCRIPTION 
        "Sets the default value for the lLCConnection2Route 
         element of the lLCConnection2Table.  When set by a 
         management station, the value set should persist across 
         agent and system reboots.  The DEFVAL, therefore, is 
         only applicable when this default has never been set by 
         a  managements station."
    REFERENCE   
        "IEEE 802.2 (ISO/IEC 8802-2)."
    ::= { lLCConnection2Defaults 8 }

lLCConnection2DefaultKStep OBJECT-TYPE
    SYNTAX      Integer32
    MAX-ACCESS  read-write
    STATUS      current
    DESCRIPTION 
        "Sets the default value for the lLCConnection2KStep 
         element of the lLCConnection2Table.  When set by a 
         management station, the value set should persist across 
         agent and system reboots.  The DEFVAL, therefore, is 
         only applicable when this default has never been set by 
         a  managements station."
    REFERENCE   
        "IEEE 802.2 (ISO/IEC 8802-2)."
    ::= { lLCConnection2Defaults 9 }

lLCConnection2DefaultMaxSendWindowSize OBJECT-TYPE
    SYNTAX      Integer32
    MAX-ACCESS  read-write
    STATUS      current
    DESCRIPTION 
        "Sets the default value for the 
         lLCConnection2MaxSendWindowSize element of the 
         lLCConnection2Table.  When set by a management 
         station, the value set should persist across agent and 
         system reboots.  The DEFVAL, therefore, is only 
         applicable when this default has never been set by a  
         managements station."
    REFERENCE   
        "IEEE 802.2 (ISO/IEC 8802-2)."
    ::= { lLCConnection2Defaults 10 }

-- type2I-P conditional package

-- type2FRMR-P conditional package

-- type2RR-P conditional package

-- type2RNR-P conditional package

-- type2REJ-P conditional package

-- type2SABME-P conditional package

-- type2UA-P conditional package

-- type2DISC-P conditional package

-- type2DM-P conditional package

-- type2PDUs-P conditional package

-- type2OptTolPDUs-P conditional package
lLCConnection2DefaultOptionalTolerationIPDUs OBJECT-TYPE
    SYNTAX      TruthValue
    MAX-ACCESS  read-write
    STATUS      current
    DESCRIPTION 
        "Sets the default value for the 
         lLCConnection2OptionalTolerationIPDUs element of the 
         lLCConnection2Table.  When set by a management 
         station, the value set should persist across agent and 
         system reboots.  The DEFVAL, therefore, is only 
         applicable when this default has never been set by a  
         management station."
    REFERENCE   
        "IEEE 802.2 (ISO/IEC 8802-2)."
    ::= { lLCConnection2Defaults 11 }

-- type2Violation-P conditional package


-- =====================================================================

-- lLCConnectionlessAckIVMO defaults

lLCConnectionlessAckDefaults OBJECT IDENTIFIER
    ::= { llcDefaults 2 }

-- lLCConnectionlessAck-P mandatory package
lLCConnectionlessAckDefaultMaximumLLCInformationFieldSize OBJECT-TYPE
    SYNTAX      Integer32
    MAX-ACCESS  read-write
    STATUS      current
    DESCRIPTION 
        "Set the default value for the 
         lLCConnectionlessAckMaximumLLCInformationFieldSize 
         element of the lLCConnectionlessAckTable.  When set 
         by a management station, the value set should persist 
         across the agen and system reboots.  The DEFVAL, 
         therefore, is only applicable when this default has 
         never been set by a management station."
    REFERENCE   
        "IEEE 802.2 (ISO/IEC 8802-2)"
    ::= { lLCConnectionlessAckDefaults 1 }

lLCConnectionlessAckDefaultMaximumRetransmissions OBJECT-TYPE
    SYNTAX      Integer32
    MAX-ACCESS  read-write
    STATUS      current
    DESCRIPTION 
        "Set the default value for the 
         lLCConnectionlessAckMaximumRetransmissions element 
         of the lLCConnectionlessAckTable.  When set by a 
         management station, the value set should persist across 
         the agen and system reboots.  The DEFVAL, therefore, is 
         only applicable when this default has never been set by 
         a management station."
    REFERENCE   
        "IEEE 802.2 (ISO/IEC 8802-2)"
    ::= { lLCConnectionlessAckDefaults 2 }

-- lLCConnectionlessAckIVMO-P mandatory package
-- type3Retranmissions-P conditional package
-- type3NoResponse-P conditional package
-- type3Command-P conditional package
-- type3Response-P conditional package
-- type3Violation-P conditional package

-- =====================================================================
--
-- Parameters for Notifications

llcNotifs OBJECT IDENTIFIER
    ::= { llcObjects 3 }

pdusDiscarded1 OBJECT-TYPE
    SYNTAX      Counter32
    MAX-ACCESS  accessible-for-notify
    STATUS      current
    DESCRIPTION 
        "Parameter for use with the lLCConnection2Event 
         notification."
    REFERENCE   
        "IEEE 802.2 (ISO/IEC 8802-2) ASN.1, pdusDiscarded1."
    ::= { llcNotifs 1 }

pdusDiscarded2 OBJECT-TYPE
    SYNTAX      Counter32
    MAX-ACCESS  accessible-for-notify
    STATUS      current
    DESCRIPTION 
        "Parameter for use with the lLCConnection2Event 
         notification."
    REFERENCE   
        "IEEE 802.2 (ISO/IEC 8802-2) ASN.1, pdusDiscarded2."
    ::= { llcNotifs 2 }

pduRetransmissions OBJECT-TYPE
    SYNTAX      Counter32
    MAX-ACCESS  accessible-for-notify
    STATUS      current
    DESCRIPTION 
        "Parameter for use with the lLCConnection2Event 
         notification."
    REFERENCE   
        "IEEE 802.2 (ISO/IEC 8802-2) ASN.1, pduRetransmissions."
    ::= { llcNotifs 3 }

acknowledgeTimeout OBJECT-TYPE
    SYNTAX      TimeInterval
    MAX-ACCESS  accessible-for-notify
    STATUS      current
    DESCRIPTION 
        "Parameter for use with the lLCConnection2Event 
         notification."
    REFERENCE   
        "IEEE 802.2 (ISO/IEC 8802-2) ASN.1, acknowledgeTimeout."
    ::= { llcNotifs 4 }

busyStateTimeout OBJECT-TYPE
    SYNTAX      TimeInterval
    MAX-ACCESS  accessible-for-notify
    STATUS      current
    DESCRIPTION 
        "Parameter for use with the lLCConnection2Event 
         notification."
    REFERENCE   
        "IEEE 802.2 (ISO/IEC 8802-2) ASN.1, busyStateTimeout."
    ::= { llcNotifs 5 }

rejectTimeout OBJECT-TYPE
    SYNTAX      TimeInterval
    MAX-ACCESS  accessible-for-notify
    STATUS      current
    DESCRIPTION 
        "Parameter for use with the lLCConnection2Event 
         notification."
    REFERENCE   
        "IEEE 802.2 (ISO/IEC 8802-2) ASN.1, rejectTimeout."
    ::= { llcNotifs 6 }

pBitTimeout OBJECT-TYPE
    SYNTAX      TimeInterval
    MAX-ACCESS  accessible-for-notify
    STATUS      current
    DESCRIPTION 
        "Parameter for use with the lLCConnection2Event 
         notification."
    REFERENCE   
        "IEEE 802.2 (ISO/IEC 8802-2) ASN.1, pBitTimeout."
    ::= { llcNotifs 7 }

type2Violation OBJECT-TYPE
    SYNTAX      Counter32
    MAX-ACCESS  accessible-for-notify
    STATUS      current
    DESCRIPTION 
        "Parameter for use with the lLCConnection2Event 
         notification."
    REFERENCE   
        "IEEE 802.2 (ISO/IEC 8802-2) ASN.1, type2Violation."
    ::= { llcNotifs 8 }

retranmissions OBJECT-TYPE
    SYNTAX      Counter32
    MAX-ACCESS  accessible-for-notify
    STATUS      current
    DESCRIPTION 
        "Parameter for use with the lLCConnection2Event or 
         lLCClessACKEvent notifications."
    REFERENCE   
        "IEEE 802.2 (ISO/IEC 8802-2) ASN.1, retransmissions."
    ::= { llcNotifs 9 }

type3Violation OBJECT-TYPE
    SYNTAX      Counter32
    MAX-ACCESS  accessible-for-notify
    STATUS      current
    DESCRIPTION 
        "Parameter for use with the lLCClessACKEvent 
         notification."
    REFERENCE   
        "IEEE 802.2 (ISO/IEC 8802-2) ASN.1, 
         LLCClessACKEvent.type3Violation."
    ::= { llcNotifs 10 }

noResponse OBJECT-TYPE
    SYNTAX      Counter32
    MAX-ACCESS  accessible-for-notify
    STATUS      current
    DESCRIPTION 
        "Parameter for use with the lLCClessACKEvent 
         notification."
    REFERENCE   
        "IEEE 802.2 (ISO/IEC 8802-2) ASN.1, 
         LLCClessACKEvent.noResponse."
    ::= { llcNotifs 11 }

pdusDiscarded OBJECT-TYPE
    SYNTAX      Counter32
    MAX-ACCESS  accessible-for-notify
    STATUS      current
    DESCRIPTION 
        "Parameter for use with the lLCStationEvent 
         notification."
    REFERENCE   
        "IEEE 802.2 (ISO/IEC 8802-2) ASN.1, 
         LLCStationEvent.pdusDiscarded."
    ::= { llcNotifs 12 }

bufferProblems OBJECT-TYPE
    SYNTAX      Counter32
    MAX-ACCESS  accessible-for-notify
    STATUS      current
    DESCRIPTION 
        "Parameter for use with the lLCStationEvent 
         notification."
    REFERENCE   
        "IEEE 802.2 (ISO/IEC 8802-2) ASN.1, 
         LLCStationEvent.bufferProblems."
    ::= { llcNotifs 13 }


-- =====================================================================
-- 
-- Notifications

llcOids OBJECT IDENTIFIER
    ::= { llcObjects 4 }

llcConformance OBJECT IDENTIFIER
    ::= { llcMIB 2 }

llcGroups OBJECT IDENTIFIER
    ::= { llcConformance 1 }

llcCompliances OBJECT IDENTIFIER
    ::= { llcConformance 2 }

lLCConnection2Event NOTIFICATION-TYPE
    OBJECTS     { tmnObjectInstance }
                -- pdusDiscarded1
                -- pdusDiscarded2
                -- pduRetransmissions
                -- acknowledgeTimeout
                -- busyStateTimeout
                -- rejectTimeout
                -- pBitTimeout
                -- type2Violation
                -- retransmissions
    STATUS      current
    DESCRIPTION 
        "This event will be sent for the following condtions: 
         DupIPDUs Received, PDUs Discarded1, PDUs Discarded2, 
         PDU Retransmissions, Type2 Violation, Type2 
         Acknowledgement Timeout Value, Type2 Reject Timeout 
         Value, Type2 Busy-State, Timeout Value Type2, P-Bit 
         Timeout Value, Retranmissions.  Fr each condition 
         there is an appropriate parameter to be included in the 
         notification."
    REFERENCE   
        "IEEE 802.2 (ISO/IEC 8802-3), lLCConnection2Event-N."
    ::= { llcNotifications 1 }

lLCClessACKEvent NOTIFICATION-TYPE
    OBJECTS     { tmnObjectInstance }
                -- type3Violation
                -- retransmissions
                -- noResponse
    STATUS      current
    DESCRIPTION 
        "This event will be sent for the following conditions: 
         Retransmission, NoResponse, Type3 Violation.  For each 
         condition, there is an appropriate parameter to be 
         included in the notification."
    REFERENCE   
        "IEEE 802.2 (ISO/IEC 8802-3), lLCClessACKEvent-N."
    ::= { llcNotifications 2 }

lLCStationEvent NOTIFICATION-TYPE
    OBJECTS     { tmnObjectInstance }
                -- pdusDiscarded
                -- bufferProblems
                -- ?? retransmissions
    STATUS      current
    DESCRIPTION 
        "This notification will be sent ofr either 
         pdusdiscarded, buffer problems, or Type 3 
         retransmissions."
    REFERENCE   
        "IEEE 802.2 (ISO/IEC 8802-3), lLCStationEvent-N."
    ::= { llcNotifications 3 }


-- =====================================================================
--
-- Groups

macBasicMandatoryGroup OBJECT-GROUP
    OBJECTS     { llcDiscontinuityTime, mACDLELocalSapNames, 
                  mACDLEProviderEntityNames, mACDLERowStatus, 
                  mACRowStatus, dLSAPSap1Address, dLSAPUserEntityNames, 
                  dLSAPRowStatus }
    STATUS      current
    DESCRIPTION 
        "This object group represents all of the management 
         aspects basic to the MAC, MAC data link entity and 
         DL-SAP.  Theses aspects are required whenever 
         MAC service is provided."
    ::= { llcGroups 1 }

llcBasicMandatoryGroup OBJECT-GROUP
    OBJECTS     { lLCDLELocalSapNames, lLCDLEProviderEntityNames, 
                  lLCDLERowStatus, lLCStationLLCName, 
                  lLCStationMaximumLSAPsConfigured, 
                  lLCStationNumberOfActiveLSAPs, 
                  lLCStationSupportedServicesTypes, lLCStationStatus, 
                  lLCStationType1AcknowledgeTimeoutValue, 
                  lLCStationType1MaximumRetryCount, 
                  lLCStationMaximumPDUN3, 
                  lLCStationMaximumRetransmissions4, 
                  lLCStationReceiveVariableLifetime, 
                  lLCStationTransmitVariableLifetime, 
                  lLCStationType3AcknowledgeTimeoutValue, 
                  lLCStationBufferSize, lLCStationSTRIndicator, 
                  lLCStationVersionNumber, lLCSAPAddress, lLCSAPRDE }
    STATUS      current
    DESCRIPTION 
        "This object group represents all of the management 
         aspects basic to the LLC, LLC data link entity, LLC 
         Station, and LLC-SAP.  These aspects are required 
         whenever LLC service is provided."
    ::= { llcGroups 2 }

llcBasicConditionalGroup OBJECT-GROUP
    OBJECTS     { resourceTypeIdName, resourceInfoManufacturerOUI, 
                  resourceInfoManufacturerName, 
                  resourceInfoManufacturerProductName, 
                  resourceInfoManufacturerProductVersion }
    STATUS      current
    DESCRIPTION 
        "This object group represents all of the management 
         aspects associated with the resource information 
         associated with the LLC station."
    ::= { llcGroups 3 }

llcBasicStatisticsGroup OBJECT-GROUP
    OBJECTS     { lLCStationAvgBufferUseSize, lLCStationBufferProblems, 
                  lLCStationMaxBufferUseSize, lLCStationInactiveLSAP, 
                  lLCStationPDUsDiscard }
    STATUS      current
    DESCRIPTION 
        "This object group represents all of the management 
         aspects associated with the statistics for LLC Station 
         operation."
    ::= { llcGroups 4 }

llcBasicNotificationGroup NOTIFICATION-GROUP
    NOTIFICATIONS { lLCStationEvent }
    STATUS      current
    DESCRIPTION 
        "This notification group represents Type 1, 2 or 3 
         operation and contains one notification which 
         corresponds to LLC station events."
    ::= { llcGroups 5 }

llcBasicParametersGroup OBJECT-GROUP
    OBJECTS     { pdusDiscarded, bufferProblems }
    STATUS      current
    DESCRIPTION 
        "This object group represents the notification 
         parameters which correspond to LLC Type 1 events."
    ::= { llcGroups 6 }

llcType1MandatoryGroup OBJECT-GROUP
    OBJECTS     { lLCCLPMOperationalState, lLCCLPMRowStatus, 
                  lLCConnectionlessName, 
                  lLCConnectionlessMaximumLLCInformationFieldSize }
    STATUS      current
    DESCRIPTION 
        "This object gorup represents all of the management 
         aspects of the LLC connectionless protocol machine and 
         LLC Type 1 operation.  These aspects are required 
         whenever LLC Type 1 service is provided."
    ::= { llcGroups 7 }

llcType1StatisticsGroup OBJECT-GROUP
    OBJECTS     { lLCStationType1AcknowledgmentTimerTimeouts, 
                  lLCCLPMTotalRemoteSAPs, 
                  lLCConnectionlessTESTReceivedABBResponse, 
                  lLCConnectionlessTESTReceivedCommand, 
                  lLCConnectionlessTESTReceivedResponse, 
                  lLCConnectionlessTESTSentABBResponse, 
                  lLCConnectionlessTESTSentCommand, 
                  lLCConnectionlessTESTSentResponse, 
                  lLCConnectionlessUIReceived, lLCConnectionlessUISent, 
                  lLCConnectionlessXIDReceivedCommand, 
                  lLCConnectionlessXIDReceivedResponse, 
                  lLCConnectionlessXIDSentCommand, 
                  lLCConnectionlessXIDSentResponse }
    STATUS      current
    DESCRIPTION 
        "This object group represents all of the management 
         aspects associated with statistics for LLC Type 1 
         operation."
    ::= { llcGroups 8 }

llcType2MandatoryGroup OBJECT-GROUP
    OBJECTS     { lLCCOPMRowStatus, lLCConnection2Name, 
                  lLCConnection2MaximumRetransmissions, 
                  lLCConnection2ReceivedWindowSize, 
                  lLCConnection2SendWindowSize, 
                  lLCConnection2AcknowledgeTimeoutValue, 
                  lLCConnection2BusyStateTimeoutValue, 
                  lLCConnection2PBitTimeoutValue, 
                  lLCConnection2RejectTimeoutValue, 
                  lLCConnection2ProtocolState }
    STATUS      current
    DESCRIPTION 
        "This object group represents all of the management 
         aspects of the LLC connection-oriented protocol machine 
         and LLC Type 2 operation.  These aspects are required 
         whenever LLC Type 2 service is provided."
    ::= { llcGroups 9 }

llcType2ConditionalGroup OBJECT-GROUP
    OBJECTS     { lLCConnection2Route, lLCConnection2KStep, 
                  lLCConnection2MaxSendWindowSize, 
                  lLCConnection2OptionalTolerationIPDUs }
    STATUS      current
    DESCRIPTION 
        "This object group represents all of the management 
         aspects of the conditional LLC Type 2 operation which 
         contains optional behaviour such as source routing, 
         flow control and toleration out of sequence I PDUs."
    ::= { llcGroups 10 }

llcType2StatisticsGroup OBJECT-GROUP
    OBJECTS     { lLCConnection2LocalBusy, lLCConnection2RemoteBusy, 
                  lLCConnection2RemoteReset, lLCConnection2LocalReset, 
                  lLCConnection2ProviderReset, lLCConnection2ReceivedI, 
                  lLCConnection2SentI, lLCConnection2SentAcks, 
                  lLCConnection2ReceivedAcks, lLCConnection2ReceivedFRMR, 
                  lLCConnection2SentFRMR, lLCConnection2ReceivedRR, 
                  lLCConnection2SentRR, lLCConnection2ReceivedRNR, 
                  lLCConnection2SentRNR, lLCConnection2ReceivedREJ, 
                  lLCConnection2SentREJ, lLCConnection2ReceivedSABME, 
                  lLCConnection2SentSABME, lLCConnection2ReceivedUA, 
                  lLCConnection2SentUA, lLCConnection2ReceivedDISC, 
                  lLCConnection2SentDISC, lLCConnection2ReceivedDM, 
                  lLCConnection2SentDM, lLCConnection2PDUsDiscarded1, 
                  lLCConnection2PDUsDiscarded2, 
                  lLCConnection2PDURetransmissions, 
                  lLCConnection2DuplicateIPDUsReceived, 
                  lLCConnection2Violation }
    STATUS      current
    DESCRIPTION 
        "This object group represents all of the management 
         aspects associated with statistics for LLC Type 2 
         operation."
    ::= { llcGroups 11 }

llcType2InitialValuesGroup OBJECT-GROUP
    OBJECTS     { lLCConnection2IVMOMaximumRetransmissions, 
                  lLCConnection2IVMOReceivedWindowSize, 
                  lLCConnection2IVMOSendWindowSize, 
                  lLCConnection2IVMOAcknowledgeTimeoutValue, 
                  lLCConnection2IVMOBusyStateTimeoutValue, 
                  lLCConnection2IVMOBitTimeoutValue, 
                  lLCConnection2IVMORejectTimeoutValue, 
                  lLCConnection2IVMORoute, lLCConnection2IVMOKStep, 
                  lLCConnection2IVMOMaxSendWindowSize, 
                  lLCConnection2IVMOOptionalTolerationIPDUs }
    STATUS      current
    DESCRIPTION 
        "This object group represents the intial values that can 
         be associated with an LLC Type 2 connection."
    ::= { llcGroups 12 }

llcType2InitialValueDefaultsGroup OBJECT-GROUP
    OBJECTS     { lLCConnection2DefaultMaximumRetransmissions, 
                  lLCConnection2DefaultReceivedWindowSize, 
                  lLCConnection2DefaultSendWindowSize, 
                  lLCConnection2DefaultAcknowledgeTimeoutValue, 
                  lLCConnection2DefaultBusyStateTimeoutValue, 
                  lLCConnection2DefaultPBitTimeoutValue, 
                  lLCConnection2DefaultRejectTimeoutValue, 
                  lLCConnection2DefaultRoute, lLCConnection2DefaultKStep, 
                  lLCConnection2DefaultMaxSendWindowSize, 
                  lLCConnection2DefaultOptionalTolerationIPDUs }
    STATUS      current
    DESCRIPTION 
        "This object group represents the objects that can be 
         used to specify defaults for the values associated with 
         the lLCConnection2IVMO managed object class.  These are 
         the default intial values for Type 2 connection 
         operation."
    REFERENCE   
        "IEEE 802.2 (ISO/IEC 8802-2) lLCConnection2IVMO."
    ::= { llcGroups 13 }

llcType2NotificationGroup NOTIFICATION-GROUP
    NOTIFICATIONS { lLCConnection2Event }
    STATUS      current
    DESCRIPTION 
        "This notification group represents Type 2 or 3 
         operation and contains one notification which 
         corresponds to LLC type 2 connection events."
    ::= { llcGroups 14 }

llcType2ParametersGroup OBJECT-GROUP
    OBJECTS     { pdusDiscarded1, pdusDiscarded2, pduRetransmissions, 
                  acknowledgeTimeout, busyStateTimeout, rejectTimeout, 
                  pBitTimeout, type2Violation, retranmissions }
    STATUS      current
    DESCRIPTION 
        "This object group represents the notification 
         parameters which correspond to LLC type 2 events."
    ::= { llcGroups 15 }

llcType2RDEConditionalGroup OBJECT-GROUP
    OBJECTS     { rDESetupAgingEnabled, rDESetupAgingValue, 
                  rDESetupEnableType2Reset, 
                  rDESetupMaximumRouteDescriptors, 
                  rDESetupMaximumResponseTime, rDESetupMinimumPDUSize, 
                  rDESetupRDEHold, rDESetupRDEReplace, rDESetupName, 
                  rDESetupResetOnTestEnabled, rDEPairDiscardCounter, 
                  rDEPairNSRPDUCounter, rDEPairNSRSelectedCounter, 
                  rDEPairRIF, rDEPairSRFPDUCounter, rDEPairQueryCounter }
    STATUS      current
    DESCRIPTION 
        "This object group represnts all of the management 
         aspects of the RDE.  These aspects are required 
         whenever the LLC RDE is required."
    ::= { llcGroups 16 }

llcType3MandatoryGroup OBJECT-GROUP
    OBJECTS     { lLCCOPMRowStatus, lLCConnectionlessAckName, 
                  lLCConnectionlessAckMaximumLLCInformationFieldSize, 
                  lLCConnectionlessAckMaximumRetransmissions }
    STATUS      current
    DESCRIPTION 
        "This object group represents all of the management 
         aspects of the LLC connection-oriented protocol machine 
         and LLC Type 3 operation.  These aspects are required 
         whenever LLC Type 3 service is provided."
    ::= { llcGroups 17 }

llcType3ConditionalGroup OBJECT-GROUP
    OBJECTS     { lLCConnectionlessAckReceiveResources }
    STATUS      current
    DESCRIPTION 
        "This object group represents all of the management 
         aspects of providing for LLC Type 3 operation."
    ::= { llcGroups 18 }

llcType3StatisticsGroup OBJECT-GROUP
    OBJECTS     { lLCStationType3Retransmissions, 
                  lLCConnectionlessAckTESTReceivedABBResponse, 
                  lLCConnectionlessAckTESTReceivedCommand, 
                  lLCConnectionlessAckTESTReceivedResponse, 
                  lLCConnectionlessAckTESTSentABBResponse, 
                  lLCConnectionlessAckTESTSentCommand, 
                  lLCConnectionlessAckTESTSentResponse, 
                  lLCConnectionlessAckUIReceived, 
                  lLCConnectionlessAckUISent, 
                  lLCConnectionlessAckXIDReceivedCommand, 
                  lLCConnectionlessAckXIDReceivedResponse, 
                  lLCConnectionlessAckXIDSentCommand, 
                  lLCConnectionlessAckXIDSentResponse, 
                  lLCConnectionlessAckRetransmissions, 
                  lLCConnectionlessAckNoResponse, 
                  lLCConnectionlessAckCommandIP, 
                  lLCConnectionlessAckCommandIT, 
                  lLCConnectionlessAckCommandOK, 
                  lLCConnectionlessAckCommandPE, 
                  lLCConnectionlessAckCommandRS, 
                  lLCConnectionlessAckCommandUE, 
                  lLCConnectionlessAckCommandUN, 
                  lLCConnectionlessAckReceivedACCommand, 
                  lLCConnectionlessAckSentACCommand, 
                  lLCConnectionlessAckResponseIP, 
                  lLCConnectionlessAckResponseIT, 
                  lLCConnectionlessAckResponseNE, 
                  lLCConnectionlessAckResponseNR, 
                  lLCConnectionlessAckResponseOK, 
                  lLCConnectionlessAckResponseRS, 
                  lLCConnectionlessAckResponseUE, 
                  lLCConnectionlessAckResponseUN, 
                  lLCConnectionlessAckViolation }
    STATUS      current
    DESCRIPTION 
        "This object group represents all of the management 
         aspects associated with statistics for LLC Type 3 
         operation."
    ::= { llcGroups 19 }

llcType3NotificationGroup NOTIFICATION-GROUP
    NOTIFICATIONS { lLCClessACKEvent }
    STATUS      current
    DESCRIPTION 
        "This notification group represents Type 3 operation and 
         contains one notification which corresponds to LLC TYpe 
         3 connection events."
    ::= { llcGroups 20 }

llcType3ParametersGroup OBJECT-GROUP
    OBJECTS     { type3Violation, retranmissions, noResponse }
    STATUS      current
    DESCRIPTION 
        "This object group represents the notification 
         parameters which correspond to LLC Type 3 events."
    ::= { llcGroups 21 }

llcType3IntialValuesGroup OBJECT-GROUP
    OBJECTS     { lLCConnectionlessAckIVMOMaximumLLCInformationFieldSize, 
                  lLCConnectionlessAckIVMOMaximumRetransmissions, 
                  lLCConnectionlessAckIVMORowStatus }
    STATUS      current
    DESCRIPTION 
        "This object group represents the initial values that 
         can be associated with an LLC Type 3 association."
    ::= { llcGroups 22 }

llcType3InitialValueDefaultsGroup OBJECT-GROUP
    OBJECTS     { 
                  lLCConnectionlessAckDefaultMaximumLLCInformationFieldSize, 
                  lLCConnectionlessAckDefaultMaximumRetransmissions }
    STATUS      current
    DESCRIPTION 
        "This object group represents the objects that can be 
         used to specify defaults for the values associated with 
         the llCConnectionlessAckIVMO managed object class.  
         THese are the default initial values for Type 3 
         connection operaiton."
    REFERENCE   
        "IEEE 802.2 (ISO/IEC 8802-2) lLCConnectionlessAckIVMO."
    ::= { llcGroups 23 }

-- llcTmnAlarmNotificationGroup NOTIFICATION-GROUP
--      NOTIFICATIONS {
--              communicationsAlarm
--      }
--      STATUS          current
--      DESCRIPTION 
--              "This notification group represents TMN style 
--               communication alarm operations.  It is required when 
--               the TMN-like aspects of the MIB are supported."
--      REFERENCE   
--              "ITU-T Rec. X.723 | ISO/IEC 10165-5."
--      ::= { llcGroups 24 }

llcTmnStateGroup OBJECT-GROUP
    OBJECTS     { mACDLEOperationalState, mACOperationalState, 
                  lLCDLEOperationalState, lLCCLPMOperationalState, 
                  lLCCOPMOperationalState, 
                  lLCConnection2OperationalState, 
                  lLCConnection2AdministrativeState, 
                  lLCConnection2UsageState, 
                  lLCConnection2ProceduralStatus, 
                  lLCConnection2AlarmStatus }
    STATUS      current
    DESCRIPTION 
        "This object group represents the TMN style state and 
         status objects associated wtih the MIB.  It is required 
         when TMN-like aspects of the MIB are supported."
    REFERENCE   
        "ITU-T Rec. X.721 | ISO/IEC 10165-2."
    ::= { llcGroups 25 }

-- =====================================================================
--
-- Compliances

llcMIBCompliance MODULE-COMPLIANCE
    STATUS      current
    DESCRIPTION 
        "Provides the module compliance requirements for the LLC 
         MIB."
    REFERENCE   
        "ITU-T Rec. X.282 | ISO/IEC 10742, IEEE 802.2 (ISO/IEC 8802-2)."

    MODULE      -- this module

        MANDATORY-GROUPS        { macBasicMandatoryGroup, 
                  llcBasicMandatoryGroup, llcType1MandatoryGroup, 
                  llcType2MandatoryGroup, llcType3MandatoryGroup }

        GROUP   llcBasicConditionalGroup
        DESCRIPTION   
              "Required when the implementation supports 
               LLC Type 1, 2 or 3 operation and supports the resource 
               type identification."

        GROUP   llcBasicStatisticsGroup
        DESCRIPTION   
              "Requires when the implementation supports LLC 
               Type 1, 2 or 3 operation and supports basic 
               statistics."

        GROUP   llcBasicNotificationGroup
        DESCRIPTION   
              "Required when the implementation supports 
               LLC Type 1, 2 or 3 operation and supports 
               lLCStationEvent notifications."

        GROUP   llcBasicParametersGroup
        DESCRIPTION   
              "Required when the implementation supports 
               LLC Type 1, 2 or 3 operation and supports 
               lLCStationEvent notifications."

        GROUP   llcType1StatisticsGroup
        DESCRIPTION   
              "Required when the implementation supports 
               LLC Type 1 operation and supports LLC Type 1 
               statistics."

        GROUP   llcType2ConditionalGroup
        DESCRIPTION   
              "Required when the implementation supports LLC 
               Type 2 operation."

        GROUP   llcType2StatisticsGroup
        DESCRIPTION   
              "Required when the implementation supports LLC 
               Type 2 statistics."

        GROUP   llcType2NotificationGroup
        DESCRIPTION   
              "Required when the implementation supports 
               LLC Type 2 or 3 operation and supports 
               lLCConnection2Event notifications."

        GROUP   llcType2ParametersGroup
        DESCRIPTION   
              "Required when the implementation supports 
               LLC Type 2 or 3 operation and suports 
               lLCConnection2Event notifications."

        GROUP   llcType2RDEConditionalGroup
        DESCRIPTION   
              "Required when the implementation supports LLC 
               Type 2 operation and supports RDE."

        GROUP   llcType2InitialValuesGroup
        DESCRIPTION   
              "Required when the implementation supports 
               LLC Type 2 or 3 operation and the setting of initial 
               values is possible."

        GROUP   llcType2InitialValueDefaultsGroup
        DESCRIPTION   
              "Required when the implementation supports 
               LLC Type 2 or 3 operation and the setting of default 
               intial values is possible."

        GROUP   llcType3ConditionalGroup
        DESCRIPTION   
              "Required when the implementation supports 
               LLC Type 3 operation."

        GROUP   llcType3StatisticsGroup
        DESCRIPTION   
              "Required when the implementation supports 
               LLC TYpe 3 operation and the collection of statistics is 
               supported."

        GROUP   llcType3NotificationGroup
        DESCRIPTION   
              "Required when the implementation supports 
               LLC Type 3 operation."

        GROUP   llcType3ParametersGroup
        DESCRIPTION   
              "Required when the implementation supports LLC 
               Type 3 operation and supports corresponding 
               notifications."

        GROUP   llcType3IntialValuesGroup
        DESCRIPTION   
              "Required when the implementation supports 
               LLC Type 3 operation and supports the setting of initial 
               values."

        GROUP   llcType3InitialValueDefaultsGroup
        DESCRIPTION   
              "Mandatory only where LLC Type 3 is 
               supported and the setting of default intial values is 
               possible."

        GROUP   llcTmnStateGroup
        DESCRIPTION   
              "Mandatory where the operational state, 
               administrative state, usage state, procedural status and 
               alarm status may be reported, along with the 
               communicationsAlarm notification."

        OBJECT  llcDiscontinuityTime
        MIN-ACCESS  read-only
        DESCRIPTION   
              "This scalar provides the last time 
               that a discontinuity in any of the Counter32 or 
               Counter64 values occured which may have resulted 
               in the reset or other discontinuity in value of 
               counters represented by those textual 
               conventions.  This scalar must be implemented.  
               When no Counter32 or Counter64 objects are 
               implemented, this value can always return zero."

        OBJECT  mACDLELocalSapNames
        MIN-ACCESS  read-only
        DESCRIPTION   
              "This object may be read-only, or 
               may only permit being written as part of a row 
               creation action and then read-only after that."

        OBJECT  mACDLEProviderEntityNames
        MIN-ACCESS  read-only
        DESCRIPTION   
              "This object may be read-only, or 
               may only permit being wirtten as part of a row 
               creation action and then read-only after that."

        OBJECT  mACDLERowStatus
        MIN-ACCESS  read-only
        DESCRIPTION   
              "Agents are not required to support 
               row creation or deletion by management stations.  
               In the case that management stations are not 
               permitted to create or delete conceptual rows in 
               the mACDLE table, this column will have an 
               access of read-only."

        OBJECT  mACRowStatus
        MIN-ACCESS  read-only
        DESCRIPTION   
              "Agents are not required to support 
               row creation and deletion by management 
               stations.  In the case that management stations 
               are not permitted to create or delete conceptual 
               rows in the mAC table, this column will have an 
               access of read-only."

        OBJECT  dLSAPSap1Address
        MIN-ACCESS  read-only
        DESCRIPTION   
              "Because the dLSAPSap1Address is 
               local, it could also be the same as the 
               dLSAPSapId, where the dLSAPSapId represents an 
               integer value."

        OBJECT  dLSAPUserEntityNames
        MIN-ACCESS  read-only
        DESCRIPTION   
              "It is optional to provide the user 
               entity names.  In many cases, the user entity 
               names may be unknown, in which case this column 
               returns the value zeroDotZero on a GET 
               operation."

        OBJECT  dLSAPRowStatus
        MIN-ACCESS  read-only
        DESCRIPTION   
              "Agents are not required to support 
               row creation and deletion by management 
               stations.  In the case that management stations 
               are not permitted to creat or delete conceptual 
               rows in the dLSAP table, this column will have 
               an access of read-only."

        OBJECT  lLCConnection2Route
        DESCRIPTION   
              "This object is required if source 
               routing is supported and the LLC Type 2 
               connection can know its own source route."

        OBJECT  lLCConnection2KStep
        DESCRIPTION   
              "This object is required if flow 
               control on LLC Type 2 connections is performed."

        OBJECT  lLCConnection2MaxSendWindowSize
        DESCRIPTION   
              "This object is required if flow 
               control on LLC Type 2 connections is performed."

        OBJECT  lLCConnection2OptionalTolerationIPDUs
        DESCRIPTION   
              "This object is required if 
               toleration of out-of-sequence I PDUs is 
               supported as an option."

        OBJECT  lLCConnection2LocalBusy
        DESCRIPTION   
              "This object is required if LLC Type 
               2 connection busy is supported."

        OBJECT  lLCConnection2RemoteBusy
        DESCRIPTION   
              "This object is required if LLC Type 
               2 connection busy is supported."

        OBJECT  lLCConnection2RemoteReset
        DESCRIPTION   
              "This object is required if LLC Type 
               2 connection reset is supported."

        OBJECT  lLCConnection2LocalReset
        DESCRIPTION   
              "This object is required if LLC Type 
               2 connection reset is supported."

        OBJECT  lLCConnection2ProviderReset
        DESCRIPTION   
              "This object is required if LLC Type 
               2 connection reset is supported."

        OBJECT  lLCConnection2ReceivedI
        DESCRIPTION   
              "This object is required if LLC Type 
               2 I frame counting is supported."

        OBJECT  lLCConnection2SentI
        DESCRIPTION   
              "This object is required if LLC Type 
               2 I frame counting is supported."

        OBJECT  lLCConnection2SentAcks
        DESCRIPTION   
              "This object is required if LLC Type 
               2 Acknowledgement counting is supported."

        OBJECT  lLCConnection2ReceivedAcks
        DESCRIPTION   
              "This object is required if LLC Type 
               2 Acknowledgement counting is supported."

        OBJECT  lLCConnection2ReceivedFRMR
        DESCRIPTION   
              "This object is required if LLC Type 
               2 FRMR frame counting is supported."

        OBJECT  lLCConnection2SentFRMR
        DESCRIPTION   
              "This object is required if LLC Type 
               2 FRMR frame counting is supported."

        OBJECT  lLCConnection2ReceivedRR
        DESCRIPTION   
              "This object is required if LLC Type 
               2 RR frame counting is supported."

        OBJECT  lLCConnection2SentRR
        DESCRIPTION   
              "This object is required if LLC Type 
               2 RR frame counting is supported."

        OBJECT  lLCConnection2ReceivedRNR
        DESCRIPTION   
              "This object is required if LLC Type 
               2 RNR frame counting is supported."

        OBJECT  lLCConnection2SentRNR
        DESCRIPTION   
              "This object is required if LLC Type 
               2 RNR frame counting is supported."

        OBJECT  lLCConnection2ReceivedREJ
        DESCRIPTION   
              "This object is required if LLC Type 
               2 REJ frame counting is supported."

        OBJECT  lLCConnection2SentREJ
        DESCRIPTION   
              "This object is required if LLC Type 
               2 REJ frame counting is supported."

        OBJECT  lLCConnection2ReceivedSABME
        DESCRIPTION   
              "This object is required if LLC Type 
               2 SABME frame counting is supported."

        OBJECT  lLCConnection2SentSABME
        DESCRIPTION   
              "This object is required if LLC Type 
               2 SABME frame counting is supported."

        OBJECT  lLCConnection2ReceivedUA
        DESCRIPTION   
              "This object is required if LLC Type 
               2 UA frame counting is supported."

        OBJECT  lLCConnection2SentUA
        DESCRIPTION   
              "This object is required if LLC Type 
               2 UA frame counting is supported."

        OBJECT  lLCConnection2ReceivedDISC
        DESCRIPTION   
              "This object is required if LLC Type 
               2 DISC frame counting is supported."

        OBJECT  lLCConnection2SentDISC
        DESCRIPTION   
              "This object is required if LLC Type 
               2 DISC frame counting is supported."

        OBJECT  lLCConnection2ReceivedDM
        DESCRIPTION   
              "This object is required if LLC Type 
               2 DM frame counting is supported."

        OBJECT  lLCConnection2SentDM
        DESCRIPTION   
              "This object is required if LLC Type 
               2 DM frame counting is supported."

        OBJECT  lLCConnection2PDUsDiscarded1
        DESCRIPTION   
              "This object is required if LLC Type 
               2 PDU discard 1  counting or lLCConnection2Event 
               notifications are supported."

        OBJECT  lLCConnection2PDUsDiscarded2
        DESCRIPTION   
              "This object is required if LLC Type 
               2 PDU discard 2  counting or lLCConnection2Event 
               notifications are supported."

        OBJECT  lLCConnection2PDURetransmissions
        DESCRIPTION   
              "This object is required if LLC Type 
               2 PDU retransmission counting or 
               lLCConnection2Event notifications are 
               supported."

        OBJECT  lLCConnection2DuplicateIPDUsReceived
        DESCRIPTION   
              "This object is required if LLC Type 
               2 duplicate PDUs received counting or 
               lLCConnection2Event notifications are 
               supported."

        OBJECT  lLCConnection2Violation
        DESCRIPTION   
              "This object is required if LLC Type 
               2 violations counting or lLCConnection2Event 
               notifications are supported."

        OBJECT  lLCConnection2DefaultRoute
        DESCRIPTION   
              "When the default route conditional 
               package is provided."

        OBJECT  lLCConnection2DefaultKStep
        DESCRIPTION   
              "When the flow control conditional 
               package is provided."

        OBJECT  lLCConnection2DefaultMaxSendWindowSize
        DESCRIPTION   
              "When the flow control conditional 
               package is provided."

        OBJECT  lLCConnection2DefaultOptionalTolerationIPDUs
        DESCRIPTION   
              "When the optional toleration of out 
               of order I PDUs is provided."

        OBJECT  mACDLEOperationalState
        MIN-ACCESS  read-only
        DESCRIPTION   
              "When provided, must reflect the 
               operational state of the MAC data link entity."

        OBJECT  mACOperationalState
        MIN-ACCESS  read-only
        DESCRIPTION   
              "When provided, must reflect the 
               operational state of the MAC."

        OBJECT  lLCDLEOperationalState
        MIN-ACCESS  read-only
        DESCRIPTION   
              "When provided, must reflect the 
               operational state of the LLC data link entity."

        OBJECT  lLCCLPMOperationalState
        MIN-ACCESS  read-only
        DESCRIPTION   
              "When provided, must reflect the 
               operational state of the LLC connectionless 
               protocol machine."

        OBJECT  lLCCOPMOperationalState
        MIN-ACCESS  read-only
        DESCRIPTION   
              "When provided, must reflect the 
               operational state of the LLC connection oriented 
               protocol machine."

        OBJECT  lLCConnection2OperationalState
        MIN-ACCESS  read-only
        DESCRIPTION   
              "When provided, must reflect the 
               operational state of the LLC connection."

        OBJECT  lLCConnection2AdministrativeState
        MIN-ACCESS  read-write
        DESCRIPTION   
              "When provided, must reflect and 
               allow control of the administrative state of the 
               LLC connection.  When unlocked, the connection 
               is permitted to form and carry traffic.  When 
               shuttingDown, the connection is not permitted to 
               reform, but is permitted to persist until there 
               are no longer any users of the connection.  When 
               locked, the connection is administratively 
               prohibited from performing services and is 
               disconnected."

        OBJECT  lLCConnection2UsageState
        MIN-ACCESS  read-only
        DESCRIPTION   
              "When provided, must reflect the 
               usage state of the LLC connection.  LLC 
               connection objects may exist for a duration of 
               time even when they are not in use by any user 
               entity (e.g.  network layer).  When idle(0), the 
               connection is not being used by any data link 
               user.  When active(1), the connection is 
               actively being used by a data link user.  When 
               busy(2), the connection is in use but is flow 
               controlled."

        OBJECT  lLCConnection2ProceduralStatus
        MIN-ACCESS  read-only
        DESCRIPTION   
              "When provided, must reflect the 
               procedural status of the LLC connection.  
               initializationRequired() is not used and does 
               not occur.  notInitialized() occurs when the 
               connection requires initialization but that 
               initialization has not yet been initiated.  
               initializing() is present when the connection is 
               forming (SABME sent or received).  terminating() 
               is presnet when the connection is termianting 
               (DM or DISC sent or received)."

        OBJECT  lLCConnection2AlarmStatus
        MIN-ACCESS  read-write
        DESCRIPTION   
              "Values that may be added to the set 
               are underRepair(0).  Values that may be removed 
               from the set are critical(1), major(2), 
               minor(3), alarmOutstanding(4)."

    ::= { llcCompliances 1 }

END -- end of module OPENSS7-LLC2-MIB.
