-- vim: ft=mib comments=\f\:\",\b\:\-\-,\:\-\-,\f\b\:- fo+=tcqlornw tw=72 nocin nosi sts=4 sw=4
-- =============================================================================
-- 
-- @(#) src/mibs/ATMF-CES-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

ATMF-CES-MIB DEFINITIONS ::= BEGIN

IMPORTS
    ifIndex
        FROM IF-MIB
    Counter32, Integer32, MODULE-IDENTITY, OBJECT-TYPE, enterprises
        FROM SNMPv2-SMI
    TEXTUAL-CONVENTION
        FROM SNMPv2-TC;

atmfDS1E1CESmib MODULE-IDENTITY
    LAST-UPDATED "199502030000Z"
    ORGANIZATION 
        "ATM Forum Circuit Emulation Working Group"
    CONTACT-INFO 
        "fedorkow@cisco.com, myron@kentrox.com"
    DESCRIPTION 
        "This MIB module is deprecated, and is being replaced by the 
         atmfCES module as a more generic Circuit emulation MIB.
         
         The MIB module to describe the DS1/E1 Circuit Emulation 
         Interworking Function (Version 1.0)"
    REVISION    "199502030000Z"
    DESCRIPTION 
        "Initial version of this module."
    ::= { atmfCESmib 1 }

-- an OBJECT IDENTIFIER for all ATM Forum circuit emulation MIBs has 
-- been assigned as a branch from the Forum Network Management tree.  
-- The DS1/E1 Circuit Emulation specification is attached as the 
-- first branch from the overall atmfCESmib object.  Future branches 
-- may be added in the future for further CES work, for example, 
-- DS3/E3 circuit emulation.

-- this is the MIB moudle for the ATM Form DS1/E1 Circuit Emulation 
-- Interworking Function objects

-- the following TEXTUAL-CONVENTIONS are used to link the CES 
-- interworking funciton to ATM interface port, plus the associated 
-- VPI and VCI.

VpiInteger ::= TEXTUAL-CONVENTION
    STATUS      deprecated
    DESCRIPTION 
        "An integer large enough to hold a VPI"
    SYNTAX      Integer32 (0..4095)

VciInteger ::= TEXTUAL-CONVENTION
    STATUS      deprecated
    DESCRIPTION 
        "An integer large enough to hold a VCI"
    SYNTAX      Integer32 (0..65535)

CESConnectionPort ::= TEXTUAL-CONVENTION
    STATUS      deprecated
    DESCRIPTION 
        "Indicates the port associated with a Circuit Emulation 
         connection.
         Objects of this type are always define as part of a set that 
         includes
         
            fooPort CESConnectionPort
            fooVPI  VpiInteger
            fooVCI  VciInteger
         
         The interpretation of these objects is as follows:
         
         1. If no connection exists, fooPort' has a value of 0.  Because 
            Interfaces table entries always have ifIndex' values greater 
            than 0, fooPort' reliably serves as a connection exists' 
            flag.
         
            If no connection exists, fooVPI' and fooVCI' are meaningless 
            and have a value of 0.
         
         2. If a PVC or SVC exists, fooPort is defined to have the value 
            of the MIB-II/RFC1573 ifIndex' of the ATM interface 
            associated with the VCC. fooVPI' and fooVCI' will contain 
            its VPI/VCI."
    SYNTAX      Integer32 (0..2147483647)

atmForum OBJECT IDENTIFIER
    ::= { enterprises 353 }

atmForumNetworkManagement OBJECT IDENTIFIER
    ::= { atmForum 5 }

atmfCESmib OBJECT IDENTIFIER
    ::= { atmForumNetworkManagement 2 }

atmfDS1E1CESmibObjects OBJECT IDENTIFIER
    ::= { atmfDS1E1CESmib 1 }

atmfDS1E1CESConfTable OBJECT-TYPE
    SYNTAX      SEQUENCE OF AtmfDS1E1CESConfEntry
    MAX-ACCESS  not-accessible
    STATUS      deprecated
    DESCRIPTION 
        "The CES configuration table. This includes mapping channels 
         from ATM Port to CBR interfaces. There is one 
         AtmfDS1E1CESConfEntry per CES Entity"
    ::= { atmfDS1E1CESmibObjects 1 }

atmfDS1E1CESConfEntry OBJECT-TYPE
    SYNTAX      AtmfDS1E1CESConfEntry
    MAX-ACCESS  not-accessible
    STATUS      deprecated
    DESCRIPTION 
        "An entry in the CES table. For each entry there is a 
         corresponding entry in the stack table"
    INDEX       { ifIndex }
    ::= { atmfDS1E1CESConfTable 1 }

AtmfDS1E1CESConfEntry ::= SEQUENCE {
    atmfDS1E1CESMapATMIndex                 CESConnectionPort,
    atmfDS1E1CESMapVPI                      VpiInteger,
    atmfDS1E1CESMapVCI                      VciInteger,
    atmfDS1E1CESCBRService                  INTEGER,
    atmfDS1E1CESCBRClockMode                INTEGER,
    atmfDS1E1CESCas                         INTEGER,
    atmfDS1E1CESPartialFill                 Integer32,
    atmfDS1E1CESBufMaxSize                  Integer32,
    atmfDS1E1CESCDVRxT                      Integer32,
    atmfDS1E1CESCellLossIntegrationPeriod   Integer32
}

atmfDS1E1CESMapATMIndex OBJECT-TYPE
    SYNTAX      CESConnectionPort
    MAX-ACCESS  read-only
    STATUS      deprecated
    DESCRIPTION 
        "The value of this object is equal to MIB II's ifIndex value of the 
         ATM Port interface mapped through this CES to a CBR interface."
    ::= { atmfDS1E1CESConfEntry 1 }

atmfDS1E1CESMapVPI OBJECT-TYPE
    SYNTAX      VpiInteger
    MAX-ACCESS  read-only
    STATUS      deprecated
    DESCRIPTION 
        "The value of this object is equal to the VPI used for the 
         emulated circuit represented by this entry in the ifTable. If 
         there is no connection, this object is meaningless and will 
         have the value zero."
    ::= { atmfDS1E1CESConfEntry 2 }

atmfDS1E1CESMapVCI OBJECT-TYPE
    SYNTAX      VciInteger
    MAX-ACCESS  read-only
    STATUS      deprecated
    DESCRIPTION 
        "The value of this object is equal to the VCI used for the 
         emulated circuit represented by this entry in the ifTable. If 
         there is no connection, this object is meaningless and will 
         have the value zero"
    ::= { atmfDS1E1CESConfEntry 3 }

atmfDS1E1CESCBRService OBJECT-TYPE
    SYNTAX      INTEGER { unstructured(1), structured(2) }
    MAX-ACCESS  read-write
    STATUS      deprecated
    DESCRIPTION 
        "Define if DS1/E1 service as structured or not. A structured(2) 
         interface is some nx64Kbps. An unstructured (1) interface is 
         1.544Mbps or 2.048Mbps. Unstructured(1) passes all bits through 
         the ATM network.  strucutured(2) passes data bits through the 
         ATM network, and may also pass signalling bits"
    ::= { atmfDS1E1CESConfEntry 4 }

atmfDS1E1CESCBRClockMode OBJECT-TYPE
    SYNTAX      INTEGER { synchronous(1), srts(2), adaptive(3) }
    MAX-ACCESS  read-write
    STATUS      deprecated
    DESCRIPTION 
        "Define if DS1/E1 service clocking mode. This maps into transmit 
         clock source of CBR interface."
    DEFVAL      { synchronous }
    ::= { atmfDS1E1CESConfEntry 5 }

atmfDS1E1CESCas OBJECT-TYPE
    SYNTAX      INTEGER { basic(1), e1Cas(2), ds1SfCas(3), ds1EsfCas(4) }
    MAX-ACCESS  read-write
    STATUS      deprecated
    DESCRIPTION 
        "This parameter selects which AAL1 Format should be used: Basic 
         does not carry CAS bits, and uses a single 125 usec frame.  
         e1Cas, ds1SfCas and dS1EsfCas carry CAS bits in a multiframe 
         structure for E1, DS1 SF and DS1 ESF respectively.  This 
         applies to structured interfaces only. Default is basic (1)."
    DEFVAL      { basic }
    ::= { atmfDS1E1CESConfEntry 6 }

atmfDS1E1CESPartialFill OBJECT-TYPE
    SYNTAX      Integer32 (0..47)
    MAX-ACCESS  read-write
    STATUS      deprecated
    DESCRIPTION 
        "If partial cell fill is used, the number of user octets per 
         cell must be set with this parameter. Setting this parameter to 
         zero disables partial cell fill, and causes all cells to be 
         completely filled before they are sent."
    DEFVAL      { 0 } -- Partial Cell Fill not used
    ::= { atmfDS1E1CESConfEntry 7 }

atmfDS1E1CESBufMaxSize OBJECT-TYPE
    SYNTAX      Integer32 (1..65536)
    MAX-ACCESS  read-write
    STATUS      deprecated
    DESCRIPTION 
        "Define maximum size in octets of the reassembly buffer.  Some 
         implementations may want allow the maximum buffer size to 
         programmed to a size less than the physical limit to reduce the 
         maximum delay through a circuit."
    DEFVAL      { 256 }
    ::= { atmfDS1E1CESConfEntry 8 }

atmfDS1E1CESCDVRxT OBJECT-TYPE
    SYNTAX      Integer32 (1..65535)
    UNITS       "10 usec"
    MAX-ACCESS  read-write
    STATUS      deprecated
    DESCRIPTION 
        "The maximum cell arrival jitter in 10 usec increments that the 
         reassembly process will tolerate in the cell stream without 
         producing errors on the CBR service interface."
    DEFVAL      { 100 }
    ::= { atmfDS1E1CESConfEntry 9 }

atmfDS1E1CESCellLossIntegrationPeriod OBJECT-TYPE
    SYNTAX      Integer32 (1000..65535)
    UNITS       "msec"
    MAX-ACCESS  read-write
    STATUS      deprecated
    DESCRIPTION 
        "The time in milliseconds for the cell loss integration period.  
         If a cells are lost for this period of time.  
         atmfDS1E1CESCellLossStatus is set to loss (2).The current 
         definition is 2500."
    DEFVAL      { 2500 }
    ::= { atmfDS1E1CESConfEntry 10 }

atmfDS1E1CESStatsTable OBJECT-TYPE
    SYNTAX      SEQUENCE OF AtmfDS1E1CESStatsEntry
    MAX-ACCESS  not-accessible
    STATUS      deprecated
    DESCRIPTION 
        "The CES AAL1 statistical data table."
    ::= { atmfDS1E1CESmibObjects 2 }

atmfDS1E1CESStatsEntry OBJECT-TYPE
    SYNTAX      AtmfDS1E1CESStatsEntry
    MAX-ACCESS  not-accessible
    STATUS      deprecated
    DESCRIPTION 
        "An entry in the CES AAL1 Stats table."
    INDEX       { ifIndex }
    ::= { atmfDS1E1CESStatsTable 1 }

AtmfDS1E1CESStatsEntry ::= SEQUENCE {
    atmfDS1E1CESReassCells          Counter32,
    atmfDS1E1CESHdrErrors           Counter32,
    atmfDS1E1CESPointerReframes     Counter32,
    atmfDS1E1CESLostCells           Counter32,
    atmfDS1E1CESBufUnderflows       Counter32,
    atmfDS1E1CESBufOverflows        Counter32,
    atmfDS1E1CESCellLossStatus      INTEGER
}

atmfDS1E1CESReassCells OBJECT-TYPE
    SYNTAX      Counter32
    MAX-ACCESS  read-only
    STATUS      deprecated
    DESCRIPTION 
        "This count gives the number of cells played out to the DS1/E1 
         Service Interface. It excludes cells that were discarded for 
         any reason, including cells that were not used due to being 
         declared misinserted, or discarded while the reassembler was 
         waiting to achieve synchronization."
    ::= { atmfDS1E1CESStatsEntry 1 }

atmfDS1E1CESHdrErrors OBJECT-TYPE
    SYNTAX      Counter32
    MAX-ACCESS  read-only
    STATUS      deprecated
    DESCRIPTION 
        "The count of the number of AAL1 header errors detected and 
         possibly corrected. Header errors include correctable and 
         uncorrectable CRC, plus bad parity."
    ::= { atmfDS1E1CESStatsEntry 2 }

atmfDS1E1CESPointerReframes OBJECT-TYPE
    SYNTAX      Counter32
    MAX-ACCESS  read-only
    STATUS      deprecated
    DESCRIPTION 
        "This records the count of the number of events in which the 
         AAL1 reassembler found that an SDT pointer is not where it is 
         expected, and the pointer must be reacquired."
    ::= { atmfDS1E1CESStatsEntry 3 }

atmfDS1E1CESLostCells OBJECT-TYPE
    SYNTAX      Counter32
    MAX-ACCESS  read-only
    STATUS      deprecated
    DESCRIPTION 
        "Number of lost cells."
    ::= { atmfDS1E1CESStatsEntry 4 }

atmfDS1E1CESBufUnderflows OBJECT-TYPE
    SYNTAX      Counter32
    MAX-ACCESS  read-only
    STATUS      deprecated
    DESCRIPTION 
        "Number of buffer underflows."
    ::= { atmfDS1E1CESStatsEntry 5 }

atmfDS1E1CESBufOverflows OBJECT-TYPE
    SYNTAX      Counter32
    MAX-ACCESS  read-only
    STATUS      deprecated
    DESCRIPTION 
        "Number of buffer overflows."
    ::= { atmfDS1E1CESStatsEntry 6 }

atmfDS1E1CESCellLossStatus OBJECT-TYPE
    SYNTAX      INTEGER { noLoss(1), loss(2) }
    MAX-ACCESS  read-only
    STATUS      deprecated
    DESCRIPTION 
        "When cells are lost for the number of milliseconds specified by 
         atmfDS1E1CESCellLossIntegrationPeriod, the value is set to loss 
         (2). When cells are no longer lost, the value is set to noLoss 
         (1)."
    ::= { atmfDS1E1CESStatsEntry 7 }

END -- end of module ATMF-CES-MIB.

-- vim: ft=mib comments=\f\:\",\b\:\-\-,\:\-\-,\f\b\:- fo+=tcqlornw tw=72 nocin nosi sts=4 sw=4 et
