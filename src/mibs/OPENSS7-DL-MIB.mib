-- vim: ft=mib comments=\f\b\:\"ITU\-T,\f\b\:ITU\-T,\f\:\",\b\:\-\-,\:\-\-,\f\b\:\-,\f\b\:\· fo+=tcqlornw12 tw=72 ai nocin nosi sts=4 sw=4 et
-- =============================================================================
-- 
-- @(#) src/mibs/OPENSS7-DL-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-DL-MIB DEFINITIONS ::= BEGIN

IMPORTS
    openss7Modules
        FROM OPENSS7-SMI
    AdministrativeState, AlarmStatus, OperationalState, ProceduralStatus, 
    SimpleNameType, UsageState, tmnObjectInstance
        FROM OPENSS7-SMI-MIB
    MODULE-COMPLIANCE, NOTIFICATION-GROUP, OBJECT-GROUP
        FROM SNMPv2-CONF
    Counter32, Gauge32, Integer32, MODULE-IDENTITY, NOTIFICATION-TYPE, 
    OBJECT-IDENTITY, OBJECT-TYPE, Unsigned32
        FROM SNMPv2-SMI
    DisplayString, RowPointer, RowStatus, TEXTUAL-CONVENTION, 
    TimeInterval, TimeStamp, TruthValue
        FROM SNMPv2-TC
    Float
        FROM UCD-SNMP-MIB;

dlMIB MODULE-IDENTITY
    LAST-UPDATED "201112101120Z"
    ORGANIZATION 
        "The OpenSS7 Project"
    CONTACT-INFO 
        "Brian Bidulock
         OpenSS7 Corporation
         1469 Jefferys Crescent
         Edmonton, Alberta  T6L 6T1
         CANADA
         Tel: +1 780 490 1141
         Fax: +1 780 490 1241
         Mob: +1 780 953 0557
         mailto:bidulock@openss7.org"
    DESCRIPTION 
        "Provides a management information base for LAPB from 
         ITU-T Rec.  X.25 | ISO/IEC 8208, LLC1/LLC2 from IEEE 
         802.2 (ISO/IEC 8802-2) based on ITU-T Rec. X.282 | 
         ISO/IEC 10742.
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201112101120Z"
    DESCRIPTION 
        "Corrections an smilint workup."
    REVISION    "201106280801Z"
    DESCRIPTION 
        "Passes smilint and reformatted with smidump."
    REVISION    "200712170903Z"
    DESCRIPTION 
        "First release of this module."
    ::= { openss7Modules 212 }


-- =====================================================================
--
-- Textual Conventions

DummySyntax ::= TEXTUAL-CONVENTION
    DISPLAY-HINT "1x"
    STATUS      current
    DESCRIPTION 
        "This textual convention is just a dummy syntax as a place 
         holder for something more complex to be added later."
    SYNTAX      OCTET STRING

DTEAddress ::= TEXTUAL-CONVENTION
    DISPLAY-HINT "1d"
    STATUS      current
    DESCRIPTION 
        "This textual convention represents a DTE address.  Per ISO/IEC 
         10733, a DTE address is a numeric string of up to 15 digits.  
         Therefore, this textual convention describes an OCTET STRING 
         where the contents of each octet is the printable (ASCII) digit 
         from 0 to 9.  The OCTET STRING can be a maximum length of 15 
         digits."
    SYNTAX      OCTET STRING (SIZE(0..15))

LLCServices ::= TEXTUAL-CONVENTION
    STATUS      current
    DESCRIPTION 
        "This textual convention represents the LLC services the are 
         available or selected.  Per ISO/IEC 8802-2, the services are 
         type1(0), type2(1), type3Initiate(2), type3ReceiveData(3) and 
         type3ReturnData(4)."
    REFERENCE   
        "IEEE 802.2 | ISO/IEC 8802-2 ASN.1, LLCServices."
    SYNTAX      BITS { type1(0), type2(1), type3Initiate(2), 
                    type3ReceiveData(3), type3ReturnData(4) }

LLCStationStatus ::= TEXTUAL-CONVENTION
    STATUS      current
    DESCRIPTION 
        "This textual convetion represents the status of an LLC station.  
         Per ISO/IEC 8802-2, the status can be up(0), down(1), or other 
         (2)."
    REFERENCE   
        "IEEE 802.2 | ISO/IEC 8802-2 ASN.1, Status."
    SYNTAX      INTEGER { up(0), down(1), other(2) }

STRIndicator ::= TEXTUAL-CONVENTION
    STATUS      current
    DESCRIPTION 
        "This textual convention indicates the type of source routed MAC 
         bridging per ISO/IEC 8802-2 (IEEE 802.2), the types are nsr(0) 
         or ste(1)."
    SYNTAX      BITS { nsr(0), ste(1) }

LSAP ::= TEXTUAL-CONVENTION
    DISPLAY-HINT "1x"
    STATUS      current
    DESCRIPTION 
        "This textual convention represents an LLC LSAP which consists 
         of a 1-octet value which contains the LLC LSAP.  Note that 
         technically the LSAP could be continued into subsequent octets, 
         however, this is not normally necessary for X.25/ISO 8208 and 
         CLNS."
    REFERENCE   
        "IEEE 802.2 (ISO/IEC 8802-2) ASN.1, LSAP."
    SYNTAX      OCTET STRING (SIZE(1))

LSAPPairId ::= TEXTUAL-CONVENTION
    DISPLAY-HINT "1x"
    STATUS      current
    DESCRIPTION 
        "This textual convention represents an RDE Pair ID whcih 
         consists of a 1-octet value which contains the LLC SSAP, 
         followed by the 6 or 8 octet MACAddress (the combination as 
         described in the DLSAP textual convention), following by anoth 
         1-octet value which contains the LLC DSAP, followed by the 6 or 
         8 octet MACAddress."
    REFERENCE   
        "IEEE 802.2 (ISO/IEC 8802-2) ASN.1, LSAPPairID."
    SYNTAX      OCTET STRING (SIZE(0 | 14 | 18))

RoutingInformationField ::= TEXTUAL-CONVENTION
    DISPLAY-HINT "1x"
    STATUS      current
    DESCRIPTION 
        "The routing information field varies in length up to 30 octets.  
         When source routing is not used the RIF is said to be NULL and 
         contains no information.  The first bit of the MAC source 
         address is defined as the Routing Information Indicator (RII). 
         When the RIF is null, the RII is set to zero (0).  When the RIF 
         is not null, the RII is set to 1.  The first two octets are the 
         Routing Control field (RC) and the remainder of the RIF 
         contains Routing Descriptors (RD).  Each RD is two octets in 
         length, therefore a maximum of 14 RDs can exists in a RIF."
    REFERENCE   
        "IEEE 802.2 (ISO/IEC 8802-2) ASN.1, RIF."
    SYNTAX      OCTET STRING (SIZE(0..30))

SystemTypes ::= TEXTUAL-CONVENTION
    STATUS      current
    DESCRIPTION 
        "A set-valued textual convention which indicates whether the 
         system is an end-system, eS(1), or an intermediate system, 
         iS(2), or both."
    REFERENCE   
        "ITU-T Rec. X.283 | ISO/IEC 10733 ASN.1 SystemTypes."
    SYNTAX      BITS { eS(0), iS(1) }

NAddress ::= TEXTUAL-CONVENTION
    DISPLAY-HINT "1x"
    STATUS      current
    DESCRIPTION 
        "A network address."
    REFERENCE   
        "ITU-T Rec. X.283 | ISO/IEC 10733 ASN.1 NAddress."
    SYNTAX      OCTET STRING (SIZE(0..20))

NAddresses ::= TEXTUAL-CONVENTION
    DISPLAY-HINT "1x"
    STATUS      current
    DESCRIPTION 
        "A set of network addresses.  Each network address is formatted 
         as a single octet length indicator, following by 'length' 
         octets SIZE(0..20) of NAddress (see the NAddress textual 
         convention), followed by another length indicator and NAddress 
         pair, etc."
    REFERENCE   
        "ITU-T Rec. X.283 | ISO/IEC 10733 ASN.1 NAddresses."
    SYNTAX      OCTET STRING

X25PLEMode ::= TEXTUAL-CONVENTION
    STATUS      current
    DESCRIPTION 
        "The mode an an X25PLE interface."
    REFERENCE   
        "ITU-T Rec. X.283 ASN.1 X25PLEMode | ISO/IEC 10733 ASN.1 
         InterfaceMode."
    SYNTAX      INTEGER { dTE(0), dCE(1), dTEasDCE(2) }

FastSelect ::= TEXTUAL-CONVENTION
    STATUS      current
    DESCRIPTION 
        "Indicates the fast select option selection.  Type of fast 
         select to used for call. This specifies that one of `fast 
         select', `fast select with retricted response', or no fast 
         select facility is to be used for the call. Includes a value 
         `not specified' which indicates that no preference is 
         expressed."
    REFERENCE   
        "ITU-T Rec. X.283 | ISO/IEC 10733 ASN.1 FastSelect."
    SYNTAX      INTEGER { notSpecified(0), fastSelect(1), 
                    fastSelectWithRestrictedResponse(2), noFastSelect(3) }

DatabaseState ::= TEXTUAL-CONVENTION
    STATUS      current
    DESCRIPTION 
        "The state of the Level 1 or 2 ISIS database."
    REFERENCE   
        "ISO/IEC 10589 ASN.1 DatabaseState."
    SYNTAX      INTEGER { off(0), on(1), waiting(2) }

OriginatingLSPBufferSize ::= TEXTUAL-CONVENTION
    DISPLAY-HINT "d-0"
    STATUS      current
    DESCRIPTION 
        "The originating LSP buffer size."
    REFERENCE   
        "ISO/IEC 10589 ASN.1 OriginatingLSPBufferSize."
    SYNTAX      Integer32 (512..1492)

AreaAddress ::= TEXTUAL-CONVENTION
    DISPLAY-HINT "1x"
    STATUS      current
    DESCRIPTION 
        "An area address."
    REFERENCE   
        "ISO/IEC 10589 ASN.1 AreaAddress."
    SYNTAX      OCTET STRING (SIZE(0..20))

AreaAddresses ::= TEXTUAL-CONVENTION
    DISPLAY-HINT "1x"
    STATUS      current
    DESCRIPTION 
        "A set of area addresses.  Each area address is formatted as a 
         single octet length indicator, followed by 'length' octets 
         SIZE(0..20) of AreaAddress (see the AreaAddress textual 
         convention), followed by another length indicator and 
         AreaAddress pair, etc."
    REFERENCE   
        "ISO/IEC 10589 ASN.1 AreaAddresses."
    SYNTAX      OCTET STRING

SNPAAddress ::= TEXTUAL-CONVENTION
    DISPLAY-HINT "1x"
    STATUS      current
    DESCRIPTION 
        "An Subnetwork Point of Attachment Address.  This is either a 
         DTE address or a MAC address expressed as an octet string."
    REFERENCE   
        "ISO/IEC 10589 ASN.1 SNPAAddress."
    SYNTAX      OCTET STRING (SIZE(0..20))

SNPAAddresses ::= TEXTUAL-CONVENTION
    DISPLAY-HINT "1x"
    STATUS      current
    DESCRIPTION 
        "A list of SNPA addresses.  Each address contained in the list 
         consists of one length octet followed by 'length' address bytes 
         forming the SNPAAddress."
    REFERENCE   
        "ISO/IEC 10589 ASN.1 SNPAAddresses."
    SYNTAX      OCTET STRING

PathMetric ::= TEXTUAL-CONVENTION
    DISPLAY-HINT "d-0"
    STATUS      current
    DESCRIPTION 
        "Describes a path metric for ISO/IEC 10589 IS-IS operation."
    REFERENCE   
        "ISO/IEC 10589 ASN.1 PathMetric."
    SYNTAX      Integer32 (0..1023)

HopMetric ::= TEXTUAL-CONVENTION
    DISPLAY-HINT "d-0"
    STATUS      current
    DESCRIPTION 
        "Describes a hop metric for ISO/IEC 10589 IS-IS operation."
    REFERENCE   
        "ISO/IEC 10589 ASN.1 HopMetric."
    SYNTAX      Integer32 (0..63)

MetricType ::= TEXTUAL-CONVENTION
    STATUS      current
    DESCRIPTION 
        "Describes a hop metric type for ISO/IEC 10589 IS-IS operation."
    REFERENCE   
        "ISO/IEC 10589 ASN.1 MetricType."
    SYNTAX      INTEGER { internal(0), external(1) }

AddressPrefix ::= TEXTUAL-CONVENTION
    DISPLAY-HINT "1x"
    STATUS      current
    DESCRIPTION 
        "Describes a network address prefix (or a complete network 
         address).  The prefix is formatted in semi-octets and contains 
         a first octet which contains the length of the remainder of the 
         address prefix in semi-octets (1..40), followed by an integral 
         number of octets containing the indicated number of semi-octets 
         in order.  When the number of semi-octets is odd, the last 4 
         bits in the last octet are not significant.  A null string 
         represents an absent address prefix rather than a zero length 
         prefix."
    REFERENCE   
        "ISO/IEC 10589 ASN.1 AddressPrefix."
    SYNTAX      OCTET STRING (SIZE(0..21))

SNPAPrefix ::= TEXTUAL-CONVENTION
    DISPLAY-HINT "1x"
    STATUS      current
    DESCRIPTION 
        "Describes an SNPA prefix.  The prefix is formatted in octets, 
         but valued in bits: that is, it is a bit string.  The first 
         octet contains the number of significant bits that follow and 
         the bits are coded in the following octets padded to the next 
         integral octet.
         
         A null octet string represents an absent SNPA prefix rather 
         than a zero length prefix."
    REFERENCE   
        "ISO/IEC 10589 ASN.1 SNPAPrefix."
    SYNTAX      OCTET STRING (SIZE(0..21))

osiNotifications OBJECT IDENTIFIER
    ::= { dlMIB 0 }

osiObjects OBJECT IDENTIFIER
    ::= { dlMIB 1 }

osiTables OBJECT IDENTIFIER
    ::= { osiObjects 1 }

communicationsEntity OBJECT IDENTIFIER
    ::= { osiTables 1 }

communicationsEntityTable OBJECT-TYPE
    SYNTAX      SEQUENCE OF CommunicationsEntityEntry
    MAX-ACCESS  not-accessible
    STATUS      current
    DESCRIPTION 
        "Provides a table of communications entities."
    REFERENCE   
        "ITU-T Rec. X.723 | ISO/IEC 10165-5 communicationsEntity MOC."
    ::= { communicationsEntity 1 }

communicationsEntityEntry OBJECT-TYPE
    SYNTAX      CommunicationsEntityEntry
    MAX-ACCESS  not-accessible
    STATUS      current
    DESCRIPTION 
        "Each row is indexed by and defines the communications entity 
         identifier.  Each row contains the local SAP names and 
         operational state of the communications entity."
    REFERENCE   
        "ITU-T Rec. X.723 | ISO/IEC 10165-5 communicationsEntity MO."
    INDEX       { communicationsEntityId }
    ::= { communicationsEntityTable 1 }

CommunicationsEntityEntry ::= SEQUENCE {
    communicationsEntityId                  SimpleNameType,
    communicationsEntityLocalSapNames       RowPointer,
    communicationsEntityOperationalState    OperationalState
}

communicationsEntityId OBJECT-TYPE
    SYNTAX      SimpleNameType (SIZE(1..32))
    MAX-ACCESS  not-accessible
    STATUS      current
    DESCRIPTION 
        "Provides an index for communications entity entries in this 
         table.  Communcations entities can be data link entities.  Data 
         link entities can be lAPBDLE, mACDLE or lLCDLE entities.
         
         In the OpenSS7 STREAMS implementation of physical entities, the 
         communication entity id is a driver name; that is, it is the 
         name of the driver node that appears in /dev/streams, but with 
         only the basename of that path.  When the communications entity 
         id is xxxx, there exists a control stream at 
         /dev/streams/xxxx/0 which provides control access to the 
         physical entity.  There also exists a /dev/streams/clone/xxxx 
         device which is a clone device for creating Type 2 SAPs on the 
         physical entity.  There also may exist /dev/streams/xxxx/nnnn, 
         where nnnn != 0, Type 1 SAPs on the physical entity.  Type 1 
         SAPs are inherently associated with a sap1Address (Physical 
         Point of Attachment).  Type 2 SAPs must be bound by the user 
         before a sap1Address (Physical Point of Attachment) is 
         associated with the SAP."
    REFERENCE   
        "ITU-T Rec. X.723 | ISO/IEC 10165-5 communicationsEntityId."
    ::= { communicationsEntityEntry 1 }

communicationsEntityLocalSapNames OBJECT-TYPE
    SYNTAX      RowPointer
    MAX-ACCESS  read-only
    STATUS      current
    DESCRIPTION 
        "The localSapNames attribute of a communications entity contains 
         a set of distinguished names of layer (N-1) SAPs or ports at 
         which services are provided to the entity.  In the case of a 
         physical entity, the localSapNames references the port at which 
         physical services are provided.
         
         The localSapNames attribute of a communications entity managed 
         object class indicate the local service access points providing 
         user access to the communications entity.  In the case of a 
         physical entity, the localSapNames identify the single 
         physicalSAP, if any, associated with the physical entity.
         
         When there is no local service access point associated with the 
         physical entity (the entity is locally isolated), this has the 
         value zeroDotZero.  When there is a service access point 
         associated with the entity, it is a RowPointer into the 
         physicalSAP table of the service access point associated with 
         the physical entity.
         
         The localSapNames attribute identifies the providing entity's 
         SAP objects.  (Note that the providing entity is identified by 
         the providerEntityNames attribute.)  
         
         In the case of the physicalEntity, the localSapNames are the 
         physicalSAP MOs that represent the user-provider relationship 
         for the physical communications entity.  For normal data 
         circuits, there is at most one physicalSAP associated with the 
         physicalEntity and visa versa.
         
         In the case of the lAPBDLE, the localSapNames identifies the 
         physicalSAP of the phsysicalEntity object which is providing 
         service to the lAPBDLE.
         
         In the case of the mACDLE, the providing entity is a 
         physicalEntity and the phsysicalSAP is indicated by the name.
         
         In the case of the lLCDLE, the localSapNames identifies the 
         dLSAP of the mACDLE object which is providing service to the 
         lLCDLE."
    REFERENCE   
        "ITU-T Rec. X.723 | ISO/IEC 10165-5 communicationsEntityId."
    ::= { communicationsEntityEntry 2 }

communicationsEntityOperationalState OBJECT-TYPE
    SYNTAX      OperationalState
    MAX-ACCESS  read-only
    STATUS      current
    DESCRIPTION 
        "Provides the operational state of the communications entity 
         following the OperationalState textual convention of the 
         OPENSS7-TMN-TC module, which is based on ITU-T Rec. X.721 | 
         ISO/IEC 10165-2 operationalState.
         
         When the communicationsEntity MO is operable, the 
         operationalState shall have the value 'enabled'; otherwise it 
         shall have the value 'disabled'.  Transitions of 
         operationalState shall be reported using the stateChange 
         notification.
         
         Provides the operational state of the physical entity in 
         accordance with the OperationalState textual convention of the 
         OPENSS7-TMN-TC module.  When 'enabled', the phsyical entity is 
         operational is carrying user traffic; when 'disabled', it is 
         not operational and is not carrying user traffic.
         
         An entity is disabled if it is inoperable or a resource on 
         which it depends is inoperable.  An entity is enabled if it is 
         operable.
         
         In the OpenSS7 STREAMS implementation, the physical entity is 
         operational when the STREAMS driver is loaded  in the system 
         and a control stream is available to the driver."
    REFERENCE   
        "ITU-T Rec. X.721 | ISO/IEC 10165-2  operationalState."
    ::= { communicationsEntityEntry 3 }

sap1 OBJECT IDENTIFIER
    ::= { osiTables 2 }

sap1Table OBJECT-TYPE
    SYNTAX      SEQUENCE OF Sap1Entry
    MAX-ACCESS  not-accessible
    STATUS      current
    DESCRIPTION 
        "Provides a table of Style 1 SAPs."
    REFERENCE   
        "ITU-T Rec. X.723 | ISO/IEC 10165-5 sap1 MOC."
    ::= { sap1 1 }

sap1Entry OBJECT-TYPE
    SYNTAX      Sap1Entry
    MAX-ACCESS  not-accessible
    STATUS      current
    DESCRIPTION 
        "Entries in this table are automatically created and deleted as 
         a part of system operation.  This table is a side-table of the 
         communicationsEntity table."
    REFERENCE   
        "ITU-T Rec. X.723 | ISO/IEC 10165-5 sap1 MO."
    INDEX       { communicationsEntityId, sapId }
    ::= { sap1Table 1 }

Sap1Entry ::= SEQUENCE {
    sapId                   SimpleNameType,
    sap1Address             Unsigned32,
    sap1UserEntityNames     RowPointer
}

sapId OBJECT-TYPE
    SYNTAX      SimpleNameType
    MAX-ACCESS  not-accessible
    STATUS      current
    DESCRIPTION 
        "Provides a naming attribute for the SAP object.
         
         In the OpenSS7 STREAMS implementation, this is either the clone 
         device, /dev/streams/clone/lapb, where lapb is the name of the 
         device driver to open to establish a dlSAP and sap1Address is 
         the Physical Point of Attachment to which to attach the dLSAP; 
         or, a Style II device, /dev/streams/lapb/yyyy, where yyyy is 
         the minor device instance name or number associated with the 
         sap1Address and the lAPBDLE.
         
         Provides the identifier of the SAP within the physical 
         subsystem and physical entity.  The SAP identifier is 
         implementation specific.  In the case of the OpenSS7 Streams 
         implementation, a SAP identifier is the device name of the 
         minor device within the driver.  This is either the instance 
         number or minor device name associated with the open Stream.  
         Streams opened by opening the clone device 
         /dev/streams/clone/xxxx, where xxxx is the name of the physical 
         entity will have SAP identifiers of nnnn, where nnnn is the 
         minor device number assigned to the Stream.  Streams opened by 
         opening a specific minor device name or number 
         /dev/streams/xxxx/yyyy will have the name yyyy."
    REFERENCE   
        "ITU-T Rec. X.723 | ISO/IEC 10165-5 sapId."
    ::= { sap1Entry 1 }

sap1Address OBJECT-TYPE
    SYNTAX      Unsigned32
    MAX-ACCESS  read-only
    STATUS      current
    DESCRIPTION 
        "Provides the address of the SAP which is only of local 
         significance.  It can be the Physical Point of Attachment 
         attached to the SAP or the interface index of the entity to 
         which the SAP is attached.
         
         A LAPB data link entity may contain at most one dLSAP managed 
         object.  The value of the sap1Address attribute is of no 
         significance.  The sap1Address is dependent on the underlying 
         provider.  In this case, the sap1Address is the Physical Point 
         of Attachment associated with the data circuit over which the 
         LAPB data link is established.
         
         The sap1Address attribute contains the selector that is 
         contributed to the address of the SAP by this layer and is 
         dependent on the SAP address of the physical medium.  That is, 
         the sap1Address is a relative distinguished name of the 
         physical medium providing underlying services to the physical 
         SAP.
         
         In the OpenSS7 STREAMS implementation, this is the Physical 
         Point of Attachment when the Stream is attached, and zero when 
         a Type 2 Stream is unattached."
    REFERENCE   
        "ITU-T Rec. X.723 | ISO/IEC 10165-5 sap1Address."
    ::= { sap1Entry 2 }

sap1UserEntityNames OBJECT-TYPE
    SYNTAX      RowPointer
    MAX-ACCESS  read-only
    STATUS      current
    DESCRIPTION 
        "Provides the distinguished names of the entities using this 
         SAP.
         
         For data links, this is a single user entity name formatted as 
         a RowPointer to the entity in the table at which the user 
         entity exists.  This is likely the network entity.  If the user 
         entity is detached or unknown, the value will be zeroDotZero.
         
         This indicates the entry in a table which represents the user 
         of the SAP.  When there is no user associated with the SAP or 
         the user of the SAP is unknown, this will have the value 
         zeroDotZero.
         
         The userEntityNames attribute contains the distinguished names 
         of the managed objects that represent the user entities that 
         are using the SAP.  For the physical layer, this is normally 
         the data link entity that is communicating via the data 
         circuit.
         
         In the OpenSS7 STREAMS implementation, a user entity name is 
         assigned when the Stream is linked under a multiplexing driver, 
         or a pushable module is pushed over the Stream.  In this case, 
         the table entry referenced is the driver or module entry in the 
         corresponding entity table."
    REFERENCE   
        "ITU-T Rec. X.723 | ISO/IEC 10165-5 userEntityNames."
    ::= { sap1Entry 3 }

sap2 OBJECT IDENTIFIER
    ::= { osiTables 3 }

sap2Table OBJECT-TYPE
    SYNTAX      SEQUENCE OF Sap2Entry
    MAX-ACCESS  not-accessible
    STATUS      current
    DESCRIPTION 
        "Provides a table of Style 2 SAPs."
    REFERENCE   
        "ITU-T Rec. X.723 | ISO/IEC 10165-5 sap2 MOC."
    ::= { sap2 1 }

sap2Entry OBJECT-TYPE
    SYNTAX      Sap2Entry
    MAX-ACCESS  not-accessible
    STATUS      current
    DESCRIPTION 
        "Each row in this table is indexed by SAP identifier.  Each row 
         contains the user entity names and provider entity names."
    REFERENCE   
        "ITU-T Rec. X.723 | ISO/IEC 10165-5 sap2 MO."
    INDEX       { sapId }
    ::= { sap2Table 1 }

Sap2Entry ::= SEQUENCE {
    sap2Address                 NAddresses,
    sap2UserEntityNames         RowPointer,
    sap2ProviderEntityNames     RowPointer
}

sap2Address OBJECT-TYPE
    SYNTAX      NAddresses
    MAX-ACCESS  read-only
    STATUS      current
    DESCRIPTION 
        "The set of addresses associated with an (N) SAP."
    REFERENCE   
        "ITU-T Rec. X.723 | ISO/IEC 10165-5 sap2Address."
    ::= { sap2Entry 1 }

sap2UserEntityNames OBJECT-TYPE
    SYNTAX      RowPointer
    MAX-ACCESS  read-only
    STATUS      current
    DESCRIPTION 
        "The distinguished names of the (N+1) layer entities that use 
         the services of this SAP."
    REFERENCE   
        "ITU-T Rec. X.723 | ISO/IEC 10165-5 userEntityNames."
    ::= { sap2Entry 2 }

sap2ProviderEntityNames OBJECT-TYPE
    SYNTAX      RowPointer
    MAX-ACCESS  read-only
    STATUS      current
    DESCRIPTION 
        "The distinguished names of the (N-1) layer entities that 
         provide services to this SAP."
    REFERENCE   
        "ITU-T Rec. X.723 | ISO/IEC 10165-5 providerEntityNames."
    ::= { sap2Entry 3 }

clProtocolMachine OBJECT IDENTIFIER
    ::= { osiTables 4 }

clProtocolMachineTable OBJECT-TYPE
    SYNTAX      SEQUENCE OF ClProtocolMachineEntry
    MAX-ACCESS  not-accessible
    STATUS      current
    DESCRIPTION 
        "Provides a table of connectionless protocol machines."
    REFERENCE   
        "ITU-T Rec. X.723 | ISO/IEC 10165-5 clProtocolMachine MOC."
    ::= { clProtocolMachine 1 }

clProtocolMachineEntry OBJECT-TYPE
    SYNTAX      ClProtocolMachineEntry
    MAX-ACCESS  not-accessible
    STATUS      current
    DESCRIPTION 
        "Entries in this table are created and deleted automatically as 
         a part of system operation.  This table is a side-table of the 
         communicationsEntity table."
    REFERENCE   
        "ITU-T Rec. X.723 | ISO/IEC 10165-5 clProtocolMachine MO."
    INDEX       { communicationsEntityId, clProtocolMachineId }
    ::= { clProtocolMachineTable 1 }

ClProtocolMachineEntry ::= SEQUENCE {
    clProtocolMachineId                 SimpleNameType,
    clProtocolMachineOperationalState   OperationalState,
    clProtocolMachineTotalRemoteSAPs    Counter32
}

clProtocolMachineId OBJECT-TYPE
    SYNTAX      SimpleNameType
    MAX-ACCESS  not-accessible
    STATUS      current
    DESCRIPTION 
        "Provides a naming attribute for the connectionless protocol 
         machine."
    REFERENCE   
        "ITU-T Rec. X.723 | ISO/IEC 10165-5 clProtocolMachineId."
    ::= { clProtocolMachineEntry 1 }

clProtocolMachineOperationalState OBJECT-TYPE
    SYNTAX      OperationalState
    MAX-ACCESS  read-only
    STATUS      current
    DESCRIPTION 
        "Provides the operational state of the connectionless protocol 
         machine."
    REFERENCE   
        "ITU-T Rec. X.721 | ISO/IEC 10165-2 operationalState."
    ::= { clProtocolMachineEntry 2 }

clProtocolMachineTotalRemoteSAPs OBJECT-TYPE
    SYNTAX      Counter32
    MAX-ACCESS  read-only
    STATUS      current
    DESCRIPTION 
        "Counts the number of remote (N) SAPs that the containing 
         clProtocolMachine has communicated with.  Incremented by 1 
         every time communications with a remote (N) SAP is acheived."
    REFERENCE   
        "ITU-T Rec. X.723 | ISO/IEC 10165-5 totalRemoteSAPs."
    ::= { clProtocolMachineEntry 3 }

coProtocolMachine OBJECT IDENTIFIER
    ::= { osiTables 5 }

coProtocolMachineTable OBJECT-TYPE
    SYNTAX      SEQUENCE OF CoProtocolMachineEntry
    MAX-ACCESS  not-accessible
    STATUS      current
    DESCRIPTION 
        "Provides a table of connection-oriented protocol machines."
    REFERENCE   
        "ITU-T Rec. X.723 | ISO/IEC 10165-5 coProtocolMachine MOC."
    ::= { coProtocolMachine 1 }

coProtocolMachineEntry OBJECT-TYPE
    SYNTAX      CoProtocolMachineEntry
    MAX-ACCESS  not-accessible
    STATUS      current
    DESCRIPTION 
        "Entries in this table are created and deleted automatically as 
         a part of system operation.  This table is a side-table of the 
         communicationsEntity table."
    REFERENCE   
        "ITU-T Rec. X.723 | ISO/IEC 10165-5 coProtocolMachine MO."
    INDEX       { communicationsEntityId, coProtocolMachineId }
    ::= { coProtocolMachineTable 1 }

CoProtocolMachineEntry ::= SEQUENCE {
    coProtocolMachineId                 SimpleNameType,
    coProtocolMachineOperationalState   OperationalState
}

coProtocolMachineId OBJECT-TYPE
    SYNTAX      SimpleNameType (SIZE(1..32))
    MAX-ACCESS  not-accessible
    STATUS      current
    DESCRIPTION 
        "Provides a naming attribute for the connection oriented 
         protocol state machine."
    REFERENCE   
        "ITU-T Rec. X.723 | ISO/IEC 10165-5 coProtocolMachineId."
    ::= { coProtocolMachineEntry 1 }

coProtocolMachineOperationalState OBJECT-TYPE
    SYNTAX      OperationalState
    MAX-ACCESS  read-only
    STATUS      current
    DESCRIPTION 
        "Provides the operational state of the connection oriented 
         protocol machine.
         
         Provides the operational state of the data circuit following 
         the OperationalState textual convention of the OPENSS7-TMN-TC 
         module.  The operational state is 'enabled' when the data 
         circuit is actively exchanging bits with the physical medium; 
         'disabled' otherwise.
         
         When the sLPPM MO is operable, the operationalState shall have 
         the value 'enabled'; otherwise, it shall have the value 
         'disabled'.  Transitions of operationalState shall be reported 
         using the stateChange notification."
    REFERENCE   
        "ITU-T Rec. X.721 | ISO/IEC 10165-2 operationalState."
    ::= { coProtocolMachineEntry 2 }

singlePeerConnection OBJECT IDENTIFIER
    ::= { osiTables 6 }

singlePeerConnectionTable OBJECT-TYPE
    SYNTAX      SEQUENCE OF SinglePeerConnectionEntry
    MAX-ACCESS  not-accessible
    STATUS      current
    DESCRIPTION 
        "This managed object class represents a view of a single peer 
         connection between a pair of entities."
    REFERENCE   
        "ITU-T Rec. X.723 | ISO/IEC 10165-5 singlePeerConnection MOC."
    ::= { singlePeerConnection 1 }

singlePeerConnectionEntry OBJECT-TYPE
    SYNTAX      SinglePeerConnectionEntry
    MAX-ACCESS  not-accessible
    STATUS      current
    DESCRIPTION 
        "Entries in this table are automatically created and deleted as 
         a part of system operation.  This table is a side-table of the 
         coProtocolMachine table."
    REFERENCE   
        "ITU-T Rec. X.723 | ISO/IEC 10165-5 singlePeerConnection MO."
    INDEX       { communicationsEntityId, coProtocolMachineId, 
                  connectionId }
    ::= { singlePeerConnectionTable 1 }

SinglePeerConnectionEntry ::= SEQUENCE {
    connectionId                SimpleNameType,
    underlyingConnectionNames   RowPointer,
    suppportedConnectionNames   RowPointer
}

connectionId OBJECT-TYPE
    SYNTAX      SimpleNameType
    MAX-ACCESS  not-accessible
    STATUS      current
    DESCRIPTION 
        "Provides a naming attribute for singlePeerConnection MOs."
    REFERENCE   
        "ITU-T Rec. X.723 | ISO/IEC 10165-5 connectionId."
    ::= { singlePeerConnectionEntry 1 }

underlyingConnectionNames OBJECT-TYPE
    SYNTAX      RowPointer
    MAX-ACCESS  read-only
    STATUS      current
    DESCRIPTION 
        "
         The underlying connection names for the sLPConnection are 
         constrained to a cardinality of one.  This will contain the 
         underlying connection name associated with the connection.  The 
         underlying connection name is a RowPointer to an entry in the 
         physicalConnection table from the OPENSS7-PHY-MIB module.  The 
         entry corresponds to the channel on the physical dataCircuit 
         which provides the communications facility."
    REFERENCE   
        "ITU-T Rec. X.723 | ISO/IEC 10165-5 underlyingConnectionNames."
    ::= { singlePeerConnectionEntry 2 }

suppportedConnectionNames OBJECT-TYPE
    SYNTAX      RowPointer
    MAX-ACCESS  read-only
    STATUS      current
    DESCRIPTION 
        "Provides the distinguished names of the supported connections."
    REFERENCE   
        "ITU-T Rec. X.723 | ISO/IEC 10165-5 supportedConnectionNames."
    ::= { singlePeerConnectionEntry 3 }

physicalEntity OBJECT IDENTIFIER
    ::= { osiTables 7 }

physicalEntityTable OBJECT-TYPE
    SYNTAX      SEQUENCE OF PhysicalEntityEntry
    MAX-ACCESS  not-accessible
    STATUS      current
    DESCRIPTION 
        "One ore more physical entity MO and physical SAP MO are 
         contained in a physical subsystem.  The physical entity MO 
         represents the whole of the management aspect of the entity 
         that executes the functions of the physical layer.  Plural 
         instances of the physical entity MO can exist in an open 
         system.
         
         The communications entity manged object class is used to 
         represent an active functional element that performs 
         communication processing within a system, e.g. Network Entity, 
         Transport Entity, or, in this case, a Physical Entity.
         
         The physical entity managed object class.  This table 
         represents all of the instances of the physical entity managed 
         object class.  There may be multiple instances of these MOs 
         within a system.  These managed objects cannot be created nor 
         deleted explicitly by management stations.  They exist 
         inherently in a system; created and deleted as a part of system 
         operations.
         
         The physical entity managed object class is derived from the 
         ITU-T Rec. X.723 | ISO/IEC 10165-5 communications entity 
         managed object class.
         
         Physical Entity Managed Object.  There may be multiple 
         instances of these MOs within a system.  These managed objects 
         can not be created or deleted explicitly by management 
         operation.  They exist inherently in a system; created and 
         deleted as part of system operation.
         
         A physicalEntity is derived from a communicationsEntity.  A 
         physicalEntity is containted by a physicalSubsystem.
         
         A dataCircuit is contained by a physicalEntity.  The name 
         binding which applies when a dataCircuit managed object can be 
         created by management as a subordinate object of a 
         physicalEntity managed object and deleted by management."
    REFERENCE   
        "ITU-T Rec. X.281 | ISO/IEC 13642, physicalEntity MOC."
    ::= { physicalEntity 1 }

physicalEntityEntry OBJECT-TYPE
    SYNTAX      PhysicalEntityEntry
    MAX-ACCESS  not-accessible
    STATUS      current
    DESCRIPTION 
        "The physical entity terminates the physical media of the data 
         circuits containing one or more physical connections.
         
         The physical entity MO has a localSapNames attribute inherited 
         from GMI:communicationsEntity.  This attribute contains the 
         local distinguished name(s) of SAP MO(s), representing the 
         point at which services are provided to the entity.
         
         A physical entity managed object instance can contain a single 
         ITU-T Rec. X.281 | ISO/EIC 13642 data circuit managed object 
         instance.  The containment relationship name binding applies 
         when a data circuit managed object is created as a subordinate 
         object of a phsyical entity managed object instance and deleted 
         by management.
         
         A stateChange notification is used to report changes to the 
         operationalState attribute, and where present, the 
         adminsitrativeState attribute.  A single parameter set is 
         included in the state change definition field.  Only the 
         (mandatory) attributeId and (optional) newAttributeValue 
         parameters are used."
    REFERENCE   
        "ITU-T Rec. X.281 | ISO/IEC 13642, physicalEntity MO."
    INDEX       { communicationsEntityId }
    ::= { physicalEntityTable 1 }

PhysicalEntityEntry ::= SEQUENCE {
    physicalEntityPhysicalEntityTitles  RowPointer
}

physicalEntityPhysicalEntityTitles OBJECT-TYPE
    SYNTAX      RowPointer
    MAX-ACCESS  read-write
    STATUS      current
    DESCRIPTION 
        "Provides the names (titles) of the data link entity to which 
         this physical entity provides service.  This is a RowPointer 
         into the appropriate table at which entry the data link entity 
         exists.
         
         The set of physical entity titles which unambiguously identify 
         the physical entity in an end or intermediate system.  The 
         value may be entered by a system management operation or it may 
         be derived by some local means.
         
         The physicalEntityTitles attribute of a physical entity managed 
         object indicates the user entities that are being provided 
         service by the physical entity.  This would normally be a row 
         pointer into a table of a managed object derived from the data 
         link entity.  This could be, for example, a lAPBDLE, mACDLE or 
         signDataLink table entry."
    REFERENCE   
        "ITU-T Rec. X.281 | ISO/IEC 13642, physicalEntityTitles."
    ::= { physicalEntityEntry 1 }

physicalSAP OBJECT IDENTIFIER
    ::= { osiTables 8 }

physicalSAPTable OBJECT-TYPE
    SYNTAX      SEQUENCE OF PhysicalSAPEntry
    MAX-ACCESS  not-accessible
    STATUS      current
    DESCRIPTION 
        "The sap1 managed object class is used to represent a service 
         access point at which services are provided by an entity to the 
         user entity, where the SAP address is dependent on the SAP 
         address of the underlying layer.
         
         The sap1Address attribute contains the selector that is  
         contributed to the address of the SAP by this layer.
         
         The userEntityNames attribute contains the distinguished names 
         of the managed objects that represent the user entities that 
         are using the SAP.
         
         Physical Service Access Point Managed Object.  Physical SAP MO 
         class is used to represent a service access point where the 
         interactions between the phsyical service and the physical 
         service provider take place.  
         
         phSAP managed objects are created automatically as part of 
         system operation when a Physical layer user requests and is 
         granted use of the Physical layer services.  The mechanism by 
         which this happens is system-specific and not subject to OSI 
         standardization."
    REFERENCE   
        "ITU-T Rec. X.281 | ISO/IEC 13642 phsicalSAP MO."
    ::= { physicalSAP 1 }

physicalSAPEntry OBJECT-TYPE
    SYNTAX      PhysicalSAPEntry
    MAX-ACCESS  not-accessible
    STATUS      current
    DESCRIPTION 
        "There is a relationship between the physical SAP MO and the 
         managed objects that represent the data link user entities that 
         are using the SAP.  This is represented by the userEntityNames 
         attribute inherited from GMI:sap1.
         
         This managed object represents the point at which an entity 
         provides services to the user entity.  Refer to the Basic 
         Reference Model (ITU-T Rec. X.210) for the definition of 
         (N)-SAP.
         
         SAP entries are in general communications entity specific when 
         created as a part of system operation following the 
         sap1-communicationsEntity name binding; however, when created 
         by management per X.281, the physicalSAP-physicalSubsystem name 
         binding is used instead.  Both name bindings use the sapId for 
         naming.  One way to ensure that the sapId distingsuishes 
         objects in the subsystem is to use a name derived from the full 
         major and minor device number of the character special file."
    REFERENCE   
        "ITU-T Rec. X.281 | ISO/IEC 13642 phsicalSAP MO."
    INDEX       { communicationsEntityId, sapId }
    ::= { physicalSAPTable 1 }

PhysicalSAPEntry ::= SEQUENCE {
    physicalSAPRowStatus    RowStatus
}

physicalSAPRowStatus OBJECT-TYPE
    SYNTAX      RowStatus
    MAX-ACCESS  read-create
    STATUS      current
    DESCRIPTION 
        "Provides a mechansim whereby mnagement stations, following the 
         RowStatus textual convention of the SNMPv2-TC module, may 
         create or delete conceptual rows in this table.
         
         The physicalSAP-PhysicalSubsystem name binding applies when a 
         physicalSAPEntry is created by management as a subordinate 
         entry of a physicalEntityEntry, or deleted by management.  
         Management stations may only delete physicalSAP objects that do 
         not contain any subordinate objects."
    REFERENCE   
        "STD 58, SNMPv2-TC RowStatus."
    ::= { physicalSAPEntry 1 }

dataCircuit OBJECT IDENTIFIER
    ::= { osiTables 9 }

dataCircuitTable OBJECT-TYPE
    SYNTAX      SEQUENCE OF DataCircuitEntry
    MAX-ACCESS  not-accessible
    STATUS      current
    DESCRIPTION 
        "The data circuit MO is a generic managed object that represents 
         the management aspect of the entity that executes the 
         tranmission of bits.
         
         The data-circuit managed object class is used to represent a 
         communication path in the physical media for OSI between two 
         phsysical entities, together with the facilities necessary in 
         the Physical Layer for the transmission of bits on it.
         
         This MOC is derived from the X.723 coProtocolMachine."
    REFERENCE   
        "ITU-T Rec. X.281 | ISO/IEC 13642 dataCircuit MO."
    ::= { dataCircuit 1 }

dataCircuitEntry OBJECT-TYPE
    SYNTAX      DataCircuitEntry
    MAX-ACCESS  not-accessible
    STATUS      current
    DESCRIPTION 
        "A protocol machine which performs connection-mode 
         communications functions.  A connection oriented protocol 
         machine is contained within a communications entity and can 
         contain a single peer connection.
         
         A data circuit managed object derives from a connection 
         oriented protocol machine and is contained by a physical entity 
         and can contain a physical connection.
         
         A data circuit can only be created by management as a 
         subordinate of a physical entity and can only be deleted by 
         management when it does not contain a physical connection.
         
         An objectCreation notification is generated whenever an 
         instance of the managed object class is created.  
         Implementations may optionally include the sourceIndicator 
         parameter in the notification.  If the creation occured as a 
         result of internal operation of the resource, the value 
         'resourceOperation' is used.  If creation occured in response 
         to a management operation, the value 'managementOperation' is 
         used.  A value of 'unknown' may be returned if it is not 
         possible to determine the source of the operation.  None of the 
         other optional parameters are used.
         
         An objectDeletion notification is generated whenever an 
         instance of the managed object class is deleted.  
         Implementations may optionally include the sourceIndicator 
         parameter in the notification.  If deletion occured as a result 
         of internal operation of the resource, the value 
         'resourceOperation' is used.  If deletion occured in response 
         to a managemetn operation, the value 'managementOperation' is 
         used.  A value of 'unknown' may be returned if it is not 
         possible to determine the source of the operation.  None of the 
         other optional parameters are used.
         
         A stateChange notification is used to report changes to the 
         operationalState attribute, and where present, the 
         adminsitrativeState attribute.  A single parameter set is 
         included in the state change definition field.  Only the 
         (mandatory) attributeId and (optional) newAttributeValue 
         parameters are used.
         
         A communicationsAlarm notification can be generated including a 
         connectionError, lossOfSignal and lossOfSyncrhonization 
         parameters.  The probableCause parameter is set to the value 
         lossOfSignal.  The perceivedSeverity parameter is set to the 
         value Critical.
         
         A communicationsInformation notification can be generated 
         including a connectionEstablished parameter.  
         
         An equipmentAlarm notification can be generated.  The 
         probableCause parameter is set to datasetOrModemError.  The 
         perceivedSeverity parameter is set to the value Major.
         
         A qualityofServiceAlarm notification can be generated including 
         a bitErrorThresholdReached parameter.  The probableCause 
         parameter is set to thresholdCrossed.  The perceivedSeverity 
         parameter is set to the value Warning."
    REFERENCE   
        "ITU-T Rec. X.281 | ISO/IEC 13642 dataCircuit MO."
    INDEX       { communicationsEntityId, coProtocolMachineId }
    ::= { dataCircuitTable 1 }

DataCircuitEntry ::= SEQUENCE {
    dataCircuitBitErrorsReceived            Counter32,
    dataCircuitBitErrorsTransmitted         Counter32,
    dataCircuitBitErrorsThreshold           Float,
    dataCircuitType                         INTEGER,
    dataCircuitPhysicalMediaNames           OCTET STRING,
    dataCircuitPhysicalInterfaceType        OCTET STRING,
    dataCircuitPhysicalInterfaceStandard    OCTET STRING,
    dataCircuitSynchronizationMode          INTEGER,
    dataCircuitTransmissionCoding           OCTET STRING,
    dataCircuitTransmissionMode             INTEGER,
    dataCircuitTransmissionRate             Float,
    dataCircuitRowStatus                    RowStatus
}

dataCircuitBitErrorsReceived OBJECT-TYPE
    SYNTAX      Counter32
    MAX-ACCESS  read-only
    STATUS      current
    DESCRIPTION 
        "Provides a count of the bit errors received on the circuit."
    REFERENCE   
        "ITU-T Rec. X.281 | ISO/IEC 13642 bitErrorsReceived."
    ::= { dataCircuitEntry 1 }

dataCircuitBitErrorsTransmitted OBJECT-TYPE
    SYNTAX      Counter32
    MAX-ACCESS  read-only
    STATUS      current
    DESCRIPTION 
        "Provides a count of the bit errors transmitted on the circuit."
    REFERENCE   
        "ITU-T Rec. X.281 | ISO/IEC 13642 bitErrorsTransmitted."
    ::= { dataCircuitEntry 2 }

dataCircuitBitErrorsThreshold OBJECT-TYPE
    SYNTAX      Float
    MAX-ACCESS  read-create
    STATUS      current
    DESCRIPTION 
        "Provides an upper threshold for bit errors."
    REFERENCE   
        "ITU-T Rec. X.281 | ISO/IEC 13642 bitErrorsThreshold."
    ::= { dataCircuitEntry 3 }

dataCircuitType OBJECT-TYPE
    SYNTAX      INTEGER { endSystem(0), relaySystem(1) }
    MAX-ACCESS  read-create
    STATUS      current
    DESCRIPTION 
        "Indicates whether the data circuit is attached to an end system 
         or a relay system.  When attached to an end-system, no 
         switching occurs between the local and remote systems and the 
         circuit is always semi-permanent.  When attached to a 
         relay-system, the circuit is either permanent, semi-permanent 
         or switched.  When switched, the circuit can be controlled by 
         the relay system, or controlled by the local system."
    REFERENCE   
        "ITU-T Rec. X.281 | ISO/IEC 13642 dataCircuitType."
    ::= { dataCircuitEntry 4 }

dataCircuitPhysicalMediaNames OBJECT-TYPE
    SYNTAX      OCTET STRING
    MAX-ACCESS  read-create
    STATUS      current
    DESCRIPTION 
        "Provides the distinguished names of the physical media."
    REFERENCE   
        "ITU-T Rec. X.281 | ISO/IEC 13642 physicalMediaNames."
    ::= { dataCircuitEntry 5 }

dataCircuitPhysicalInterfaceType OBJECT-TYPE
    SYNTAX      OCTET STRING
    MAX-ACCESS  read-create
    STATUS      current
    DESCRIPTION 
        "Provides the physical interface type."
    REFERENCE   
        "ITU-T Rec. X.281 | ISO/IEC 13642 physicalInterfaceType."
    ::= { dataCircuitEntry 6 }

dataCircuitPhysicalInterfaceStandard OBJECT-TYPE
    SYNTAX      OCTET STRING
    MAX-ACCESS  read-create
    STATUS      current
    DESCRIPTION 
        "Provides the physical interface standard."
    REFERENCE   
        "ITU-T Rec. X.281 | ISO/IEC 13642 physicalInterfaceStandard."
    ::= { dataCircuitEntry 7 }

dataCircuitSynchronizationMode OBJECT-TYPE
    SYNTAX      INTEGER { synchronous(0), asynchronous(1) }
    MAX-ACCESS  read-create
    STATUS      current
    DESCRIPTION 
        "Indicates whether the data circuit is syncrhonous or 
         asynchronous in terms of the definition provided in ISO 7776.  
         When HDLC is provided on the data circuit, the form of bit or 
         character patterns used by the data link depend upon this 
         syncrhonization mode.  This is a read-only attribute as this is 
         an intrinsic property of the data circuit."
    REFERENCE   
        "ITU-T Rec. X.281 | ISO/IEC 13642 synchornizationMode."
    ::= { dataCircuitEntry 8 }

dataCircuitTransmissionCoding OBJECT-TYPE
    SYNTAX      OCTET STRING
    MAX-ACCESS  read-create
    STATUS      current
    DESCRIPTION 
        "Indicates the transmission coding of the data circuit."
    REFERENCE   
        "ITU-T Rec. X.281 | ISO/IEC 13642 transmissionCoding."
    ::= { dataCircuitEntry 9 }

dataCircuitTransmissionMode OBJECT-TYPE
    SYNTAX      INTEGER { simplex(0), duplex(1), halfDuplex(2) }
    MAX-ACCESS  read-create
    STATUS      current
    DESCRIPTION 
        "Indicates the transmission mode, either simplex(0), one-way 
         outgoing or one-way incoming, duplex(1), two-way simultaneous 
         communications, or halfDuplex(2), alternating two-way 
         communications.  Normally the data link entity must know 
         whether the communications is full or half duplex and most data 
         link entities expect duplex instead of simplex operation.  When 
         the data circuit only supports half-duplex operation, a 
         half-duplex module is required between the physical SAP and the 
         user data link entity to provide a convergence sublayer.  This 
         can be implemetned under STREAMS as a separate pushable module 
         (the HDM or half-duplex module).  The use of such a module is 
         described in ITU-T Rec. X.211 (1995) | ISO/IEC 10022 : 1996 
         Annex B."
    REFERENCE   
        "ITU-T Rec. X.281 | ISO/IEC 13642 transmissionMode."
    ::= { dataCircuitEntry 10 }

dataCircuitTransmissionRate OBJECT-TYPE
    SYNTAX      Float
    MAX-ACCESS  read-create
    STATUS      current
    DESCRIPTION 
        "This is a floating point number indicating the transmission 
         rate of the data circuit."
    REFERENCE   
        "ITU-T Rec. X.281 | ISO/IEC 13642 transmissionRate."
    ::= { dataCircuitEntry 11 }

dataCircuitRowStatus OBJECT-TYPE
    SYNTAX      RowStatus
    MAX-ACCESS  read-create
    STATUS      current
    DESCRIPTION 
        "Provides a mechanism whereby management stations, following the 
         RowStatus textual convention of the SNMPv2-TC module, may 
         create or delete conceptual rows in this table.
         
         Data circuits can be deleted by management only if they do not 
         contain physical connections.  Data circuits may not be created 
         explicitly by management stations.
         
         The dataCircuit-PhysicalEntity name binding applies when a 
         dataCircuit managed object can be created by management as a 
         subordinate object of a physicalEntity managed object and 
         deleted by management."
    REFERENCE   
        "STD 58, SNMPv2-TC RowStatus."
    ::= { dataCircuitEntry 12 }

physicalConnection OBJECT IDENTIFIER
    ::= { osiTables 10 }

physicalConnectionTable OBJECT-TYPE
    SYNTAX      SEQUENCE OF PhysicalConnectionEntry
    MAX-ACCESS  not-accessible
    STATUS      current
    DESCRIPTION 
        "The physical connection MO represents the management view of 
         connections established using relaying functions.
         
         Multiplexing consists of supporting multiple physical 
         connections on a single data circuit.
         
         A physical connection is associated with a single physical SAP.  
         If more than one physical connection is associated wtih a 
         physical SAP, the endpoint identification is used to distiguish 
         between physical connections accessible via the SAP.
         
         Physical connection identifiers are not globally known.  In the 
         case of mujltiplexing, they will be conveyed implicitly or 
         explicitly via the Physical protocol.
         
         Physical Connection Managed Object.  The physical connection 
         managed object class is used to represent an interconnection of 
         data circuits in the physical layer."
    REFERENCE   
        "ITU-T Rec. X.281 | ISO/IEC 13642 physicalConnection MOC."
    ::= { physicalConnection 1 }

physicalConnectionEntry OBJECT-TYPE
    SYNTAX      PhysicalConnectionEntry
    MAX-ACCESS  not-accessible
    STATUS      current
    DESCRIPTION 
        "There is a relationship between the physical connection MO and 
         the managed objects that represent the Data Link connections.
         
         An objectCreation notification is generated whenever an 
         instance of the managed object class is created.  
         Implementations may optionally include the sourceIndicator 
         parameter in the notification.  If the creation occured as a 
         result of internal operation of the resource, the value 
         'resourceOperation' is used.  If creation occured in response 
         to a management operation, the value 'managementOperation' is 
         used.  A value of 'unknown' may be returned if it is not 
         possible to determine the source of the operation.  None of the 
         other optional parameters are used.
         
         An objectDeletion notification is generated whenever an 
         instance of the managed object class is deleted.  
         Implementations may optionally include the sourceIndicator 
         parameter in the notification.  If deletion occured as a result 
         of internal operation of the resource, the value 
         'resourceOperation' is used.  If deletion occured in response 
         to a managemetn operation, the value 'managementOperation' is 
         used.  A value of 'unknown' may be returned if it is not 
         possible to determine the source of the operation.  None of the 
         other optional parameters are used.
         
         A stateChange notification is used to report changes to the 
         operationalState attribute, and where present, the 
         adminsitrativeState attribute.  A single parameter set is 
         included in the state change definition field.  Only the 
         (mandatory) attributeId and (optional) newAttributeValue 
         parameters are used.
         
         The PhS provides for PhCs between PhS users.  Since connections 
         cannot be established through the protocol at the Physical 
         Layer but rather are configured when the service is created, 
         the PhC, which is a logical concept, nevertheless must relate 
         directly to the real physical media paths provided to the 
         Physical Layer.  For this reason: a) There is no distinction 
         between connection-mode and connectionless-mode at the Physical 
         Layer.  The service is independent of whether the higher layers 
         operate in connection-mode or connectionless-mode.  b) Each PhC 
         is identified within the Physical Layer.  c) A PhC can only 
         relate to a particular PhSAP (i.e. a PhC implies a specific 
         source PhSAP, and a specific destination PhSAP or group of 
         PhSAPs if a multi-endpoint connection).
         
         The PhC may traverse Physical Layer relay, or intermediate 
         systems when several physical media are used in tandem.  Such 
         relaying may be controlled through a mangement function 
         exercised over a separate, but related, PhC, or may be 
         controlled form the Network Layer, as specified in ITU-T Rec. 
         X.200 | ISO/IEC 7498-1, 7.5.4.2, for the interconnection of 
         data circuits.  The Physical Layer does not make any routing 
         decisions.  Intermediate systems may also be used for mapping 
         different Physical Layer protocols associated with a PhC."
    REFERENCE   
        "ITU-T Rec. X.281 | ISO/IEC 13642 physicalConnection MO."
    INDEX       { communicationsEntityId, coProtocolMachineId, 
                  connectionId }
    ::= { physicalConnectionTable 1 }

PhysicalConnectionEntry ::= SEQUENCE {
    physicalConnectionEndpointIdentifier    OCTET STRING,
    physicalConnectionPortNumber            Integer32,
    physicalConnectionRowStatus             RowStatus
}

physicalConnectionEndpointIdentifier OBJECT-TYPE
    SYNTAX      OCTET STRING
    MAX-ACCESS  read-create
    STATUS      current
    DESCRIPTION 
        "The physical endpoint identifier is only necessary when there 
         are multiple physical connections that are associated with a 
         given SAP, in which case, the endpointIdentifier is used to 
         distinguish between the physical connections accessible via the 
         SAP."
    REFERENCE   
        "ITU-T Rec. X.281 | ISO/IEC 13642 endpointIdentifier."
    ::= { physicalConnectionEntry 1 }

physicalConnectionPortNumber OBJECT-TYPE
    SYNTAX      Integer32
    MAX-ACCESS  read-create
    STATUS      current
    DESCRIPTION 
        "The physical port number "
    REFERENCE   
        "ITU-T Rec. X.281 | ISO/IEC 13642 portNumber."
    ::= { physicalConnectionEntry 2 }

physicalConnectionRowStatus OBJECT-TYPE
    SYNTAX      RowStatus
    MAX-ACCESS  read-create
    STATUS      current
    DESCRIPTION 
        "Provides a mechanism whereby management stations, following the 
         RowStatustextual convetion of the SNMPv2-TC module, may creat 
         or delete conceptual rows in this table.
         
         Physical connections are contained by data circuits at two 
         levels the singlePeerConnection-coProtocolMachine name binding 
         from ITU-T Rec. X.723 | ISO/IEC 10165-5 and the 
         physicalConnection-dataCircuit name binding, both which are 
         named by attribute connectionId.  The former name binding 
         permits neither creation nor deletion; the later, only 
         deletion.
         
         Physical connections can be deleted by management only if they 
         do not contain other objects.  Physical connection may not be 
         created explicitly by management stations.  (I don't know what 
         the value is in deleting physical connections from data 
         circuits without the ability to create them.)
         
         Provides a mechanism whereby management stations, following the 
         RowStatus textual convention of the SNMPv2-TC module, may 
         create or delete conceptual rows in this table.
         
         Management stations do not create rows in this table, but may 
         delete them.  Deleting a row in this table may result in 
         deactivation of the physical connection, but the row may be 
         readded as a part of system operation.
         
         The physicalConnection-dataCircuit name binding pplies when a 
         physicalConnection managed object (or an instance of a subclass 
         of the physicalConnection MO class) can be changed by 
         management as a subordinate object of a dataCircuit managed 
         object (or subclass) and deleted by management."
    REFERENCE   
        "STD 58, SNMPv2-TC RowStatus."
    ::= { physicalConnectionEntry 3 }

datalinkEntity OBJECT IDENTIFIER
    ::= { osiTables 11 }

datalinkEntityTable OBJECT-TYPE
    SYNTAX      SEQUENCE OF DatalinkEntityEntry
    MAX-ACCESS  not-accessible
    STATUS      current
    DESCRIPTION 
        "Provides a table of data link entities."
    REFERENCE   
        "ITU-T Rec. X.282 | ISO/IEC 10742 datalinkEntity MOC."
    ::= { datalinkEntity 1 }

datalinkEntityEntry OBJECT-TYPE
    SYNTAX      DatalinkEntityEntry
    MAX-ACCESS  not-accessible
    STATUS      current
    DESCRIPTION 
        "Each row in this table is indexed by communications entity 
         identifier.  Each row contains the provider entity names."
    REFERENCE   
        "ITU-T Rec. X.282 | ISO/IEC 10742 datalinkEntity MO."
    INDEX       { communicationsEntityId }
    ::= { datalinkEntityTable 1 }

DatalinkEntityEntry ::= SEQUENCE {
    datalinkEntityProviderEntityNames   RowPointer,
    datalinkEntityRowStatus             RowStatus
}

datalinkEntityProviderEntityNames OBJECT-TYPE
    SYNTAX      RowPointer
    MAX-ACCESS  read-create
    STATUS      current
    DESCRIPTION 
        "The providerEntityNames attribute identifies the entities 
         providing service to this datalinkEntity.
         
         In the case of the LAPB data link entity, lAPBDLE, the provider 
         entity is a physicalEntity.  At most one physicalEntity  can 
         provide service to an lAPBDLE without the mlp package; multiple 
         physicalEntities provide service to a lAPBDLE with the mlp 
         package; only  one lAPBDLE can be provided service by a 
         physicalEntity.
         
         In the case of the LLC data link entity, lLCDLE, the provider 
         entity is a MAC data link entity, mACDLE.  At most one mACDLE 
         can provide service to an lLCDLE, and at most one lLCDLE can be 
         provided service by a mACDLE.
         
         When there is no mACDLE providing service to the lLCDLE, this 
         attribute will contain zeroDotZero.  When there is a mACDLE 
         associated with this lLCDLE, the value of this attribute will 
         be the RowPointer to the entry in the mACDLE table at which the 
         corresponding mACDLE entry occurs.
         
         When there is a mACDLE providing service to this lLCDLE, the 
         communicationsEntityId will be the same as the 
         communicationsEntityId and this entry will contain the 
         RowPointer of the corresponding row in the mACDLE table."
    REFERENCE   
        "ITU-T Rec. X.282 | ISO/IEC 10742, providerEntityNames."
    ::= { datalinkEntityEntry 1 }

datalinkEntityRowStatus OBJECT-TYPE
    SYNTAX      RowStatus
    MAX-ACCESS  read-create
    STATUS      current
    DESCRIPTION 
        "Provides a mechanism whereby management stations may create and 
         delete rows in this table.  Entries must persist across agent 
         reboots."
    REFERENCE   
        "ITU-T Rec. X.282 | ISO/IEC 10742, 
         datalinkEntity-datalinkSubsystem."
    ::= { datalinkEntityEntry 2 }

dLSAP OBJECT IDENTIFIER
    ::= { osiTables 12 }

dLSAPTable OBJECT-TYPE
    SYNTAX      SEQUENCE OF DLSAPEntry
    MAX-ACCESS  not-accessible
    STATUS      current
    DESCRIPTION 
        "The data link service access point managed object.  The dLSAP 
         managed object class is used to represent a service access 
         point at which services are provided by a data link entity to 
         the user entity.  Instances of the dLSAP managed object class 
         are contained within instances of subclasses derived from the 
         datalinkEntity managed object class.  Constraints on the number 
         of contained dLSAP MOs and any specific semantics of the 
         attributes are given as part of the definition of the 
         containing data link entity managed object class.
         
         A dLSAP managed object may be created and deleted explicitly by 
         management operation or created and deleted automatically as 
         part of system operation, e.g.  when a user of the data link 
         layer service requests and is granted use of the service.  The 
         mechanism by which this happens is a local matter and not 
         subject to OSI standardization.
         
         A lAPBDLE MO may contain at most one dLSAP MO.  The value of 
         the sap1Address atribute is of no significance.  The 
         cardinality of the userEntityNames attribute is limited to 
         one."
    REFERENCE   
        "ITU-T Rec. X.282 | ISO/IEC 10742 dLSAP MOC."
    ::= { dLSAP 1 }

dLSAPEntry OBJECT-TYPE
    SYNTAX      DLSAPEntry
    MAX-ACCESS  not-accessible
    STATUS      current
    DESCRIPTION 
        "Each row in this table is indexed by communications entity and 
         SAP identifiers.  Beyond membership, entries are otherwise 
         empty."
    REFERENCE   
        "ITU-T Rec. X.282 | ISO/IEC 10742 dLSAP MO."
    INDEX       { communicationsEntityId, sapId }
    ::= { dLSAPTable 1 }

DLSAPEntry ::= SEQUENCE {
    dLSAPRowStatus  RowStatus
}

dLSAPRowStatus OBJECT-TYPE
    SYNTAX      RowStatus
    MAX-ACCESS  read-create
    STATUS      current
    DESCRIPTION 
        "Provides a mechanism whereby management stations, following the 
         RowStatus textual convention of the SNMPv2-TC module, may 
         create or delete conceptual rows in this table.
         
         The dLSAP-datalinkEntity-Management name binding applies when a 
         dLSAP managed object (or an isntance of a subclass of the dLSAP 
         MO class) is created by management as a subordinate object of a 
         datalinkEntity managed object (or subclasses), or deleted by 
         management."
    REFERENCE   
        "ITU-T Rec. X.282 | ISO/IEC 10742 
         dLSAP-datalinkEntity-management, STD 58, SNMPv2-TC RowStatus."
    ::= { dLSAPEntry 1 }

lAPBDLE OBJECT IDENTIFIER
    ::= { osiTables 13 }

lAPBDLETable OBJECT-TYPE
    SYNTAX      SEQUENCE OF LAPBDLEEntry
    MAX-ACCESS  not-accessible
    STATUS      current
    DESCRIPTION 
        "The LAPB data link entity managed object.  There may be 
         multiple instances of the lLAPBDLE managed object in a system.  
         Systems not supporting the LAPB data link procedures defined in 
         ISO/IEC 7776 are not required to support the lAPBDLE and 
         contained managed objects.
         
         The lAPBDLE managed object has a conditional mlp package.  
         There may be multiple instances of lAPBDLE MO in a system, both 
         with and without the mlp package.  For those instances in which 
         the package is absent, the mlp procedures do not apply and the 
         lAPBDLE MO may contain at most on sLPPM MO.  For those 
         instances in which the package is present, the mlp proceudres 
         do apply and the lAPBDLE MO may contain multiplex instances of 
         sLPPM MO.
         
         A lAPBDLE MO may contain at most one dLSAP MO.  The value of 
         the sap1Address atribute is of no significance.  The 
         cardinality of the userEntityNames attribute is limited to one.
         
         A lAPBDLE MO may be created and deleted explicitly by 
         management operation or created and deleted automatically as a 
         part of system operation.
         
         When the lAPBDLE MO is operable, the operationalState shall 
         have the value 'enabled'; otherwise, it shall have the value 
         'disabled'.  Transitions of operationalState shall be reported 
         using the stateChange notification."
    REFERENCE   
        "ITU-T Rec. X.282 | ISO/IEC 10742 lAPBDLE MOC."
    ::= { lAPBDLE 1 }

lAPBDLEEntry OBJECT-TYPE
    SYNTAX      LAPBDLEEntry
    MAX-ACCESS  not-accessible
    STATUS      current
    DESCRIPTION 
        "This entiry is derived from the datalinkEntity and uses the 
         same primary index."
    REFERENCE   
        "ITU-T Rec. X.282 | ISO/IEC 10742 lAPBDLE MOC."
    INDEX       { communicationsEntityId }
    ::= { lAPBDLETable 1 }

LAPBDLEEntry ::= SEQUENCE {
    lAPBDLEmT1Timer                         TimeInterval,
    lAPBDLEmT3Timer                         TimeInterval,
    lAPBDLEmW                               Integer32,
    lAPBDLEmXSend                           Integer32,
    lAPBDLEmXReceive                        Integer32,
    lAPBDLEmT2Timer                         TimeInterval,
    lAPBDLEreceivedMlpResets                Counter32,
    lAPBDLEtimesMT1Expired                  Counter32,
    lAPBDLEIframesReassignments             Counter32,
    lAPBDLEmlpFramesReceived                Counter32,
    lAPBDLEmlpFramesSent                    Counter32,
    lAPBDLEmlpFramesOutsideWindowGuard      Counter32,
    lAPBDLEreceivedMlpFramesInGuardRegion   Counter32,
    lAPBDLERowStatus                        RowStatus
}

lAPBDLEmT1Timer OBJECT-TYPE
    SYNTAX      TimeInterval
    UNITS       "seconds"
    MAX-ACCESS  read-create
    STATUS      current
    DESCRIPTION 
        "Value of the ISO/IEC 7776 parameter MT1 (lost frame timer).  
         This value is ignored and will default to zero if multiple 
         single link protocol protocol machines are not assigned to this 
         LAPB data link entity."
    REFERENCE   
        "ITU-T Rec. X.282 | ISO/IEC 10742, ISO/IEC 7776."
    ::= { lAPBDLEEntry 1 }

lAPBDLEmT3Timer OBJECT-TYPE
    SYNTAX      TimeInterval
    UNITS       "seconds"
    MAX-ACCESS  read-create
    STATUS      current
    DESCRIPTION 
        "Value of the ISO/IEC 7776 parameter MT3 (mlp reset confirmation 
         timer).  This value is ignored and will default to zero if 
         multiple single link protocol protocol machines are not 
         assigned to this LAPB data link entity."
    REFERENCE   
        "ITU-T Rec. X.282 | ISO/IEC 10742, ISO/IEC 7776."
    ::= { lAPBDLEEntry 2 }

lAPBDLEmW OBJECT-TYPE
    SYNTAX      Integer32
    MAX-ACCESS  read-create
    STATUS      current
    DESCRIPTION 
        "MLP window size.  This value is ignored and will default to 
         zero if multiple single link protocol protocol machines are not 
         assigned to this LAPB data link entity."
    REFERENCE   
        "ITU-T Rec. X.282 | ISO/IEC 10742, ISO/IEC 7776."
    ::= { lAPBDLEEntry 3 }

lAPBDLEmXSend OBJECT-TYPE
    SYNTAX      Integer32
    MAX-ACCESS  read-create
    STATUS      current
    DESCRIPTION 
        "Receive MLP window in the Guard Region.  This value is ignored 
         and will default to zero if multiple single link protocol 
         protocol machines are not assigned to this LAPB data link 
         entity."
    REFERENCE   
        "ITU-T Rec. X.282 | ISO/IEC 10742, ISO/IEC 7776."
    ::= { lAPBDLEEntry 4 }

lAPBDLEmXReceive OBJECT-TYPE
    SYNTAX      Integer32
    MAX-ACCESS  read-create
    STATUS      current
    DESCRIPTION 
        "Receive MLP window in the Guard Region.  This value is ignored 
         and will default to zero if multiple single link protocol 
         protocol machines are not assigned to this LAPB data link 
         entity."
    REFERENCE   
        "ITU-T Rec. X.282 | ISO/IEC 10742, ISO/IEC 7776."
    ::= { lAPBDLEEntry 5 }

lAPBDLEmT2Timer OBJECT-TYPE
    SYNTAX      TimeInterval
    UNITS       "seconds"
    MAX-ACCESS  read-create
    STATUS      current
    DESCRIPTION 
        "Value of the ISO/IEC 7776 parameter MT2 (group busy timer).  
         This value is ignored and will default to zero if multiple 
         single link protocol protocol machines are not assigned to this 
         LAPB data link entity."
    REFERENCE   
        "ITU-T Rec. X.282 | ISO/IEC 10742, ISO/IEC 7776."
    ::= { lAPBDLEEntry 6 }

lAPBDLEreceivedMlpResets OBJECT-TYPE
    SYNTAX      Counter32
    MAX-ACCESS  read-only
    STATUS      current
    DESCRIPTION 
        "Count of the number of received MLP Resets.  This value will 
         always return zero if multiple single link protocol protocol 
         machines are not assigned to this LAPB data link entity."
    REFERENCE   
        "ITU-T Rec. X.282 | ISO/IEC 10742, receivedMlpResets."
    ::= { lAPBDLEEntry 7 }

lAPBDLEtimesMT1Expired OBJECT-TYPE
    SYNTAX      Counter32
    MAX-ACCESS  read-only
    STATUS      current
    DESCRIPTION 
        "Count of the number of lost multilink frames.  This value will 
         always return zero if multiple single link protocol protocol 
         machines are not assigned to this LAPB data link entity."
    REFERENCE   
        "ITU-T Rec. X.282 | ISO/IEC 10742, timesMT1Expired."
    ::= { lAPBDLEEntry 8 }

lAPBDLEIframesReassignments OBJECT-TYPE
    SYNTAX      Counter32
    MAX-ACCESS  read-only
    STATUS      current
    DESCRIPTION 
        "Count of the number of reassignments of IFrames on another slp.  
         This value will always return zero if multiple single link 
         protocol protocol machines are not assigned to this LAPB data 
         link entity."
    REFERENCE   
        "ITU-T Rec. X.282 | ISO/IEC 10742, iFrameReassignments."
    ::= { lAPBDLEEntry 9 }

lAPBDLEmlpFramesReceived OBJECT-TYPE
    SYNTAX      Counter32
    MAX-ACCESS  read-only
    STATUS      current
    DESCRIPTION 
        "Count of the total number of MLP frames received.  This value 
         will always return zero if multiple single link protocol 
         protocol machines are not assigned to this LAPB data link 
         entity."
    REFERENCE   
        "ITU-T Rec. X.282 | ISO/IEC 10742, mlpFramesReceived."
    ::= { lAPBDLEEntry 10 }

lAPBDLEmlpFramesSent OBJECT-TYPE
    SYNTAX      Counter32
    MAX-ACCESS  read-only
    STATUS      current
    DESCRIPTION 
        "Count of the total number of MLP frames sent.  This value will 
         always return zero if multiple single link protocol protocol 
         machines are not assigned to this LAPB data link entity."
    REFERENCE   
        "ITU-T Rec. X.282 | ISO/IEC 10742, mlpFramesSent."
    ::= { lAPBDLEEntry 11 }

lAPBDLEmlpFramesOutsideWindowGuard OBJECT-TYPE
    SYNTAX      Counter32
    MAX-ACCESS  read-only
    STATUS      current
    DESCRIPTION 
        "Count of the total number of MLP frames outwide the window 
         guard that have been received.  This value will always return 
         zero if multiple single link protocol protocol machines are not 
         assigned to this LAPB data link entity."
    REFERENCE   
        "ITU-T Rec. X.282 | ISO/IEC 10742, mlpFramesOutsideWindowGuard."
    ::= { lAPBDLEEntry 12 }

lAPBDLEreceivedMlpFramesInGuardRegion OBJECT-TYPE
    SYNTAX      Counter32
    MAX-ACCESS  read-only
    STATUS      current
    DESCRIPTION 
        "Count of the number of MLP frames received in the Guard Region.  
         This value will always return zero if multiple single link 
         protocol protocol machines are not assigned to this LAPB data 
         link entity."
    REFERENCE   
        "ITU-T Rec. X.282 | ISO/IEC 10742, 
         receivedMlpFramesInGuardRegion."
    ::= { lAPBDLEEntry 13 }

lAPBDLERowStatus OBJECT-TYPE
    SYNTAX      RowStatus
    MAX-ACCESS  read-create
    STATUS      current
    DESCRIPTION 
        "Provides a mechanism whereby management stations, following the 
         RowStatus textual convention of the SNMPv2-TC module, to create 
         and delete conceptual rows in this table."
    REFERENCE   
        "ITU-T Rec. X.282 | ISO/IEC 10742, STD 58, SNMPv2-TC RowStatus."
    ::= { lAPBDLEEntry 14 }

sLPPM OBJECT IDENTIFIER
    ::= { osiTables 14 }

sLPPMTable OBJECT-TYPE
    SYNTAX      SEQUENCE OF SLPPMEntry
    MAX-ACCESS  not-accessible
    STATUS      current
    DESCRIPTION 
        "The LAPB single link protoocol machine managed object.  The 
         sLPPM managed object represents the operation of the LAPB data 
         link layer protocol machine described in ISO/IEC 7776 over a 
         single physical link.  An sLPPM managed object may contain at 
         most one sLPConnection MO and one or more sLPConnectionIVMO.
         
         An sLPPM MO may be crated and deleted explicitly by management 
         operation or created and deleted automatically a part of system 
         oepration.
         
         When the sLPPM MO is operable, the operationalState shall have 
         the value 'enabled'; otherwise, it shall have the value 
         'disabled'.  Transitions of operationalState shall be reported 
         using the stateChange notification.
         
         Creation of an entry in this table will be notified with the 
         objectCreation notification of the OPENSS7-TMN-SMI module and 
         the sourceIndicator parameter indicating the source of the 
         creation.
         
         Deletion of a entry in this table will be notified with the 
         objectDeletion notification of the OPENSS7-TMN-SMI module with 
         the sourceIndicator parameter indicate the source of the 
         deletion.
         
         An activate and deactivate action is defined for these managed 
         objects in TMN; howere, these actions are mimiced by adding an 
         administrativeState element."
    REFERENCE   
        "ITU-T Rec. X.282 | ISO/IEC 10742 sLPPM MOC."
    ::= { sLPPM 1 }

sLPPMEntry OBJECT-TYPE
    SYNTAX      SLPPMEntry
    MAX-ACCESS  not-accessible
    STATUS      current
    DESCRIPTION 
        "The sLPPM MO is contained by a lAPBDLE MO.  The name binding 
         which applies when a sLPPM managed object (or an instance of a 
         subclass of the sLPPM MO class) can be created by management as 
         a subordinate object of a lAPBDLE managed object (or subclass), 
         and deleted by management."
    REFERENCE   
        "ITU-T Rec. X.282 | ISO/IEC 10742 sLPPM MOC."
    INDEX       { communicationsEntityId, coProtocolMachineId }
    ::= { sLPPMTable 1 }

SLPPMEntry ::= SEQUENCE {
    sLPPMadministrativeState    AdministrativeState,
    sLPPMRowStatus              RowStatus
}

sLPPMadministrativeState OBJECT-TYPE
    SYNTAX      AdministrativeState
    MAX-ACCESS  read-create
    STATUS      current
    DESCRIPTION 
        "Provides a mechanism whereby management stations may activate, 
         set to locked(), or deactivate, set to unlocked(), the single 
         link protocol protocol machine.  This has the effect of 
         activating or deactivating the data link."
    REFERENCE   
        "ITU-T Rec. X.282 | ISO/IEC 10742 activate and deactivate 
         ACTIONS."
    ::= { sLPPMEntry 3 }

sLPPMRowStatus OBJECT-TYPE
    SYNTAX      RowStatus
    MAX-ACCESS  read-create
    STATUS      current
    DESCRIPTION 
        "Provides a mechanism whereby management stations, following the 
         RowStatus textual convention of the SNMPv2-TC module, may 
         create and delete conceptual rows in this table.
         
         The name binding which applies when a sLPPM managed object (or 
         an instance of a subclass of the sLPPM MO class) can be created 
         by management as a subordinate object of a lAPBDLE managed 
         object (or subclass), and deleted by management.
         
         When a lAPBDLE only support SLP, at most one instance of a 
         sLPPM can exist for a given lAPBDLE.  When a lAPBDLE supports 
         MLP, multiple instances of sLPPM can exist for a given 
         lAPBDLE."
    REFERENCE   
        "ITU-T Rec. X.282 | ISO/IEC 10742 sLPPM-lAPBDLE-Management, STD 
         58, SNMPv2-TC RowStatus."
    ::= { sLPPMEntry 4 }

sLPConnection OBJECT IDENTIFIER
    ::= { osiTables 15 }

sLPConnectionTable OBJECT-TYPE
    SYNTAX      SEQUENCE OF SLPConnectionEntry
    MAX-ACCESS  not-accessible
    STATUS      current
    DESCRIPTION 
        "The LAPB single link protocol connection managed object.  The 
         sLPConnection mnaged object represents the local view of a 
         connection between LAPB DLEs over a single physical link.  This 
         table provides the configuration, state and statistics for a 
         given LAPB connection which is associated with a specific LAPB 
         interface.  An sLPConnection MO is created automatically as a 
         part of system operation.  An sLPConnection MO may be deleted 
         automatically as part of system operation or may be deleted as 
         a result of the deactivate or delete management operations.  An 
         sLPConnectionIVMO may be used as the source of initial values 
         of attributes of an sLPConnection MO.
         
         The LAPB Single Link Protocol Machine managed object The sLPPM 
         managed object represents the operation of the LAPB Data Link 
         layer protocol machine described in ISO/IEC 7776 over a single 
         physical link.  An sLPPM managed object may contain at most one 
         sLPConnection MO and one or more sLPConnectionIVMO.
         
         Entries in this table support a 'deactivate' action."
    REFERENCE   
        "ITU-T Rec. X.282 | ISO/IEC 10742 sLPConnection MOC."
    ::= { sLPConnection 1 }

sLPConnectionEntry OBJECT-TYPE
    SYNTAX      SLPConnectionEntry
    MAX-ACCESS  not-accessible
    STATUS      current
    DESCRIPTION 
        "This is an entry in the state table representing a single LAPB 
         data link connection.
         
         This table entry provides detailed statistics for a given LAPB 
         connection associatedw with a given LAPB interface."
    REFERENCE   
        "ITU-T Rec. X.282 | ISO/IEC 10742 sLPConnection MOC."
    INDEX       { communicationsEntityId, coProtocolMachineId, 
                  connectionId }
    ::= { sLPConnectionTable 1 }

SLPConnectionEntry ::= SEQUENCE {
    sLPConnectionInterfaceType                      INTEGER,
    sLPConnectionK                                  Integer32,
    sLPConnectionN1                                 Integer32,
    sLPConnectionN2                                 Integer32,
    sLPConnectionSequenceModulus                    Integer32,
    sLPConnectionT1Timer                            TimeInterval,
    sLPConnectionT2Timer                            TimeInterval,
    sLPConnectionFCSErrorsReceived                  Counter32,
    sLPConnectionFRMRsReceived                      Counter32,
    sLPConnectionFRMRsSent                          Counter32,
    sLPConnectionIFrameDataOctetsReceived           Counter32,
    sLPConnectionIFrameDataOctetsSent               Counter32,
    sLPConnectionIFramesReceived                    Counter32,
    sLPConnectionIFramesSent                        Counter32,
    sLPConnectionPollsReceived                      Counter32,
    sLPConnectionREJsReceived                       Counter32,
    sLPConnectionREJsSent                           Counter32,
    sLPConnectionRNRsReceived                       Counter32,
    sLPConnectionRNRsSent                           Counter32,
    sLPConnectionSABMsReceived                      Counter32,
    sLPConnectionSABMsSent                          Counter32,
    sLPConnectionProtocolState                      INTEGER,
    sLPConnectionTimesT1Expired                     Counter32,
    sLPConnectionT3Timer                            TimeInterval,
    sLPConnectionTimesT3Expired                     Counter32,
    sLPConnectionT4Timer                            TimeInterval,
    sLPConnectionTimesT4Expired                     Counter32,
    sLPConnectionAbnormalLinkDisconnectsReceived    Counter32,
    sLPConnectionAbnormalLinkDisconnectsSent        Counter32,
    sLPConnectionLinkResetsReceived                 Counter32,
    sLPConnectionLinkResetsSent                     Counter32,
    sLPConnectionTimesN2Reached                     Counter32,
    sLPConnectionAdministrativeState                AdministrativeState,
    sLPConnectionOperationalState                   OperationalState,
    sLPConnectionUsageState                         UsageState,
    sLPConnectionProceduralStatus                   ProceduralStatus,
    sLPConnectionAlarmStatus                        AlarmStatus,
    sLPConnectionRowStatus                          RowStatus
}

sLPConnectionInterfaceType OBJECT-TYPE
    SYNTAX      INTEGER { dTE(0), dCE(1) }
    MAX-ACCESS  read-create
    STATUS      current
    DESCRIPTION 
        "Determines the address mode used by the local DTE."
    REFERENCE   
        "ITU-T Rec. X.282 | ISO/IEC 10742, interfaceType."
    ::= { sLPConnectionEntry 1 }

sLPConnectionK OBJECT-TYPE
    SYNTAX      Integer32
    MAX-ACCESS  read-create
    STATUS      current
    DESCRIPTION 
        "Value of the ISO/IEC 7776 parameter k.  The maximum number of 
         sequentially numbered I frames that a DTE may have outstanding 
         (i.e. unacknowledged) at any fiven time."
    REFERENCE   
        "ITU-T Rec. X.282 | ISO/IEC 10742, k."
    ::= { sLPConnectionEntry 2 }

sLPConnectionN1 OBJECT-TYPE
    SYNTAX      Integer32
    MAX-ACCESS  read-create
    STATUS      current
    DESCRIPTION 
        "Value of the ISO/IEC 7776 parameter N1.  The maximum number of 
         bits in an I frame (excluding flags and 0 bits inserted for 
         transparency."
    REFERENCE   
        "ITU-T Rec. X.282 | ISO/IEC 10742, n1."
    ::= { sLPConnectionEntry 3 }

sLPConnectionN2 OBJECT-TYPE
    SYNTAX      Integer32
    MAX-ACCESS  read-create
    STATUS      current
    DESCRIPTION 
        "Value of the ISO/IEC 7776 parameter N2.  The maximum number of 
         attempts that shall be made to complete the successful 
         transmission of a frame."
    REFERENCE   
        "ITU-T Rec. X.282 | ISO/IEC 10742, n2."
    ::= { sLPConnectionEntry 4 }

sLPConnectionSequenceModulus OBJECT-TYPE
    SYNTAX      Integer32 (8 | 128)
    MAX-ACCESS  read-create
    STATUS      current
    DESCRIPTION 
        "Determines basic (modulo 8) or extended (modulo 128) 
         operation."
    REFERENCE   
        "ITU-T Rec. X.282 | ISO/IEC 10742, sequenceModulus."
    ::= { sLPConnectionEntry 5 }

sLPConnectionT1Timer OBJECT-TYPE
    SYNTAX      TimeInterval
    MAX-ACCESS  read-create
    STATUS      current
    DESCRIPTION 
        "Value of the ISO/IEC 7776 parameter Timer T1.  Unit is 
         centiseconds."
    REFERENCE   
        "ITU-T Rec. X.282 | ISO/IEC 10742, t1Timer."
    ::= { sLPConnectionEntry 6 }

sLPConnectionT2Timer OBJECT-TYPE
    SYNTAX      TimeInterval
    MAX-ACCESS  read-create
    STATUS      current
    DESCRIPTION 
        "Value of the ISO/IEC 7776 parameter T2.  Units is 
         centiseconds."
    REFERENCE   
        "ITU-T Rec. X.282 | ISO/IEC 10742, t2Timer."
    ::= { sLPConnectionEntry 7 }

sLPConnectionFCSErrorsReceived OBJECT-TYPE
    SYNTAX      Counter32
    MAX-ACCESS  read-only
    STATUS      current
    DESCRIPTION 
        "Counter.  Total number of frames received with a bad checksum."
    REFERENCE   
        "ITU-T Rec. X.282 | ISO/IEC 10742, fCSErrorsReceived."
    ::= { sLPConnectionEntry 8 }

sLPConnectionFRMRsReceived OBJECT-TYPE
    SYNTAX      Counter32
    MAX-ACCESS  read-only
    STATUS      current
    DESCRIPTION 
        "Counter.  Total number of FRMR frames received."
    REFERENCE   
        "ITU-T Rec. X.282 | ISO/IEC 10742, fRMRsReceived."
    ::= { sLPConnectionEntry 9 }

sLPConnectionFRMRsSent OBJECT-TYPE
    SYNTAX      Counter32
    MAX-ACCESS  read-only
    STATUS      current
    DESCRIPTION 
        "Counter.  Total number of FRMR frames sent."
    REFERENCE   
        "ITU-T Rec. X.282 | ISO/IEC 10742, fRMRsSent."
    ::= { sLPConnectionEntry 10 }

sLPConnectionIFrameDataOctetsReceived OBJECT-TYPE
    SYNTAX      Counter32
    MAX-ACCESS  read-only
    STATUS      current
    DESCRIPTION 
        "Counter Total number of data octets received in I frames.  Only 
         data octets in new I frames are counted, i.e. retransmitted 
         frames that are received do not cause the counter to be 
         incremented."
    REFERENCE   
        "ITU-T Rec. X.282 | ISO/IEC 10742, iFrameDataOctetsReceived."
    ::= { sLPConnectionEntry 11 }

sLPConnectionIFrameDataOctetsSent OBJECT-TYPE
    SYNTAX      Counter32
    MAX-ACCESS  read-only
    STATUS      current
    DESCRIPTION 
        "Counter.  Total number of data octets sent in I frames.  Only 
         data octets in new I frames are counted, i.e., retransmitted 
         frames that are sent do not cause the counter to be 
         incremented."
    REFERENCE   
        "ITU-T Rec. X.282 | ISO/IEC 10742, iFrameDataOctetsSent."
    ::= { sLPConnectionEntry 12 }

sLPConnectionIFramesReceived OBJECT-TYPE
    SYNTAX      Counter32
    MAX-ACCESS  read-only
    STATUS      current
    DESCRIPTION 
        "Counter.  Total number of I frames received.  Only new I frames 
         are counted, i.e. retransmitted frames that are received do not 
         cause the counter to be incremented."
    REFERENCE   
        "ITU-T Rec. X.282 | ISO/IEC 10742, iFramesReceived."
    ::= { sLPConnectionEntry 13 }

sLPConnectionIFramesSent OBJECT-TYPE
    SYNTAX      Counter32
    MAX-ACCESS  read-only
    STATUS      current
    DESCRIPTION 
        "Counter.  Total number of I frame sent.  Only new I frames are 
         counted, i.e., retransmitted frames that are sent do not cause 
         the counter to be incremented."
    REFERENCE   
        "ITU-T Rec. X.282 | ISO/IEC 10742, iFramesSent."
    ::= { sLPConnectionEntry 14 }

sLPConnectionPollsReceived OBJECT-TYPE
    SYNTAX      Counter32
    MAX-ACCESS  read-only
    STATUS      current
    DESCRIPTION 
        "Counter.  Total number of command frames received with P-bit 
         set."
    REFERENCE   
        "ITU-T Rec. X.282 | ISO/IEC 10742, pollsReceived."
    ::= { sLPConnectionEntry 15 }

sLPConnectionREJsReceived OBJECT-TYPE
    SYNTAX      Counter32
    MAX-ACCESS  read-only
    STATUS      current
    DESCRIPTION 
        "Counter.  Total number of REJ frames received."
    REFERENCE   
        "ITU-T Rec. X.282 | ISO/IEC 10742, rEJsReceived."
    ::= { sLPConnectionEntry 16 }

sLPConnectionREJsSent OBJECT-TYPE
    SYNTAX      Counter32
    MAX-ACCESS  read-only
    STATUS      current
    DESCRIPTION 
        "Counter.  Total number of REJ frames sent."
    REFERENCE   
        "ITU-T Rec. X.282 | ISO/IEC 10742, rEJsSent."
    ::= { sLPConnectionEntry 17 }

sLPConnectionRNRsReceived OBJECT-TYPE
    SYNTAX      Counter32
    MAX-ACCESS  read-only
    STATUS      current
    DESCRIPTION 
        "Counter Total number of RNR frames received."
    REFERENCE   
        "ITU-T Rec. X.282 | ISO/IEC 10742, rNRsReceived."
    ::= { sLPConnectionEntry 18 }

sLPConnectionRNRsSent OBJECT-TYPE
    SYNTAX      Counter32
    MAX-ACCESS  read-only
    STATUS      current
    DESCRIPTION 
        "Counter.  Total number of RNR frames sent."
    REFERENCE   
        "ITU-T Rec. X.282 | ISO/IEC 10742, rNRsSent."
    ::= { sLPConnectionEntry 19 }

sLPConnectionSABMsReceived OBJECT-TYPE
    SYNTAX      Counter32
    MAX-ACCESS  read-only
    STATUS      current
    DESCRIPTION 
        "Counter.  Total number of SABM/SABME frames received."
    REFERENCE   
        "ITU-T Rec. X.282 | ISO/IEC 10742, sABMsReceived."
    ::= { sLPConnectionEntry 20 }

sLPConnectionSABMsSent OBJECT-TYPE
    SYNTAX      Counter32
    MAX-ACCESS  read-only
    STATUS      current
    DESCRIPTION 
        "Counter.  Total number of SABM/SABME frames sent."
    REFERENCE   
        "ITU-T Rec. X.282 | ISO/IEC 10742, sABMsSent."
    ::= { sLPConnectionEntry 21 }

sLPConnectionProtocolState OBJECT-TYPE
    SYNTAX      INTEGER { disconnectedPhase(0), 
                    linkdisconnectionPhase(1), linkSetUpPhase(2), 
                    informationTransferPhase(3), frameRejectCondition(4), 
                    busyCondition(5), sentRejectCondition(6), 
                    systemParametersAndErrorRecovery(7) }
    MAX-ACCESS  read-only
    STATUS      current
    DESCRIPTION 
        "Local state of a LAPB (SLP) connection."
    REFERENCE   
        "ITU-T Rec. X.282 | ISO/IEC 10742, sLPProtocolState."
    ::= { sLPConnectionEntry 22 }

sLPConnectionTimesT1Expired OBJECT-TYPE
    SYNTAX      Counter32
    MAX-ACCESS  read-only
    STATUS      current
    DESCRIPTION 
        "Counter.  Total number of times the local Timer T1 expired."
    REFERENCE   
        "ITU-T Rec. X.282 | ISO/IEC 10742, timesT1Expired."
    ::= { sLPConnectionEntry 23 }

sLPConnectionT3Timer OBJECT-TYPE
    SYNTAX      TimeInterval
    MAX-ACCESS  read-create
    STATUS      current
    DESCRIPTION 
        "Value of the ISO/IEC 7776 parameter or ITU-T X.25 mandatory 
         parameter T3.  Unit is centiseconds."
    REFERENCE   
        "ITU-T Rec. X.282 | ISO/IEC 10742, t3Timer."
    ::= { sLPConnectionEntry 24 }

sLPConnectionTimesT3Expired OBJECT-TYPE
    SYNTAX      Counter32
    MAX-ACCESS  read-only
    STATUS      current
    DESCRIPTION 
        "Counter.  Total number of times local Timer T3 expired."
    REFERENCE   
        "ITU-T Rec. X.282 | ISO/IEC 10742, timesT3Expired."
    ::= { sLPConnectionEntry 25 }

sLPConnectionT4Timer OBJECT-TYPE
    SYNTAX      TimeInterval
    MAX-ACCESS  read-create
    STATUS      current
    DESCRIPTION 
        "Value of the ISO/IEC 7776 parameter T4.  The maximum time a DTE 
         or a DCE will allow without frames being exchangd on the data 
         link.  Units is centiseconds."
    REFERENCE   
        "ITU-T Rec. X.282 | ISO/IEC 10742, t4Timer."
    ::= { sLPConnectionEntry 26 }

sLPConnectionTimesT4Expired OBJECT-TYPE
    SYNTAX      Counter32
    MAX-ACCESS  read-only
    STATUS      current
    DESCRIPTION 
        "Counter.  Total number of times local Timer T4 expired."
    REFERENCE   
        "ITU-T Rec. X.282 | ISO/IEC 10742, timesT4Expired."
    ::= { sLPConnectionEntry 27 }

sLPConnectionAbnormalLinkDisconnectsReceived OBJECT-TYPE
    SYNTAX      Counter32
    MAX-ACCESS  read-only
    STATUS      current
    DESCRIPTION 
        "Counter.  Total number of received abnormal Link Disconnects."
    REFERENCE   
        "ITU-T Rec. X.282 | ISO/IEC 10742."
    ::= { sLPConnectionEntry 28 }

sLPConnectionAbnormalLinkDisconnectsSent OBJECT-TYPE
    SYNTAX      Counter32
    MAX-ACCESS  read-only
    STATUS      current
    DESCRIPTION 
        "Counter.  Total number of sent abnormal Link Disconnects."
    REFERENCE   
        "ITU-T Rec. X.282 | ISO/IEC 10742."
    ::= { sLPConnectionEntry 29 }

sLPConnectionLinkResetsReceived OBJECT-TYPE
    SYNTAX      Counter32
    MAX-ACCESS  read-only
    STATUS      current
    DESCRIPTION 
        "Counter.  Total number of received Link Resets."
    REFERENCE   
        "ITU-T Rec. X.282 | ISO/IEC 10742."
    ::= { sLPConnectionEntry 30 }

sLPConnectionLinkResetsSent OBJECT-TYPE
    SYNTAX      Counter32
    MAX-ACCESS  read-only
    STATUS      current
    DESCRIPTION 
        "Counter.  Total number of sent Link Resets."
    REFERENCE   
        "ITU-T Rec. X.282 | ISO/IEC 10742."
    ::= { sLPConnectionEntry 31 }

sLPConnectionTimesN2Reached OBJECT-TYPE
    SYNTAX      Counter32
    MAX-ACCESS  read-only
    STATUS      current
    DESCRIPTION 
        "Counter.  Total number of times N2 was reached."
    REFERENCE   
        "ITU-T Rec. X.282 | ISO/IEC 10742."
    ::= { sLPConnectionEntry 32 }

sLPConnectionAdministrativeState OBJECT-TYPE
    SYNTAX      AdministrativeState
    MAX-ACCESS  read-create
    STATUS      current
    DESCRIPTION 
        "Provides the X.731 administrative status of the LAPB 
         connection.  When locked(0), the LAPB connection is 
         administratively prohibitted from forming and when set to 
         locked(0) will be abruptly disconnected if already formed.  
         When unlocked(1) the LAPB connection is administratively 
         permitted to form.  When set to
         shuttingDown(2), the LAPB connection will be gracefully 
         withdrawn from service and will enter the locked(0) state when 
         shut down."
    REFERENCE   
        "ITU-T Rec. X.282 | ISO/IEC 10742,
         ITU-T Rec. X.721 (1992)."
    ::= { sLPConnectionEntry 33 }

sLPConnectionOperationalState OBJECT-TYPE
    SYNTAX      OperationalState
    MAX-ACCESS  read-only
    STATUS      current
    DESCRIPTION 
        "Provides the X.731 operational state of this LAPB connection.
         
         When the sLPPM MO is operable, the operationalState shall have 
         the value 'enabled'; otherwise it shall have the value 
         'disabled'.  Transitions of operationalState shall be reported 
         using the stateChange notification with the RowPointer for the 
         corresponding entry as the objectInstance value and the old and 
         new values of the attribute as additional information."
    REFERENCE   
        "ITU-T Rec. X.282 | ISO/IEC 10742,
         ITU-T Rec. X.721 (1992)."
    ::= { sLPConnectionEntry 34 }

sLPConnectionUsageState OBJECT-TYPE
    SYNTAX      UsageState
    MAX-ACCESS  read-only
    STATUS      current
    DESCRIPTION 
        "Provides the X.731 usage state of this LAPB connection.  When 
         idle(0), the LABP connection is not currently in use (although 
         it may still be formed).  When active(1), the resource is being 
         used and has sufficient spare operating capacity to provide for 
         additional users simultaneously.  When busy(2), the resource is 
         in use, but it has no spare capacity to provide additional 
         users at this instant."
    REFERENCE   
        "ITU-T Rec. X.282 | ISO/IEC 10742,
         ITU-T Rec. X.721 (1992)."
    ::= { sLPConnectionEntry 35 }

sLPConnectionProceduralStatus OBJECT-TYPE
    SYNTAX      ProceduralStatus
    MAX-ACCESS  read-only
    STATUS      current
    DESCRIPTION 
        "Provides the X.731 procedural status of this LAPB connection.  
         The procedural status contains initializationRequired(0) when 
         the LAPB requires initiation action to form or reform a 
         connection.  It contains notInitialized(1) when the LAPB 
         connection is in disconnected mode (ADM); initializing(2) when 
         forming connection (SABM) and terminating(3) when disconnecting 
         (DISC)."
    REFERENCE   
        "ITU-T Rec. X.282 | ISO/IEC 10742,
         ITU-T Rec. X.721 (1992)."
    ::= { sLPConnectionEntry 36 }

sLPConnectionAlarmStatus OBJECT-TYPE
    SYNTAX      AlarmStatus
    MAX-ACCESS  read-only
    STATUS      current
    DESCRIPTION 
        "Provides the alarm status of this LAPB connection.
         
         The sLPConnection entry may issue a communicationsAlarm 
         notification using the RowPointer of the corresponding entry in 
         the objectInstance parameter of the communicationsAlarm.
         
         The probableCause is fRMRReceived.  The specificProblems is one 
         of:
         
         - fRMRReasonsControlFieldUndefinedOrUnimplemented,
         - fRMRReasonsFormatError,
         - fRMRReasonsInfoFieldLengthGreaterThanMaximum,
         - fRMRReasonsInvalidNR,
         - fRMRReasonsNonSpecific.
         
         The perceivedSeverity parameter is set to the value Minor.  A 
         subsequent communicationsAlarm with a perceivedSeverity of 
         Cleared is not generated.  Alarms must be cleared by management 
         stations using the sLPConnectionAlarmStatus or locally.
         
         The fRMR parameter containing the received frame is included in 
         the additionalInformation.  No other parameters are used."
    REFERENCE   
        "ITU-T Rec. X.282 | ISO/IEC 10742,
         ITU-T Rec. X.721 (1992)."
    ::= { sLPConnectionEntry 37 }

sLPConnectionRowStatus OBJECT-TYPE
    SYNTAX      RowStatus
    MAX-ACCESS  read-create
    STATUS      current
    DESCRIPTION 
        "Provides a mechanism whereby management stations, following the 
         RowStatus textual convetion of the SNMPv2-TC module, may create 
         or delete conceptual rows in this table.
         
         Whenever entries are created in this table, whether explicitly 
         by a management station or automatically as a part of system 
         operation, an objectCreation notification is issued with the 
         RowPointer corresponding to the created entry contained in the 
         objectInstance parameter of the notification and the 
         read-create access attributes as additional information.
         
         Whenever entries are deleted from this table, whether 
         explicitly by a management station or automatically as a part 
         of system operation, an objectDeletion notification is issued 
         with the RowPointer corresponding to the deleted etnry 
         contained in the objectInstance parameter of the notification 
         and the accessible attributes as additional information.
         
         An sLPConnection MO is created automatically as part of a 
         system operation.  When created, an objectCreation notification 
         is generated.
         
         An sLPConnection MO may be deleted automatically as a part of 
         system operation or may be deleted as a result of the 
         deactivate or delete management operations.  When deleted, an 
         objectDeletion notification is generated."
    REFERENCE   
        "STD 58, SNMPv2-TC RowStatus."
    ::= { sLPConnectionEntry 38 }

sLPConnectionIVMO OBJECT IDENTIFIER
    ::= { osiTables 16 }

sLPConnectionIVMOTable OBJECT-TYPE
    SYNTAX      SEQUENCE OF SLPConnectionIVMOEntry
    MAX-ACCESS  not-accessible
    STATUS      current
    DESCRIPTION 
        "Provides a table of signle link protocol connection initial 
         value managed objects."
    REFERENCE   
        "ITU-T Rec. X.282 | ISO/IEC 10742 sLPConnectionIVMO MOC."
    ::= { sLPConnectionIVMO 1 }

sLPConnectionIVMOEntry OBJECT-TYPE
    SYNTAX      SLPConnectionIVMOEntry
    MAX-ACCESS  not-accessible
    STATUS      current
    DESCRIPTION 
        "Each row in this table in indexed by and defines the SLP 
         connection IVMO identifier.  Each row contains initial values 
         to be used when forming SLP connections."
    REFERENCE   
        "ITU-T Rec. X.282 | ISO/IEC 10742 sLPConnectionIVMO MOC."
    INDEX       { sLPConnectionIVMOid }
    ::= { sLPConnectionIVMOTable 1 }

SLPConnectionIVMOEntry ::= SEQUENCE {
    sLPConnectionIVMOid                 SimpleNameType,
    sLPConnectionIVMOinterfaceType      INTEGER,
    sLPConnectionIVMOk                  Integer32,
    sLPConnectionIVMOn1                 Integer32,
    sLPConnectionIVMOn2                 Integer32,
    sLPConnectionIVMOsequenceModulus    Integer32,
    sLPConnectionIVMOt1Timer            TimeInterval,
    sLPConnectionIVMOt2Timer            TimeInterval,
    sLPConnectionIVMOt3Timer            TimeInterval,
    sLPConnectionIVMOt4Timer            TimeInterval,
    sLPConnectionIVMORowStatus          RowStatus
}

sLPConnectionIVMOid OBJECT-TYPE
    SYNTAX      SimpleNameType
    MAX-ACCESS  not-accessible
    STATUS      current
    DESCRIPTION 
        "Provides an index into the SLP connection IVMO table."
    REFERENCE   
        "ITU-T Rec. X.282 | ISO/IEC 10742."
    ::= { sLPConnectionIVMOEntry 1 }

sLPConnectionIVMOinterfaceType OBJECT-TYPE
    SYNTAX      INTEGER { dTE(0), dCE(1) }
    MAX-ACCESS  read-create
    STATUS      current
    DESCRIPTION 
        "Sets the default interface type for this profile.  The default 
         is the value of sLPConnectionDefaultInterfaceType."
    REFERENCE   
        "ITU-T Rec. X.282 | ISO/IEC 10742."
    ::= { sLPConnectionIVMOEntry 2 }

sLPConnectionIVMOk OBJECT-TYPE
    SYNTAX      Integer32
    MAX-ACCESS  read-create
    STATUS      current
    DESCRIPTION 
        "Sets the default k value for this profile.  The default is the 
         value of sLPConnectionDefaultK."
    REFERENCE   
        "ITU-T Rec. X.282 | ISO/IEC 10742."
    ::= { sLPConnectionIVMOEntry 3 }

sLPConnectionIVMOn1 OBJECT-TYPE
    SYNTAX      Integer32
    MAX-ACCESS  read-create
    STATUS      current
    DESCRIPTION 
        "Sets the default n1 value for this profile.  The default is the 
         value of sLPConnectionDefaultN1."
    REFERENCE   
        "ITU-T Rec. X.282 | ISO/IEC 10742."
    ::= { sLPConnectionIVMOEntry 4 }

sLPConnectionIVMOn2 OBJECT-TYPE
    SYNTAX      Integer32
    MAX-ACCESS  read-create
    STATUS      current
    DESCRIPTION 
        "Sets the default n2 value for this profile.  The default is the 
         value of sLPConnectionDefaultN2."
    REFERENCE   
        "ITU-T Rec. X.282 | ISO/IEC 10742."
    ::= { sLPConnectionIVMOEntry 5 }

sLPConnectionIVMOsequenceModulus OBJECT-TYPE
    SYNTAX      Integer32 (8 | 128)
    MAX-ACCESS  read-create
    STATUS      current
    DESCRIPTION 
        "Sets the default sequence modulus for this profile.  The 
         default is the value of sLPConnectionDefaultSequenceModulus."
    REFERENCE   
        "ITU-T Rec. X.282 | ISO/IEC 10742."
    ::= { sLPConnectionIVMOEntry 6 }

sLPConnectionIVMOt1Timer OBJECT-TYPE
    SYNTAX      TimeInterval
    MAX-ACCESS  read-create
    STATUS      current
    DESCRIPTION 
        "Sets the default initial t1Timer value for this profile.  The 
         default is the value of sLPConnectionDefaultT1Timer."
    REFERENCE   
        "ITU-T Rec. X.282 | ISO/IEC 10742."
    ::= { sLPConnectionIVMOEntry 7 }

sLPConnectionIVMOt2Timer OBJECT-TYPE
    SYNTAX      TimeInterval
    MAX-ACCESS  read-create
    STATUS      current
    DESCRIPTION 
        "Sets the default initial t2Timer value for this profile.  The 
         default is the value of sLPConnectionDefaultT2Timer."
    REFERENCE   
        "ITU-T Rec. X.282 | ISO/IEC 10742."
    ::= { sLPConnectionIVMOEntry 8 }

sLPConnectionIVMOt3Timer OBJECT-TYPE
    SYNTAX      TimeInterval
    MAX-ACCESS  read-create
    STATUS      current
    DESCRIPTION 
        "Sets the default initial t3Timer value for this profile.  The 
         default is the value of sLPConnectionDefaultT3Timer."
    REFERENCE   
        "ITU-T Rec. X.282 | ISO/IEC 10742."
    ::= { sLPConnectionIVMOEntry 9 }

sLPConnectionIVMOt4Timer OBJECT-TYPE
    SYNTAX      TimeInterval
    MAX-ACCESS  read-create
    STATUS      current
    DESCRIPTION 
        "Sets the default initial t4Timer value for this profile.  The 
         default is the value of sLPConnectionDefaultT4Timer."
    REFERENCE   
        "ITU-T Rec. X.282 | ISO/IEC 10742."
    ::= { sLPConnectionIVMOEntry 10 }

sLPConnectionIVMORowStatus OBJECT-TYPE
    SYNTAX      RowStatus
    MAX-ACCESS  read-create
    STATUS      current
    DESCRIPTION 
        "Provides a mechanism whereby management stations, following the 
         RowStatus textual convention of the SNMPv2-TC module, may 
         create or destroy conceptual rows in this table."
    REFERENCE   
        "ITU-T Rec. X.282 | ISO/IEC 10742."
    ::= { sLPConnectionIVMOEntry 11 }

mACDLE OBJECT IDENTIFIER
    ::= { osiTables 17 }

mACDLETable OBJECT-TYPE
    SYNTAX      SEQUENCE OF MACDLEEntry
    MAX-ACCESS  not-accessible
    STATUS      current
    DESCRIPTION 
        "The MAC Data Link Entity managed object class.  There may be 
         multiple instances of the mACDLE managed object in a system.  
         Systems not supported connections to LAN media are not required 
         to support the mACDLE and contained managed objects.
         
         A mACDLE managed object may contain at modes on instance of a 
         mac-specific MO derived from the generic mAC MO.  A mACDLE MO 
         may contain at most one dLSAP MO.  The value of the sap1Address 
         attribute is of no significance.  The cardinality of the 
         userEntityNames attribute is limited to one.
         
         A mACDLE MO may be created and deleted explicitly by management 
         operation or created and deleted automatically as part of 
         system operation.
         
         When the mACDLE MO is operable, the operationalState shall have 
         the value 'enabled'; otherwise, it shall have the value 
         'disabled'.  Transitions of operationalState shall be reported 
         using the stateChange notification.
         
         The mACDLE MOC is derived from the datalinkEntity MOC.  The 
         mACDLE MO contains mAC MOs.
         
         An instance of the mACDLE MO represents an instance of the IEEE 
         802.2 MAC sublayer.  The MAC data link entity can contain mAC 
         MOs.  Each mAC MO instance contained represents a MAC address 
         that belongs to the mACDLE."
    REFERENCE   
        "ITU-T Rec. X.272 | ISO/IEC 10742, mACDLE MOC."
    ::= { mACDLE 1 }

mACDLEEntry OBJECT-TYPE
    SYNTAX      MACDLEEntry
    MAX-ACCESS  not-accessible
    STATUS      current
    DESCRIPTION 
        "Each row in this table is indexed by communications entity 
         identifier.  Each row, beyond membership, is otherwise empty."
    REFERENCE   
        "ITU-T Rec. X.272 | ISO/IEC 10742, mACDLE MO."
    INDEX       { communicationsEntityId }
    ::= { mACDLETable 1 }

MACDLEEntry ::= SEQUENCE {
    mACDLERowStatus     RowStatus
}

mACDLERowStatus OBJECT-TYPE
    SYNTAX      RowStatus
    MAX-ACCESS  read-create
    STATUS      current
    DESCRIPTION 
        "Provides a mechanism whereby management stations may create and 
         delete rows in this table.  Entries must persist across agent 
         reboots."
    REFERENCE   
        "ITU-T Rec. X.282 | ISO/IEC 10742, mACDLE."
    ::= { mACDLEEntry 1 }

mAC OBJECT IDENTIFIER
    ::= { osiTables 18 }

mACTable OBJECT-TYPE
    SYNTAX      SEQUENCE OF MACEntry
    MAX-ACCESS  not-accessible
    STATUS      current
    DESCRIPTION 
        "Provides a table of MAC addresses."
    REFERENCE   
        "ITU-T Rec. X.282 | ISO/IEC 10742 mAC MOC."
    ::= { mAC 1 }

mACEntry OBJECT-TYPE
    SYNTAX      MACEntry
    MAX-ACCESS  not-accessible
    STATUS      current
    DESCRIPTION 
        "Each row in this table is indexed by communications entity 
         identifier and defines the MAC identifier.  Each row contains 
         the operational state of the MAC."
    REFERENCE   
        "ITU-T Rec. X.282 | ISO/IEC 10742 mAC MO."
    INDEX       { communicationsEntityId, mACId }
    ::= { mACTable 1 }

MACEntry ::= SEQUENCE {
    mACOperationalState     OperationalState,
    mACId                   SimpleNameType,
    mACRowStatus            RowStatus
}

mACOperationalState OBJECT-TYPE
    SYNTAX      OperationalState
    MAX-ACCESS  read-only
    STATUS      current
    DESCRIPTION 
        "Provides the X.721 operationalState of the mAC according to the 
         OperationalState textual convention from the OPENSS7-TMN-TC 
         module.  The state is 'enabled' when the mAC is operational; 
         'disabled' otherwise."
    REFERENCE   
        "ITU-T Rec. X.721 | ISO/IEC 10165-2 operationalState."
    ::= { mACEntry 1 }

mACId OBJECT-TYPE
    SYNTAX      SimpleNameType
    MAX-ACCESS  not-accessible
    STATUS      current
    DESCRIPTION 
        "Provides a naming attribute for the mAC MO."
    REFERENCE   
        "ITU-T Rec. X.282 | ISO/IEC 10742 mACId."
    ::= { mACEntry 2 }

mACRowStatus OBJECT-TYPE
    SYNTAX      RowStatus
    MAX-ACCESS  read-create
    STATUS      current
    DESCRIPTION 
        "
         The mACId-mACDLE-Automatic name binding applies when a mAC 
         managed object (or an instance of a subclass of the mAC MO 
         class) is created automatically by the operation of the system 
         as a subordinate object of a mACDLE managed object (or 
         subclass), and deleted automatically.
         
         The mACId-mACDLE-Management name binding applies when a mAC 
         managed object (or an instance of a subclass or the mAC MO 
         class) can be created by management as a subordiante object of 
         a mACDLE managed object (or subclass), and deleted by 
         management."
    REFERENCE   
        "ITU-T Rec. X.282 | ISO/IEC 10742 mACId-mACDLE-Automatic, 
         mACId-mACDLE-Management, STD 58, SNMPv2-TC RowStatus."
    ::= { mACEntry 3 }

lLCDLE OBJECT IDENTIFIER
    ::= { osiTables 19 }

lLCDLETable OBJECT-TYPE
    SYNTAX      SEQUENCE OF LLCDLEEntry
    MAX-ACCESS  not-accessible
    STATUS      current
    DESCRIPTION 
        "The LLC Data Link Entity managed object.  There may be multiple 
         instances of the lLCDLE managed object in a system.  Systems 
         not supporting LLC procedures are not required to support the 
         lLCDLE and contained managed objects.
         
         An lLCDLE managed object may contain instances of llc-specific 
         connectionless and connection-mode protocol machine MOs derived 
         form the generic lLCCOPM and lLCCLPM MO.  An lLCDLE MO may 
         contain multiple dLSAP MOs.  The cardinality of the 
         userEntityNames attribute is limited to one.
         
         An lLCDLE MO may be created and deleted explicity by management 
         operation or created and deleted automatically as part of 
         ssytem operation.
         
         When the lLCDLE MO is operable, the operationalState shall have 
         the value 'enabled'; otherwise it shall have the value 
         'disabled'.  Transitions of operationalState shall be reported 
         using the stateChange notification.
         
         The lLCDLE MOC is derived from the datalinkEntity MOC.  The 
         lLCDLE contains connectionless and connection oriented protocol 
         machines representing LLC1, and LLC2 and/or LLC3 operation.  
         The lLCDLE also contains an LLC station and one or more lLCSAP 
         service access points.
         
         Each lLCDLE MO uses the services of a mACDLE.  The mACDLE 
         provides service to an lLCDLE.  (Note that Ethernet II accesses 
         the MAC sublayer directly, via a dlSAP MO contained by the 
         mACDLE.)
         
         An instance of the lLCDLE MO represents an instance of the IEEE 
         802.2 LLC sublayer.  The LLC data link entity can contain 
         lLCCLPM and lLCCOPM protocol machines MOs, an lLCstation MO, 
         and one or more lLCSAP MOs."
    REFERENCE   
        "ITU-T Rec. X.282 | ISO/IEC 10742, lLCDLE MOC."
    ::= { lLCDLE 1 }

lLCDLEEntry OBJECT-TYPE
    SYNTAX      LLCDLEEntry
    MAX-ACCESS  not-accessible
    STATUS      current
    DESCRIPTION 
        "Each entry in this table is indexed by communications entity 
         identifier.  Each row, beyond membership, is otherwise empty."
    REFERENCE   
        "ITU-T Rec. X.282 | ISO/IEC 10742, lLCDLE MO."
    INDEX       { communicationsEntityId }
    ::= { lLCDLETable 1 }

LLCDLEEntry ::= SEQUENCE {
    lLCDLERowStatus     RowStatus
}

lLCDLERowStatus OBJECT-TYPE
    SYNTAX      RowStatus
    MAX-ACCESS  read-create
    STATUS      current
    DESCRIPTION 
        "Provides a mechanism whereby management stations, following the 
         RowStatus textual convention of the SNMPv2-TC module, may 
         create and destroy conceptual rows in this table.
         
         Rows must have been created by a management station to be 
         deleted by a management station.  Rows created by system 
         operation must be deleted by system operation."
    REFERENCE   
        "STD 58, SNMPv2-TC RowStatus."
    ::= { lLCDLEEntry 1 }

lLCCLPM OBJECT IDENTIFIER
    ::= { osiTables 20 }

lLCCLPMTable OBJECT-TYPE
    SYNTAX      SEQUENCE OF LLCCLPMEntry
    MAX-ACCESS  not-accessible
    STATUS      current
    DESCRIPTION 
        "The LLC Connectionless Protocol Machine managed object.  The 
         generic LLC Connectionless PM MO from which protocol-specific 
         LLC PM MOs bay be derived."
    REFERENCE   
        "ITU-T Rec. X.282 | ISO/IEC 10742"
    ::= { lLCCLPM 1 }

lLCCLPMEntry OBJECT-TYPE
    SYNTAX      LLCCLPMEntry
    MAX-ACCESS  not-accessible
    STATUS      current
    DESCRIPTION 
        "The CL PM is contaned by a datalinkEntity, in this case a 
         lLCDLE.
         
         
         Each entry supports an activation and deactivation action.
         
         Whenever an entry is created, the objectCreation notification 
         is issued.  Whenever an entry is deleted, the objectDeletion 
         notification is issued.  Whenever the operational state changes 
         a stateChange notification is issued.  Objects may be created 
         and deleted by explicity management operation.  Deletion and 
         deactivation have a similar effect, as does creation and 
         activation."
    REFERENCE   
        "ITU-T Rec. X.282 | ISO/IEC 10742"
    INDEX       { communicationsEntityId, clProtocolMachineId }
    ::= { lLCCLPMTable 1 }

LLCCLPMEntry ::= SEQUENCE {
    lLCCLPMRowStatus    RowStatus
}

lLCCLPMRowStatus OBJECT-TYPE
    SYNTAX      RowStatus
    MAX-ACCESS  read-create
    STATUS      current
    DESCRIPTION 
        "Provides a mechanism whereby management stations, following the 
         RowStatus textual convention of the SNMPv2-TC module, may 
         create or delete conceptual rows from this table.
         
         The lLCCLPM-lLCDLE-Management name binding applies when an 
         lLCCLPM managed object (or an instance of a subclass of the 
         lLCCLPM MO class) can be created by management as a subordinate 
         object of a lLCDLE managed object (or subclasses), and deleted 
         by mangement."
    REFERENCE   
        "ITU-T Rec. X.282 | ISO/IEC 10742, lLCCLPM-lLCDLE-Management, 
         STD 58, SNMPv2-TC RowStatus."
    ::= { lLCCLPMEntry 1 }

lLCCOPM OBJECT IDENTIFIER
    ::= { osiTables 21 }

lLCCOPMTable OBJECT-TYPE
    SYNTAX      SEQUENCE OF LLCCOPMEntry
    MAX-ACCESS  not-accessible
    STATUS      current
    DESCRIPTION 
        "The LLC Connection-mode Protocol Machine managed object.  The 
         generic LLC Connection-mode PM MO from which protocol specific 
         LLC PM MOs may be derived."
    ::= { lLCCOPM 1 }

lLCCOPMEntry OBJECT-TYPE
    SYNTAX      LLCCOPMEntry
    MAX-ACCESS  not-accessible
    STATUS      current
    DESCRIPTION 
        "Each row in this table is indexed by communications entity and 
         connection-oriented protocol machine identifiers.  Each row, 
         beyond membership, is otherwise empty."
    INDEX       { communicationsEntityId, coProtocolMachineId }
    ::= { lLCCOPMTable 1 }

LLCCOPMEntry ::= SEQUENCE {
    lLCCOPMRowStatus    RowStatus
}

lLCCOPMRowStatus OBJECT-TYPE
    SYNTAX      RowStatus
    MAX-ACCESS  read-create
    STATUS      current
    DESCRIPTION 
        "Provides a mechanism whereby management stations, following the 
         RowStatus textual convention of the SNMPv2-TC module, may 
         create or delete conceptual rows from this table.
         
         The lLCCOPM-lLCDLE-Management name binding applies when an 
         lLCCOPM managed object (or an instance of a subclass of the 
         lLCCOPM MO class) can be created by management as a subordinate 
         object of a lLCDLE managed object (or subclasses), and deleted 
         by mangement."
    REFERENCE   
        "ITU-T Rec. X.282 | ISO/IEC 10742, lLCCOPM-lLCDLE-Management, 
         STD 58, SNMPv2-TC RowStatus."
    ::= { lLCCOPMEntry 1 }

resourceTypeId OBJECT IDENTIFIER
    ::= { osiTables 22 }

resourceTypeIdTable OBJECT-TYPE
    SYNTAX      SEQUENCE OF ResourceTypeIdEntry
    MAX-ACCESS  not-accessible
    STATUS      current
    DESCRIPTION 
        "Provides a table of resources associated with MAC DLEs."
    REFERENCE   
        "ISO/IEC 10742 but not ITU-T Rec. X.282"
    ::= { resourceTypeId 1 }

resourceTypeIdEntry OBJECT-TYPE
    SYNTAX      ResourceTypeIdEntry
    MAX-ACCESS  not-accessible
    STATUS      current
    DESCRIPTION 
        "Each row in this table is indexed by communications entity 
         identifier which identifies the MAC DLE.  Each row contains the 
         available resources associated with the MAC DLE."
    REFERENCE   
        "ISO/IEC 10742 but not ITU-T Rec. X.282"
    INDEX       { communicationsEntityId }
    ::= { resourceTypeIdTable 1 }

ResourceTypeIdEntry ::= SEQUENCE {
    resourceTypeIdName                      SimpleNameType,
    resourceInfoManufacturerOUI             OCTET STRING,
    resourceInfoManufacturerName            DisplayString,
    resourceInfoManufacturerProductName     DisplayString,
    resourceInfoManufacturerProductVersion  DisplayString
}

resourceTypeIdName OBJECT-TYPE
    SYNTAX      SimpleNameType
    MAX-ACCESS  read-only
    STATUS      current
    DESCRIPTION 
        "Provides an simple name for the resource entry."
    REFERENCE   
        "ISO/IEC 10742 but not ITU-T Rec. X.282"
    DEFVAL      { "RTID" }
    ::= { resourceTypeIdEntry 1 }

resourceInfoManufacturerOUI OBJECT-TYPE
    SYNTAX      OCTET STRING
    MAX-ACCESS  read-only
    STATUS      current
    DESCRIPTION 
        "ManufacturerOUI takes the value of an Organizationally Unique 
         Identifier, as defined in secion 5.1 of IEEE 802.1 Overview and 
         Architecture.  When encoded as an OCTET STRING, the encoding of 
         the value field of the OCTET STRING shall comply with the 
         representation defined in sections 5.1.2 of the Overview and 
         Architecture.  Inasmcuh as multiple OUI assignements are 
         possible for a given manufacturer and no public registry of 
         such assigments exists, methods for application of the OUI as a 
         globally unique manufacturer identifier is outside the scope of 
         this standard."
    REFERENCE   
        "ISO/IEC 10742 but not ITU-T Rec. X.282"
    ::= { resourceTypeIdEntry 2 }

resourceInfoManufacturerName OBJECT-TYPE
    SYNTAX      DisplayString (SIZE(0..128))
    MAX-ACCESS  read-only
    STATUS      current
    DESCRIPTION 
        "ManufactererName is a printable string used to identify the 
         manufacturer of the resource.  Global assignment of unique name 
         strngs is outside the scope of this standard.  Maximum string 
         length is 128 octets."
    REFERENCE   
        "ISO/IEC 10742 but not ITU-T Rec. X.282"
    ::= { resourceTypeIdEntry 3 }

resourceInfoManufacturerProductName OBJECT-TYPE
    SYNTAX      DisplayString (SIZE(0..128))
    MAX-ACCESS  read-only
    STATUS      current
    DESCRIPTION 
        "ManufactererProductName is a printable string used to identify 
         the manufacturer's product name of the resource.  Maximum 
         string length is 128 octets."
    REFERENCE   
        "ISO/IEC 10742 but not ITU-T Rec. X.282"
    ::= { resourceTypeIdEntry 4 }

resourceInfoManufacturerProductVersion OBJECT-TYPE
    SYNTAX      DisplayString (SIZE(0..128))
    MAX-ACCESS  read-only
    STATUS      current
    DESCRIPTION 
        "ManufacturerProductVersion is a printable string used to 
         identify the manufacturer's product version of the resource.  
         Maximum string length is 128."
    REFERENCE   
        "ISO/IEC 10742 but not ITU-T Rec. X.282"
    ::= { resourceTypeIdEntry 5 }

lLCStation OBJECT IDENTIFIER
    ::= { osiTables 23 }

lLCStationTable OBJECT-TYPE
    SYNTAX      SEQUENCE OF LLCStationEntry
    MAX-ACCESS  not-accessible
    STATUS      current
    DESCRIPTION 
        "The station component is responsible for processing the events 
         that affect the entire LLC entity.  The station component 
         handles PDUs addressed to the null DSAP address and processes 
         the duplicate address check, if implemented.  One station 
         component shall exist for each MAC service access point present 
         on the local area network.
         
         Provides a table of LLC Stations.  There is in entry in this 
         table for each MAC service access point present on the local 
         area network.
         
         Provides a table of statistics for LLC stations.  There is an 
         entry in this table for each MAC service access point present 
         on a local area network attached to this system."
    REFERENCE   
        "IEEE 802.2 | ISO/IEC 8802-2, lLCStation MOC."
    ::= { lLCStation 1 }

lLCStationEntry OBJECT-TYPE
    SYNTAX      LLCStationEntry
    MAX-ACCESS  not-accessible
    STATUS      current
    DESCRIPTION 
        "The station component is responsible for handling all events 
         that are directed to the LLC as a whole (i.e, events affecting 
         all SAPs and connections serviced by that LLC).  The station 
         component shall begin in the DOWN state, optionally check for a 
         duplicate station address, and potentially enter the UP state; 
         see figure 
         24 and table 1 of IEEE 802.2 (ISO/IEC 8802-2).  The UP state of 
            the LLC station component provides the enabling conditions 
            for the operation of the service access point (SAP) 
            components.
         
         The station component shall be capable of receiving and 
         responding to XID and TEST command PDUs.  It shall optionally 
         be capable of initiating the XID commend PDU, if duplicate 
         address checking is performed by the LLC entity in a particular 
         implementation; see table 2 of IEEE 802.2 (ISO/IEC 8802-2).  
         These PDUs shall used the null DSAP address to denote that the 
         station component is being referenced.
         
         The performance of the duplicate address check requires that 
         the station component be prepared to received its own XID PDUs.  
         The definition of the MAC operation provides for the ability to 
         simultaneously transmit and receive.  Since the DA = SA in the 
         XID PDUs can be used for duplicate address check, the MAC will 
         recognize its own address and pass the PDU to the station 
         component.  The station component will respond to an XID 
         command PDU with an XID responose PDU, regardless of whether it 
         originated from itself or a remote LLC.  The station component 
         provides the duplicate address check by maintaining a count of 
         received XID response PDUs.  If more than one XID response PDU 
         is received, then at least one other identical MAC DA exists on 
         the LAN.  See figure 24 and table 1 in IEEE 802.2 (ISO/IEC 
         8802-2) for details.
         
         Provides an entry in the X.25 LLC2 Station table for one LLC2 
         connection to the media (MAC Access).  Each MAC is indexed by 
         its ifIndex into the interface table.
         
         Provides an enty in the X.25 LLC Station table for one LLC 
         connection to the media (MAC Access).  Each MAC is indexed by 
         its ifIndex into the interface table."
    REFERENCE   
        "IEEE 802.2 | ISO/IEC 8802-2, lLCStation MO."
    INDEX       { communicationsEntityId, sapId }
    ::= { lLCStationTable 1 }

LLCStationEntry ::= SEQUENCE {
    lLCStationLLCName                           SimpleNameType,
    lLCStationMaximumLSAPsConfigured            Integer32,
    lLCStationNumberOfActiveLSAPs               Gauge32,
    lLCStationSupportedServicesTypes            LLCServices,
    lLCStationStatus                            LLCStationStatus,
    lLCStationType1AcknowledgeTimeoutValue      TimeInterval,
    lLCStationType1MaximumRetryCount            Integer32,
    lLCStationMaximumPDUN3                      Integer32,
    lLCStationMaximumRetransmissions4           Integer32,
    lLCStationReceiveVariableLifetime           TimeInterval,
    lLCStationTransmitVariableLifetime          TimeInterval,
    lLCStationType3AcknowledgeTimeoutValue      TimeInterval,
    lLCStationType3Retransmissions              Counter32,
    lLCStationAvgBufferUseSize                  Gauge32,
    lLCStationBufferProblems                    Counter32,
    lLCStationBufferSize                        Integer32,
    lLCStationMaxBufferUseSize                  Gauge32,
    lLCStationInactiveLSAP                      Counter32,
    lLCStationPDUsDiscard                       Counter32,
    lLCStationSTRIndicator                      STRIndicator,
    lLCStationVersionNumber                     Integer32,
    lLCStationType1AcknowledgmentTimerTimeouts  Counter32
}

lLCStationLLCName OBJECT-TYPE
    SYNTAX      SimpleNameType
    MAX-ACCESS  read-write
    STATUS      current
    DESCRIPTION 
        "This attriute is used to name the instance of the lLCStation 
         managed object."
    REFERENCE   
        "IEEE 802.2 | ISO/IEC 8802-2, lLCName"
    ::= { lLCStationEntry 1 }

lLCStationMaximumLSAPsConfigured OBJECT-TYPE
    SYNTAX      Integer32 (1..128)
    UNITS       "LSAPs"
    MAX-ACCESS  read-only
    STATUS      current
    DESCRIPTION 
        "The maximum number of LSAPs that can be supported by this 
         station at any moment in time.  All LLC stations must support 
         at least one LSAP (the null LSAP used for duplicate address 
         detection and station-wide XID and TEST commands).  Station 
         numbers (LSAP IDs) range from 
         0 to 127.  Therefore, the range of this value is from 1 to 128.  
           IEEE 802.2F (ISO/IEC 8802-2) does not constrain the range of 
           this attribute.  The number reported is implementation 
           dependent.  This is a read-only column."
    REFERENCE   
        "IEEE 802.2 | ISO/IEC 8802-2, maximumLSAPsConfigured"
    ::= { lLCStationEntry 2 }

lLCStationNumberOfActiveLSAPs OBJECT-TYPE
    SYNTAX      Gauge32 (1..128)
    UNITS       "LSAPs"
    MAX-ACCESS  read-only
    STATUS      current
    DESCRIPTION 
        "The number of active LSAPs that the station currently 
         supports."
    REFERENCE   
        "IEEE 802.2 | ISO/IEC 8802-2, numberOfActiveLSAPs"
    ::= { lLCStationEntry 3 }

lLCStationSupportedServicesTypes OBJECT-TYPE
    SYNTAX      LLCServices
    MAX-ACCESS  read-write
    STATUS      current
    DESCRIPTION 
        "The type or types of service supported (i.e., Type 1, Type 2, 
         Type 3.) The type or types of service supported by this 
         station.  The type are a combination of 
         
         - type1(0),
         - type2(1),
         - type3Initiate(2),
         - kype3ReceiveData(3),
         - type3ReturnData(4).
         
         Implementations supporting this MIB must support at least 
         type1(0) and should support type2(1) if at all possible."
    REFERENCE   
        "IEEE 802.2 | ISO/IEC 8802-2, supportedServicesTypes"
    ::= { lLCStationEntry 4 }

lLCStationStatus OBJECT-TYPE
    SYNTAX      LLCStationStatus
    MAX-ACCESS  read-only
    STATUS      current
    DESCRIPTION 
        "Provides the status of the station.  This attribute allows a 
         manager to determine what state (UP, DOWN, etc.) the LLC 
         Station entity is in.  Note that the only reason that the 
         integer values start at zero (0) here instead of one (1) is 
         that the values are already defined in the GDMO MIBs of IEEE 
         802.2 (ISO/IEC 8802-2)."
    REFERENCE   
        "IEEE 802.2 | ISO/IEC 8802-2, status"
    ::= { lLCStationEntry 5 }

lLCStationType1AcknowledgeTimeoutValue OBJECT-TYPE
    SYNTAX      TimeInterval
    MAX-ACCESS  read-write
    STATUS      current
    DESCRIPTION 
        "The timeout value of the Ack timer, which is measured in 
         centiseconds, displayed in seconds.  THe Ack timer is described 
         in IEEE 802.2 (ISO/IEC 8802-2) 6.9.2.2 and 
         6.9.2.3.  It is used by the station to supervise the 
           acknowledgement of an XID message sent to detect duplicate 
           MAC addresses.  If no XID response message is received within 
           this time period, the XID message will be reattempted up to 
           the maximum retry count."
    REFERENCE   
        "IEEE 802.2 (ISO/IEC 8802-2), type1AcknowledgeTimeoutValue, 
         6.9.2.2 and 6.9.2.3."
    ::= { lLCStationEntry 6 }

lLCStationType1MaximumRetryCount OBJECT-TYPE
    SYNTAX      Integer32
    UNITS       "retries"
    MAX-ACCESS  read-write
    STATUS      current
    DESCRIPTION 
        "The maximum number of retries during duplicate address 
         checking.  If the acknowledgement timer expires after sending 
         an XID message for duplicate address checking, the XID message 
         will be retransmitted this number of times, before moving to 
         the UP state."
    REFERENCE   
        "ISO/IEC 8802-2 (IEEE 802.2), type1MaximumRetryCount, 
         6.9.2.2 and 6.9.2.3."
    ::= { lLCStationEntry 7 }

lLCStationMaximumPDUN3 OBJECT-TYPE
    SYNTAX      Integer32
    UNITS       "octets"
    MAX-ACCESS  read-write
    STATUS      current
    DESCRIPTION 
        "The maximum size of a Type 3 command PDU.
         
         Unless Type 3 service is supported on the LLC station, this 
         value is of no significance."
    REFERENCE   
        "IEEE 802.2 | ISO/IEC 8802-2, maximumPDUN3"
    ::= { lLCStationEntry 8 }

lLCStationMaximumRetransmissions4 OBJECT-TYPE
    SYNTAX      Integer32
    UNITS       "retransmissions"
    MAX-ACCESS  read-write
    STATUS      current
    DESCRIPTION 
        "The number of retransmissions of a Type 3 PDU due to error 
         conditions preventing receive of an acknowledgement.
         
         Unless Type 3 service is supported on the LLC station, this 
         value is of no significance."
    REFERENCE   
        "IEEE 802.2 | ISO/IEC 8802-2, maximumRetransmissions4"
    ::= { lLCStationEntry 9 }

lLCStationReceiveVariableLifetime OBJECT-TYPE
    SYNTAX      TimeInterval
    MAX-ACCESS  read-write
    STATUS      current
    DESCRIPTION 
        "The amount of time the Type 3 LLC receive state variables are 
         maintained.
         
         Unless Type 3 service is suported on the LLC station, this 
         value is of no significance."
    REFERENCE   
        "IEEE 802.2 | ISO/IEC 8802-2, receiveVariableLifetime"
    ::= { lLCStationEntry 10 }

lLCStationTransmitVariableLifetime OBJECT-TYPE
    SYNTAX      TimeInterval
    MAX-ACCESS  read-write
    STATUS      current
    DESCRIPTION 
        "The amout of time the Type 3 LLC transmit state variables are 
         maintained.
         
         Unless Type 3 service is supported on the LLC station, this 
         value is of no significance."
    REFERENCE   
        "IEEE 802.2 | ISO/IEC 8802-2, transmitVariableLifetime"
    ::= { lLCStationEntry 11 }

lLCStationType3AcknowledgeTimeoutValue OBJECT-TYPE
    SYNTAX      TimeInterval
    MAX-ACCESS  read-write
    STATUS      current
    DESCRIPTION 
        "Specifies the time interval during which the LLC expects to 
         receive a response to an acknowledged connectionless request.
         
         Unless Type 3 service is supported by the LLC station, this 
         value is of no significance."
    REFERENCE   
        "IEEE 802.2 | ISO/IEC 8802-2, type3AcknowledgeTimeoutValue"
    ::= { lLCStationEntry 12 }

lLCStationType3Retransmissions OBJECT-TYPE
    SYNTAX      Counter32
    UNITS       "octets"
    MAX-ACCESS  read-only
    STATUS      current
    DESCRIPTION 
        "Provides a count of the number of PDUs which were retrasmitted 
         (at least once) by the Type 3 LLC service.
         
         Provides a count of the number of PDUs which were retransmitted 
         (at least once) by the Type 3 LLC service.  This value is of no 
         significance unless the LLC station supports Type 3 operation."
    REFERENCE   
        "IEEE 802.2 | ISO/IEC 8802-2, type3Retransmissions"
    ::= { lLCStationEntry 13 }

lLCStationAvgBufferUseSize OBJECT-TYPE
    SYNTAX      Gauge32
    UNITS       "octets"
    MAX-ACCESS  read-only
    STATUS      current
    DESCRIPTION 
        "Specifies the average amount of buffer space (in octets) in use 
         at the same time by LLC for this station."
    REFERENCE   
        "IEEE 802.2 | ISO/IEC 8802-2, avgBufferUseSize"
    ::= { lLCStationEntry 14 }

lLCStationBufferProblems OBJECT-TYPE
    SYNTAX      Counter32
    UNITS       "PDUs"
    MAX-ACCESS  read-only
    STATUS      current
    DESCRIPTION 
        "This counter provides a count of PDUs discarded due to buffer 
         limitations."
    REFERENCE   
        "IEEE 802.2 | ISO/IEC 8802-2, bufferProblems"
    ::= { lLCStationEntry 15 }

lLCStationBufferSize OBJECT-TYPE
    SYNTAX      Integer32
    UNITS       "octets"
    MAX-ACCESS  read-write
    STATUS      current
    DESCRIPTION 
        "THe amount of buffer space (in octets) for use by LLC."
    REFERENCE   
        "IEEE 802.2 | ISO/IEC 8802-2, bufferSize"
    ::= { lLCStationEntry 16 }

lLCStationMaxBufferUseSize OBJECT-TYPE
    SYNTAX      Gauge32
    UNITS       "octets"
    MAX-ACCESS  read-only
    STATUS      current
    DESCRIPTION 
        "Specifies the maximum amount of buffer space (in octets) in use 
         at the same time by LLC for this station."
    REFERENCE   
        "IEEE 802.2 | ISO/IEC 8802-2, maxBufferUseSize"
    ::= { lLCStationEntry 17 }

lLCStationInactiveLSAP OBJECT-TYPE
    SYNTAX      Counter32
    UNITS       "PDUs"
    MAX-ACCESS  read-only
    STATUS      current
    DESCRIPTION 
        "This counts the number of PDUs discarded due to the 
         specification of an inactive DSAP."
    REFERENCE   
        "IEEE 802.2 | ISO/IEC 8802-2, inactiveLSAP"
    ::= { lLCStationEntry 18 }

lLCStationPDUsDiscard OBJECT-TYPE
    SYNTAX      Counter32
    UNITS       "invalid PDUs"
    MAX-ACCESS  read-only
    STATUS      current
    DESCRIPTION 
        "Provides a total count of invalid PDUs that are discarded.  A 
         discarded (invalid) PDU shall be defined as one that meets at 
         least one of the following coniditions:
         
         1. It is identified by such by the PHY or the MAC sublayer;
         2. It is not an integral number of octets in length;
         3. It does not contain two properly formatted address fields, 
            one control field, and optionally an information field in 
            their proper order.
         4. Its length is less that 3 octets (one-octet control field) 
            or 4 octets (two-octet control field)."
    REFERENCE   
        "IEEE 802.2 | ISO/IEC 8802-2, pDUsDiscard"
    ::= { lLCStationEntry 19 }

lLCStationSTRIndicator OBJECT-TYPE
    SYNTAX      STRIndicator
    MAX-ACCESS  read-write
    STATUS      current
    DESCRIPTION 
        "A value that indicates if the spanning tree will be traversed 
         by a NSR or STE routing."
    REFERENCE   
        "IEEE 802.2 | ISO/IEC 8802-2, sTRIndicator"
    ::= { lLCStationEntry 20 }

lLCStationVersionNumber OBJECT-TYPE
    SYNTAX      Integer32
    MAX-ACCESS  read-write
    STATUS      current
    DESCRIPTION 
        "The version of sap RDE protocol implemented at this station.  
         The value of 1 will be used to represent the current version.  
         The special value zero (0) indicates that RDE is not support at 
         this station."
    REFERENCE   
        "IEEE 802.2 | ISO/IEC 8802-2, versionNumber"
    ::= { lLCStationEntry 21 }

lLCStationType1AcknowledgmentTimerTimeouts OBJECT-TYPE
    SYNTAX      Counter32
    UNITS       "ACK timer expiries"
    MAX-ACCESS  read-only
    STATUS      current
    DESCRIPTION 
        "Specifies the number of times the ACK timer has expired."
    REFERENCE   
        "ISO/IEC 8802-2 (IEEE 802.2), type1AcknowledgmentTimerTimeouts, 
         6.9.2.2 and 6.9.2.3."
    ::= { lLCStationEntry 22 }

lLCSAP OBJECT IDENTIFIER
    ::= { osiTables 24 }

lLCSAPTable OBJECT-TYPE
    SYNTAX      SEQUENCE OF LLCSAPEntry
    MAX-ACCESS  not-accessible
    STATUS      current
    DESCRIPTION 
        "The Link Service Access Point (SAP) component  is responsible 
         for processing the events that affect a specific operating 
         service access point.  One SAP component shall exist for each 
         SAP within the LLC entity.
         
         lLCSAP managed object.  This managed object contains attributes 
         associated wtih an LLC SAP that are independent of any 
         paticular type of Operation."
    REFERENCE   
        "IEEE 802.2 (ISO/IEC 8802-2)."
    ::= { lLCSAP 1 }

lLCSAPEntry OBJECT-TYPE
    SYNTAX      LLCSAPEntry
    MAX-ACCESS  not-accessible
    STATUS      current
    DESCRIPTION 
        "Each row in this table is indexed by communications entity and 
         SAP identifiers.  Each row contains the LSAP and whether RDE is 
         provided."
    REFERENCE   
        "IEEE 802.2 (ISO/IEC 8802-2)."
    INDEX       { communicationsEntityId, sapId }
    ::= { lLCSAPTable 1 }

LLCSAPEntry ::= SEQUENCE {
    lLCSAPName      SimpleNameType,
    lLCSAPAddress   LSAP,
    lLCSAPRDE       TruthValue
}

lLCSAPName OBJECT-TYPE
    SYNTAX      SimpleNameType
    MAX-ACCESS  not-accessible
    STATUS      current
    DESCRIPTION 
        "Used to name the instance of this lLCSAP managed object within 
         the scope of a containing lLCDLE managed object."
    REFERENCE   
        "IEEE 802.2 (ISO/IEC 8802-2), lLCSAPName."
    ::= { lLCSAPEntry 1 }

lLCSAPAddress OBJECT-TYPE
    SYNTAX      LSAP
    MAX-ACCESS  read-only
    STATUS      current
    DESCRIPTION 
        "The individual LLC address identifying this LSAP."
    REFERENCE   
        "IEEE 802.2 (ISO/IEC 8802-2), lLCAddress."
    ::= { lLCSAPEntry 2 }

lLCSAPRDE OBJECT-TYPE
    SYNTAX      TruthValue
    MAX-ACCESS  read-only
    STATUS      current
    DESCRIPTION 
        "A boolean value that, if set to true, means that RDE is 
         supported by this SAP."
    REFERENCE   
        "IEEE 802.2 (ISO/IEC 8802-2), rDE."
    ::= { lLCSAPEntry 3 }

rDESetup OBJECT IDENTIFIER
    ::= { osiTables 25 }

rDESetupTable OBJECT-TYPE
    SYNTAX      SEQUENCE OF RDESetupEntry
    MAX-ACCESS  not-accessible
    STATUS      current
    DESCRIPTION 
        "RDE setup managed object.  A rDESetup managed object instance 
         is instaniated if an instance of the lLCSAP object enables RDE.  
         RDE setup managed objects are not created nor deleted 
         explicitly by management operation."
    REFERENCE   
        "IEEE 802.2 | ISO/IEC 8802-2 rDESetup MOC."
    ::= { rDESetup 1 }

rDESetupEntry OBJECT-TYPE
    SYNTAX      RDESetupEntry
    MAX-ACCESS  not-accessible
    STATUS      current
    DESCRIPTION 
        "Each row in this table is indexed by communications entity and 
         SAP identifiers.  Each row contains information regarding RDE 
         operation for the LLC SAP."
    REFERENCE   
        "IEEE 802.2 | ISO/IEC 8802-2 rDESetup MO."
    INDEX       { communicationsEntityId, sapId }
    ::= { rDESetupTable 1 }

RDESetupEntry ::= SEQUENCE {
    rDESetupAgingEnabled                TruthValue,
    rDESetupAgingValue                  Integer32,
    rDESetupEnableType2Reset            Integer32,
    rDESetupMaximumRouteDescriptors     Integer32,
    rDESetupMaximumResponseTime         TimeInterval,
    rDESetupMinimumPDUSize              Integer32,
    rDESetupRDEHold                     TruthValue,
    rDESetupRDEReplace                  TruthValue,
    rDESetupName                        Integer32,
    rDESetupResetOnTestEnabled          TruthValue
}

rDESetupAgingEnabled OBJECT-TYPE
    SYNTAX      TruthValue
    MAX-ACCESS  read-write
    STATUS      current
    DESCRIPTION 
        "A boolean value representing the policy that, when true, allows 
         a manager to age a route."
    REFERENCE   
        "IEEE 802.2 (ISO/IEC 8802-2), agingEnabled."
    ::= { rDESetupEntry 1 }

rDESetupAgingValue OBJECT-TYPE
    SYNTAX      Integer32
    MAX-ACCESS  read-write
    STATUS      current
    DESCRIPTION 
        "A value used to determine if a route should be flushed due to 
         inactivity for a specified time period."
    REFERENCE   
        "IEEE 802.2 (ISO/IEC 8802-2), agingValue."
    ::= { rDESetupEntry 2 }

rDESetupEnableType2Reset OBJECT-TYPE
    SYNTAX      Integer32
    MAX-ACCESS  read-write
    STATUS      current
    DESCRIPTION 
        "A value used to determine whether to enable Type 2 reset."
    REFERENCE   
        "IEEE 802.2 (ISO/IEC 8802-2), enableType2Reset."
    ::= { rDESetupEntry 3 }

rDESetupMaximumRouteDescriptors OBJECT-TYPE
    SYNTAX      Integer32
    MAX-ACCESS  read-write
    STATUS      current
    DESCRIPTION 
        "The maximum number or route descriptors that an acceptable 
         route may contain."
    REFERENCE   
        "IEEE 802.2 (ISO/IEC 8802-2), maximumRouteDescriptors."
    ::= { rDESetupEntry 4 }

rDESetupMaximumResponseTime OBJECT-TYPE
    SYNTAX      TimeInterval
    MAX-ACCESS  read-write
    STATUS      current
    DESCRIPTION 
        "The timer value used to limit the maximum route trip response 
         time allowed for route discovery and consequently the maximum 
         time a PDU can reamin in the system."
    REFERENCE   
        "IEEE 802.2 (ISO/IEC 8802-2), maximumResponseTime."
    ::= { rDESetupEntry 5 }

rDESetupMinimumPDUSize OBJECT-TYPE
    SYNTAX      Integer32
    MAX-ACCESS  read-write
    STATUS      current
    DESCRIPTION 
        "The minimum number of octets that must be supported by an 
         acceptable route as indicated by the LF bits of the routing 
         information field."
    REFERENCE   
        "IEEE 802.2 (ISO/IEC 8802-2), minimumPDUSize."
    ::= { rDESetupEntry 6 }

rDESetupRDEHold OBJECT-TYPE
    SYNTAX      TruthValue
    MAX-ACCESS  read-write
    STATUS      current
    DESCRIPTION 
        "A boolean value representing the policy that, when true, 
         requires RDE to withhold sending PDUs while changing routes."
    REFERENCE   
        "IEEE 802.2 (ISO/IEC 8802-2), rDEHold."
    ::= { rDESetupEntry 7 }

rDESetupRDEReplace OBJECT-TYPE
    SYNTAX      TruthValue
    MAX-ACCESS  read-write
    STATUS      current
    DESCRIPTION 
        "A boolean value representing the policy that, when true, 
         enables the RDE to use the route selected by the remote 
         station."
    REFERENCE   
        "IEEE 802.2 (ISO/IEC 8802-2), rDEReplace."
    ::= { rDESetupEntry 8 }

rDESetupName OBJECT-TYPE
    SYNTAX      Integer32
    MAX-ACCESS  read-only
    STATUS      current
    DESCRIPTION 
        "Naming attribute for the rDESetup managed object."
    REFERENCE   
        "IEEE 802.2 (ISO/IEC 8802-2), rDESetupName."
    ::= { rDESetupEntry 9 }

rDESetupResetOnTestEnabled OBJECT-TYPE
    SYNTAX      TruthValue
    MAX-ACCESS  read-write
    STATUS      current
    DESCRIPTION 
        "This attribute is a boolean value.  If the attribute is true, 
         then if a test frame is rceieved the source route is reset."
    REFERENCE   
        "IEEE 802.2 (ISO/IEC 8802-2), resetOnTestEnabled."
    ::= { rDESetupEntry 10 }

rDEPair OBJECT IDENTIFIER
    ::= { osiTables 26 }

rDEPairTable OBJECT-TYPE
    SYNTAX      SEQUENCE OF RDEPairEntry
    MAX-ACCESS  not-accessible
    STATUS      current
    DESCRIPTION 
        "
         RDE pair managed object.  An instance of this managed object 
         will exist for each RDE pair used by any type of LLC service 
         provided.  This managed object contains the local MAC address 
         and local SAP and the remote MAC address and remote SAP, plus 
         counters.
         
         An instance of this managed object will exist for each RDE pair 
         used by any type of LLC service provided. This managed object 
         contains the local MAC address and local SAP and the remote MAC 
         address and remote SAP, plus counters.
         
         Provides a table that lists the pairing of local LSAP and MAC 
         with remote LSAP Id and MAC, as a pair for use by the route 
         determination entity (RDE)."
    REFERENCE   
        "IEEE 802.2 (ISO/IEC 8802-2) rDEPair MOC."
    ::= { rDEPair 1 }

rDEPairEntry OBJECT-TYPE
    SYNTAX      RDEPairEntry
    MAX-ACCESS  not-accessible
    STATUS      current
    DESCRIPTION 
        "Provides an entry into the rDEPairTable which represets the 
         route determination entity routing information for one local 
         LSAP/MAC and remote LSAPId/MAC pair.  The pair is indexed by 
         the rDEPairIndex which indicates the local LLC station and the 
         rDEPairName which indicates the remote LLC station.
         
         Each entry can have the flushRoute action performed on it.  The 
         flushRoute action takes no parameters.  This action will be 
         sent when management requests an RDE Parit o flush its route.  
         This does not cause the RDE to discover a new route.
         
         Each entry can have the the readCounters action performed on 
         it.  The readCounters action will be sent when management 
         requests information concerning RDE counters."
    REFERENCE   
        "IEEE 802.2 (ISO/IEC 8802-2) rDEPair MO."
    INDEX       { communicationsEntityId, sapId, rDEPairName }
    ::= { rDEPairTable 1 }

RDEPairEntry ::= SEQUENCE {
    rDEPairName                 LSAPPairId,
    rDEPairDiscardCounter       Counter32,
    rDEPairNSRPDUCounter        Counter32,
    rDEPairNSRSelectedCounter   Counter32,
    rDEPairRIF                  RoutingInformationField,
    rDEPairSRFPDUCounter        Counter32,
    rDEPairQueryCounter         Counter32
}

rDEPairName OBJECT-TYPE
    SYNTAX      LSAPPairId
    MAX-ACCESS  not-accessible
    STATUS      current
    DESCRIPTION 
        "The local LSAP and remote LSAPId and the local and remote MAC 
         Addresses.  Because the local LSAP and local MAC address are 
         implied by this LAN station, only the remote LSAPId and remote 
         MAC are provided in this attribute.  The field is encoded as a 
         MACAddress textual convenstion (6 octet or 8 octet MAC address) 
         except that it is also followed by a single octet inicating the 
         remote LSAPId and can have values between 
         0 and 127."
    REFERENCE   
        "IEEE 802.2 (ISO/IEC 8802-2) rDEPairName."
    ::= { rDEPairEntry 1 }

rDEPairDiscardCounter OBJECT-TYPE
    SYNTAX      Counter32
    MAX-ACCESS  read-only
    STATUS      current
    DESCRIPTION 
        "A value that represents the number of times a new selection has 
         been made."
    REFERENCE   
        "IEEE 802.2 (ISO/IEC 8802-2) discardCounter."
    ::= { rDEPairEntry 2 }

rDEPairNSRPDUCounter OBJECT-TYPE
    SYNTAX      Counter32
    UNITS       "frames"
    MAX-ACCESS  read-only
    STATUS      current
    DESCRIPTION 
        "A value that represents the number of frames without a routing 
         field."
    REFERENCE   
        "IEEE 802.2 (ISO/IEC 8802-2) nSRPDUCounter."
    ::= { rDEPairEntry 3 }

rDEPairNSRSelectedCounter OBJECT-TYPE
    SYNTAX      Counter32
    MAX-ACCESS  read-only
    STATUS      current
    DESCRIPTION 
        "A value that represents the number of times that acceptable SRF 
         route existed resulting in the selection of the NSR path."
    REFERENCE   
        "IEEE 802.2 (ISO/IEC 8802-2) nSRSelectedCounter."
    ::= { rDEPairEntry 4 }

rDEPairRIF OBJECT-TYPE
    SYNTAX      RoutingInformationField
    MAX-ACCESS  read-only
    STATUS      current
    DESCRIPTION 
        "The routing information field varies in length up to 30 octets.  
         When source routing is not used the RIF is said to be NULL and 
         contains no information.  The first bit of the MAC source 
         address is defined as the Routing Information Indicator (RII). 
         When the RIF is null, the RII is set to zero (0).  When the RIF 
         is not null, the RII is set to 1.  The first two octets are the 
         Routing Control field (RC) and the remainder of the RIF 
         contains Routing Descriptors (RD).  Each RD is two octets in 
         length, therefore a maximum of 14 RDs can exists in a RIF."
    REFERENCE   
        "IEEE 802.2 (ISO/IEC 8802-2) rIF."
    ::= { rDEPairEntry 5 }

rDEPairSRFPDUCounter OBJECT-TYPE
    SYNTAX      Counter32
    UNITS       "frames"
    MAX-ACCESS  read-only
    STATUS      current
    DESCRIPTION 
        "A value that represents the number of frames with routing 
         field."
    REFERENCE   
        "IEEE 802.2 (ISO/IEC 8802-2) sRFPDUCounter."
    ::= { rDEPairEntry 6 }

rDEPairQueryCounter OBJECT-TYPE
    SYNTAX      Counter32
    UNITS       "RQ commands"
    MAX-ACCESS  read-only
    STATUS      current
    DESCRIPTION 
        "A value that represents the numer of Route Query commands 
         generated."
    REFERENCE   
        "IEEE 802.2 (ISO/IEC 8802-2) queryCounter."
    ::= { rDEPairEntry 7 }

lLCConnectionLess OBJECT IDENTIFIER
    ::= { osiTables 27 }

lLCConnectionLessTable OBJECT-TYPE
    SYNTAX      SEQUENCE OF LLCConnectionLessEntry
    MAX-ACCESS  not-accessible
    STATUS      current
    DESCRIPTION 
        "lLCConnectionless MOC. This clause contains those attributes, 
         actions, and event notifications associated with an LLC 
         connectionless environment.  This managed object class is 
         responsible for processing the attributes, actions and 
         notifications that are associated with the LLC connectionless 
         service.
         
         The managed object class is derived from the lLCCLPM LLC 
         connectionless protocol machine managed object class, and is 
         also contained by an instance of the lLCCLPM with the 
         lLCClessName as the relative name."
    REFERENCE   
        "IEEE 802.2 (ISO/IEC 8802-2), lLCConnectionless MOC."
    ::= { lLCConnectionLess 1 }

lLCConnectionLessEntry OBJECT-TYPE
    SYNTAX      LLCConnectionLessEntry
    MAX-ACCESS  not-accessible
    STATUS      current
    DESCRIPTION 
        "Each row in this table is indexed by communications entity 
         and connectionless protocol machine.  Each row contains 
         measurements concerning the connectionless SAP."
    REFERENCE   
        "IEEE 802.2 (ISO/IEC 8802-2), lLCConnectionless MO."
    INDEX       { communicationsEntityId, clProtocolMachineId, 
                  clProtocolMachineId }
    ::= { lLCConnectionLessTable 1 }

LLCConnectionLessEntry ::= SEQUENCE {
    lLCConnectionlessName                               SimpleNameType,
    lLCConnectionlessMaximumLLCInformationFieldSize     Integer32,
    lLCConnectionlessTESTReceivedABBResponse            Counter32,
    lLCConnectionlessTESTReceivedCommand                Counter32,
    lLCConnectionlessTESTReceivedResponse               Counter32,
    lLCConnectionlessTESTSentABBResponse                Counter32,
    lLCConnectionlessTESTSentCommand                    Counter32,
    lLCConnectionlessTESTSentResponse                   Counter32,
    lLCConnectionlessUIReceived                         Counter32,
    lLCConnectionlessUISent                             Counter32,
    lLCConnectionlessXIDReceivedCommand                 Counter32,
    lLCConnectionlessXIDReceivedResponse                Counter32,
    lLCConnectionlessXIDSentCommand                     Counter32,
    lLCConnectionlessXIDSentResponse                    Counter32
}

lLCConnectionlessName OBJECT-TYPE
    SYNTAX      SimpleNameType
    MAX-ACCESS  read-write
    STATUS      current
    DESCRIPTION 
        "Provides the name of the higher level entity associated with 
         this object class.
         
         Because the lLCConnectionlessName is used as a relative name 
         within the containing lLCCLPM table entry, all 
         lLCConnectionless entries with the same indexed lLCCLPM table 
         entry must have unique names."
    REFERENCE   
        "IEEE 802.2 (ISO/IEC 8802-2) lLCClessName."
    ::= { lLCConnectionLessEntry 1 }

lLCConnectionlessMaximumLLCInformationFieldSize OBJECT-TYPE
    SYNTAX      Integer32
    MAX-ACCESS  read-write
    STATUS      current
    DESCRIPTION 
        "The maximum length SDU that the LSAP will accomodate.  For 
         Ethernet 10baseT and 100baseT LANs this is typically the 1500 
         byte MTU minus the SNAP header, minus the address fields and 
         command field, or 1492 bytes."
    REFERENCE   
        "IEEE 802.2 (ISO/IEC 8802-2) maximumLLCInformationFieldSize."
    ::= { lLCConnectionLessEntry 2 }

lLCConnectionlessTESTReceivedABBResponse OBJECT-TYPE
    SYNTAX      Counter32
    UNITS       "TEST ABB responses received"
    MAX-ACCESS  read-only
    STATUS      current
    DESCRIPTION 
        "Provides a count of TEST responses received by this LSAP 
         without the LSDU due to limited resources at the remote 
         station."
    REFERENCE   
        "IEEE 802.2 (ISO/IEC 8802-2) tESTReceivedABBResponse."
    ::= { lLCConnectionLessEntry 3 }

lLCConnectionlessTESTReceivedCommand OBJECT-TYPE
    SYNTAX      Counter32
    UNITS       "TEST commands received"
    MAX-ACCESS  read-only
    STATUS      current
    DESCRIPTION 
        "Provides a count of TEST commands received from the MAC 
         sublayer by this LSAP.  This includes commands recieved with 
         any group address recognized by this LSAP."
    REFERENCE   
        "IEEE 802.2 (ISO/IEC 8802-2) tESTReceivedCommand."
    ::= { lLCConnectionLessEntry 4 }

lLCConnectionlessTESTReceivedResponse OBJECT-TYPE
    SYNTAX      Counter32
    UNITS       "TEST responses received"
    MAX-ACCESS  read-only
    STATUS      current
    DESCRIPTION 
        "Provides a count of TEST responses received from the MAC 
         sublayer by this LSAP."
    REFERENCE   
        "IEEE 802.2 (ISO/IEC 8802-2) tESTReceivedResponse."
    ::= { lLCConnectionLessEntry 5 }

lLCConnectionlessTESTSentABBResponse OBJECT-TYPE
    SYNTAX      Counter32
    UNITS       "TEST ABB response sent"
    MAX-ACCESS  read-only
    STATUS      current
    DESCRIPTION 
        "Provides a count of TEST responses that were delivered to the 
         MAC without the LSDU data due to limited resources."
    REFERENCE   
        "IEEE 802.2 (ISO/IEC 8802-2) tESTSentABBResponse."
    ::= { lLCConnectionLessEntry 6 }

lLCConnectionlessTESTSentCommand OBJECT-TYPE
    SYNTAX      Counter32
    UNITS       "TEST commands sent"
    MAX-ACCESS  read-only
    STATUS      current
    DESCRIPTION 
        "Provides a count of TEST command set to the MAC sublayer by 
         this LSAP."
    REFERENCE   
        "IEEE 802.2 (ISO/IEC 8802-2) tESTSentCommand."
    ::= { lLCConnectionLessEntry 7 }

lLCConnectionlessTESTSentResponse OBJECT-TYPE
    SYNTAX      Counter32
    UNITS       "TEST responses sent"
    MAX-ACCESS  read-only
    STATUS      current
    DESCRIPTION 
        "Provides a count of TEST responses sent to the MAC sublayer by 
         this LSAP."
    REFERENCE   
        "IEEE 802.2 (ISO/IEC 8802-2) tESTSentResponse."
    ::= { lLCConnectionLessEntry 8 }

lLCConnectionlessUIReceived OBJECT-TYPE
    SYNTAX      Counter32
    UNITS       "UI frames received"
    MAX-ACCESS  read-only
    STATUS      current
    DESCRIPTION 
        "Provides a count of user data PDUs that were received by the 
         LSAP from the MAC sublayer and passed to the user layer.  This 
         includes commands received with group addresses of which the 
         LSAP is a member."
    REFERENCE   
        "IEEE 802.2 (ISO/IEC 8802-2) uIReceived."
    ::= { lLCConnectionLessEntry 9 }

lLCConnectionlessUISent OBJECT-TYPE
    SYNTAX      Counter32
    UNITS       "UI frames sent"
    MAX-ACCESS  read-only
    STATUS      current
    DESCRIPTION 
        "Provides a count of user data PDUs that were accepted by the 
         LSAP from the user layer and delivered to the MAC sublayer."
    REFERENCE   
        "IEEE 802.2 (ISO/IEC 8802-2) uISent."
    ::= { lLCConnectionLessEntry 10 }

lLCConnectionlessXIDReceivedCommand OBJECT-TYPE
    SYNTAX      Counter32
    UNITS       "XID commands received"
    MAX-ACCESS  read-only
    STATUS      current
    DESCRIPTION 
        "Proivdes a count of XID commands received from the MAC sublayer 
         by this LSAP.  This includes commands received with any group 
         address recognized by this LSAP."
    REFERENCE   
        "IEEE 802.2 (ISO/IEC 8802-2) xIDReceivedCommand."
    ::= { lLCConnectionLessEntry 11 }

lLCConnectionlessXIDReceivedResponse OBJECT-TYPE
    SYNTAX      Counter32
    UNITS       "XID responses received"
    MAX-ACCESS  read-only
    STATUS      current
    DESCRIPTION 
        "Provides a count of XID responses received from the MAC 
         sublayer by this LSAP."
    REFERENCE   
        "IEEE 802.2 (ISO/IEC 8802-2) xIDReceivedResponse."
    ::= { lLCConnectionLessEntry 12 }

lLCConnectionlessXIDSentCommand OBJECT-TYPE
    SYNTAX      Counter32
    UNITS       "XID commands sent"
    MAX-ACCESS  read-only
    STATUS      current
    DESCRIPTION 
        "Provides a count of XID commands sent to the MAC sublayer by 
         this LSAP."
    REFERENCE   
        "IEEE 802.2 (ISO/IEC 8802-2) xIDSentCommand."
    ::= { lLCConnectionLessEntry 13 }

lLCConnectionlessXIDSentResponse OBJECT-TYPE
    SYNTAX      Counter32
    UNITS       "XID responses sent"
    MAX-ACCESS  read-only
    STATUS      current
    DESCRIPTION 
        "Provides a count of the XID responses sent to the MAC sublayer 
         by this LSAP."
    REFERENCE   
        "IEEE 802.2 (ISO/IEC 8802-2) xIDSentResponse."
    ::= { lLCConnectionLessEntry 14 }

lLCConnection2 OBJECT IDENTIFIER
    ::= { osiTables 28 }

lLCConnection2Table OBJECT-TYPE
    SYNTAX      SEQUENCE OF LLCConnection2Entry
    MAX-ACCESS  not-accessible
    STATUS      current
    DESCRIPTION 
        "The Connection component is responsible for processing the 
         events that affect a specific data link connection for Type 2 
         procedures only.  One connection component shall exist for each 
         data link connection supported in the LLC entity.
         
         LLCConnection2 managed object.  This clause contains those 
         attributes, actions, and event notifications associated with an 
         LLC Type 2 (connection) environment.  This managed object is 
         responsible for processing the events that affect the current 
         data link connection during its lifetime (i.e., timeframe of 
         link established until link disconnect).  One LLC Connection 
         managed object shall exist for each data link (LLC Type 
         2) connection supported in the LLC entity.
         
         The managed object is derived from the iLLCCOPM LLC 
         connection-oriented protocol machine managed object lcass, and 
         is also contained by an instance of the lLCCOPM with the 
         lLCConnection2Name as the relative name.
         
         Provides a table of statistics for each LLC2 connection to a 
         remote LLC2 station.
         
         Provides a table of configuration for each LLC2 connection to a 
         remote LLC2 station.  This table provides the configuration 
         (non-statistical) atribtues for the lLCConnection2 managed 
         object from ISO/IEC 8802-2 (IEEE 802.2).  It includes 
         attributes from both mandatory and conditional packages.  
         Attributes that belong to conditional packages in the GDMOs 
         have a default value that reperesents the feature being 
         disabled.
         
         The table is indexed by the ifIndex into the ifTable that 
         represents the local MAC coupled with the Remote MAC Address 
         and LSAP that represents the specific connection."
    REFERENCE   
        "IEEE 802.2 (ISO/IEC 8802-2), lLCConnection2 MOC."
    ::= { lLCConnection2 1 }

lLCConnection2Entry OBJECT-TYPE
    SYNTAX      LLCConnection2Entry
    MAX-ACCESS  not-accessible
    STATUS      current
    DESCRIPTION 
        "Each entry in this table represents an instance of the 
         lLCConnection2 managed object class.  Each instance oft the 
         lLCConnection2 managed object lcass is responsible  for 
         processing the events that affect the current data link 
         connection during its lifetime (i.e., timeframe of link 
         established until link disconnect).  One lLCConnection2 manged 
         object instance shall exist for each data link (LLC Type 2) 
         conenction supported in the LLC entity.
         
         Provides an entry in the X.25 LLC2 Connection table for one 
         LLC2 connection to a remote station.  Each connection is 
         indexed by its ifIndex into the interface table plus a 
         connection identifier.  Each connection is associated with a 
         unique remote DLSAP (MAC address and LSAP), used as a secondary 
         index into this table.
         
         Provides an entry in the X.25 LLC2 Connection table for one LLC 
         connection to a remote station.  Each connection is indexed by 
         its ifIndex into the interface table plus a connection 
         identifier.  Each connection is associated with a unique remote 
         DLSAP (MAC addres and LSAP).
         
         Entries support a correlatorExchange action.  The action is 
         used when two ends or a link cnnection report errors relating 
         tot he same problem.  A correlator is reported in the events so 
         that the managing process can assume that the errors are 
         related to the same failure.  This section describes the 
         function that uses the CMIP protoocl verb Confirmed Action to 
         facilitate a correlator exchange between the two ends of the 
         link connection.  At the end of the link connection set-up 
         (when the LSAP Pair has initially entered into LINK-OPENED 
         state), a Manager will send a confirmed Correlator Exchange 
         CAction to the Manager of the adjacent link station.  Upon 
         receipt of this Action, the Manager will compute a correlator.  
         Once this correlator is generated, it is returned to the 
         initiating Manager.  This correlator will be sent in events 
         relating to the link connection.  If the response is not 
         received, no correlator is send in the events.  If the MAC 
         address of the two ends of the link connection are the same, 
         the link station that initiated the connection (sent SABME) 
         should intiiate the Correlator Exchange Action.
         
         Entries support the communicationsAlarm notification and the 
         lLCConnection2Event notification."
    REFERENCE   
        "IEEE 802.2 (ISO/IEC 8802-2), lLCConnection2 MO."
    INDEX       { communicationsEntityId, coProtocolMachineId, 
                  coProtocolMachineId }
    ::= { lLCConnection2Table 1 }

LLCConnection2Entry ::= SEQUENCE {
    lLCConnection2Name                      SimpleNameType,
    lLCConnection2MaximumRetransmissions    Integer32,
    lLCConnection2ReceivedWindowSize        Integer32,
    lLCConnection2SendWindowSize            Integer32,
    lLCConnection2AcknowledgeTimeoutValue   TimeInterval,
    lLCConnection2BusyStateTimeoutValue     TimeInterval,
    lLCConnection2PBitTimeoutValue          TimeInterval,
    lLCConnection2RejectTimeoutValue        TimeInterval,
    lLCConnection2LocalBusy                 Counter32,
    lLCConnection2RemoteBusy                Counter32,
    lLCConnection2RemoteReset               Counter32,
    lLCConnection2LocalReset                Counter32,
    lLCConnection2ProviderReset             Counter32,
    lLCConnection2Route                     OCTET STRING,
    lLCConnection2KStep                     Integer32,
    lLCConnection2MaxSendWindowSize         Integer32,
    lLCConnection2ReceivedI                 Counter32,
    lLCConnection2SentI                     Counter32,
    lLCConnection2SentAcks                  Counter32,
    lLCConnection2ReceivedAcks              Counter32,
    lLCConnection2ReceivedFRMR              Counter32,
    lLCConnection2SentFRMR                  Counter32,
    lLCConnection2ReceivedRR                Counter32,
    lLCConnection2SentRR                    Counter32,
    lLCConnection2ReceivedRNR               Counter32,
    lLCConnection2SentRNR                   Counter32,
    lLCConnection2ReceivedREJ               Counter32,
    lLCConnection2SentREJ                   Counter32,
    lLCConnection2ReceivedSABME             Counter32,
    lLCConnection2SentSABME                 Counter32,
    lLCConnection2ReceivedUA                Counter32,
    lLCConnection2SentUA                    Counter32,
    lLCConnection2ReceivedDISC              Counter32,
    lLCConnection2SentDISC                  Counter32,
    lLCConnection2ReceivedDM                Counter32,
    lLCConnection2SentDM                    Counter32,
    lLCConnection2PDUsDiscarded1            Counter32,
    lLCConnection2PDUsDiscarded2            Counter32,
    lLCConnection2PDURetransmissions        Counter32,
    lLCConnection2OptionalTolerationIPDUs   TruthValue,
    lLCConnection2DuplicateIPDUsReceived    Counter32,
    lLCConnection2Violation                 Counter32,
    lLCConnection2ProtocolState             INTEGER,
    lLCConnection2AdministrativeState       AdministrativeState,
    lLCConnection2OperationalState          OperationalState,
    lLCConnection2UsageState                UsageState,
    lLCConnection2ProceduralStatus          ProceduralStatus,
    lLCConnection2AlarmStatus               AlarmStatus
}

lLCConnection2Name OBJECT-TYPE
    SYNTAX      SimpleNameType
    MAX-ACCESS  read-write
    STATUS      current
    DESCRIPTION 
        "The localLSAP and remoteLSAPId and the local and remote 
         MACAddress.
         
         Because the lLCConnection2Name is used as a relative name 
         within the containing lLCCOPM table entry, all lLCConnection2 
         entries with the same indexed lLCCOPM table entry must have 
         unique names.
         
         Provides an index in to the ifTable that identifies the primary 
         MAC interface through which multilple LLC2 connections are 
         established.
         
         Provides a connection identifier that identifies the explicit 
         connection made via the MAC device identified by the 
         lLCConnection2StatsIndex above.  These two fields form the 
         index and identify the specific LLC2 connection within this 
         host."
    REFERENCE   
        "IEEE 802.2 (ISO/IEC 8802-2) lLCConnection2Name."
    ::= { lLCConnection2Entry 1 }

lLCConnection2MaximumRetransmissions OBJECT-TYPE
    SYNTAX      Integer32
    MAX-ACCESS  read-write
    STATUS      current
    DESCRIPTION 
        "The number of times that the LLC Type 2 should attempt to 
         realize a successful PDU transfer."
    REFERENCE   
        "IEEE 802.2 (ISO/IEC 8802-2) maximumRetransmissions."
    ::= { lLCConnection2Entry 2 }

lLCConnection2ReceivedWindowSize OBJECT-TYPE
    SYNTAX      Integer32
    MAX-ACCESS  read-write
    STATUS      current
    DESCRIPTION 
        "The value of the receive window."
    REFERENCE   
        "IEEE 802.2 (ISO/IEC 8802-2) receivedWindowSize."
    ::= { lLCConnection2Entry 3 }

lLCConnection2SendWindowSize OBJECT-TYPE
    SYNTAX      Integer32
    MAX-ACCESS  read-write
    STATUS      current
    DESCRIPTION 
        "The value of the send window."
    REFERENCE   
        "IEEE 802.2 (ISO/IEC 8802-2) sendWindowSize."
    ::= { lLCConnection2Entry 4 }

lLCConnection2AcknowledgeTimeoutValue OBJECT-TYPE
    SYNTAX      TimeInterval
    MAX-ACCESS  read-write
    STATUS      current
    DESCRIPTION 
        "This attribute defines the time interval during which the LLC 
         shall expect to receive an acknowledgment to one or more 
         outstanding I PDUs or an expected response PDU to a sent 
         unnumbered command PDU.  This value is measured in centiseconds 
         and displayed in seconds."
    REFERENCE   
        "IEEE 802.2 (ISO/IEC 8802-2), type2AcknowledgeTimeoutValue, 
         7.4.1, 7.4.3, 7.4.5, 7.5, 7.5.5, 7.5.9, 7.6, 7.8.1.1, 7.9.2, 
         7.9.2.2, and 7.9.2.3."
    ::= { lLCConnection2Entry 5 }

lLCConnection2BusyStateTimeoutValue OBJECT-TYPE
    SYNTAX      TimeInterval
    MAX-ACCESS  read-write
    STATUS      current
    DESCRIPTION 
        "This attribute defines the time interval during which the LLC 
         shall wait for an indication of the clearance of a busy 
         condition at the other LLC.  This time value is measured in 
         centiseconds and displayed in seconds."
    REFERENCE   
        "IEEE 802.2 (ISO/IEC 8802-2), type2BusyStateTimeoutValue, 7.5.7, 
         7.5.9, 7.8.1.4, 7.9.2, 7.9.2.2, and 7.9.2.3."
    ::= { lLCConnection2Entry 6 }

lLCConnection2PBitTimeoutValue OBJECT-TYPE
    SYNTAX      TimeInterval
    MAX-ACCESS  read-write
    STATUS      current
    DESCRIPTION 
        "The P-bit timer defines the time interval during which the LLC 
         shall expect to receive a PDU with the F bit set to '1' in 
         response to a sent Type 2 command with the P bit set to '1'. 
         This value is measured in centiseconds and dsiplayed in 
         seconds."
    REFERENCE   
        "IEEE 802.2 (ISO/IEC 8802-2), type2BitTimeoutValue, 
         7.5.9, 7.8.1.2, 7.9.2, 7.9.2.2, and 7.9.2.3."
    ::= { lLCConnection2Entry 7 }

lLCConnection2RejectTimeoutValue OBJECT-TYPE
    SYNTAX      TimeInterval
    MAX-ACCESS  read-write
    STATUS      current
    DESCRIPTION 
        "The Reject timer defines the time interval during which the LLC 
         shall expect to receive a reply to a sent REJ PDU. This value 
         is measured in centiseconds and displayed in seconds."
    REFERENCE   
        "IEEE 802.2 (ISO/IEC 8802-2), type2RejectTimeoutValue, 
         7.5.4, 7.8.1.3, 7.9.2, 7.9.2.2, and 7.9.2.3."
    ::= { lLCConnection2Entry 8 }

-- need action correlatorExchange
-- need notification communicationsAlarm
-- need notification lLCConnection2Event

-- connectionBusy-P conditional package
--
-- Contains attributes that count instances of local or remote busy 
-- conditions.

lLCConnection2LocalBusy OBJECT-TYPE
    SYNTAX      Counter32
    MAX-ACCESS  read-only
    STATUS      current
    DESCRIPTION 
        "Provides a count of the occurences of entry into the busy 
         condition."
    REFERENCE   
        "IEEE 802.2 (ISO/IEC 8802-2) localBusy."
    ::= { lLCConnection2Entry 9 }

lLCConnection2RemoteBusy OBJECT-TYPE
    SYNTAX      Counter32
    UNITS       "PDUs"
    MAX-ACCESS  read-only
    STATUS      current
    DESCRIPTION 
        "Provides a count of the RNR PDUs received when the remote busy 
         condition is not already set."
    REFERENCE   
        "IEEE 802.2 (ISO/IEC 8802-2) remoteBusy."
    ::= { lLCConnection2Entry 10 }

-- connectionReset-P conditioanl package
--
-- Contains attributes that count instances of particular types of 
-- reset.

lLCConnection2RemoteReset OBJECT-TYPE
    SYNTAX      Counter32
    UNITS       "PDUs"
    MAX-ACCESS  read-only
    STATUS      current
    DESCRIPTION 
        "Provides a count of instances of partner-initiated reset (SABME 
         PDU received in a connected state)."
    REFERENCE   
        "IEEE 802.2 (ISO/IEC 8802-2) remoteReset."
    ::= { lLCConnection2Entry 11 }

lLCConnection2LocalReset OBJECT-TYPE
    SYNTAX      Counter32
    UNITS       "requests"
    MAX-ACCESS  read-only
    STATUS      current
    DESCRIPTION 
        "Provides a count of the instances of user request for reset 
         while in the connected state."
    REFERENCE   
        "IEEE 802.2 (ISO/IEC 8802-2) localReset."
    ::= { lLCConnection2Entry 12 }

lLCConnection2ProviderReset OBJECT-TYPE
    SYNTAX      Counter32
    UNITS       "resets"
    MAX-ACCESS  read-only
    STATUS      current
    DESCRIPTION 
        "Provides a count of the instances of provider-initiated reset 
         due to FRMR PDU sent, FRMR received, or retry exhaustion."
    REFERENCE   
        "IEEE 802.2 (ISO/IEC 8802-2) providerReset."
    ::= { lLCConnection2Entry 13 }

-- connectionRoute-P conditional package
--
-- This is a conditional part of the LLC Connection Object. It is 
-- present if source routing is used and the connection is cognizant of 
-- its route.  This conditional package contains one attribute, the 
-- source route that the LSAP Pair uses to communicate. Source Routing 
-- is described in ISO/IEC 10038 : 1993.

lLCConnection2Route OBJECT-TYPE
    SYNTAX      OCTET STRING (SIZE(4))
    MAX-ACCESS  read-write
    STATUS      current
    DESCRIPTION 
        "This is a conditional part of the LSAP Pair Object. It is 
         present if source routing is used and the LSAP Pair is 
         cognizant of its route. This attribute is used by the LSAP Pair 
         to communicate. Source Routing is described in ISO/IEC 10038 : 
         1993 (IEEE 802.1D 1993).
         
         The syntax of the octet string is as follows:
         
         RoutingControl ::= OCTET STRING(SIZE(2))
         RoutingDescriptors ::= OCTET STRING(SIZE(2))
         Route ::= SEQUENCE {
             routingControl [0] IMPLICIT RoutingControl,
             routingDescriptors [1] IMPLICIT RoutingDescriptors }"
    REFERENCE   
        "IEEE 802.2 (ISO/IEC 8802-2), route, IEEE 802.2D 1993 (ISO/IEC 
         10038 : 1993)."
    ::= { lLCConnection2Entry 14 }

-- type2FlowControl-P conditional package
--
-- This conditional package contains two attributes that are used to 
-- provide flow control.

lLCConnection2KStep OBJECT-TYPE
    SYNTAX      Integer32
    MAX-ACCESS  read-write
    STATUS      current
    DESCRIPTION 
        "The value of the flow control parameter."
    REFERENCE   
        "IEEE 802.2 (ISO/IEC 8802-2) kStep."
    ::= { lLCConnection2Entry 15 }

lLCConnection2MaxSendWindowSize OBJECT-TYPE
    SYNTAX      Integer32
    MAX-ACCESS  read-write
    STATUS      current
    DESCRIPTION 
        "The maximum size of the send window."
    REFERENCE   
        "IEEE 802.2 (ISO/IEC 8802-2) sendWindowSize."
    ::= { lLCConnection2Entry 16 }

-- type2I-P conditional package
--
-- This conditional package counts the number of I PDUs received and 
-- sent (see 7.5.1, 7.5.6, 7.5.8, 7.5.9, and 7.8.4).

lLCConnection2ReceivedI OBJECT-TYPE
    SYNTAX      Counter32
    MAX-ACCESS  read-only
    STATUS      current
    DESCRIPTION 
        "Provides a count of the number of I PDUs received from the MAC 
         and passed to the LLC user on this connection."
    REFERENCE   
        "IEEE 802.2 (ISO/IEC 8802-2) type2ReceivedI."
    ::= { lLCConnection2Entry 17 }

lLCConnection2SentI OBJECT-TYPE
    SYNTAX      Counter32
    MAX-ACCESS  read-only
    STATUS      current
    DESCRIPTION 
        "Provides a count of the number of I PDUs delivered to the MAC 
         on this connection."
    REFERENCE   
        "IEEE 802.2 (ISO/IEC 8802-2) type2SentI."
    ::= { lLCConnection2Entry 18 }

-- type2Iack-P conditional package
--
-- Contains attributes that count acknowledgments sent and received.

lLCConnection2SentAcks OBJECT-TYPE
    SYNTAX      Counter32
    MAX-ACCESS  read-only
    STATUS      current
    DESCRIPTION 
        "Provides a count of the number of acknowledgments sent for 
         received I PDUs on this connection."
    REFERENCE   
        "IEEE 802.2 (ISO/IEC 8802-2) sentAcks."
    ::= { lLCConnection2Entry 19 }

lLCConnection2ReceivedAcks OBJECT-TYPE
    SYNTAX      Counter32
    MAX-ACCESS  read-only
    STATUS      current
    DESCRIPTION 
        "Provides a count of the number of I PDUs acknowledged by 
         connection partner on this connection."
    REFERENCE   
        "IEEE 802.2 (ISO/IEC 8802-2) receivedAcks."
    ::= { lLCConnection2Entry 20 }

-- type2FRMR-P conditional package
--
-- Specifies a count of FRMR PDUs delivered to the MAC and a count of 
-- FRMR PDUs received from the MAC and not discarded.

lLCConnection2ReceivedFRMR OBJECT-TYPE
    SYNTAX      Counter32
    MAX-ACCESS  read-only
    STATUS      current
    DESCRIPTION 
        "Provides a count of the number of FRMR PDUs received from the 
         MAC and not discarded on this connection."
    REFERENCE   
        "IEEE 802.2 (ISO/IEC 8802-2) type2ReceivedFRMR."
    ::= { lLCConnection2Entry 21 }

lLCConnection2SentFRMR OBJECT-TYPE
    SYNTAX      Counter32
    MAX-ACCESS  read-only
    STATUS      current
    DESCRIPTION 
        "Provides a count of the number of FRMR PDUs delivered to the 
         MAC on this connection."
    REFERENCE   
        "IEEE 802.2 (ISO/IEC 8802-2) type2SentFRMR."
    ::= { lLCConnection2Entry 22 }

-- type2RR-P conditional package
--
-- Specifies a count of RR PDUs either delivered or received from the 
-- MAC.

lLCConnection2ReceivedRR OBJECT-TYPE
    SYNTAX      Counter32
    MAX-ACCESS  read-only
    STATUS      current
    DESCRIPTION 
        "Provides a count of the number of RR PDUs received from the MAC 
         and not discarded on this connection."
    REFERENCE   
        "IEEE 802.2 (ISO/IEC 8802-2) type2ReceivedRR."
    ::= { lLCConnection2Entry 23 }

lLCConnection2SentRR OBJECT-TYPE
    SYNTAX      Counter32
    MAX-ACCESS  read-only
    STATUS      current
    DESCRIPTION 
        "Provides a count of the number of RR PDUs delivered to  the MAC 
         on this connection."
    REFERENCE   
        "IEEE 802.2 (ISO/IEC 8802-2) type2SentRR."
    ::= { lLCConnection2Entry 24 }

-- type2RNR-P conditional package
--
-- This conditional package contains attributes that specify the count 
-- of RNR PDUs either delivered or received from the MAC.

lLCConnection2ReceivedRNR OBJECT-TYPE
    SYNTAX      Counter32
    MAX-ACCESS  read-only
    STATUS      current
    DESCRIPTION 
        "Provides a count of the number of RNR PDUs received from the 
         MAC and not discarded on this connection."
    REFERENCE   
        "IEEE 802.2 (ISO/IEC 8802-2) type2ReceivedRNR."
    ::= { lLCConnection2Entry 25 }

lLCConnection2SentRNR OBJECT-TYPE
    SYNTAX      Counter32
    MAX-ACCESS  read-only
    STATUS      current
    DESCRIPTION 
        "Provides a count of the number of RNR PDUs delivered to  the 
         MAC on this connection."
    REFERENCE   
        "IEEE 802.2 (ISO/IEC 8802-2) type2SentRNR."
    ::= { lLCConnection2Entry 26 }

-- type2REJ-P conditional package
--
-- This conditional package contains two attributes to count sent and 
-- received REJ PDUs (see Clause 7.5.9).

lLCConnection2ReceivedREJ OBJECT-TYPE
    SYNTAX      Counter32
    MAX-ACCESS  read-only
    STATUS      current
    DESCRIPTION 
        "Provides a count of the number of REJ PDUs received from the 
         MAC and not discarded on this connection."
    REFERENCE   
        "IEEE 802.2 (ISO/IEC 8802-2) type2ReceivedREJ."
    ::= { lLCConnection2Entry 27 }

lLCConnection2SentREJ OBJECT-TYPE
    SYNTAX      Counter32
    MAX-ACCESS  read-only
    STATUS      current
    DESCRIPTION 
        "Provides a count of the number of REJ PDUs delivered to  the 
         MAC on this connection."
    REFERENCE   
        "IEEE 802.2 (ISO/IEC 8802-2) type2SentREJ."
    ::= { lLCConnection2Entry 28 }

-- type2SABME-P conditional package
--
-- This conditional package contains attributes that specify the count 
-- of SABME PDUs either delivered or received.

lLCConnection2ReceivedSABME OBJECT-TYPE
    SYNTAX      Counter32
    MAX-ACCESS  read-only
    STATUS      current
    DESCRIPTION 
        "Provides a count of the number of SABME PDUs received from the 
         MAC and not discarded on this connection."
    REFERENCE   
        "IEEE 802.2 (ISO/IEC 8802-2) type2ReceivedSABME."
    ::= { lLCConnection2Entry 29 }

lLCConnection2SentSABME OBJECT-TYPE
    SYNTAX      Counter32
    MAX-ACCESS  read-only
    STATUS      current
    DESCRIPTION 
        "Provides a count of the number of SABME PDUs delivered to the 
         MAC  on this connection."
    REFERENCE   
        "IEEE 802.2 (ISO/IEC 8802-2) type2SentSABME."
    ::= { lLCConnection2Entry 30 }

-- type2UA-P conditional package
--
-- Specifies a count of UA PDUs either delivered or received from the 
-- MAC.

lLCConnection2ReceivedUA OBJECT-TYPE
    SYNTAX      Counter32
    MAX-ACCESS  read-only
    STATUS      current
    DESCRIPTION 
        "Provides a count of the number of UA PDUs received from the MAC 
         and not discarded on this connection."
    REFERENCE   
        "IEEE 802.2 (ISO/IEC 8802-2) type2ReceivedUA."
    ::= { lLCConnection2Entry 31 }

lLCConnection2SentUA OBJECT-TYPE
    SYNTAX      Counter32
    MAX-ACCESS  read-only
    STATUS      current
    DESCRIPTION 
        "Provides a count of the number of UA PDUs delivered to  the MAC 
         on this connection."
    REFERENCE   
        "IEEE 802.2 (ISO/IEC 8802-2) type2SentUA."
    ::= { lLCConnection2Entry 32 }

-- type2DISC-P conditional package
--
-- Specifies a count of DISC PDUs either delivered or received from the 
-- MAC.

lLCConnection2ReceivedDISC OBJECT-TYPE
    SYNTAX      Counter32
    MAX-ACCESS  read-only
    STATUS      current
    DESCRIPTION 
        "Provides a count of the number of DISC PDUs received from the 
         MAC and not discarded on this connection."
    REFERENCE   
        "IEEE 802.2 (ISO/IEC 8802-2) type2ReceivedDISC."
    ::= { lLCConnection2Entry 33 }

lLCConnection2SentDISC OBJECT-TYPE
    SYNTAX      Counter32
    MAX-ACCESS  read-only
    STATUS      current
    DESCRIPTION 
        "Provides a count of the number of DISC PDUs delivered to the 
         MAC  on this connection."
    REFERENCE   
        "IEEE 802.2 (ISO/IEC 8802-2) type2SentDISC."
    ::= { lLCConnection2Entry 34 }

-- type2DM-P conditional package
--
-- Specifies a count of DM PDUs either delivered or received from the 
-- MAC.

lLCConnection2ReceivedDM OBJECT-TYPE
    SYNTAX      Counter32
    MAX-ACCESS  read-only
    STATUS      current
    DESCRIPTION 
        "Provides a count of the number of DM PDUs received from the MAC 
         and not discarded on this connection."
    REFERENCE   
        "IEEE 802.2 (ISO/IEC 8802-2) type2ReceivedDM."
    ::= { lLCConnection2Entry 35 }

lLCConnection2SentDM OBJECT-TYPE
    SYNTAX      Counter32
    MAX-ACCESS  read-only
    STATUS      current
    DESCRIPTION 
        "Provides a count of the number of DM PDUs delivered to  the MAC 
         on this connection."
    REFERENCE   
        "IEEE 802.2 (ISO/IEC 8802-2) type2SentDM."
    ::= { lLCConnection2Entry 36 }

-- type2PDUs-P conditional package
--
-- This conditional package contains attributes that count a number of 
-- different types of discarded PDUs.

lLCConnection2PDUsDiscarded1 OBJECT-TYPE
    SYNTAX      Counter32
    MAX-ACCESS  read-only
    STATUS      current
    DESCRIPTION 
        "Provides a count of the number of PDUs discarded due to 
         insufficient resources for this connection."
    REFERENCE   
        "IEEE 802.2 (ISO/IEC 8802-2) pDUsDiscarded1."
    ::= { lLCConnection2Entry 37 }

lLCConnection2PDUsDiscarded2 OBJECT-TYPE
    SYNTAX      Counter32
    MAX-ACCESS  read-only
    STATUS      current
    DESCRIPTION 
        "Provides a count of the number of PDUs discarded due to 
         unexpected or invalid sequence numberfor this connection."
    REFERENCE   
        "IEEE 802.2 (ISO/IEC 8802-2) pDUsDiscarded2."
    ::= { lLCConnection2Entry 38 }

lLCConnection2PDURetransmissions OBJECT-TYPE
    SYNTAX      Counter32
    MAX-ACCESS  read-only
    STATUS      current
    DESCRIPTION 
        "Provides a count of the number of times the Type 2 LLC service 
         retransmitted PDUs for this connection."
    REFERENCE   
        "IEEE 802.2 (ISO/IEC 8802-2) pDURetransmissions."
    ::= { lLCConnection2Entry 39 }

-- need lLCConnection2Event notification
-- type2OptTolIPDUs-P conditional package
--
-- This optional package contains two attributes: a Boolean to indicate 
-- support for the Optional Toleration of Duplicate I PDUs function and 
-- an event counter to count the number of Duplicate I PDUs received.

lLCConnection2OptionalTolerationIPDUs OBJECT-TYPE
    SYNTAX      TruthValue
    MAX-ACCESS  read-write
    STATUS      current
    DESCRIPTION 
        "Indicates if the Toleration of Duplicate I PDUs is on or off."
    REFERENCE   
        "IEEE 802.2 (ISO/IEC 8802-2) optionalTolerationIPDUs."
    ::= { lLCConnection2Entry 40 }

lLCConnection2DuplicateIPDUsReceived OBJECT-TYPE
    SYNTAX      Counter32
    MAX-ACCESS  read-only
    STATUS      current
    DESCRIPTION 
        "Provides a count of the number of duplicated I PDUs received on 
         this connection.  Duplication I PDUs are those that have a 
         sequence number within the current window and which have 
         already been received."
    REFERENCE   
        "IEEE 802.2 (ISO/IEC 8802-2) duplicatePDUsReceived, (also 
         dupIPDUsReceived)."
    ::= { lLCConnection2Entry 41 }

-- need lLCConnection2Event notification
-- type2Violation-P conditional package
--
-- This conditional package provides an attribute and notification for 
-- type 2 violations.

lLCConnection2Violation OBJECT-TYPE
    SYNTAX      Counter32
    MAX-ACCESS  read-only
    STATUS      current
    DESCRIPTION 
        "Provides a count of the number of LLC Type 2 protocol 
         violations detected by this connection. Protocol violations 
         include the following:
         1. those that result in the LLC entity sending an FRMR frame;
         2. those that result in a data link resetting action to be 
            initiated by the receiving LLC entity itself."
    REFERENCE   
        "IEEE 802.2 (ISO/IEC 8802-2) type2Violation."
    ::= { lLCConnection2Entry 42 }

lLCConnection2ProtocolState OBJECT-TYPE
    SYNTAX      INTEGER { disconnectedPhase(0), linkdiconnectionPhase(1), 
                    linkSetUpPhase(2), informationTransferPhase(3), 
                    frameRejectCondition(4), busyCondition(5), 
                    sentRejectCondition(6), 
                    systemParametersAndErrorRecovery(7) }
    MAX-ACCESS  read-only
    STATUS      current
    DESCRIPTION 
        "Local state of an LLC2 connection."
    ::= { lLCConnection2Entry 43 }

lLCConnection2AdministrativeState OBJECT-TYPE
    SYNTAX      AdministrativeState
    MAX-ACCESS  read-write
    STATUS      current
    DESCRIPTION 
        "Provides the X.731 administrative status of the LLC2 
         connection.  When locked(0), the LLC2 connection is 
         administratively prohibitted from forming and when set to 
         locked(0) will be abruptly disconnected if already formed.  
         When unlocked(1) the LLC2 connection is administratively 
         permitted to form.  When set to
         shuttingDown(2), the LLC2 connection will be gracefully 
         withdrawn from service and will enter the locked(0) state when 
         shut down."
    ::= { lLCConnection2Entry 44 }

lLCConnection2OperationalState OBJECT-TYPE
    SYNTAX      OperationalState
    MAX-ACCESS  read-only
    STATUS      current
    DESCRIPTION 
        "Provides the X.731 operational state of this LAPB connection."
    ::= { lLCConnection2Entry 45 }

lLCConnection2UsageState OBJECT-TYPE
    SYNTAX      UsageState
    MAX-ACCESS  read-only
    STATUS      current
    DESCRIPTION 
        "Provides the X.731 usage state of this LLC2 connection.  When 
         idle(0), the LLC2 connection is not currently in use (although 
         it may still be formed).  When active(1), the resource is being 
         used and has sufficient spare operating capacity to provide for 
         additional users simultaneously.  When busy(2), the resource is 
         in use, but it has no spare capacity to provide additional 
         users at this instant."
    ::= { lLCConnection2Entry 46 }

lLCConnection2ProceduralStatus OBJECT-TYPE
    SYNTAX      ProceduralStatus
    MAX-ACCESS  read-only
    STATUS      current
    DESCRIPTION 
        "Provides the X.731 procedural status of this LLC2 connection.  
         The procedural status contains initializationRequired(0) when 
         the LLC2 requires initiation action to form or reform a 
         connection.  It contains notInitialized(1) when the LLC2 
         connection is in disconnected mode (ADM); initializing(2) when 
         forming connection (SABM) and terminating(3) when disconnecting 
         (DISC)."
    ::= { lLCConnection2Entry 47 }

lLCConnection2AlarmStatus OBJECT-TYPE
    SYNTAX      AlarmStatus
    MAX-ACCESS  read-write
    STATUS      current
    DESCRIPTION 
        "Provides the alarm status of this LLC2 connection.
         
         The lLCConnection2f entry may issue a communicationsAlarm 
         notification using the RowPointer of the corresponding entry in 
         the objectIsntance parameter of the communicationsAlarm.
         
         The probableCause is fRMRReceived.  The specificProblems is one 
         of:
         
         - fRMRReasonsControlFieldUndefinedOrUnimplemented,
         - fRMRReasonsFormatError,
         - fRMRReasonsInfoFieldLengthGreaterThanMaximum,
         - fRMRReasonsInvalidNR,
         - fRMRReasonsNonSpecific.
         
         The perceivedSeverity parameter is set to the value Minor.  A 
         subsequent communicationsAlarm with a perceivedSeverity of 
         Cleared is not generated.  Alarms must be cleared by management 
         stations using the lLCConnection2AlarmStatus or locally.
         
         The fRMR parameter containing the received frame is included in 
         the additionalInformation.  No other parameters are used."
    ::= { lLCConnection2Entry 48 }

lLCConnection2IVMO OBJECT IDENTIFIER
    ::= { osiTables 29 }

lLCConnection2IVMOTable OBJECT-TYPE
    SYNTAX      SEQUENCE OF LLCConnection2IVMOEntry
    MAX-ACCESS  not-accessible
    STATUS      current
    DESCRIPTION 
        "lLCConnection2IVMO managed object.  A lLCConnection2IVMO may be 
         used to supply initial values for the attributes of 
         lLCConnection2 MOs.  Different instances of lLCConnection2IVMO 
         may contain different initial values.
         
         Provides a table of configuration defaults for LLC2 connections 
         to remote LLC2 stations from this LLC station.
         
         This table provides initial values for connection associated 
         with the MAC/LLC stations indicated by the index into the 
         table.  Note that if the management station does not assign 
         values ot a MAC/LLC station, the agent or implementation will 
         assign default values or values specified by local 
         configuration.  These are only default values for new 
         connections formed to or from the LLC station.  The management 
         station can alter the operational values via the 
         lLCConnection2Table.  The agent or implementation may also 
         alter operational values.  
         
         Changes made to values in this table will not necessarily 
         affect operational connections, but will be used as default 
         values for new connection formed subsequent to the change.  
         Note that managements stations may not add rows to or delete 
         rows from this table.  Rows are allocated by the implementation 
         and correspond each to available LLC stations."
    REFERENCE   
        "IEEE 802.2 (ISO/IEC 8802-2), lLCConenction2IVMO MOC."
    ::= { lLCConnection2IVMO 1 }

lLCConnection2IVMOEntry OBJECT-TYPE
    SYNTAX      LLCConnection2IVMOEntry
    MAX-ACCESS  not-accessible
    STATUS      current
    DESCRIPTION 
        "Each row in this table is indexed by and defines the LLC 
         style 2 connection IVMO identifier.  Each row contains initial 
         values to be used when forming LLC style 2 connections."
    REFERENCE   
        "IEEE 802.2 (ISO/IEC 8802-2), lLCConenction2IVMO MO."
    INDEX       { lLCConnection2IVMOName }
    ::= { lLCConnection2IVMOTable 1 }

LLCConnection2IVMOEntry ::= SEQUENCE {
    lLCConnection2IVMOName                      SimpleNameType,
    lLCConnection2IVMOMaximumRetransmissions    Unsigned32,
    lLCConnection2IVMOReceivedWindowSize        Unsigned32,
    lLCConnection2IVMOSendWindowSize            Unsigned32,
    lLCConnection2IVMOAcknowledgeTimeoutValue   TimeInterval,
    lLCConnection2IVMOBusyStateTimeoutValue     TimeInterval,
    lLCConnection2IVMOBitTimeoutValue           TimeInterval,
    lLCConnection2IVMORejectTimeoutValue        TimeInterval,
    lLCConnection2IVMORoute                     Unsigned32,
    lLCConnection2IVMOKStep                     Unsigned32,
    lLCConnection2IVMOMaxSendWindowSize         Unsigned32,
    lLCConnection2IVMOOptionalTolerationIPDUs   TruthValue
}

lLCConnection2IVMOName OBJECT-TYPE
    SYNTAX      SimpleNameType
    MAX-ACCESS  not-accessible
    STATUS      current
    DESCRIPTION 
        "Provides a name for the set of initial values."
    REFERENCE   
        "IEEE 802.2 (ISO/IEC 8802-2)."
    ::= { lLCConnection2IVMOEntry 1 }

lLCConnection2IVMOMaximumRetransmissions OBJECT-TYPE
    SYNTAX      Unsigned32
    MAX-ACCESS  read-write
    STATUS      current
    DESCRIPTION 
        "The default value, when not explicity specified by a management 
         station, is derived from the 
         lLCConnection2DefaultMaximumRetransmissions scalar."
    REFERENCE   
        "IEEE 802.2 (ISO/IEC 8802-2)."
    ::= { lLCConnection2IVMOEntry 2 }

lLCConnection2IVMOReceivedWindowSize OBJECT-TYPE
    SYNTAX      Unsigned32
    MAX-ACCESS  read-write
    STATUS      current
    DESCRIPTION 
        "The default value, when not explicity specified by a management 
         station, is derived from the 
         lLCConnection2DefaultReceivedWindowSize scalar."
    REFERENCE   
        "IEEE 802.2 (ISO/IEC 8802-2)."
    ::= { lLCConnection2IVMOEntry 3 }

lLCConnection2IVMOSendWindowSize OBJECT-TYPE
    SYNTAX      Unsigned32
    MAX-ACCESS  read-write
    STATUS      current
    DESCRIPTION 
        "The default value, when not explicity specified by a management 
         station, is derived from the 
         lLCConnection2DefaultSendWindowSize scalar."
    REFERENCE   
        "IEEE 802.2 (ISO/IEC 8802-2)."
    ::= { lLCConnection2IVMOEntry 4 }

lLCConnection2IVMOAcknowledgeTimeoutValue OBJECT-TYPE
    SYNTAX      TimeInterval
    MAX-ACCESS  read-write
    STATUS      current
    DESCRIPTION 
        "The default value, when not explicity specified by a management 
         station, is derived from the 
         lLCConnection2DefaultAcknowledgeTimeoutValue scalar."
    REFERENCE   
        "IEEE 802.2 (ISO/IEC 8802-2)."
    ::= { lLCConnection2IVMOEntry 5 }

lLCConnection2IVMOBusyStateTimeoutValue OBJECT-TYPE
    SYNTAX      TimeInterval
    MAX-ACCESS  read-write
    STATUS      current
    DESCRIPTION 
        "The default value, when not explicity specified by a management 
         station, is derived from the 
         lLCConnection2DefaultBusyStateTimeoutValue scalar."
    REFERENCE   
        "IEEE 802.2 (ISO/IEC 8802-2)."
    ::= { lLCConnection2IVMOEntry 6 }

lLCConnection2IVMOBitTimeoutValue OBJECT-TYPE
    SYNTAX      TimeInterval
    MAX-ACCESS  read-write
    STATUS      current
    DESCRIPTION 
        "The default value, when not explicity specified by a management 
         station, is derived from the 
         lLCConnection2DefaultPBitTimeoutValue scalar."
    REFERENCE   
        "IEEE 802.2 (ISO/IEC 8802-2)."
    ::= { lLCConnection2IVMOEntry 7 }

lLCConnection2IVMORejectTimeoutValue OBJECT-TYPE
    SYNTAX      TimeInterval
    MAX-ACCESS  read-write
    STATUS      current
    DESCRIPTION 
        "The default value, when not explicity specified by a management 
         station, is derived from the 
         lLCConnection2DefaultRejectTimeoutValue scalar."
    REFERENCE   
        "IEEE 802.2 (ISO/IEC 8802-2)."
    ::= { lLCConnection2IVMOEntry 8 }

lLCConnection2IVMORoute OBJECT-TYPE
    SYNTAX      Unsigned32
    MAX-ACCESS  read-write
    STATUS      current
    DESCRIPTION 
        "The default value, when not explicity specified by a management 
         station, is derived from the lLCConnection2DefaultRoute 
         scalar."
    REFERENCE   
        "IEEE 802.2 (ISO/IEC 8802-2)."
    ::= { lLCConnection2IVMOEntry 9 }

lLCConnection2IVMOKStep OBJECT-TYPE
    SYNTAX      Unsigned32
    MAX-ACCESS  read-write
    STATUS      current
    DESCRIPTION 
        "The default value, when not explicity specified by a management 
         station, is derived from the lLCConnection2DefaultKStep 
         scalar."
    REFERENCE   
        "IEEE 802.2 (ISO/IEC 8802-2)."
    ::= { lLCConnection2IVMOEntry 10 }

lLCConnection2IVMOMaxSendWindowSize OBJECT-TYPE
    SYNTAX      Unsigned32
    MAX-ACCESS  read-write
    STATUS      current
    DESCRIPTION 
        "The default value, when not explicity specified by a management 
         station, is derived from the 
         lLCConnection2DefaultMaxSendWindowSize scalar."
    REFERENCE   
        "IEEE 802.2 (ISO/IEC 8802-2)."
    ::= { lLCConnection2IVMOEntry 11 }

lLCConnection2IVMOOptionalTolerationIPDUs OBJECT-TYPE
    SYNTAX      TruthValue
    MAX-ACCESS  read-write
    STATUS      current
    DESCRIPTION 
        "The default value, when not explicity specified by a management 
         station, is derived from the 
         lLCConnection2DefaultOptionalTolerationIPDUs scalar."
    REFERENCE   
        "IEEE 802.2 (ISO/IEC 8802-2)."
    ::= { lLCConnection2IVMOEntry 12 }

lLCConnectionlessAck OBJECT IDENTIFIER
    ::= { osiTables 30 }

lLCConnectionlessAckTable OBJECT-TYPE
    SYNTAX      SEQUENCE OF LLCConnectionlessAckEntry
    MAX-ACCESS  not-accessible
    STATUS      current
    DESCRIPTION 
        "The Type 3 Received component is responsible for processing 
         Type 3 commands as they are received from the medium access 
         control sublayer, and for returning Type 3 responses to the 
         originators of the commands.  At a given station there is 
         potentially a separate Type 
         3 Receiver component for each possible combination of remote 
           address (SA and SSAP), and MAC priority.  In most 
           applications, however, only a subset of the possible Receiver 
           components will exist, since a component is needed only for 
           those address and priority combinations for which Type 3 
           commands are actually received.
         
         The Type 3 Sender component is responsible for sending Type 3 
         commands upon request of the network layer, and for processing 
         of Type 3 responses when they are received from the medium 
         access control sublayer.  At any given station there is 
         potentially a spearate Type 
         3 Sender component for each possible combination of local LSAP, 
           DA portion of the remote address, and MAC priority.  In most 
           applications, however, only a subset of the possible Sender 
           components will exist, since a component is needed only for 
           those address and priority combinations for which Type 3 
           commands are actually sent."
    REFERENCE   
        "IEEE 802.2 (ISO/IEC 8802-2), lLCConnectionlessAck MOC."
    ::= { lLCConnectionlessAck 1 }

lLCConnectionlessAckEntry OBJECT-TYPE
    SYNTAX      LLCConnectionlessAckEntry
    MAX-ACCESS  not-accessible
    STATUS      current
    DESCRIPTION 
        "Each row in this table is indexed by communications entity, 
         connection-oriented protocol machine, and acknowledged 
         connectionless association identifiers.  Each row contains 
         measurements for a given acknowledged connectionless 
         association."
    REFERENCE   
        "IEEE 802.2 (ISO/IEC 8802-2), lLCConnectionlessAck MO."
    INDEX       { communicationsEntityId, coProtocolMachineId, 
                  coProtocolMachineId, lLCConnectionlessAckName }
    ::= { lLCConnectionlessAckTable 1 }

LLCConnectionlessAckEntry ::= SEQUENCE {
    lLCConnectionlessAckName                            SimpleNameType,
    lLCConnectionlessAckMaximumLLCInformationFieldSize  Integer32,
    lLCConnectionlessAckMaximumRetransmissions          Integer32,
    lLCConnectionlessAckTESTReceivedABBResponse         Counter32,
    lLCConnectionlessAckTESTReceivedCommand             Counter32,
    lLCConnectionlessAckTESTReceivedResponse            Counter32,
    lLCConnectionlessAckTESTSentABBResponse             Counter32,
    lLCConnectionlessAckTESTSentCommand                 Counter32,
    lLCConnectionlessAckTESTSentResponse                Counter32,
    lLCConnectionlessAckReceiveResources                TruthValue,
    lLCConnectionlessAckUIReceived                      Counter32,
    lLCConnectionlessAckUISent                          Counter32,
    lLCConnectionlessAckXIDReceivedCommand              Counter32,
    lLCConnectionlessAckXIDReceivedResponse             Counter32,
    lLCConnectionlessAckXIDSentCommand                  Counter32,
    lLCConnectionlessAckXIDSentResponse                 Counter32,
    lLCConnectionlessAckRetransmissions                 Counter32,
    lLCConnectionlessAckNoResponse                      Counter32,
    lLCConnectionlessAckCommandIP                       Counter32,
    lLCConnectionlessAckCommandIT                       Counter32,
    lLCConnectionlessAckCommandOK                       Counter32,
    lLCConnectionlessAckCommandPE                       Counter32,
    lLCConnectionlessAckCommandRS                       Counter32,
    lLCConnectionlessAckCommandUE                       Counter32,
    lLCConnectionlessAckCommandUN                       Counter32,
    lLCConnectionlessAckReceivedACCommand               Counter32,
    lLCConnectionlessAckSentACCommand                   Counter32,
    lLCConnectionlessAckResponseIP                      Counter32,
    lLCConnectionlessAckResponseIT                      Counter32,
    lLCConnectionlessAckResponseNE                      Counter32,
    lLCConnectionlessAckResponseNR                      Counter32,
    lLCConnectionlessAckResponseOK                      Counter32,
    lLCConnectionlessAckResponseRS                      Counter32,
    lLCConnectionlessAckResponseUE                      Counter32,
    lLCConnectionlessAckResponseUN                      Counter32,
    lLCConnectionlessAckViolation                       Counter32
}

lLCConnectionlessAckName OBJECT-TYPE
    SYNTAX      SimpleNameType (SIZE(1..32))
    MAX-ACCESS  not-accessible
    STATUS      current
    DESCRIPTION 
        "The localLSAP and remoteLSAPId and the local and remote MAC 
         Address."
    REFERENCE   
        "IEEE 802.2 (ISO/IEC 8802-2), lLCConnectionlessAckName."
    ::= { lLCConnectionlessAckEntry 1 }

lLCConnectionlessAckMaximumLLCInformationFieldSize OBJECT-TYPE
    SYNTAX      Integer32
    MAX-ACCESS  read-write
    STATUS      current
    DESCRIPTION 
        "The maximum length SDU that the LSAP will accomodate."
    REFERENCE   
        "IEEE 802.2 (ISO/IEC 8802-2), maximumLLCInformationFieldSize."
    ::= { lLCConnectionlessAckEntry 2 }

lLCConnectionlessAckMaximumRetransmissions OBJECT-TYPE
    SYNTAX      Integer32
    MAX-ACCESS  read-write
    STATUS      current
    DESCRIPTION 
        "The number of times that the LLC Type 2 should attempt to 
         realize a successful PDU transfer."
    REFERENCE   
        "IEEE 802.2 (ISO/IEC 8802-2), maximumRetransmissions."
    ::= { lLCConnectionlessAckEntry 3 }

lLCConnectionlessAckTESTReceivedABBResponse OBJECT-TYPE
    SYNTAX      Counter32
    UNITS       "TEST ABB responses received"
    MAX-ACCESS  read-only
    STATUS      current
    DESCRIPTION 
        "Provides a count of TEST responses received by this LSAP 
         without the LSDU due to limited resources at the remote 
         station."
    REFERENCE   
        "IEEE 802.2 (ISO/IEC 8802-2), tESTReceivedABBResponse."
    ::= { lLCConnectionlessAckEntry 4 }

lLCConnectionlessAckTESTReceivedCommand OBJECT-TYPE
    SYNTAX      Counter32
    UNITS       "TEST commands received"
    MAX-ACCESS  read-only
    STATUS      current
    DESCRIPTION 
        "Provides a count of TEST commands received from the MAC 
         sublayer by this LSAP.  This includes commands recieved with 
         any group address recognized by this LSAP."
    REFERENCE   
        "IEEE 802.2 (ISO/IEC 8802-2), tESTReceivedCommand."
    ::= { lLCConnectionlessAckEntry 5 }

lLCConnectionlessAckTESTReceivedResponse OBJECT-TYPE
    SYNTAX      Counter32
    UNITS       "TEST responses received"
    MAX-ACCESS  read-only
    STATUS      current
    DESCRIPTION 
        "Provides a count of TEST responses received from the MAC 
         sublayer by this LSAP."
    REFERENCE   
        "IEEE 802.2 (ISO/IEC 8802-2), tESTReceivedResponse."
    ::= { lLCConnectionlessAckEntry 6 }

lLCConnectionlessAckTESTSentABBResponse OBJECT-TYPE
    SYNTAX      Counter32
    UNITS       "TEST ABB responses sent"
    MAX-ACCESS  read-only
    STATUS      current
    DESCRIPTION 
        "Provides a count of TEST responses that were delivered to the 
         MAC without the LSDU data due to limited resources."
    REFERENCE   
        "IEEE 802.2 (ISO/IEC 8802-2), tESTSentABBResponse."
    ::= { lLCConnectionlessAckEntry 7 }

lLCConnectionlessAckTESTSentCommand OBJECT-TYPE
    SYNTAX      Counter32
    UNITS       "TEST commands sent"
    MAX-ACCESS  read-only
    STATUS      current
    DESCRIPTION 
        "Provides a count of TEST command set to the MAC sublayer by 
         this LSAP."
    REFERENCE   
        "IEEE 802.2 (ISO/IEC 8802-2), tESTSentCommand."
    ::= { lLCConnectionlessAckEntry 8 }

lLCConnectionlessAckTESTSentResponse OBJECT-TYPE
    SYNTAX      Counter32
    UNITS       "TEST responses sent"
    MAX-ACCESS  read-only
    STATUS      current
    DESCRIPTION 
        "Provides a count of TEST responses sent to the MAC sublayer by 
         this LSAP."
    REFERENCE   
        "IEEE 802.2 (ISO/IEC 8802-2), tESTSentResponse."
    ::= { lLCConnectionlessAckEntry 9 }

lLCConnectionlessAckReceiveResources OBJECT-TYPE
    SYNTAX      TruthValue
    MAX-ACCESS  read-write
    STATUS      current
    DESCRIPTION 
        "Causes the LSAP entity to either enable or disable the 
         resources for reception of the data field of Type 3 command 
         PDUs sent to this LSAP.  If a Type 3 PDU containing data is 
         received while disabled, the UN status code is returned in the 
         CCCC field of the response PDU."
    REFERENCE   
        "IEEE 802.2 (ISO/IEC 8802-2), type3ReceiveResources."
    ::= { lLCConnectionlessAckEntry 10 }

lLCConnectionlessAckUIReceived OBJECT-TYPE
    SYNTAX      Counter32
    UNITS       "UI frames received"
    MAX-ACCESS  read-only
    STATUS      current
    DESCRIPTION 
        "Provides a count of user data PDUs that were received by the 
         LSAP from the MAC sublayer and passed to the user layer.  This 
         includes commands received with group addresses of which the 
         LSAP is a member."
    REFERENCE   
        "IEEE 802.2 (ISO/IEC 8802-2), uIReceived."
    ::= { lLCConnectionlessAckEntry 11 }

lLCConnectionlessAckUISent OBJECT-TYPE
    SYNTAX      Counter32
    UNITS       "UI frames sent"
    MAX-ACCESS  read-only
    STATUS      current
    DESCRIPTION 
        "Provides a count of user data PDUs that were accepted by the 
         LSAP from the user layer and delivered to the MAC sublayer."
    REFERENCE   
        "IEEE 802.2 (ISO/IEC 8802-2), uISent."
    ::= { lLCConnectionlessAckEntry 12 }

lLCConnectionlessAckXIDReceivedCommand OBJECT-TYPE
    SYNTAX      Counter32
    UNITS       "XID commands received"
    MAX-ACCESS  read-only
    STATUS      current
    DESCRIPTION 
        "Proivdes a count of XID commands received from the MAC sublayer 
         by this LSAP.  This includes commands received with any group 
         address recognized by this LSAP."
    REFERENCE   
        "IEEE 802.2 (ISO/IEC 8802-2), xIDReceivedCommand."
    ::= { lLCConnectionlessAckEntry 13 }

lLCConnectionlessAckXIDReceivedResponse OBJECT-TYPE
    SYNTAX      Counter32
    UNITS       "XID responses received"
    MAX-ACCESS  read-only
    STATUS      current
    DESCRIPTION 
        "Provides a count of XID responses received from the MAC 
         sublayer by this LSAP."
    REFERENCE   
        "IEEE 802.2 (ISO/IEC 8802-2), xIDReceivedResponse."
    ::= { lLCConnectionlessAckEntry 14 }

lLCConnectionlessAckXIDSentCommand OBJECT-TYPE
    SYNTAX      Counter32
    UNITS       "XID commands sent"
    MAX-ACCESS  read-only
    STATUS      current
    DESCRIPTION 
        "Provides a count of XID commands sent to the MAC sublayer by 
         this LSAP."
    REFERENCE   
        "IEEE 802.2 (ISO/IEC 8802-2), xIDSentCommand."
    ::= { lLCConnectionlessAckEntry 15 }

lLCConnectionlessAckXIDSentResponse OBJECT-TYPE
    SYNTAX      Counter32
    UNITS       "XID responses sent"
    MAX-ACCESS  read-only
    STATUS      current
    DESCRIPTION 
        "Provides a count of the XID responses sent to the MAC sublayer 
         by this LSAP."
    REFERENCE   
        "IEEE 802.2 (ISO/IEC 8802-2), xIDSentResponse."
    ::= { lLCConnectionlessAckEntry 16 }

-- type3Retranmissions-P conditional package
--
-- Provides a count of retransmissions that have occurred to the 
-- destination associated with this LSAP pair.

lLCConnectionlessAckRetransmissions OBJECT-TYPE
    SYNTAX      Counter32
    UNITS       "retransmissions"
    MAX-ACCESS  read-only
    STATUS      current
    DESCRIPTION 
        "Provides a count of the number of PDUs which were retrasmitted 
         (at least once) by the Type 3 LLC service."
    REFERENCE   
        "IEEE 802.2 (ISO/IEC 8802-2), type3Retransmissions."
    ::= { lLCConnectionlessAckEntry 17 }

-- type3NoResponse-P conditional package
--
-- Provides a count of failures to obtain a response from the 
-- destination associated with an LSAPPairComponent, after exhausting 
-- the retry counter Retransmission4. When this counter is updated an 
-- event notification is forwarded.

lLCConnectionlessAckNoResponse OBJECT-TYPE
    SYNTAX      Counter32
    UNITS       "failures"
    MAX-ACCESS  read-only
    STATUS      current
    DESCRIPTION 
        "Provides a count of failures to obtain a response from the 
         destination associated with this LSAP pair, after exhausting 
         the retry counter MaximumRetransmissions4."
    REFERENCE   
        "IEEE 802.2 (ISO/IEC 8802-2), type3NoResponse."
    ::= { lLCConnectionlessAckEntry 18 }

-- type3Command-P conditional package
--
-- This conditional packages contains attributes (counters) that count 
-- received responses with the command status field set.

lLCConnectionlessAckCommandIP OBJECT-TYPE
    SYNTAX      Counter32
    UNITS       "responses"
    MAX-ACCESS  read-only
    STATUS      current
    DESCRIPTION 
        "Provides a count of the received responses with the command 
         status field set to indicate 'Permanent implementation 
         dependent error,' as defined in 
         5.4.3.2."
    REFERENCE   
        "IEEE 802.2 (ISO/IEC 8802-2), type3CommandIP."
    ::= { lLCConnectionlessAckEntry 19 }

lLCConnectionlessAckCommandIT OBJECT-TYPE
    SYNTAX      Counter32
    UNITS       "responses"
    MAX-ACCESS  read-only
    STATUS      current
    DESCRIPTION 
        "Provides a count of the received responses with the command 
         status field set to indicate 'Temporarily implementation 
         dependent error,' as defined in 
         5.4.3.2."
    REFERENCE   
        "IEEE 802.2 (ISO/IEC 8802-2), type3CommandIT."
    ::= { lLCConnectionlessAckEntry 20 }

lLCConnectionlessAckCommandOK OBJECT-TYPE
    SYNTAX      Counter32
    UNITS       "responses"
    MAX-ACCESS  read-only
    STATUS      current
    DESCRIPTION 
        "Provides a count of the received responses with the command 
         status field set to indicate 'Command accepted,' as defined in 
         5.4.3.2."
    REFERENCE   
        "IEEE 802.2 (ISO/IEC 8802-2), type3CommandOK."
    ::= { lLCConnectionlessAckEntry 21 }

lLCConnectionlessAckCommandPE OBJECT-TYPE
    SYNTAX      Counter32
    UNITS       "responses"
    MAX-ACCESS  read-only
    STATUS      current
    DESCRIPTION 
        "Provides a count of the received responses with the command 
         status field set to indicate 'Protocol error,' as defined in 
         5.4.3.2."
    REFERENCE   
        "IEEE 802.2 (ISO/IEC 8802-2), type3CommandPE."
    ::= { lLCConnectionlessAckEntry 22 }

lLCConnectionlessAckCommandRS OBJECT-TYPE
    SYNTAX      Counter32
    UNITS       "responses"
    MAX-ACCESS  read-only
    STATUS      current
    DESCRIPTION 
        "Provides a count of the received responses with the command 
         status field set to indicate 'Unimplemented or inactivated 
         service,' as defined in 5.4.3.2."
    REFERENCE   
        "IEEE 802.2 (ISO/IEC 8802-2), type3CommandRS."
    ::= { lLCConnectionlessAckEntry 23 }

lLCConnectionlessAckCommandUE OBJECT-TYPE
    SYNTAX      Counter32
    UNITS       "responses"
    MAX-ACCESS  read-only
    STATUS      current
    DESCRIPTION 
        "Provides a count of the received responses with the command 
         status field set to indicate 'LLC user interface error,' as 
         defined in 5.4.3.2."
    REFERENCE   
        "IEEE 802.2 (ISO/IEC 8802-2), type3CommandUE."
    ::= { lLCConnectionlessAckEntry 24 }

lLCConnectionlessAckCommandUN OBJECT-TYPE
    SYNTAX      Counter32
    UNITS       "responses"
    MAX-ACCESS  read-only
    STATUS      current
    DESCRIPTION 
        "Provides a count of the received responses with the command 
         status field set to indicate 'Resources temporarily 
         unavailable,' as defined in 5.4.3.2."
    REFERENCE   
        "IEEE 802.2 (ISO/IEC 8802-2), type3CommandUN."
    ::= { lLCConnectionlessAckEntry 25 }

lLCConnectionlessAckReceivedACCommand OBJECT-TYPE
    SYNTAX      Counter32
    UNITS       "AC command PDUs received"
    MAX-ACCESS  read-only
    STATUS      current
    DESCRIPTION 
        "Provides a count of AC command PDUs received from the other 
         LSAP of the connection (LSAP PAIR)."
    REFERENCE   
        "IEEE 802.2 (ISO/IEC 8802-2), type3ReceivedACCommand."
    ::= { lLCConnectionlessAckEntry 26 }

lLCConnectionlessAckSentACCommand OBJECT-TYPE
    SYNTAX      Counter32
    UNITS       "AC command PDUs sent"
    MAX-ACCESS  read-only
    STATUS      current
    DESCRIPTION 
        "Provides a count of AC command PDUs sent to the other LSAP of 
         the connection (LSAP PAIR)."
    REFERENCE   
        "IEEE 802.2 (ISO/IEC 8802-2), type3SentACCommand."
    ::= { lLCConnectionlessAckEntry 27 }

-- type3Response-P conditional package
--
-- This conditional packages contains attributes (counters) that count 
-- received responses with the response status field set.

lLCConnectionlessAckResponseIP OBJECT-TYPE
    SYNTAX      Counter32
    UNITS       "responses"
    MAX-ACCESS  read-only
    STATUS      current
    DESCRIPTION 
        "Provides a count of the received responses with the response 
         status field set to indicate 'Permanent implementation 
         dependent error,' as defined in 
         5.4.3.2."
    REFERENCE   
        "IEEE 802.2 (ISO/IEC 8802-2), type3ResponseIP."
    ::= { lLCConnectionlessAckEntry 28 }

lLCConnectionlessAckResponseIT OBJECT-TYPE
    SYNTAX      Counter32
    UNITS       "responses"
    MAX-ACCESS  read-only
    STATUS      current
    DESCRIPTION 
        "Provides a count of the received responses with the response 
         status field set to indicate 'Temporary implementation 
         dependent error,' as defined in 
         5.4.3.2."
    REFERENCE   
        "IEEE 802.2 (ISO/IEC 8802-2), type3ResponseIT."
    ::= { lLCConnectionlessAckEntry 29 }

lLCConnectionlessAckResponseNE OBJECT-TYPE
    SYNTAX      Counter32
    UNITS       "responses"
    MAX-ACCESS  read-only
    STATUS      current
    DESCRIPTION 
        "Provides a count of the received responses with the response 
         status field set to indicate 'Response LSDU never submitted,' 
         as defined in 5.4.3.2."
    REFERENCE   
        "IEEE 802.2 (ISO/IEC 8802-2), type3ResponseNE."
    ::= { lLCConnectionlessAckEntry 30 }

lLCConnectionlessAckResponseNR OBJECT-TYPE
    SYNTAX      Counter32
    UNITS       "responses"
    MAX-ACCESS  read-only
    STATUS      current
    DESCRIPTION 
        "Provides a count of the received responses with the response 
         status field set to indicate 'Response LSDU not requested,' as 
         defined in 5.4.3.2."
    REFERENCE   
        "IEEE 802.2 (ISO/IEC 8802-2), type3ResponseNR."
    ::= { lLCConnectionlessAckEntry 31 }

lLCConnectionlessAckResponseOK OBJECT-TYPE
    SYNTAX      Counter32
    UNITS       "responses"
    MAX-ACCESS  read-only
    STATUS      current
    DESCRIPTION 
        "Provides a count of the received responses with the response 
         status field set to indicate 'Response LSDU present,' as 
         defined in 5.4.3.2."
    REFERENCE   
        "IEEE 802.2 (ISO/IEC 8802-2), type3ResponseOK."
    ::= { lLCConnectionlessAckEntry 32 }

lLCConnectionlessAckResponseRS OBJECT-TYPE
    SYNTAX      Counter32
    UNITS       "responses"
    MAX-ACCESS  read-only
    STATUS      current
    DESCRIPTION 
        "Provides a count of the received responses with the response 
         status field set to indicate 'Unimplemented or inactivated 
         service,' as defined in 5.4.3.2."
    REFERENCE   
        "IEEE 802.2 (ISO/IEC 8802-2), type3ResponseRS."
    ::= { lLCConnectionlessAckEntry 33 }

lLCConnectionlessAckResponseUE OBJECT-TYPE
    SYNTAX      Counter32
    UNITS       "responses"
    MAX-ACCESS  read-only
    STATUS      current
    DESCRIPTION 
        "Provides a count of the received responses with the response 
         status field set to indicate 'LLC user interface error,' as 
         defined in 5.4.3.2."
    REFERENCE   
        "IEEE 802.2 (ISO/IEC 8802-2), type3ResponseUE."
    ::= { lLCConnectionlessAckEntry 34 }

lLCConnectionlessAckResponseUN OBJECT-TYPE
    SYNTAX      Counter32
    UNITS       "responses"
    MAX-ACCESS  read-only
    STATUS      current
    DESCRIPTION 
        "Provides a count of the received responses with the response 
         status field set to indicate 'Resources temporarily 
         unavailable,' as defined in 5.4.3.2."
    REFERENCE   
        "IEEE 802.2 (ISO/IEC 8802-2), type3ResponseUN."
    ::= { lLCConnectionlessAckEntry 35 }

-- type3Violation-P conditional package
--
-- Provides a count of the number of protocol violations detected by 
-- this connection.

lLCConnectionlessAckViolation OBJECT-TYPE
    SYNTAX      Counter32
    UNITS       "protocol violations"
    MAX-ACCESS  read-only
    STATUS      current
    DESCRIPTION 
        "Provides a count of the number of protocol violations detected 
         by this connection."
    REFERENCE   
        "IEEE 802.2 (ISO/IEC 8802-2), type3Violation."
    ::= { lLCConnectionlessAckEntry 36 }

lLCConnectionlessAckIVMO OBJECT IDENTIFIER
    ::= { osiTables 31 }

lLCConnectionlessAckIVMOTable OBJECT-TYPE
    SYNTAX      SEQUENCE OF LLCConnectionlessAckIVMOEntry
    MAX-ACCESS  not-accessible
    STATUS      current
    DESCRIPTION 
        "Provides a table of initial values for acknowledged 
         connectionless associations."
    REFERENCE   
        "IEEE 802.2 (ISO/IEC 8802-2), lLCCOnnectionlessAckIVMO MOC."
    ::= { lLCConnectionlessAckIVMO 1 }

lLCConnectionlessAckIVMOEntry OBJECT-TYPE
    SYNTAX      LLCConnectionlessAckIVMOEntry
    MAX-ACCESS  not-accessible
    STATUS      current
    DESCRIPTION 
        "Each row in this table is indexed by communications entity, 
         connection-oriented protocol machine identifiers and profile 
         name.  Each row contains initial values."
    REFERENCE   
        "IEEE 802.2 (ISO/IEC 8802-2), lLCCOnnectionlessAckIVMO MO."
    INDEX       { communicationsEntityId, coProtocolMachineId, 
                  lLCConnectionlessAckIVMOName }
    ::= { lLCConnectionlessAckIVMOTable 1 }

LLCConnectionlessAckIVMOEntry ::= SEQUENCE {
    lLCConnectionlessAckIVMOName                            SimpleNameType,
    lLCConnectionlessAckIVMOMaximumLLCInformationFieldSize  Integer32,
    lLCConnectionlessAckIVMOMaximumRetransmissions          Integer32,
    lLCConnectionlessAckIVMORowStatus                       RowStatus
}

-- lLCConnectionlessAckIVMO-P mandatory package
lLCConnectionlessAckIVMOName OBJECT-TYPE
    SYNTAX      SimpleNameType
    MAX-ACCESS  not-accessible
    STATUS      current
    DESCRIPTION 
        "Provides a name for this initial value managed object."
    REFERENCE   
        "IEEE 802.2 (ISO/IEC 8802-2), lLCConnecionlessAckIVMOName."
    ::= { lLCConnectionlessAckIVMOEntry 1 }

-- lLCConnectionlessAck-P mandatory package
lLCConnectionlessAckIVMOMaximumLLCInformationFieldSize OBJECT-TYPE
    SYNTAX      Integer32
    MAX-ACCESS  read-create
    STATUS      current
    DESCRIPTION 
        "The maximum length SDU that the LSAP will accomodate."
    REFERENCE   
        "IEEE 802.2 (ISO/IEC 8802-2), maximumLLCInformationFieldSize."
    ::= { lLCConnectionlessAckIVMOEntry 2 }

lLCConnectionlessAckIVMOMaximumRetransmissions OBJECT-TYPE
    SYNTAX      Integer32
    MAX-ACCESS  read-create
    STATUS      current
    DESCRIPTION 
        "The number of times that the LLC Type 3 should attempt to 
         realize a successful PDU transfer."
    REFERENCE   
        "IEEE 802.2 (ISO/IEC 8802-2), maximumRetransmissions."
    ::= { lLCConnectionlessAckIVMOEntry 3 }

-- type3Retranmissions-P conditional package
-- type3NoResponse-P conditional package
-- type3Command-P conditional package
-- type3Response-P conditional package
-- type3Violation-P conditional package

lLCConnectionlessAckIVMORowStatus OBJECT-TYPE
    SYNTAX      RowStatus
    MAX-ACCESS  read-create
    STATUS      current
    DESCRIPTION 
        "Provides a mechanism whereby management stations may create and 
         delete rows in this table.  Entries must persist across agent 
         reboots."
    REFERENCE   
        "STD 58, SNMPv2-TC RowStatus."
    ::= { lLCConnectionlessAckIVMOEntry 4 }

networkEntity OBJECT IDENTIFIER
    ::= { osiTables 32 }

networkEntityTable OBJECT-TYPE
    SYNTAX      SEQUENCE OF NetworkEntityEntry
    MAX-ACCESS  not-accessible
    STATUS      current
    DESCRIPTION 
        "The network entity managed object.  There may be multiple 
         instances of these MOs within a system.  Its definition permits 
         it to be deleted and created explicitly by management 
         operation, or to be created and deleted automatically as a part 
         of system operation."
    REFERENCE   
        "ITU-T Rec. X.283 | ISO/IEC 10733 networkEntity MOC."
    ::= { networkEntity 1 }

networkEntityEntry OBJECT-TYPE
    SYNTAX      NetworkEntityEntry
    MAX-ACCESS  not-accessible
    STATUS      current
    DESCRIPTION 
        "Entries in this table generated an objectCreation notification 
         when a row is added and an objectDeletion notification when a 
         row is removed."
    REFERENCE   
        "ITU-T Rec. X.283 | ISO/IEC 10733 networkEntity MO."
    INDEX       { communicationsEntityId }
    ::= { networkEntityTable 1 }

NetworkEntityEntry ::= SEQUENCE {
    networkEntityTitles         NAddresses,
    networkEntitySystemTypes    SystemTypes,
    networkEntityRowStatus      RowStatus
}

networkEntityTitles OBJECT-TYPE
    SYNTAX      NAddresses
    MAX-ACCESS  read-create
    STATUS      current
    DESCRIPTION 
        "The set of Network Entity Titles (having the same abstract 
         syntax as an NSAP address), which unambiguously identify the 
         Network Entity in an End or Intermediate System. The value may 
         be entered by a system management operation or it may be 
         derived by some local means, for example by autoconfiguration.
         
         The OCTET STRING is a set of NAddresses which consist of one 
         octet length (0..20) and length octets of address, followed by 
         the next NAddress."
    REFERENCE   
        "ITU-T Rec. X.283 | ISO/IEC 10733 networkEntityTitles."
    ::= { networkEntityEntry 1 }

networkEntitySystemTypes OBJECT-TYPE
    SYNTAX      SystemTypes
    MAX-ACCESS  read-create
    STATUS      current
    DESCRIPTION 
        "Indicates whether the system is an end-system or and 
         intermediate-system, or both.
         
         The set of system roles supported by this Network Entity. This 
         may be End System, Intermediate System or both. The actual role 
         in which a particular instance of the protocol machine is 
         operating is determined by the operationalSystemType attribute 
         of the cLNS or cONS MO.
         
         The set of CLNS system roles supported by this Network Entity. 
         This may be End System, Intermediate System or both. The actual 
         role in which a particular instance of the cLNS protocol 
         machine is operating is determined by the operationalSystemType 
         attribute of the cLNS MO."
    REFERENCE   
        "ITU-T Rec. X.283 | ISO/IEC 10733 systemTypes."
    ::= { networkEntityEntry 2 }

networkEntityRowStatus OBJECT-TYPE
    SYNTAX      RowStatus
    MAX-ACCESS  read-create
    STATUS      current
    DESCRIPTION 
        "The networkEntity-networkSubsystem-Automatic name binding shall 
         be used when the networkEntity MO is created automatically by 
         operation of the system.  The details of these operations are 
         outside the scope of this Specification.
         
         The networkEntity-networkSubsystem-Management name binding 
         shall be used when the networkEntity MO is created explicitly 
         by system management."
    REFERENCE   
        "ITU-T Rec. X.283 | ISO/IEC 10733 
         networkEntity-networkSubsystem-Automatic, 
         networkEntity-networkSubsystem-Management, STD 58, SNMPv2-TC 
         RowStatus."
    ::= { networkEntityEntry 3 }

nSAP OBJECT IDENTIFIER
    ::= { osiTables 33 }

nSAPTable OBJECT-TYPE
    SYNTAX      SEQUENCE OF NSAPEntry
    MAX-ACCESS  not-accessible
    STATUS      current
    DESCRIPTION 
        "The NSAP managed object.
         
         There is one nSAP MO for each set of NSAPs supported by the 
         Network Subsystem associated with a single Transport layer 
         client.  Each NSAP MO corresponds to a set of one or more NSAPs 
         supported by the Network Subsystem.
         
         There is not more than one Transport layer client associated 
         with a single nSAP MO, but there may be more than one nSAP MO, 
         and corresponding sets of NSAPs, associated with a single 
         Transport layer client.  Its definition permits it to be 
         created and deleted explicitly by management operation or to be 
         created and deleted automatically as part of system operation."
    REFERENCE   
        "ITU-T Rec. X.283 | ISO/IEC 10733 nSAP MOC."
    ::= { nSAP 1 }

nSAPEntry OBJECT-TYPE
    SYNTAX      NSAPEntry
    MAX-ACCESS  not-accessible
    STATUS      current
    DESCRIPTION 
        "Entries in this table generated an objectCreation notification 
         when they are first added and an objectDeletion notification 
         when they are removed.
         
         If the package is created using the 
         nSAP-networkSubsystem-Automatic name binding the initial value 
         of the sap2Address is not constrained by this Specification.  
         However, if the package is created using the 
         nSAP-networkSubsystem-Management name binding the initial value 
         of the sap2Address attribute shall be specified in the CMIP 
         create."
    REFERENCE   
        "ITU-T Rec. X.283 | ISO/IEC 10733 nSAP MO."
    INDEX       { sapId }
    ::= { nSAPTable 1 }

NSAPEntry ::= SEQUENCE {
    nSAPRowStatus   RowStatus
}

nSAPRowStatus OBJECT-TYPE
    SYNTAX      RowStatus
    MAX-ACCESS  read-create
    STATUS      current
    DESCRIPTION 
        "Provides a mechanism whereby management stations, following the 
         RowStatus textual convention of the SNMPv2-TC module, may 
         create and delete conceptual rows in this table.
         
         The nSAP-networkSubsystem-Automatic name binding shall be used 
         when the nSAP MO is created automatically by the operation of 
         the network entity. For example, by the use of 
         autoconfiguration or dynamic NSAP Address assignment 
         techniques. The details of the operation of these techniques 
         are outside the scope of this Specification.
         
         The nSAP-networkSubsystem-Management name binding shall be used 
         when the nSAP MO is created by system management. The value of 
         the sap2Address attribute shall be specified in the CMIP 
         create."
    REFERENCE   
        "ITU-T Rec. X.283 | ISO/IEC 10733 
         nSAP-networkSubsystem-Automatic, 
         nSAP-networkSubsystem-Management, STD 58, SNMPv2-TC RowStatus."
    ::= { nSAPEntry 1 }

cLNS OBJECT IDENTIFIER
    ::= { osiTables 34 }

cLNSTable OBJECT-TYPE
    SYNTAX      SEQUENCE OF CLNSEntry
    MAX-ACCESS  not-accessible
    STATUS      current
    DESCRIPTION 
        "The connectionless-mode network service managed object.
         
         There is no more than one of these MOs per network entity.  Its 
         definition permits it to be created and deleted explicitly by 
         management operation, but in some systems it will exist 
         inherently and neither creation nor deletion by management 
         operation will be possible.  Name bindings are defined for both 
         cases.
         
         When the protocol machine is operable, the operationalState 
         shall have the value 'enabled'; otherwise it shall have the 
         value 'disabled'.  Transitions of operationalState shall be 
         reported using the stateChange notification. A cLNS MO may be 
         created in the 'enabled' operational state."
    REFERENCE   
        "ITU-T Rec. X.283 | ISO/IEC 10733 cLNS MOC."
    ::= { cLNS 1 }

cLNSEntry OBJECT-TYPE
    SYNTAX      CLNSEntry
    MAX-ACCESS  not-accessible
    STATUS      current
    DESCRIPTION 
        "Entries in this table generate an objectCreation notification 
         when added to the table; an objectDeletion notification when 
         removed from the table, and a stateChange notification when the 
         value of the operationalState attribute changes.
         
         Actions 'activate', 'deactivate' and 'deactivateWhenNoUsers' 
         and are the same as the 'unlocked', 'locked' and 'shutting 
         down' settings of the administrative state.
         
         Note that the clProtocolMachineId value is 'CLNS'."
    REFERENCE   
        "ITU-T Rec. X.283 | ISO/IEC 10733 cLNS MO."
    INDEX       { communicationsEntityId, clProtocolMachineId }
    ::= { cLNSTable 1 }

CLNSEntry ::= SEQUENCE {
    cLNSAdministrativeState             AdministrativeState,
    cLNSSupportedProtocols              OCTET STRING,
    cLNSOperationalSystemType           SystemTypes,
    cLNSOctetsSentCounter               Counter32,
    cLNSOctetsReceivedCounter           Counter32,
    cLNSSegmentsReceived                Counter32,
    cLNSSegmentsDiscarded               Counter32,
    cLNSAssemblingSegmentsDiscarded     Counter32,
    cLNSErrorReportsReceived            Counter32,
    cLNSpDUDiscards                     Counter32,
    cLNSCongestionDiscards              Counter32,
    cLNSMaximumLifetime                 Integer32,
    cLNSEnableChecksum                  TruthValue,
    cLNSRowStatus                       RowStatus
}

cLNSAdministrativeState OBJECT-TYPE
    SYNTAX      AdministrativeState
    MAX-ACCESS  read-create
    STATUS      current
    DESCRIPTION 
        "Provides the administrative state of the connectionless network 
         service connectionless protocol machine following the 
         AdministrativeState textual convention of the OPENSS7-TMN-TC 
         module, per ITU-T Rec. X.721 | ISO/IEC 10165-2 
         administrativeState.
         
         When 'locked', the protocol machine is administratively 
         prohibited from providing service to users.  When 'unlocked', 
         the protocol machine is administratively permitted to provider 
         service to users.  When 'shutting down' the protocol machine is 
         administratively prohibited from providing service to new 
         users."
    REFERENCE   
        "ITU-T Rec. X.721 | ISO/IEC 10165-2 administrativeState."
    ::= { cLNSEntry 1 }

cLNSSupportedProtocols OBJECT-TYPE
    SYNTAX      OCTET STRING
    MAX-ACCESS  read-create
    STATUS      current
    DESCRIPTION 
        "The set of Connectionless Network protocols supported by this 
         instance of the cLNS protocol machine, expressed except where 
         otherwise indicated (for example because there are more than 
         one protocol described in a single International Standard) as 
         the registered object identifiers of the relevant International 
         Standard. The operation of a particular protocol over a 
         particular linkage is determined by the linkage 
         operationalProtocols attribute. The value of the 
         supportedProtocols attribute is determined by the 
         implementation.
         
         This attribute is an autonomous type which provides an object 
         identifier that identifies the protocols supported, the 
         protocol versions supported, and the defects repaired in the 
         protocol versions supported."
    REFERENCE   
        "ITU-T Rec. X.283 | ISO/IEC 10733 supportedProtocols."
    ::= { cLNSEntry 2 }

cLNSOperationalSystemType OBJECT-TYPE
    SYNTAX      SystemTypes
    MAX-ACCESS  read-create
    STATUS      current
    DESCRIPTION 
        "The system role in which this instance is operating. A value of 
         ES indicates that the system shall perform no forwarding 
         operations upon non-local PDUs. A value of IS indicates that 
         the system is permitted to perform forwarding operations, but 
         the decision to forward individual PDUs, or not to forward 
         them, shall be taken on the basis of the available routing 
         information.
         
         If the MO is created by management operation (using the 
         cLNS-networkEntity-Management or cONS-networkEntity-Management 
         name binding), the initial value of the operationalSystemType 
         attribute shall be specified in the CMIP create. Otherwise, the 
         value shall be determined in an implementation specific manner. 
         The value shall be one of those present in the systemTypes 
         attribute of the superior Network Entity MO."
    REFERENCE   
        "ITU-T Rec. X.283 | ISO/IEC 10733 operationalSystemType."
    ::= { cLNSEntry 3 }

-- X.283 cLNS8473-P conditional package
--
-- The cLNS8473-P package imports octetsSentCounter and 
-- octetsReceivedCounter from DIS 10165-2. They are used to count the 
-- number of octets of data transmitted or received by the local network 
-- entity in ISO 8473 Data PDUs. (i.e. those which which have a source 
-- or destination N-Address, respectively, which corresponds to that of 
-- the local network entity.).
--
-- The cLNS8473-P package imports the communicationsAlarm notification 
-- from Rec.  721 | ISO/IEC 10165-2. It is used to report the following 
-- cLNS managed object events.
--
-- pDUDiscard: Generated when a data NPDU is discarded due to any of the 
-- reasons specified in ISO 8473 Table 7, with the exception of `PDU 
-- Discarded due to Congestion' The header of the PDU in error shall be 
-- reported as a parameter in the additionalInformation field of the 
-- communicationsAlarm, using the notificationPDUHeader PARAMETER.
--
-- The significance sub-parameter of each item of additionalInformation 
-- shall be set to the value `False' (i.e. not significant) so that a 
-- managing system receiving the event report will be less likely to 
-- reject it. The value NLM.pDUDiscard and that corresponding to the 
-- Reason For Discard shall both be reported in the specificProblems 
-- parameter.
--
-- The probableCause shall be set to NLM.communicationsProtocolError.
--
-- The perceivedSeverity shall be set to `Minor'. A subsequent 
-- communicationsAlarm with a perceivedSeverity value of `Cleared' shall 
-- not be generated. No other fields or parameters shall be used, with 
-- the exception of further parameters in the AdditionalInformation 
-- field. A PDU which does not contain one of the protocol identifiers 
-- defined in ISO 8473 shall not cause this event.
--
-- A PDU with a protocol ID 1000 0001 shall not cause this event if it 
-- does not also contain the Version/Protocol Identifier extension in 
-- clause 7.2.4 of ISO 8473. If an error report PDU is generated, the 
-- PDU header and Discard Reason in the error report shall be the same 
-- as those in the corresponding notification.;
--
cLNSOctetsSentCounter OBJECT-TYPE
    SYNTAX      Counter32
    MAX-ACCESS  read-only
    STATUS      current
    DESCRIPTION 
        "Provides a count of the number of octets sent."
    REFERENCE   
        "ITU-T Rec. X.283 | ISO/IEC 10733 octetsSentCounter."
    ::= { cLNSEntry 4 }

cLNSOctetsReceivedCounter OBJECT-TYPE
    SYNTAX      Counter32
    MAX-ACCESS  read-only
    STATUS      current
    DESCRIPTION 
        "Provides a count of the number of octets received."
    REFERENCE   
        "ITU-T Rec. X.283 | ISO/IEC 10733 octetsSentCounter."
    ::= { cLNSEntry 5 }

cLNSSegmentsReceived OBJECT-TYPE
    SYNTAX      Counter32
    MAX-ACCESS  read-only
    STATUS      current
    DESCRIPTION 
        "Provides a count of the number of segments received."
    REFERENCE   
        "ITU-T Rec. X.283 | ISO/IEC 10733 octetsSentCounter."
    ::= { cLNSEntry 6 }

cLNSSegmentsDiscarded OBJECT-TYPE
    SYNTAX      Counter32
    MAX-ACCESS  read-only
    STATUS      current
    DESCRIPTION 
        "Provides a count of the number of segments discarded."
    REFERENCE   
        "ITU-T Rec. X.283 | ISO/IEC 10733 octetsSentCounter."
    ::= { cLNSEntry 7 }

cLNSAssemblingSegmentsDiscarded OBJECT-TYPE
    SYNTAX      Counter32
    MAX-ACCESS  read-only
    STATUS      current
    DESCRIPTION 
        "Provides a count of the number of assembling segments 
         discarded."
    REFERENCE   
        "ITU-T Rec. X.283 | ISO/IEC 10733 octetsSentCounter."
    ::= { cLNSEntry 8 }

cLNSErrorReportsReceived OBJECT-TYPE
    SYNTAX      Counter32
    MAX-ACCESS  read-only
    STATUS      current
    DESCRIPTION 
        "Provides a count of the number of error reports received."
    REFERENCE   
        "ITU-T Rec. X.283 | ISO/IEC 10733 octetsSentCounter."
    ::= { cLNSEntry 9 }

cLNSpDUDiscards OBJECT-TYPE
    SYNTAX      Counter32
    MAX-ACCESS  read-only
    STATUS      current
    DESCRIPTION 
        "Provides a count of the number of PDU discards."
    REFERENCE   
        "ITU-T Rec. X.283 | ISO/IEC 10733 octetsSentCounter."
    ::= { cLNSEntry 10 }

cLNSCongestionDiscards OBJECT-TYPE
    SYNTAX      Counter32
    MAX-ACCESS  read-only
    STATUS      current
    DESCRIPTION 
        "Provides a count of the number of congestion discard."
    REFERENCE   
        "ITU-T Rec. X.283 | ISO/IEC 10733 octetsSentCounter."
    ::= { cLNSEntry 11 }

cLNSMaximumLifetime OBJECT-TYPE
    SYNTAX      Integer32 (1..255)
    UNITS       "half-seconds"
    MAX-ACCESS  read-create
    STATUS      current
    DESCRIPTION 
        "Provides the maximum lifetime in seconds."
    REFERENCE   
        "ITU-T Rec. X.283 | ISO/IEC 10733 maximumLifetime."
    ::= { cLNSEntry 12 }

-- uses the communicationsAlarm

-- X.283 cLNSChecksum-P conditional package
--
-- When present checksum generation is controlled by the 8473 
-- enableChecksum attribute.
cLNSEnableChecksum OBJECT-TYPE
    SYNTAX      TruthValue
    MAX-ACCESS  read-create
    STATUS      current
    DESCRIPTION 
        "When True, the generation of checksums is enabled."
    REFERENCE   
        "ITU-T Rec. X.283 | ISO/IEC 10733 enableChecksum."
    DEFVAL      { false }
    ::= { cLNSEntry 13 }

-- cLNS-networkEntity-Management name binding
-- cLNS-networkEntity-Automatic name binding
cLNSRowStatus OBJECT-TYPE
    SYNTAX      RowStatus
    MAX-ACCESS  read-create
    STATUS      current
    DESCRIPTION 
        "Provides a mechanism whereby management stations, following the 
         RowStatus textual convention from the SNMPv2-TC module, may 
         create or delete conceptual rows in this table.
         
         There is only one cLNS entry per networkEntity with the name 
         clProtocolMachineId 'CLNS'.
         
         The cLNS-networkEntity-Management name binding applies when the 
         cLNS managed object can be created and deleted by management.
         
         The cLNS-networkEntity-Automatic name binding applies when the 
         cLNS managed object cannot be created or deleted by 
         management."
    REFERENCE   
        "ITU-T Rec. X.283 | ISO/IEC 10733, 
         cLNS-networkEntity-Management, cLNS-networkEntity-Automatic, 
         STD 58, SNMPv2-TC RowStatus."
    ::= { cLNSEntry 14 }

cLNSISIS OBJECT IDENTIFIER
    ::= { osiTables 35 }

cLNSISISTable OBJECT-TYPE
    SYNTAX      SEQUENCE OF CLNSISISEntry
    MAX-ACCESS  not-accessible
    STATUS      current
    DESCRIPTION 
        "Provides a table of ISIS protocol machines."
    REFERENCE   
        "ITU-T Rec. X.283 | ISO/IEC 10733."
    ::= { cLNSISIS 1 }

cLNSISISEntry OBJECT-TYPE
    SYNTAX      CLNSISISEntry
    MAX-ACCESS  not-accessible
    STATUS      current
    DESCRIPTION 
        "Each row is indexed by communications entity and connectionless 
         protocol machine identifiers.  Each row contains protocol 
         parameters for the ISIS protocol machine."
    REFERENCE   
        "ITU-T Rec. X.283 | ISO/IEC 10733."
    INDEX       { communicationsEntityId, clProtocolMachineId }
    ::= { cLNSISISTable 1 }

CLNSISISEntry ::= SEQUENCE {
    cLNSISISversion                                     DummySyntax,
    cLNSISISiSType                                      Integer32,
    cLNSISISsystemId                                    DummySyntax,
    cLNSISISmaximumPathSplits                           Integer32,
    cLNSISISminimumLSPTransmissionInterval              TimeInterval,
    cLNSISISmaximumLSPGenerationInterval                TimeInterval,
    cLNSISISminimumBroadcastLSPTransmissionInterval     TimeInterval,
    cLNSISIScompleteSNPInterval                         TimeInterval,
    cLNSISISoriginatingL1LSPBufferSize                  OriginatingLSPBufferSize,
    cLNSISISmanualAreaAddresses                         DummySyntax,
    cLNSISISmaximumAreaAddresses                        Integer32,
    cLNSISISminimumLSPGenerationInterval                TimeInterval,
    cLNSISISpollESHelloRate                             TimeInterval,
    cLNSISISpartialSNPInterval                          TimeInterval,
    cLNSISISwaitingTime                                 TimeInterval,
    cLNSISISdRISISHelloTimer                            TimeInterval,
    cLNSISISl1State                                     DatabaseState,
    cLNSISISareaAddresses                               DummySyntax,
    cLNSISIScorruptedLSPsDetected                       Counter32,
    cLNSISISlSPL1DatabaseOverloads                      Counter32,
    cLNSISISmanualAddressesDroppedFromAreas             Counter32,
    cLNSISISattemptsToExceedMaximumSequenceNumber       Counter32,
    cLNSISISsequenceNumberSkips                         Counter32,
    cLNSISISownLSPPurges                                Counter32,
    cLNSISISiDFieldLengthMismatches                     Counter32,
    cLNSISISmaximumAreaAddressesMismatches              Counter32,
    cLNSISISoriginatingLSPBufferSizeMismatches          Counter32,
    cLNSISISlSPTooLargeToPropagate                      Counter32,
    cLNSISISareaTransmitPassword                        DummySyntax,
    cLNSISISareaReceivePasswords                        DummySyntax,
    cLNSISISauthenticationFailures                      Counter32,
    cLNSISISRowStatus                                   RowStatus
}

cLNSISISversion OBJECT-TYPE
    SYNTAX      DummySyntax
    MAX-ACCESS  read-only
    STATUS      current
    DESCRIPTION 
        "Provides the ISIS version."
    ::= { cLNSISISEntry 1 }

cLNSISISiSType OBJECT-TYPE
    SYNTAX      Integer32
    MAX-ACCESS  read-only
    STATUS      current
    DESCRIPTION 
        "Provides the ISIS type."
    ::= { cLNSISISEntry 2 }

cLNSISISsystemId OBJECT-TYPE
    SYNTAX      DummySyntax
    MAX-ACCESS  read-only
    STATUS      current
    DESCRIPTION 
        "Provides the ISIS system identifier."
    ::= { cLNSISISEntry 3 }

cLNSISISmaximumPathSplits OBJECT-TYPE
    SYNTAX      Integer32 (1..32)
    MAX-ACCESS  read-only
    STATUS      current
    DESCRIPTION 
        "Provides the maximum number of path splits."
    ::= { cLNSISISEntry 4 }

cLNSISISminimumLSPTransmissionInterval OBJECT-TYPE
    SYNTAX      TimeInterval
    MAX-ACCESS  read-only
    STATUS      current
    DESCRIPTION 
        "Provides the minimum LSP transmission interval."
    ::= { cLNSISISEntry 5 }

cLNSISISmaximumLSPGenerationInterval OBJECT-TYPE
    SYNTAX      TimeInterval
    MAX-ACCESS  read-only
    STATUS      current
    DESCRIPTION 
        "Provides the maximum LSP generation interval."
    ::= { cLNSISISEntry 6 }

cLNSISISminimumBroadcastLSPTransmissionInterval OBJECT-TYPE
    SYNTAX      TimeInterval
    MAX-ACCESS  read-only
    STATUS      current
    DESCRIPTION 
        "Provides the minimum broadcast LSP transmission interval."
    ::= { cLNSISISEntry 7 }

cLNSISIScompleteSNPInterval OBJECT-TYPE
    SYNTAX      TimeInterval
    MAX-ACCESS  read-only
    STATUS      current
    DESCRIPTION 
        "Provides the complete SNP interval."
    ::= { cLNSISISEntry 8 }

cLNSISISoriginatingL1LSPBufferSize OBJECT-TYPE
    SYNTAX      OriginatingLSPBufferSize
    MAX-ACCESS  read-only
    STATUS      current
    DESCRIPTION 
        "Provides the originating L1 LSP buffer size."
    ::= { cLNSISISEntry 9 }

cLNSISISmanualAreaAddresses OBJECT-TYPE
    SYNTAX      DummySyntax
    MAX-ACCESS  read-only
    STATUS      current
    DESCRIPTION 
        "Provides the manual area addresses."
    ::= { cLNSISISEntry 10 }

cLNSISISmaximumAreaAddresses OBJECT-TYPE
    SYNTAX      Integer32 (0..254)
    MAX-ACCESS  read-only
    STATUS      current
    DESCRIPTION 
        "Provides the maximum number of area addresses."
    ::= { cLNSISISEntry 11 }

cLNSISISminimumLSPGenerationInterval OBJECT-TYPE
    SYNTAX      TimeInterval
    MAX-ACCESS  read-only
    STATUS      current
    DESCRIPTION 
        "Provides the minimum LSP generation interval."
    ::= { cLNSISISEntry 12 }

cLNSISISpollESHelloRate OBJECT-TYPE
    SYNTAX      TimeInterval
    MAX-ACCESS  read-only
    STATUS      current
    DESCRIPTION 
        "Provides the poll end-system hello rate."
    ::= { cLNSISISEntry 13 }

cLNSISISpartialSNPInterval OBJECT-TYPE
    SYNTAX      TimeInterval
    MAX-ACCESS  read-only
    STATUS      current
    DESCRIPTION 
        "Provides the paritial SNP interval."
    ::= { cLNSISISEntry 14 }

cLNSISISwaitingTime OBJECT-TYPE
    SYNTAX      TimeInterval
    MAX-ACCESS  read-only
    STATUS      current
    DESCRIPTION 
        "Provides the waiting time."
    ::= { cLNSISISEntry 15 }

cLNSISISdRISISHelloTimer OBJECT-TYPE
    SYNTAX      TimeInterval
    MAX-ACCESS  read-only
    STATUS      current
    DESCRIPTION 
        "Provides the DR ISIS hello timer."
    ::= { cLNSISISEntry 16 }

cLNSISISl1State OBJECT-TYPE
    SYNTAX      DatabaseState
    MAX-ACCESS  read-only
    STATUS      current
    DESCRIPTION 
        "Provides the L1 state."
    ::= { cLNSISISEntry 17 }

cLNSISISareaAddresses OBJECT-TYPE
    SYNTAX      DummySyntax
    MAX-ACCESS  read-only
    STATUS      current
    DESCRIPTION 
        "Provides the area addresses."
    ::= { cLNSISISEntry 18 }

cLNSISIScorruptedLSPsDetected OBJECT-TYPE
    SYNTAX      Counter32
    MAX-ACCESS  read-only
    STATUS      current
    DESCRIPTION 
        "Provides a count of the number of corrupted LSPs detected."
    ::= { cLNSISISEntry 19 }

cLNSISISlSPL1DatabaseOverloads OBJECT-TYPE
    SYNTAX      Counter32
    MAX-ACCESS  read-only
    STATUS      current
    DESCRIPTION 
        "Provides a count of the number of LSP L1 database overloads."
    ::= { cLNSISISEntry 20 }

cLNSISISmanualAddressesDroppedFromAreas OBJECT-TYPE
    SYNTAX      Counter32
    MAX-ACCESS  read-only
    STATUS      current
    DESCRIPTION 
        "Provides a count of the number of manual addresses dropped from 
         areas."
    ::= { cLNSISISEntry 21 }

cLNSISISattemptsToExceedMaximumSequenceNumber OBJECT-TYPE
    SYNTAX      Counter32
    MAX-ACCESS  read-only
    STATUS      current
    DESCRIPTION 
        "Provides a count of the number of attempts to exceed maximum 
         sequence number."
    ::= { cLNSISISEntry 22 }

cLNSISISsequenceNumberSkips OBJECT-TYPE
    SYNTAX      Counter32
    MAX-ACCESS  read-only
    STATUS      current
    DESCRIPTION 
        "Provides a count of the number of sequence number skips."
    ::= { cLNSISISEntry 23 }

cLNSISISownLSPPurges OBJECT-TYPE
    SYNTAX      Counter32
    MAX-ACCESS  read-only
    STATUS      current
    DESCRIPTION 
        "Provides a count of the number of own-LSP purges."
    ::= { cLNSISISEntry 24 }

cLNSISISiDFieldLengthMismatches OBJECT-TYPE
    SYNTAX      Counter32
    MAX-ACCESS  read-only
    STATUS      current
    DESCRIPTION 
        "Provides a count of the number of field length mismatches."
    ::= { cLNSISISEntry 25 }

cLNSISISmaximumAreaAddressesMismatches OBJECT-TYPE
    SYNTAX      Counter32
    MAX-ACCESS  read-only
    STATUS      current
    DESCRIPTION 
        "Provides a count of the number of maximum area address 
         mismatches."
    ::= { cLNSISISEntry 26 }

cLNSISISoriginatingLSPBufferSizeMismatches OBJECT-TYPE
    SYNTAX      Counter32
    MAX-ACCESS  read-only
    STATUS      current
    DESCRIPTION 
        "Provides a count of the number of originating LSP buffer size 
         mismatches."
    ::= { cLNSISISEntry 27 }

cLNSISISlSPTooLargeToPropagate OBJECT-TYPE
    SYNTAX      Counter32
    MAX-ACCESS  read-only
    STATUS      current
    DESCRIPTION 
        "Provides a count of the number of LSP too large to propagate 
         events."
    ::= { cLNSISISEntry 28 }

cLNSISISareaTransmitPassword OBJECT-TYPE
    SYNTAX      DummySyntax
    MAX-ACCESS  read-only
    STATUS      current
    DESCRIPTION 
        "Provides a count of the number of area transmit passwords."
    ::= { cLNSISISEntry 29 }

cLNSISISareaReceivePasswords OBJECT-TYPE
    SYNTAX      DummySyntax
    MAX-ACCESS  read-only
    STATUS      current
    DESCRIPTION 
        "Provides a count of the number of area receive passwords."
    ::= { cLNSISISEntry 30 }

cLNSISISauthenticationFailures OBJECT-TYPE
    SYNTAX      Counter32
    MAX-ACCESS  read-only
    STATUS      current
    DESCRIPTION 
        "Provides a count of the number of authentication failures."
    ::= { cLNSISISEntry 31 }

cLNSISISRowStatus OBJECT-TYPE
    SYNTAX      RowStatus
    MAX-ACCESS  read-create
    STATUS      current
    DESCRIPTION 
        "Provides a mechanism whereby management stations may create and 
         delete rows in this table.  Entries must persist across agent 
         reboots."
    ::= { cLNSISISEntry 32 }

cLNSISISLevel2 OBJECT IDENTIFIER
    ::= { osiTables 36 }

cLNSISISLevel2Table OBJECT-TYPE
    SYNTAX      SEQUENCE OF CLNSISISLevel2Entry
    MAX-ACCESS  not-accessible
    STATUS      current
    DESCRIPTION 
        "Provides a table of ISIS Level 2 protocol machines."
    ::= { cLNSISISLevel2 1 }

cLNSISISLevel2Entry OBJECT-TYPE
    SYNTAX      CLNSISISLevel2Entry
    MAX-ACCESS  not-accessible
    STATUS      current
    DESCRIPTION 
        "Each row in this table is indexed by connection-oriented 
         protocol machine identifier.  Each row contains parameters and 
         measurements of ISIS level 2 operation."
    INDEX       { coProtocolMachineId }
    ::= { cLNSISISLevel2Table 1 }

CLNSISISLevel2Entry ::= SEQUENCE {
    cLNSISISLevel2maximumVirtualAdjacencies                 Integer32,
    cLNSISISLevel2partitionAreaAddresses                    DummySyntax,
    cLNSISISLevel2partitionDesignatedL2IntermediateSystem   DummySyntax,
    cLNSISISLevel2partitionVirtualLinkChanges               Counter32,
    cLNSISISLevel2originatingL2LSPBufferSize                OriginatingLSPBufferSize,
    cLNSISISLevel2l2State                                   DatabaseState,
    cLNSISISLevel2lSPL2DatabaseOverloads                    Counter32,
    cLNSISISLevel2domainTransmitPassword                    DummySyntax,
    cLNSISISLevel2domainReceivePasswords                    DummySyntax,
    cLNSISISLevel2RowStatus                                 RowStatus
}

cLNSISISLevel2maximumVirtualAdjacencies OBJECT-TYPE
    SYNTAX      Integer32 (0..32)
    MAX-ACCESS  read-only
    STATUS      current
    DESCRIPTION 
        "Provides the maximum virtual adjacencies."
    ::= { cLNSISISLevel2Entry 1 }

cLNSISISLevel2partitionAreaAddresses OBJECT-TYPE
    SYNTAX      DummySyntax
    MAX-ACCESS  read-only
    STATUS      current
    DESCRIPTION 
        "Provides the partition area addresses."
    ::= { cLNSISISLevel2Entry 2 }

cLNSISISLevel2partitionDesignatedL2IntermediateSystem OBJECT-TYPE
    SYNTAX      DummySyntax
    MAX-ACCESS  read-only
    STATUS      current
    DESCRIPTION 
        "Provides the partition designated L2 intermediate system."
    ::= { cLNSISISLevel2Entry 3 }

cLNSISISLevel2partitionVirtualLinkChanges OBJECT-TYPE
    SYNTAX      Counter32
    MAX-ACCESS  read-only
    STATUS      current
    DESCRIPTION 
        "Provides a count of the number of partition virtual link 
         changes."
    ::= { cLNSISISLevel2Entry 4 }

cLNSISISLevel2originatingL2LSPBufferSize OBJECT-TYPE
    SYNTAX      OriginatingLSPBufferSize
    MAX-ACCESS  read-only
    STATUS      current
    DESCRIPTION 
        "Provides the originating L2 LSP buffer size."
    ::= { cLNSISISLevel2Entry 5 }

cLNSISISLevel2l2State OBJECT-TYPE
    SYNTAX      DatabaseState
    MAX-ACCESS  read-only
    STATUS      current
    DESCRIPTION 
        "Provides the ISIS L2 state."
    ::= { cLNSISISLevel2Entry 6 }

cLNSISISLevel2lSPL2DatabaseOverloads OBJECT-TYPE
    SYNTAX      Counter32
    MAX-ACCESS  read-only
    STATUS      current
    DESCRIPTION 
        "Provides a count of the number of LSP L2 database overloads."
    ::= { cLNSISISLevel2Entry 7 }

cLNSISISLevel2domainTransmitPassword OBJECT-TYPE
    SYNTAX      DummySyntax
    MAX-ACCESS  read-only
    STATUS      current
    DESCRIPTION 
        "Provides the domain transmit password."
    ::= { cLNSISISLevel2Entry 8 }

cLNSISISLevel2domainReceivePasswords OBJECT-TYPE
    SYNTAX      DummySyntax
    MAX-ACCESS  read-only
    STATUS      current
    DESCRIPTION 
        "Provides the domain receive passwords."
    ::= { cLNSISISLevel2Entry 9 }

cLNSISISLevel2RowStatus OBJECT-TYPE
    SYNTAX      RowStatus
    MAX-ACCESS  read-create
    STATUS      current
    DESCRIPTION 
        "Provides a mechanism whereby management stations may create and 
         delete rows in this table.  Entries must persist across agent 
         reboots."
    ::= { cLNSISISLevel2Entry 10 }

linkage OBJECT IDENTIFIER
    ::= { osiTables 37 }

linkageTable OBJECT-TYPE
    SYNTAX      SEQUENCE OF LinkageEntry
    MAX-ACCESS  not-accessible
    STATUS      current
    DESCRIPTION 
        "The linkage managed object.
         
         There is one of these MOs associated with each separate 
         provision of the underlying service to the superior protocol 
         machine.  Its definition permits it to be created and deleted 
         explicitly by management operation, but in some systems it will 
         exist inherently and neither creation nor deletion by 
         management operation will be possible. Name bindings are 
         defined for both cases.
         
         When the linkage is operable, the operationalState shall have 
         the value 'enabled'; otherwise it shall have the value 
         'disabled'.  Transitions of operationalState shall be reported 
         using the stateChange notification. A linkage MO may be created 
         in the 'enabled' operational state."
    REFERENCE   
        "ITU-T Rec. X.283 | ISO/IEC 10733 linkage MOC."
    ::= { linkage 1 }

linkageEntry OBJECT-TYPE
    SYNTAX      LinkageEntry
    MAX-ACCESS  not-accessible
    STATUS      current
    DESCRIPTION 
        "Each row in this table is indexed by communications entity and 
         defines the protocol machine and linkage identifiers.  Each row 
         contains characteristics and measurements associated with the 
         linkage."
    REFERENCE   
        "ITU-T Rec. X.283 | ISO/IEC 10733 linkage MO."
    INDEX       { communicationsEntityId, protocolMachineId, linkageId }
    ::= { linkageTable 1 }

LinkageEntry ::= SEQUENCE {
    protocolMachineId                                       SimpleNameType,
    linkageId                                               SimpleNameType,
    linkageOperationalState                                 OperationalState,
    linkageAdministrativeState                              AdministrativeState,
    linkageSnServiceProvider                                DummySyntax,
    linkageSnSAP                                            RowPointer,
    linkageOperationalProtocols                             OCTET STRING,
    linkageISiSO9542OperationalSubsets                      DummySyntax,
    linkageISHoldingTimerMultiplier                         DummySyntax,
    linkageISISConfigurationTimer                           DummySyntax,
    linkageISSuggestedEsConfigurationTimer                  DummySyntax,
    linkageISRedirectHoldingTime                            DummySyntax,
    linkageISESReachabilityChanges                          Counter32,
    linkageISInvalid9542PDUs                                Counter32,
    linkageESiSO9542OperationalSubsets                      DummySyntax,
    linkageESHoldingTimerMultiplier                         DummySyntax,
    linkageESManualISSNPAAddress                            DummySyntax,
    linkageESDefaultESConfigTimer                           DummySyntax,
    linkageESActiveESConfigTimer                            DummySyntax,
    linkageESISReachabilityChanges                          Counter32,
    linkageESInvalid9542PDUs                                Counter32,
    linkageEnableChecksum                                   TruthValue,
    linkageInitialMinimumTimer                              DummySyntax,
    linkageReserveTimer                                     DummySyntax,
    linkageIdleTimer                                        DummySyntax,
    linkageSNDCFCallsPlaced                                 Counter32,
    linkageSNDCFCallsFailed                                 Counter32,
    linkageCODLCallsPlaced                                  Counter32,
    linkageCODLCallsFailed                                  Counter32,
    linkageISISType                                         DummySyntax,
    linkageISISiSISHelloTimer                               DummySyntax,
    linkageISISl1DefaultMetric                              DummySyntax,
    linkageISISl1DelayMetric                                DummySyntax,
    linkageISISl1ExpenseMetric                              DummySyntax,
    linkageISISl1ErrorMetric                                DummySyntax,
    linkageISISexternalDomain                               DummySyntax,
    linkageISISchangedInAdjacencyState                      Counter32,
    linkageISISinitialisationFailures                       Counter32,
    linkageISISrejectedAdjacencies                          Counter32,
    linkageISISiSISControlPDUsSent                          Counter32,
    linkageISISiSISControlPDUsReceived                      Counter32,
    linkageISISiDFieldLengthMismatches                      Counter32,
    linkageISISmaximumAreaAddressesMismatches               Counter32,
    linkageISIScircuitTransmitPassword                      DummySyntax,
    linkageISIScircuitReceivedPasswords                     DummySyntax,
    linkageISISauthenticationFailures                       Counter32,
    linkageISISl1IntermediateSystemPriority                 DummySyntax,
    linkageISISl1CircuitID                                  DummySyntax,
    linkageISISl1DesignatedIntermediateSystem               DummySyntax,
    linkageISISlanL1DesignatedIntermediateSystemChanges     Counter32,
    linkageISIScallEstablishmentDefaultMetricIncrement      DummySyntax,
    linkageISIScallEstablishmentDelayMetricIncrement        DummySyntax,
    linkageISIScallEstablishmentExpenseMetricIncrement      DummySyntax,
    linkageISIScallEstablishmentErrorMetricIncrement        DummySyntax,
    linkageISISptPtCircuitID                                DummySyntax,
    linkageISISoutgoingCallIVMO                             DummySyntax,
    linkageISISneighborSNPAAddress                          DummySyntax,
    linkageISISl2DefaultMetric                              DummySyntax,
    linkageISISl2DelayMetric                                DummySyntax,
    linkageISISl2ExpenseMetric                              DummySyntax,
    linkageISISl2ErrorMetric                                DummySyntax,
    linkageISISmanualL2OnlyMode                             TruthValue,
    linkageISISl2IntermediateSystemPriority                 DummySyntax,
    linkageISISl2CircuitID                                  DummySyntax,
    linkageISISl2DesignatedIntermediateSystem               DummySyntax,
    linkageISISlanL2DesignatedIntermediateSystemChanges     Counter32,
    linkageRowStatus                                        RowStatus
}

protocolMachineId OBJECT-TYPE
    SYNTAX      SimpleNameType
    MAX-ACCESS  not-accessible
    STATUS      current
    DESCRIPTION 
        "Provides a protocol machine identifier for use as an index."
    ::= { linkageEntry 1 }

linkageId OBJECT-TYPE
    SYNTAX      SimpleNameType
    MAX-ACCESS  not-accessible
    STATUS      current
    DESCRIPTION 
        "Provides a linkage identifier for use as an index."
    ::= { linkageEntry 2 }

linkageOperationalState OBJECT-TYPE
    SYNTAX      OperationalState
    MAX-ACCESS  read-only
    STATUS      current
    DESCRIPTION 
        "Provides the operational state of the linkage following the 
         OperationalState textual conventions and X.721."
    ::= { linkageEntry 3 }

linkageAdministrativeState OBJECT-TYPE
    SYNTAX      AdministrativeState
    MAX-ACCESS  read-only
    STATUS      current
    DESCRIPTION 
        "Provides the administrative state of the linkage following the 
         AdministrativeState textual convention and X.721."
    ::= { linkageEntry 4 }

linkageSnServiceProvider OBJECT-TYPE
    SYNTAX      DummySyntax
    MAX-ACCESS  read-only
    STATUS      current
    DESCRIPTION 
        "Provides provides a pointer to the subnetwork service provider 
         for this linkage."
    ::= { linkageEntry 5 }

linkageSnSAP OBJECT-TYPE
    SYNTAX      RowPointer
    MAX-ACCESS  read-only
    STATUS      current
    DESCRIPTION 
        "Provides a pointer to the SAP for this linkage."
    ::= { linkageEntry 6 }

linkageOperationalProtocols OBJECT-TYPE
    SYNTAX      OCTET STRING
    MAX-ACCESS  read-only
    STATUS      current
    DESCRIPTION 
        "Provides the operational protocols supported by the linkage."
    ::= { linkageEntry 7 }

-- linkage-ISO9542IS-P conditional package OBJECT-TYPE
linkageISiSO9542OperationalSubsets OBJECT-TYPE
    SYNTAX      DummySyntax
    MAX-ACCESS  read-only
    STATUS      current
    DESCRIPTION 
        "Provides the ISO 9542 operational subsets supported by the 
         linkage."
    ::= { linkageEntry 8 }

linkageISHoldingTimerMultiplier OBJECT-TYPE
    SYNTAX      DummySyntax
    MAX-ACCESS  read-only
    STATUS      current
    DESCRIPTION 
        "Provides the IS holding time multiplier."
    ::= { linkageEntry 9 }

linkageISISConfigurationTimer OBJECT-TYPE
    SYNTAX      DummySyntax
    MAX-ACCESS  read-only
    STATUS      current
    DESCRIPTION 
        "Provides the ISIS configuration timer."
    ::= { linkageEntry 10 }

linkageISSuggestedEsConfigurationTimer OBJECT-TYPE
    SYNTAX      DummySyntax
    MAX-ACCESS  read-only
    STATUS      current
    DESCRIPTION 
        "Provides the IS suggested ES configuration timer."
    ::= { linkageEntry 11 }

linkageISRedirectHoldingTime OBJECT-TYPE
    SYNTAX      DummySyntax
    MAX-ACCESS  read-only
    STATUS      current
    DESCRIPTION 
        "Provides the IS redirect holding time."
    ::= { linkageEntry 12 }

linkageISESReachabilityChanges OBJECT-TYPE
    SYNTAX      Counter32
    MAX-ACCESS  read-only
    STATUS      current
    DESCRIPTION 
        "Provides a count of the number of IS-ES reachability changes."
    ::= { linkageEntry 13 }

linkageISInvalid9542PDUs OBJECT-TYPE
    SYNTAX      Counter32
    MAX-ACCESS  read-only
    STATUS      current
    DESCRIPTION 
        "Provides a count of the number of invalid ISO 9542 PDUs 
         received."
    ::= { linkageEntry 14 }

-- linkage-ISO9542ES-P conditional package OBJECT-TYPE
linkageESiSO9542OperationalSubsets OBJECT-TYPE
    SYNTAX      DummySyntax
    MAX-ACCESS  read-only
    STATUS      current
    DESCRIPTION 
        "Provides the ES ISO 9542 operational subsets for the linkage."
    ::= { linkageEntry 15 }

linkageESHoldingTimerMultiplier OBJECT-TYPE
    SYNTAX      DummySyntax
    MAX-ACCESS  read-only
    STATUS      current
    DESCRIPTION 
        "Provides the ES holding time multiplier."
    ::= { linkageEntry 16 }

linkageESManualISSNPAAddress OBJECT-TYPE
    SYNTAX      DummySyntax
    MAX-ACCESS  read-only
    STATUS      current
    DESCRIPTION 
        "Provides the ES manual IS SNPA address."
    ::= { linkageEntry 17 }

linkageESDefaultESConfigTimer OBJECT-TYPE
    SYNTAX      DummySyntax
    MAX-ACCESS  read-only
    STATUS      current
    DESCRIPTION 
        "Provides the ES default ES configuration timer."
    ::= { linkageEntry 18 }

linkageESActiveESConfigTimer OBJECT-TYPE
    SYNTAX      DummySyntax
    MAX-ACCESS  read-only
    STATUS      current
    DESCRIPTION 
        "Provides the ES active ES configuration timer."
    ::= { linkageEntry 19 }

linkageESISReachabilityChanges OBJECT-TYPE
    SYNTAX      Counter32
    MAX-ACCESS  read-only
    STATUS      current
    DESCRIPTION 
        "Provides a count of the number of IS reachability changes."
    ::= { linkageEntry 20 }

linkageESInvalid9542PDUs OBJECT-TYPE
    SYNTAX      Counter32
    MAX-ACCESS  read-only
    STATUS      current
    DESCRIPTION 
        "Provides a count of the number of ES invalid ISO 9542 PDUs 
         received."
    ::= { linkageEntry 21 }

-- linkage-ISO9542Checksum-P conditional package OBJECT-TYPE
linkageEnableChecksum OBJECT-TYPE
    SYNTAX      TruthValue
    MAX-ACCESS  read-only
    STATUS      current
    DESCRIPTION 
        "Specifies whether checksums are to be applied."
    ::= { linkageEntry 22 }

-- linkageInitialMinimumTimer-P conditional package OBJECT-TYPE
linkageInitialMinimumTimer OBJECT-TYPE
    SYNTAX      DummySyntax
    MAX-ACCESS  read-only
    STATUS      current
    DESCRIPTION 
        "Specifies whether initial minimum timer handling is to be 
         performed."
    ::= { linkageEntry 23 }

-- linkageReserveTimer-P conditional package OBJECT-TYPE
linkageReserveTimer OBJECT-TYPE
    SYNTAX      DummySyntax
    MAX-ACCESS  read-only
    STATUS      current
    DESCRIPTION 
        "Provides the reserve timer."
    ::= { linkageEntry 24 }

-- linkageIdleTimer-P conditional package OBJECT-TYPE
linkageIdleTimer OBJECT-TYPE
    SYNTAX      DummySyntax
    MAX-ACCESS  read-only
    STATUS      current
    DESCRIPTION 
        "Provides the idle timer."
    ::= { linkageEntry 25 }

-- linkage-ISO8473-ISO8208SNDCF-P conditional package OBJECT-TYPE
linkageSNDCFCallsPlaced OBJECT-TYPE
    SYNTAX      Counter32
    MAX-ACCESS  read-only
    STATUS      current
    DESCRIPTION 
        "Provides a count of the number of SNDCF calls placed."
    ::= { linkageEntry 26 }

linkageSNDCFCallsFailed OBJECT-TYPE
    SYNTAX      Counter32
    MAX-ACCESS  read-only
    STATUS      current
    DESCRIPTION 
        "Provides a count of the number of SNDCF calls failed."
    ::= { linkageEntry 27 }

-- linkageCODLService-P conditional package OBJECT-TYPE
linkageCODLCallsPlaced OBJECT-TYPE
    SYNTAX      Counter32
    MAX-ACCESS  read-only
    STATUS      current
    DESCRIPTION 
        "Provides a count of the number of CODL calls placed."
    ::= { linkageEntry 28 }

linkageCODLCallsFailed OBJECT-TYPE
    SYNTAX      Counter32
    MAX-ACCESS  read-only
    STATUS      current
    DESCRIPTION 
        "Provides a count of the number of CODL calls failed."
    ::= { linkageEntry 29 }

-- linkageISISBasic-P conditional package OBJECT-TYPE
linkageISISType OBJECT-TYPE
    SYNTAX      DummySyntax
    MAX-ACCESS  read-only
    STATUS      current
    DESCRIPTION 
        "Provides the ISIS type."
    ::= { linkageEntry 30 }

linkageISISiSISHelloTimer OBJECT-TYPE
    SYNTAX      DummySyntax
    MAX-ACCESS  read-only
    STATUS      current
    DESCRIPTION 
        "Provides the ISIS hello timer."
    ::= { linkageEntry 31 }

linkageISISl1DefaultMetric OBJECT-TYPE
    SYNTAX      DummySyntax
    MAX-ACCESS  read-only
    STATUS      current
    DESCRIPTION 
        "Provides the ISIS L1 default metric."
    ::= { linkageEntry 32 }

linkageISISl1DelayMetric OBJECT-TYPE
    SYNTAX      DummySyntax
    MAX-ACCESS  read-only
    STATUS      current
    DESCRIPTION 
        "Provides the ISIS L1 delay metric."
    ::= { linkageEntry 33 }

linkageISISl1ExpenseMetric OBJECT-TYPE
    SYNTAX      DummySyntax
    MAX-ACCESS  read-only
    STATUS      current
    DESCRIPTION 
        "Provides the ISIS L1 expense metric."
    ::= { linkageEntry 34 }

linkageISISl1ErrorMetric OBJECT-TYPE
    SYNTAX      DummySyntax
    MAX-ACCESS  read-only
    STATUS      current
    DESCRIPTION 
        "Provides the ISIS L1 error metric."
    ::= { linkageEntry 35 }

linkageISISexternalDomain OBJECT-TYPE
    SYNTAX      DummySyntax
    MAX-ACCESS  read-only
    STATUS      current
    DESCRIPTION 
        "Provides the ISIS external domain."
    ::= { linkageEntry 36 }

linkageISISchangedInAdjacencyState OBJECT-TYPE
    SYNTAX      Counter32
    MAX-ACCESS  read-only
    STATUS      current
    DESCRIPTION 
        "Provides a count of the number of ISIS changes in adjacency 
         state."
    ::= { linkageEntry 37 }

linkageISISinitialisationFailures OBJECT-TYPE
    SYNTAX      Counter32
    MAX-ACCESS  read-only
    STATUS      current
    DESCRIPTION 
        "Provides a count of the number of ISIS initialization failures."
    ::= { linkageEntry 38 }

linkageISISrejectedAdjacencies OBJECT-TYPE
    SYNTAX      Counter32
    MAX-ACCESS  read-only
    STATUS      current
    DESCRIPTION 
        "Provides a count of the number of ISIS rejected adjacencies."
    ::= { linkageEntry 39 }

linkageISISiSISControlPDUsSent OBJECT-TYPE
    SYNTAX      Counter32
    MAX-ACCESS  read-only
    STATUS      current
    DESCRIPTION 
        "Provides a count of the number of ISIS control PDUs sent."
    ::= { linkageEntry 40 }

linkageISISiSISControlPDUsReceived OBJECT-TYPE
    SYNTAX      Counter32
    MAX-ACCESS  read-only
    STATUS      current
    DESCRIPTION 
        "Provides a count of the number of ISIS control PDUs received."
    ::= { linkageEntry 41 }

linkageISISiDFieldLengthMismatches OBJECT-TYPE
    SYNTAX      Counter32
    MAX-ACCESS  read-only
    STATUS      current
    DESCRIPTION 
        "Provides a count of the number of ISIS Id field length 
         mismatches."
    ::= { linkageEntry 42 }

linkageISISmaximumAreaAddressesMismatches OBJECT-TYPE
    SYNTAX      Counter32
    MAX-ACCESS  read-only
    STATUS      current
    DESCRIPTION 
        "Provides a count of the number of ISIS maximum area addresses 
         mismatches."
    ::= { linkageEntry 43 }

-- linkageISISAuthentication-P conditional package OBJECT-TYPE
linkageISIScircuitTransmitPassword OBJECT-TYPE
    SYNTAX      DummySyntax
    MAX-ACCESS  read-only
    STATUS      current
    DESCRIPTION 
        "Provides the ISIS circuit transmit password."
    ::= { linkageEntry 44 }

linkageISIScircuitReceivedPasswords OBJECT-TYPE
    SYNTAX      DummySyntax
    MAX-ACCESS  read-only
    STATUS      current
    DESCRIPTION 
        "Provides the ISIS circuit received passwords."
    ::= { linkageEntry 45 }

linkageISISauthenticationFailures OBJECT-TYPE
    SYNTAX      Counter32
    MAX-ACCESS  read-only
    STATUS      current
    DESCRIPTION 
        "Provides a count of the number of ISIS authentication 
         failures."
    ::= { linkageEntry 46 }

-- linkageISISBroadcast-P conditional package OBJECT-TYPE
linkageISISl1IntermediateSystemPriority OBJECT-TYPE
    SYNTAX      DummySyntax
    MAX-ACCESS  read-only
    STATUS      current
    DESCRIPTION 
        "Provides the ISIS L1 intermediate system priority."
    ::= { linkageEntry 47 }

linkageISISl1CircuitID OBJECT-TYPE
    SYNTAX      DummySyntax
    MAX-ACCESS  read-only
    STATUS      current
    DESCRIPTION 
        "Provides the ISIS L1 circuit identifier."
    ::= { linkageEntry 48 }

linkageISISl1DesignatedIntermediateSystem OBJECT-TYPE
    SYNTAX      DummySyntax
    MAX-ACCESS  read-only
    STATUS      current
    DESCRIPTION 
        "Provides the ISIS L1 designated intermediate system."
    ::= { linkageEntry 49 }

linkageISISlanL1DesignatedIntermediateSystemChanges OBJECT-TYPE
    SYNTAX      Counter32
    MAX-ACCESS  read-only
    STATUS      current
    DESCRIPTION 
        "Provides a count fo the number of ISIS LAN L1 designated 
         intermediate system changes."
    ::= { linkageEntry 50 }

-- linkageISISDACallEstablishmentMetricIncrement-P conditional package 
-- OBJECT-TYPE
linkageISIScallEstablishmentDefaultMetricIncrement OBJECT-TYPE
    SYNTAX      DummySyntax
    MAX-ACCESS  read-only
    STATUS      current
    DESCRIPTION 
        "Provides the ISIS call establishment default metric increment."
    ::= { linkageEntry 51 }

linkageISIScallEstablishmentDelayMetricIncrement OBJECT-TYPE
    SYNTAX      DummySyntax
    MAX-ACCESS  read-only
    STATUS      current
    DESCRIPTION 
        "Provides the ISIS call establishment delay metric increment."
    ::= { linkageEntry 52 }

linkageISIScallEstablishmentExpenseMetricIncrement OBJECT-TYPE
    SYNTAX      DummySyntax
    MAX-ACCESS  read-only
    STATUS      current
    DESCRIPTION 
        "Provides the ISIS call establishment expense metric increment."
    ::= { linkageEntry 53 }

linkageISIScallEstablishmentErrorMetricIncrement OBJECT-TYPE
    SYNTAX      DummySyntax
    MAX-ACCESS  read-only
    STATUS      current
    DESCRIPTION 
        "Provides the ISIS call establishment error metric increment."
    ::= { linkageEntry 54 }

-- linkageISISPtToPt-P or linkageISISStatic-P conditional package
linkageISISptPtCircuitID OBJECT-TYPE
    SYNTAX      DummySyntax
    MAX-ACCESS  read-only
    STATUS      current
    DESCRIPTION 
        "Provides the ISIS point-to-point circuit identifier."
    ::= { linkageEntry 55 }

-- linkageISISStatic-P conditional package OBJECT-TYPE
linkageISISoutgoingCallIVMO OBJECT-TYPE
    SYNTAX      DummySyntax
    MAX-ACCESS  read-only
    STATUS      current
    DESCRIPTION 
        "Provides a pointer to the ISIS outgoing call initial values 
         managed object (IVMO)."
    ::= { linkageEntry 56 }

linkageISISneighborSNPAAddress OBJECT-TYPE
    SYNTAX      DummySyntax
    MAX-ACCESS  read-only
    STATUS      current
    DESCRIPTION 
        "Provides the ISIS neighbor SNPA address."
    ::= { linkageEntry 57 }

-- linkageISISLevel2-P conditional package OBJECT-TYPE
linkageISISl2DefaultMetric OBJECT-TYPE
    SYNTAX      DummySyntax
    MAX-ACCESS  read-only
    STATUS      current
    DESCRIPTION 
        "Provides the ISIS L2 default metric."
    ::= { linkageEntry 58 }

linkageISISl2DelayMetric OBJECT-TYPE
    SYNTAX      DummySyntax
    MAX-ACCESS  read-only
    STATUS      current
    DESCRIPTION 
        "Provides the ISIS L2 delay metric."
    ::= { linkageEntry 59 }

linkageISISl2ExpenseMetric OBJECT-TYPE
    SYNTAX      DummySyntax
    MAX-ACCESS  read-only
    STATUS      current
    DESCRIPTION 
        "Provides the ISIS L2 expense metric."
    ::= { linkageEntry 60 }

linkageISISl2ErrorMetric OBJECT-TYPE
    SYNTAX      DummySyntax
    MAX-ACCESS  read-only
    STATUS      current
    DESCRIPTION 
        "Provides the ISIS L2 error metric."
    ::= { linkageEntry 61 }

linkageISISmanualL2OnlyMode OBJECT-TYPE
    SYNTAX      TruthValue
    MAX-ACCESS  read-only
    STATUS      current
    DESCRIPTION 
        "Provides the ISIS manual L2 only mode setting."
    ::= { linkageEntry 62 }

-- linkageISISLevel2Broadcast-P conditional package OBJECT-TYPE
linkageISISl2IntermediateSystemPriority OBJECT-TYPE
    SYNTAX      DummySyntax
    MAX-ACCESS  read-only
    STATUS      current
    DESCRIPTION 
        "Provides the ISIS L2 intermediate system priority."
    ::= { linkageEntry 63 }

linkageISISl2CircuitID OBJECT-TYPE
    SYNTAX      DummySyntax
    MAX-ACCESS  read-only
    STATUS      current
    DESCRIPTION 
        "Provides the ISIS L2 circuit identifier."
    ::= { linkageEntry 64 }

linkageISISl2DesignatedIntermediateSystem OBJECT-TYPE
    SYNTAX      DummySyntax
    MAX-ACCESS  read-only
    STATUS      current
    DESCRIPTION 
        "Provides the ISIS L2 designated intermediate system."
    ::= { linkageEntry 65 }

linkageISISlanL2DesignatedIntermediateSystemChanges OBJECT-TYPE
    SYNTAX      Counter32
    MAX-ACCESS  read-only
    STATUS      current
    DESCRIPTION 
        "Provides a count of the number of ISIS LAN L2 designated 
         intermediate system changes."
    ::= { linkageEntry 66 }

-- OBJECT-TYPE
linkageRowStatus OBJECT-TYPE
    SYNTAX      RowStatus
    MAX-ACCESS  read-create
    STATUS      current
    DESCRIPTION 
        "Provides a mechanism whereby management stations may create and 
         delete rows in this table.  Entries must persist across agent 
         reboots."
    ::= { linkageEntry 67 }

cONS OBJECT IDENTIFIER
    ::= { osiTables 38 }

cONSTable OBJECT-TYPE
    SYNTAX      SEQUENCE OF CONSEntry
    MAX-ACCESS  not-accessible
    STATUS      current
    DESCRIPTION 
        "The connection-mode network service managed object.
         
         There is no more than one of these MOs per network entity.  Its 
         definition permits it to be created and deleted explicitly by 
         management operation, but in some systems it will exist 
         inherently and neither creation nor deletion by management 
         operation will be possible.  Name bindings are defined for both 
         cases.
         
         When the protocol machine is operable, the operationalState 
         shall have the value 'enabled'; otherwise it shall have the 
         value 'disabled'.  Transitions of operationalState shall be 
         reported using the stateChange notification. A cONS MO may be 
         created in the 'enabled' operational state."
    REFERENCE   
        "ITU-T Rec. X.283 | ISO/IEC 10733 cONS MOC."
    ::= { cONS 1 }

cONSEntry OBJECT-TYPE
    SYNTAX      CONSEntry
    MAX-ACCESS  not-accessible
    STATUS      current
    DESCRIPTION 
        "Each entry in this table is indexed by communications entity 
         and connection-oriented protocol machine identifiers.  Each 
         entry contains the administrative state of the CONS and system 
         types."
    REFERENCE   
        "ITU-T Rec. X.283 | ISO/IEC 10733 cONS MOC."
    INDEX       { communicationsEntityId, coProtocolMachineId }
    ::= { cONSTable 1 }

CONSEntry ::= SEQUENCE {
    cONSAdministrativeState     AdministrativeState,
    cONSOperationalSystemType   SystemTypes,
    cONSRowStatus               RowStatus
}

-- cONS-P mandatory package
cONSAdministrativeState OBJECT-TYPE
    SYNTAX      AdministrativeState
    MAX-ACCESS  read-create
    STATUS      current
    DESCRIPTION 
        "Provides the administrative state of the CONS following the 
         AdministrativeState textual convention and X.721."
    REFERENCE   
        "ITU-T Rec. X.721 | ISO/IEC 10165-2 administrativeState."
    ::= { cONSEntry 1 }

cONSOperationalSystemType OBJECT-TYPE
    SYNTAX      SystemTypes
    MAX-ACCESS  read-create
    STATUS      current
    DESCRIPTION 
        "Provides the operational system type, which can be one or both 
         of: es(0), end system; or, is(1) intermediate system."
    REFERENCE   
        "ITU-T Rec. X.283 | ISO/IEC 10733 operationalSystemType."
    ::= { cONSEntry 2 }

-- cONS-networkEntity-Management name binding
-- cONS-networkEntity-Automatic name binding
cONSRowStatus OBJECT-TYPE
    SYNTAX      RowStatus
    MAX-ACCESS  read-create
    STATUS      current
    DESCRIPTION 
        "The cONS-networkEntity-Mangagement name binding applies when 
         the cONS managed object can be created and deleted by 
         management.
         
         The cONS-networkEntity-Automatic name binding applies when the 
         cONS managed object cannot be created or deleted by 
         management."
    REFERENCE   
        "ITU-T Rec. X.283 | ISO/IEC 10733 cONS-networkEntity-Management, 
         cONS-networkEntity-Automatic, STD 58, SNMPv2-TC RowStatus."
    ::= { cONSEntry 3 }

networkConnection OBJECT IDENTIFIER
    ::= { osiTables 39 }

networkConnectionTable OBJECT-TYPE
    SYNTAX      SEQUENCE OF NetworkConnectionEntry
    MAX-ACCESS  not-accessible
    STATUS      current
    DESCRIPTION 
        "The network connection managed object.
         
         There is one instance of this MO corresponding to each network 
         connection. It is created and deleted by the operation of the 
         protocol machine.
         
         In some configurations the underlyingConnectionNames attribute 
         may contain more than one distinguished name.  In this case, 
         the type of the underlying MO (and hence the particular 
         underlying resource) can only be determined by inspection of 
         the MO pointed to by this distinguished name."
    REFERENCE   
        "ITU-T Rec. X.283 | ISO/IEC 10733 networkConnection MOC."
    ::= { networkConnection 1 }

networkConnectionEntry OBJECT-TYPE
    SYNTAX      NetworkConnectionEntry
    MAX-ACCESS  not-accessible
    STATUS      current
    DESCRIPTION 
        "The GMI:underlyingConnectionNames attribute shall contain the 
         distinguished name(s) of the other MO(s) which represent the 
         resources used to support this connection. In the case of the 
         CONS operating directly over X.25, this shall be the single 
         distinguished name of the underlying virtual call or permanent 
         virtual circuit MO."
    REFERENCE   
        "ITU-T Rec. X.283 | ISO/IEC 10733 networkConnection MO."
    INDEX       { communicationsEntityId, coProtocolMachineId, 
                  connectionId }
    ::= { networkConnectionTable 1 }

NetworkConnectionEntry ::= SEQUENCE {
    networkConnectionLocalNSAPMO        DummySyntax,
    networkConnectionRemoteNSAPAddress  DummySyntax,
    networkConnectionRowStatus          RowStatus
}

networkConnectionLocalNSAPMO OBJECT-TYPE
    SYNTAX      DummySyntax
    MAX-ACCESS  read-only
    STATUS      current
    DESCRIPTION 
        "Provides a pointer to the local NSAP managed object for this 
         network connection."
    ::= { networkConnectionEntry 1 }

networkConnectionRemoteNSAPAddress OBJECT-TYPE
    SYNTAX      DummySyntax
    MAX-ACCESS  read-only
    STATUS      current
    DESCRIPTION 
        "Provides a pointer to the remote NSAP managed object for this 
         network connection."
    ::= { networkConnectionEntry 2 }

networkConnectionRowStatus OBJECT-TYPE
    SYNTAX      RowStatus
    MAX-ACCESS  read-create
    STATUS      current
    DESCRIPTION 
        "Provides a mechanism whereby management stations may create and 
         delete rows in this table.  Entries created by management 
         stations must perist across agent reboots."
    ::= { networkConnectionEntry 3 }

x25PLE OBJECT IDENTIFIER
    ::= { osiTables 40 }

x25PLETable OBJECT-TYPE
    SYNTAX      SEQUENCE OF X25PLEEntry
    MAX-ACCESS  not-accessible
    STATUS      current
    DESCRIPTION 
        "Provides a table of X.25 packet layer link entities."
    REFERENCE   
        "ITU-T Rec. X.283 | ISO/IEC 10733 x25PLE MOC."
    ::= { x25PLE 1 }

x25PLEEntry OBJECT-TYPE
    SYNTAX      X25PLEEntry
    MAX-ACCESS  not-accessible
    STATUS      current
    DESCRIPTION 
        "Each row in this table is defines the X.25 packet layer link 
         entity identifier."
    REFERENCE   
        "ITU-T Rec. X.283 | ISO/IEC 10733 x25PLE MO."
    INDEX       { x25PLEId }
    ::= { x25PLETable 1 }

X25PLEEntry ::= SEQUENCE {
    x25PLEId                                    SimpleNameType,
    x25PLEoperationalState                      OperationalState,
    x25PLEadministrativeState                   AdministrativeState,
    x25PLEprotocolVersionSupported              DummySyntax,
    x25PLElocalDTEAddress                       DTEAddress,
    x25PLEMode                                  X25PLEMode,
    x25PLEdefaultThroughputClasses              DummySyntax,
    x25PLEflowControlParameterNegotiation       DummySyntax,
    x25PLEdefaultPackageSizes                   DummySyntax,
    x25PLEthroughputClassNegotiation            DummySyntax,
    x25PLEsNserviceProvider                     DummySyntax,
    x25PLEsNsAP                                 DummySyntax,
    x25PElogicalChannelAssignments              DummySyntax,
    x25PLEinterfaceMode                         X25PLEMode,
    x25PLEdefaultThroughputClass                DummySyntax,
    x25PLEflowControlNegotiationPermitted       DummySyntax,
    x25PLEcallDeflectionSubscription            TruthValue,
    x25PLEmaxActiveCircuits                     DummySyntax,
    x25PLErestartTime                           DummySyntax,
    x25PLEdefaultPacketSize                     DummySyntax,
    x25PLEdefaultWindowSize                     DummySyntax,
    x25PLEminimumRecallTimer                    DummySyntax,
    x25PLErestartCount                          DummySyntax,
    x25PLEsN-ServiceProvider                    DummySyntax,
    x25PLEsN-SA-P                               DummySyntax,
    x25PLElogicalChannelAssignments             DummySyntax,
    x25PLEpacketSequencing                      DummySyntax,
    x25PLEoctetsSentCounter                     DummySyntax,
    x25PLEoctetsReceivedCounter                 DummySyntax,
    x25PLEdataPacketsSent                       DummySyntax,
    x25PLEdataPacketsReceived                   DummySyntax,
    x25PLEcallAttempts                          DummySyntax,
    x25PLEcallsConnected                        DummySyntax,
    x25PLEproviderInitiatedDisconnects          Counter32,
    x25PLEcallTimeouts                          DummySyntax,
    x25PLEclearTimeouts                         DummySyntax,
    x25PLEremotelyInitiatedResets               DummySyntax,
    x25PLEdataRetransmissionTimerExpiries       DummySyntax,
    x25PLEproviderInitiatedResets               DummySyntax,
    x25PLEresetTimeouts                         DummySyntax,
    x25PLEremotelyInitiatedRestarts             DummySyntax,
    x25PLErestartCountsExceeded                 DummySyntax,
    x25PLEprotocolErrorsDetectedLocally         DummySyntax,
    x25PLEprotocolErrorsAccusedOf               DummySyntax,
    x25PLEcallEstablishmentRetryCountsExceeded  DummySyntax,
    x25PLEclearCountsExceeded                   DummySyntax,
    x25PLEpLEClientMOName                       DummySyntax,
    x25PLEregistrationRequestTime               DummySyntax,
    x25PLEregistrationRequestCount              DummySyntax,
    x25PLEregistrationPermitted                 TruthValue,
    x25PLERowStatus                             RowStatus
}

x25PLEId OBJECT-TYPE
    SYNTAX      SimpleNameType
    MAX-ACCESS  not-accessible
    STATUS      current
    DESCRIPTION 
        "Provides an X.25 packet layer link entity identifier for use as 
         an index into this table."
    ::= { x25PLEEntry 1 }

x25PLEoperationalState OBJECT-TYPE
    SYNTAX      OperationalState
    MAX-ACCESS  read-only
    STATUS      current
    DESCRIPTION 
        "Provides the operational state of the link entity following the 
         OperationalState textual convention and X.721."
    ::= { x25PLEEntry 2 }

x25PLEadministrativeState OBJECT-TYPE
    SYNTAX      AdministrativeState
    MAX-ACCESS  read-only
    STATUS      current
    DESCRIPTION 
        "Provides the administrative state of the link entity following 
         the AdministrativeState textual convention an X.721."
    ::= { x25PLEEntry 3 }

x25PLEprotocolVersionSupported OBJECT-TYPE
    SYNTAX      DummySyntax
    MAX-ACCESS  read-only
    STATUS      current
    DESCRIPTION 
        "Provides the protocol versions supported."
    ::= { x25PLEEntry 4 }

x25PLElocalDTEAddress OBJECT-TYPE
    SYNTAX      DTEAddress
    MAX-ACCESS  read-only
    STATUS      current
    DESCRIPTION 
        "Provides the local DTE address."
    ::= { x25PLEEntry 5 }

x25PLEMode OBJECT-TYPE
    SYNTAX      X25PLEMode
    MAX-ACCESS  read-only
    STATUS      current
    DESCRIPTION 
        "Provides the mode."
    ::= { x25PLEEntry 6 }

x25PLEdefaultThroughputClasses OBJECT-TYPE
    SYNTAX      DummySyntax
    MAX-ACCESS  read-only
    STATUS      current
    DESCRIPTION 
        "Provides the default throughput class."
    ::= { x25PLEEntry 7 }

x25PLEflowControlParameterNegotiation OBJECT-TYPE
    SYNTAX      DummySyntax
    MAX-ACCESS  read-only
    STATUS      current
    DESCRIPTION 
        "Provides for flow control parameter negotiation."
    ::= { x25PLEEntry 8 }

x25PLEdefaultPackageSizes OBJECT-TYPE
    SYNTAX      DummySyntax
    MAX-ACCESS  read-only
    STATUS      current
    DESCRIPTION 
        "Provides the default packet sizes."
    ::= { x25PLEEntry 9 }

x25PLEthroughputClassNegotiation OBJECT-TYPE
    SYNTAX      DummySyntax
    MAX-ACCESS  read-only
    STATUS      current
    DESCRIPTION 
        "Provides for throughput class negotiation."
    ::= { x25PLEEntry 10 }

x25PLEsNserviceProvider OBJECT-TYPE
    SYNTAX      DummySyntax
    MAX-ACCESS  read-only
    STATUS      current
    DESCRIPTION 
        "Provides a pointer to the SN service provider."
    ::= { x25PLEEntry 11 }

x25PLEsNsAP OBJECT-TYPE
    SYNTAX      DummySyntax
    MAX-ACCESS  read-only
    STATUS      current
    DESCRIPTION 
        "Provides the SN SAP."
    ::= { x25PLEEntry 12 }

x25PElogicalChannelAssignments OBJECT-TYPE
    SYNTAX      DummySyntax
    MAX-ACCESS  read-only
    STATUS      current
    DESCRIPTION 
        "Provides the logical channel assignments."
    ::= { x25PLEEntry 13 }

x25PLEinterfaceMode OBJECT-TYPE
    SYNTAX      X25PLEMode
    MAX-ACCESS  read-only
    STATUS      current
    DESCRIPTION 
        "Provides the interface mode."
    ::= { x25PLEEntry 14 }

x25PLEdefaultThroughputClass OBJECT-TYPE
    SYNTAX      DummySyntax
    MAX-ACCESS  read-only
    STATUS      current
    DESCRIPTION 
        "Provides the default throughput class."
    ::= { x25PLEEntry 15 }

x25PLEflowControlNegotiationPermitted OBJECT-TYPE
    SYNTAX      DummySyntax
    MAX-ACCESS  read-only
    STATUS      current
    DESCRIPTION 
        "Provides for flow control negotiation permission."
    ::= { x25PLEEntry 16 }

x25PLEcallDeflectionSubscription OBJECT-TYPE
    SYNTAX      TruthValue
    MAX-ACCESS  read-only
    STATUS      current
    DESCRIPTION 
        "Provides for call deflection subscription."
    ::= { x25PLEEntry 17 }

x25PLEmaxActiveCircuits OBJECT-TYPE
    SYNTAX      DummySyntax
    MAX-ACCESS  read-only
    STATUS      current
    DESCRIPTION 
        "Provides the maximum number of active circuits."
    ::= { x25PLEEntry 18 }

x25PLErestartTime OBJECT-TYPE
    SYNTAX      DummySyntax
    MAX-ACCESS  read-only
    STATUS      current
    DESCRIPTION 
        "Provides the restart time."
    ::= { x25PLEEntry 19 }

x25PLEdefaultPacketSize OBJECT-TYPE
    SYNTAX      DummySyntax
    MAX-ACCESS  read-only
    STATUS      current
    DESCRIPTION 
        "Provides the default packet size."
    ::= { x25PLEEntry 20 }

x25PLEdefaultWindowSize OBJECT-TYPE
    SYNTAX      DummySyntax
    MAX-ACCESS  read-only
    STATUS      current
    DESCRIPTION 
        "Provides the default window size."
    ::= { x25PLEEntry 21 }

x25PLEminimumRecallTimer OBJECT-TYPE
    SYNTAX      DummySyntax
    MAX-ACCESS  read-only
    STATUS      current
    DESCRIPTION 
        "Provides the minimum recall timer."
    ::= { x25PLEEntry 22 }

x25PLErestartCount OBJECT-TYPE
    SYNTAX      DummySyntax
    MAX-ACCESS  read-only
    STATUS      current
    DESCRIPTION 
        "Provides the restart count."
    ::= { x25PLEEntry 23 }

x25PLEsN-ServiceProvider OBJECT-TYPE
    SYNTAX      DummySyntax
    MAX-ACCESS  read-only
    STATUS      current
    DESCRIPTION 
        "Provides the SN service provider."
    ::= { x25PLEEntry 24 }

x25PLEsN-SA-P OBJECT-TYPE
    SYNTAX      DummySyntax
    MAX-ACCESS  read-only
    STATUS      current
    DESCRIPTION 
        "Provides the SN SA P."
    ::= { x25PLEEntry 25 }

x25PLElogicalChannelAssignments OBJECT-TYPE
    SYNTAX      DummySyntax
    MAX-ACCESS  read-only
    STATUS      current
    DESCRIPTION 
        "Provides logical channel assignments."
    ::= { x25PLEEntry 26 }

x25PLEpacketSequencing OBJECT-TYPE
    SYNTAX      DummySyntax
    MAX-ACCESS  read-only
    STATUS      current
    DESCRIPTION 
        "Provides for packet sequencing."
    ::= { x25PLEEntry 27 }

x25PLEoctetsSentCounter OBJECT-TYPE
    SYNTAX      DummySyntax
    MAX-ACCESS  read-only
    STATUS      current
    DESCRIPTION 
        "Provides a count of the number of octets sent."
    ::= { x25PLEEntry 28 }

x25PLEoctetsReceivedCounter OBJECT-TYPE
    SYNTAX      DummySyntax
    MAX-ACCESS  read-only
    STATUS      current
    DESCRIPTION 
        "Provides a count of the number of octets received."
    ::= { x25PLEEntry 29 }

x25PLEdataPacketsSent OBJECT-TYPE
    SYNTAX      DummySyntax
    MAX-ACCESS  read-only
    STATUS      current
    DESCRIPTION 
        "Provides a count of the number of data packets sent."
    ::= { x25PLEEntry 30 }

x25PLEdataPacketsReceived OBJECT-TYPE
    SYNTAX      DummySyntax
    MAX-ACCESS  read-only
    STATUS      current
    DESCRIPTION 
        "Provides a count of the number of data packets received."
    ::= { x25PLEEntry 31 }

x25PLEcallAttempts OBJECT-TYPE
    SYNTAX      DummySyntax
    MAX-ACCESS  read-only
    STATUS      current
    DESCRIPTION 
        "Provides a count of the number of call attempts."
    ::= { x25PLEEntry 32 }

x25PLEcallsConnected OBJECT-TYPE
    SYNTAX      DummySyntax
    MAX-ACCESS  read-only
    STATUS      current
    DESCRIPTION 
        "Provides a count of the number of calls connected."
    ::= { x25PLEEntry 33 }

x25PLEproviderInitiatedDisconnects OBJECT-TYPE
    SYNTAX      Counter32
    MAX-ACCESS  read-only
    STATUS      current
    DESCRIPTION 
        "Provides a count of the number of provider initiated 
         disconnects."
    ::= { x25PLEEntry 34 }

x25PLEcallTimeouts OBJECT-TYPE
    SYNTAX      DummySyntax
    MAX-ACCESS  read-only
    STATUS      current
    DESCRIPTION 
        "Provides a count of the number of call timeouts."
    ::= { x25PLEEntry 35 }

x25PLEclearTimeouts OBJECT-TYPE
    SYNTAX      DummySyntax
    MAX-ACCESS  read-only
    STATUS      current
    DESCRIPTION 
        "Provides a count of the number of clear timeouts."
    ::= { x25PLEEntry 36 }

x25PLEremotelyInitiatedResets OBJECT-TYPE
    SYNTAX      DummySyntax
    MAX-ACCESS  read-only
    STATUS      current
    DESCRIPTION 
        "Provides a count of the number of remotely initiated resets."
    ::= { x25PLEEntry 37 }

x25PLEdataRetransmissionTimerExpiries OBJECT-TYPE
    SYNTAX      DummySyntax
    MAX-ACCESS  read-only
    STATUS      current
    DESCRIPTION 
        "Provides a count of the number of data retransmission timer 
         expiries."
    ::= { x25PLEEntry 38 }

x25PLEproviderInitiatedResets OBJECT-TYPE
    SYNTAX      DummySyntax
    MAX-ACCESS  read-only
    STATUS      current
    DESCRIPTION 
        "Provides a count of the number of provider initiated resets."
    ::= { x25PLEEntry 39 }

x25PLEresetTimeouts OBJECT-TYPE
    SYNTAX      DummySyntax
    MAX-ACCESS  read-only
    STATUS      current
    DESCRIPTION 
        "Provides a count of the number of reset timeouts."
    ::= { x25PLEEntry 40 }

x25PLEremotelyInitiatedRestarts OBJECT-TYPE
    SYNTAX      DummySyntax
    MAX-ACCESS  read-only
    STATUS      current
    DESCRIPTION 
        "Provides a count of the number of remotely initiated restarts."
    ::= { x25PLEEntry 41 }

x25PLErestartCountsExceeded OBJECT-TYPE
    SYNTAX      DummySyntax
    MAX-ACCESS  read-only
    STATUS      current
    DESCRIPTION 
        "Provides a count of the number of restart counts exceeded."
    ::= { x25PLEEntry 42 }

x25PLEprotocolErrorsDetectedLocally OBJECT-TYPE
    SYNTAX      DummySyntax
    MAX-ACCESS  read-only
    STATUS      current
    DESCRIPTION 
        "Provides a count of the number of protocol errors detected 
         locally."
    ::= { x25PLEEntry 43 }

x25PLEprotocolErrorsAccusedOf OBJECT-TYPE
    SYNTAX      DummySyntax
    MAX-ACCESS  read-only
    STATUS      current
    DESCRIPTION 
        "Provides a count of the number of protocol errors accused of."
    ::= { x25PLEEntry 44 }

x25PLEcallEstablishmentRetryCountsExceeded OBJECT-TYPE
    SYNTAX      DummySyntax
    MAX-ACCESS  read-only
    STATUS      current
    DESCRIPTION 
        "Provides a count of the number of call establishment retry 
         counts exceeded."
    ::= { x25PLEEntry 45 }

x25PLEclearCountsExceeded OBJECT-TYPE
    SYNTAX      DummySyntax
    MAX-ACCESS  read-only
    STATUS      current
    DESCRIPTION 
        "Provides a count of the number of clear counts exceeded."
    ::= { x25PLEEntry 46 }

x25PLEpLEClientMOName OBJECT-TYPE
    SYNTAX      DummySyntax
    MAX-ACCESS  read-only
    STATUS      current
    DESCRIPTION 
        "Provides the PLE client MO name."
    ::= { x25PLEEntry 47 }

x25PLEregistrationRequestTime OBJECT-TYPE
    SYNTAX      DummySyntax
    MAX-ACCESS  read-only
    STATUS      current
    DESCRIPTION 
        "Provides the registration request time."
    ::= { x25PLEEntry 48 }

x25PLEregistrationRequestCount OBJECT-TYPE
    SYNTAX      DummySyntax
    MAX-ACCESS  read-only
    STATUS      current
    DESCRIPTION 
        "Provides the registration request count."
    ::= { x25PLEEntry 49 }

x25PLEregistrationPermitted OBJECT-TYPE
    SYNTAX      TruthValue
    MAX-ACCESS  read-only
    STATUS      current
    DESCRIPTION 
        "Specifies whether registration is permitted."
    ::= { x25PLEEntry 50 }

x25PLERowStatus OBJECT-TYPE
    SYNTAX      RowStatus
    MAX-ACCESS  read-create
    STATUS      current
    DESCRIPTION 
        "Provides a mechanism whereby management stations may create and 
         delete rows in this table.  Entries created by management 
         stations must persist across agent reboots."
    ::= { x25PLEEntry 51 }

x25PLE-DTE OBJECT IDENTIFIER
    ::= { osiTables 41 }

x25PLE-DTETable OBJECT-TYPE
    SYNTAX      SEQUENCE OF X25PLE-DTEEntry
    MAX-ACCESS  not-accessible
    STATUS      current
    DESCRIPTION 
        "The X.25 PLE DTE managed object.
         
         There may be multiple instances of these MOs within a system, 
         corresponding to Multiple X.25 PLEs.
         
         The definition of this MO permits it to be created and deleted 
         explicitly by management operation or to be created and deleted 
         automatically as part of system operation. When an instance of 
         this MO is created automatically, an instance of the 
         x25PLEIVMO-DTE may be used as the source of the initial values 
         for attributes of this MO.
         
         When the x25 PLE is operable, the operationalState shall have 
         the value 'enabled'; otherwise it shall have the value 
         'disabled'.  Transitions of operationalState shall be reported 
         using the stateChange notification."
    REFERENCE   
        "ITU-T Rec. X.283 | ISO/IEC 10733 x25PLE-DTE MOC."
    ::= { x25PLE-DTE 1 }

x25PLE-DTEEntry OBJECT-TYPE
    SYNTAX      X25PLE-DTEEntry
    MAX-ACCESS  not-accessible
    STATUS      current
    DESCRIPTION 
        "Each row in this table is indexed by X.25 packet layer entity 
         identifier.  Each row contains characteristics and operational 
         status and measurements corresponding to the X.25 PLE DTE."
    REFERENCE   
        "ITU-T Rec. X.283 | ISO/IEC 10733 x25PLE-DTE MO."
    INDEX       { x25PLEId }
    ::= { x25PLE-DTETable 1 }

X25PLE-DTEEntry ::= SEQUENCE {
    x25PLE-DTEcallDeflectionSubscription                TruthValue,
    x25PLE-DTEcallRequestResponseTimer                  DummySyntax,
    x25PLE-DTEextendedPacketSequenceNumbering           DummySyntax,
    x25PLE-DTEmaxActiveCircuits                         DummySyntax,
    x25PLE-DTEminimumRecallTimer                        DummySyntax,
    x25PLE-DTEresetRequestResponseTimer                 DummySyntax,
    x25PLE-DTErestartRequestRetransmissionCount         DummySyntax,
    x25PLE-DTErestartRequestResponseTimer               DummySyntax,
    x25PLE-DTEclearRequestResponseTimer                 DummySyntax,
    x25PLE-DTEinterruptResponseTimer                    DummySyntax,
    x25PLE-DTEresetRequestRetransmissionCount           DummySyntax,
    x25PLE-DTEclearRequestRetransmissionCount           DummySyntax,
    x25PLE-DTEcallAttempts                              Counter32,
    x25PLE-DTEprotocolErrorsDetectedLocally             Counter32,
    x25PLE-DTEprotocolErrorsAccusedOf                   Counter32,
    x25PLE-DTEcallEstablishmentRetryCountsExceeded      Counter32,
    x25PLE-DTEoctetsReceivedCounter                     Counter32,
    x25PLE-DTEoctetsSentCounter                         Counter32,
    x25PLE-DTEcallTimeouts                              Counter32,
    x25PLE-DTEcallsConnected                            Counter32,
    x25PLE-DTEclearCountsExceeded                       Counter32,
    x25PLE-DTEclearTimeouts                             Counter32,
    x25PLE-DTEdataPacketsReceived                       Counter32,
    x25PLE-DTEdataPacketsSent                           Counter32,
    x25PLE-DTEdataRetransmissionTimerExpiries           Counter32,
    x25PLE-DTEproviderInitiatedResets                   Counter32,
    x25PLE-DTEproviderInitiatedDisconnects              Counter32,
    x25PLE-DTEremotelyInitiatedResets                   Counter32,
    x25PLE-DTEremotelyInitiatedRestarts                 Counter32,
    x25PLE-DTEresetTimeouts                             Counter32,
    x25PLE-DTErestartCountsExceeded                     Counter32,
    x25PLE-DTEwindowStatusTransmissionTimer             DummySyntax,
    x25PLE-DTEwindowRotationTimer                       DummySyntax,
    x25PLE-DTEdataPacketRetransmissionCount             DummySyntax,
    x25PLE-DTErejectResponseTimer                       DummySyntax,
    x25PLE-DTErejectRetransmissionCount                 DummySyntax,
    x25PLE-DTEregistrationRequestResponseTimer          DummySyntax,
    x25PLE-DTEregistrationRequestRetransmissionCount    DummySyntax,
    x25PLE-DTEregistrationPermitted                     TruthValue
}

x25PLE-DTEcallDeflectionSubscription OBJECT-TYPE
    SYNTAX      TruthValue
    MAX-ACCESS  read-only
    STATUS      current
    DESCRIPTION 
        "Specifies whether call deflection is subscribed."
    ::= { x25PLE-DTEEntry 1 }

x25PLE-DTEcallRequestResponseTimer OBJECT-TYPE
    SYNTAX      DummySyntax
    MAX-ACCESS  read-only
    STATUS      current
    DESCRIPTION 
        "Provides the call request response timer."
    ::= { x25PLE-DTEEntry 2 }

x25PLE-DTEextendedPacketSequenceNumbering OBJECT-TYPE
    SYNTAX      DummySyntax
    MAX-ACCESS  read-only
    STATUS      current
    DESCRIPTION 
        "Provides extended packet sequence numbering."
    ::= { x25PLE-DTEEntry 3 }

x25PLE-DTEmaxActiveCircuits OBJECT-TYPE
    SYNTAX      DummySyntax
    MAX-ACCESS  read-only
    STATUS      current
    DESCRIPTION 
        "Specifies the maximum number of active circuits."
    ::= { x25PLE-DTEEntry 4 }

x25PLE-DTEminimumRecallTimer OBJECT-TYPE
    SYNTAX      DummySyntax
    MAX-ACCESS  read-only
    STATUS      current
    DESCRIPTION 
        "Specifies the minimum recall timer."
    ::= { x25PLE-DTEEntry 5 }

x25PLE-DTEresetRequestResponseTimer OBJECT-TYPE
    SYNTAX      DummySyntax
    MAX-ACCESS  read-only
    STATUS      current
    DESCRIPTION 
        "Provides the reset request response timer."
    ::= { x25PLE-DTEEntry 6 }

x25PLE-DTErestartRequestRetransmissionCount OBJECT-TYPE
    SYNTAX      DummySyntax
    MAX-ACCESS  read-only
    STATUS      current
    DESCRIPTION 
        "Provides the restart request retransmission count."
    ::= { x25PLE-DTEEntry 7 }

x25PLE-DTErestartRequestResponseTimer OBJECT-TYPE
    SYNTAX      DummySyntax
    MAX-ACCESS  read-only
    STATUS      current
    DESCRIPTION 
        "Provides the restart request response timer."
    ::= { x25PLE-DTEEntry 8 }

x25PLE-DTEclearRequestResponseTimer OBJECT-TYPE
    SYNTAX      DummySyntax
    MAX-ACCESS  read-only
    STATUS      current
    DESCRIPTION 
        "Provides the clear request response timer."
    ::= { x25PLE-DTEEntry 9 }

x25PLE-DTEinterruptResponseTimer OBJECT-TYPE
    SYNTAX      DummySyntax
    MAX-ACCESS  read-only
    STATUS      current
    DESCRIPTION 
        "Provides the interrupt response timer."
    ::= { x25PLE-DTEEntry 10 }

x25PLE-DTEresetRequestRetransmissionCount OBJECT-TYPE
    SYNTAX      DummySyntax
    MAX-ACCESS  read-only
    STATUS      current
    DESCRIPTION 
        "Provides the reset request retransmission count."
    ::= { x25PLE-DTEEntry 11 }

x25PLE-DTEclearRequestRetransmissionCount OBJECT-TYPE
    SYNTAX      DummySyntax
    MAX-ACCESS  read-only
    STATUS      current
    DESCRIPTION 
        "Provides the clear request retransmission count."
    ::= { x25PLE-DTEEntry 12 }

x25PLE-DTEcallAttempts OBJECT-TYPE
    SYNTAX      Counter32
    MAX-ACCESS  read-only
    STATUS      current
    DESCRIPTION 
        "Provides a count of the number of call attempts."
    ::= { x25PLE-DTEEntry 13 }

x25PLE-DTEprotocolErrorsDetectedLocally OBJECT-TYPE
    SYNTAX      Counter32
    MAX-ACCESS  read-only
    STATUS      current
    DESCRIPTION 
        "Provides a count of the number of protocol errors detected 
         locally."
    ::= { x25PLE-DTEEntry 14 }

x25PLE-DTEprotocolErrorsAccusedOf OBJECT-TYPE
    SYNTAX      Counter32
    MAX-ACCESS  read-only
    STATUS      current
    DESCRIPTION 
        "Provides a count of the number of protocol errors accused of."
    ::= { x25PLE-DTEEntry 15 }

x25PLE-DTEcallEstablishmentRetryCountsExceeded OBJECT-TYPE
    SYNTAX      Counter32
    MAX-ACCESS  read-only
    STATUS      current
    DESCRIPTION 
        "Provides a count of the number of call establishment retry 
         counts exceeded."
    ::= { x25PLE-DTEEntry 16 }

-- dTEX25PLECounters-P conditional package OBJECT-TYPE
x25PLE-DTEoctetsReceivedCounter OBJECT-TYPE
    SYNTAX      Counter32
    MAX-ACCESS  read-only
    STATUS      current
    DESCRIPTION 
        "Provides a count of the number of octets received."
    ::= { x25PLE-DTEEntry 17 }

x25PLE-DTEoctetsSentCounter OBJECT-TYPE
    SYNTAX      Counter32
    MAX-ACCESS  read-only
    STATUS      current
    DESCRIPTION 
        "Provides a count of the number of octets sent."
    ::= { x25PLE-DTEEntry 18 }

x25PLE-DTEcallTimeouts OBJECT-TYPE
    SYNTAX      Counter32
    MAX-ACCESS  read-only
    STATUS      current
    DESCRIPTION 
        "Provides a count of the number of call timeouts."
    ::= { x25PLE-DTEEntry 19 }

x25PLE-DTEcallsConnected OBJECT-TYPE
    SYNTAX      Counter32
    MAX-ACCESS  read-only
    STATUS      current
    DESCRIPTION 
        "Provides a count of the number of calls connected."
    ::= { x25PLE-DTEEntry 20 }

x25PLE-DTEclearCountsExceeded OBJECT-TYPE
    SYNTAX      Counter32
    MAX-ACCESS  read-only
    STATUS      current
    DESCRIPTION 
        "Provides a count of the number of clear counts exceeded."
    ::= { x25PLE-DTEEntry 21 }

x25PLE-DTEclearTimeouts OBJECT-TYPE
    SYNTAX      Counter32
    MAX-ACCESS  read-only
    STATUS      current
    DESCRIPTION 
        "Provides a count of the number of clear timeouts."
    ::= { x25PLE-DTEEntry 22 }

x25PLE-DTEdataPacketsReceived OBJECT-TYPE
    SYNTAX      Counter32
    MAX-ACCESS  read-only
    STATUS      current
    DESCRIPTION 
        "Provides a count of the number of data packets received."
    ::= { x25PLE-DTEEntry 23 }

x25PLE-DTEdataPacketsSent OBJECT-TYPE
    SYNTAX      Counter32
    MAX-ACCESS  read-only
    STATUS      current
    DESCRIPTION 
        "Provides a count of the number of data packets sent."
    ::= { x25PLE-DTEEntry 24 }

x25PLE-DTEdataRetransmissionTimerExpiries OBJECT-TYPE
    SYNTAX      Counter32
    MAX-ACCESS  read-only
    STATUS      current
    DESCRIPTION 
        "Provides a count of the number of data retransmission timer 
         expiries."
    ::= { x25PLE-DTEEntry 25 }

x25PLE-DTEproviderInitiatedResets OBJECT-TYPE
    SYNTAX      Counter32
    MAX-ACCESS  read-only
    STATUS      current
    DESCRIPTION 
        "Provides a count of the number of provider initiated resets."
    ::= { x25PLE-DTEEntry 26 }

x25PLE-DTEproviderInitiatedDisconnects OBJECT-TYPE
    SYNTAX      Counter32
    MAX-ACCESS  read-only
    STATUS      current
    DESCRIPTION 
        "Provides a count of the number of provider initiated 
         disconnects."
    ::= { x25PLE-DTEEntry 27 }

x25PLE-DTEremotelyInitiatedResets OBJECT-TYPE
    SYNTAX      Counter32
    MAX-ACCESS  read-only
    STATUS      current
    DESCRIPTION 
        "Proivdes a count of the number of remotely initiated resets."
    ::= { x25PLE-DTEEntry 28 }

x25PLE-DTEremotelyInitiatedRestarts OBJECT-TYPE
    SYNTAX      Counter32
    MAX-ACCESS  read-only
    STATUS      current
    DESCRIPTION 
        "Provides a count of the number of remotely initiated restarts."
    ::= { x25PLE-DTEEntry 29 }

x25PLE-DTEresetTimeouts OBJECT-TYPE
    SYNTAX      Counter32
    MAX-ACCESS  read-only
    STATUS      current
    DESCRIPTION 
        "Provides a count of the number of reset timeouts."
    ::= { x25PLE-DTEEntry 30 }

x25PLE-DTErestartCountsExceeded OBJECT-TYPE
    SYNTAX      Counter32
    MAX-ACCESS  read-only
    STATUS      current
    DESCRIPTION 
        "Provides a count of the number of restart counts exceeded."
    ::= { x25PLE-DTEEntry 31 }

-- receivingWindowRotationRecoveryProcedures-P conditional package 
-- OBJECT-TYPE
x25PLE-DTEwindowStatusTransmissionTimer OBJECT-TYPE
    SYNTAX      DummySyntax
    MAX-ACCESS  read-only
    STATUS      current
    DESCRIPTION 
        "Provides the window status transmission timer."
    ::= { x25PLE-DTEEntry 32 }

-- transmittingWindowRotationRecoveryProcedures-P conditional package 
-- OBJECT-TYPE
x25PLE-DTEwindowRotationTimer OBJECT-TYPE
    SYNTAX      DummySyntax
    MAX-ACCESS  read-only
    STATUS      current
    DESCRIPTION 
        "Provides the window rotation timer."
    ::= { x25PLE-DTEEntry 33 }

x25PLE-DTEdataPacketRetransmissionCount OBJECT-TYPE
    SYNTAX      DummySyntax
    MAX-ACCESS  read-only
    STATUS      current
    DESCRIPTION 
        "Provides the data packet retransmission count."
    ::= { x25PLE-DTEEntry 34 }

-- packetRetransmissionProcedures-P conditional package OBJECT-TYPE
x25PLE-DTErejectResponseTimer OBJECT-TYPE
    SYNTAX      DummySyntax
    MAX-ACCESS  read-only
    STATUS      current
    DESCRIPTION 
        "Provides the reject response timer."
    ::= { x25PLE-DTEEntry 35 }

x25PLE-DTErejectRetransmissionCount OBJECT-TYPE
    SYNTAX      DummySyntax
    MAX-ACCESS  read-only
    STATUS      current
    DESCRIPTION 
        "Provides the reject retransmission count."
    ::= { x25PLE-DTEEntry 36 }

-- onlineRegistration-P conditional package OBJECT-TYPE
x25PLE-DTEregistrationRequestResponseTimer OBJECT-TYPE
    SYNTAX      DummySyntax
    MAX-ACCESS  read-only
    STATUS      current
    DESCRIPTION 
        "Provides the registration request response timer."
    ::= { x25PLE-DTEEntry 37 }

x25PLE-DTEregistrationRequestRetransmissionCount OBJECT-TYPE
    SYNTAX      DummySyntax
    MAX-ACCESS  read-only
    STATUS      current
    DESCRIPTION 
        "Provides the registration request retransmission count."
    ::= { x25PLE-DTEEntry 38 }

x25PLE-DTEregistrationPermitted OBJECT-TYPE
    SYNTAX      TruthValue
    MAX-ACCESS  read-only
    STATUS      current
    DESCRIPTION 
        "Specifies whether registration is permitted."
    ::= { x25PLE-DTEEntry 39 }

x25PLE-DCE OBJECT IDENTIFIER
    ::= { osiTables 42 }

x25PLE-DCETable OBJECT-TYPE
    SYNTAX      SEQUENCE OF X25PLE-DCEEntry
    MAX-ACCESS  not-accessible
    STATUS      current
    DESCRIPTION 
        "The X.25 PLE DCE managed object.
         
         There may be multiple instances of these MOs within a system, 
         corresponding to Multiple X.25 PLEs.
         
         The definition of this MO permits it to be created and deleted 
         explicitly by management operation or to be created and deleted 
         automatically as part of system operation. When an instance of 
         this MO is created automatically, an instance of the 
         x25PLEIVMO-DCE may be used as the source of the initial values 
         for attributes of this MO.
         
         When the x25 PLE is operable, the operationalState shall have 
         the value 'enabled'; otherwise it shall have the value 
         'disabled'.  Transitions of operationalState shall be reported 
         using the stateChange notification."
    REFERENCE   
        "ITU-T Rec. X.283 | ISO/IEC 10733 x25PLE-DCE MOC."
    ::= { x25PLE-DCE 1 }

x25PLE-DCEEntry OBJECT-TYPE
    SYNTAX      X25PLE-DCEEntry
    MAX-ACCESS  not-accessible
    STATUS      current
    DESCRIPTION 
        "Each row in this table is indexed by the X.25 packet layer 
         entity identifier.  Each row contains characteristics and 
         operational status and measurements for the corresponding X.25 
         PLE DCE."
    REFERENCE   
        "ITU-T Rec. X.283 | ISO/IEC 10733 x25PLE-DCE MO."
    INDEX       { x25PLEId }
    ::= { x25PLE-DCETable 1 }

X25PLE-DCEEntry ::= SEQUENCE {
    x25PLE-DCEcallAttempts                          Counter32,
    x25PLE-DCEcallsConnected                        Counter32,
    x25PLE-DCEcUG                                   TruthValue,
    x25PLE-DCEfastSelectAcceptance                  TruthValue,
    x25PLE-DCEincomingCallsBarred                   TruthValue,
    x25PLE-DCEoneWayLogicalChannelOutgoing          TruthValue,
    x25PLE-DCEoutgoingCallsBarred                   TruthValue,
    x25PLE-DCEdataPacketsReceived                   Counter32,
    x25PLE-DCEdataPacketsSent                       Counter32,
    x25PLE-DCEinterruptPacketsReceived              Counter32,
    x25PLE-DCEinterruptPacketsSent                  Counter32,
    x25PLE-DCEinterruptTimerExpiries                Counter32,
    x25PLE-DCEoctetsReceivedCounter                 Counter32,
    x25PLE-DCEoctetsSentCounter                     Counter32,
    x25PLE-DCEproviderInitiatedDisconnects          Counter32,
    x25PLE-DCEproviderInitiatedResets               Counter32,
    x25PLE-DCEremotelyInitiatedRestarts             Counter32,
    x25PLE-DCEremotelyInitiatedResets               Counter32,
    x25PLE-DCEresetTimeouts                         Counter32,
    x25PLE-DCEx25SegmentsReceived                   Counter32,
    x25PLE-DCEx25SegmentsSent                       Counter32,
    x25PLE-DCEbilateralCUG                          TruthValue,
    x25PLE-DCEbilateralCUGWithOutgoingAccess        TruthValue,
    x25PLE-DCEcallDeflectionSubscription            TruthValue,
    x25PLE-DCEcallRedirection                       TruthValue,
    x25PLE-DCEchargingInformation                   TruthValue,
    x25PLE-DCEcUGWithIncomingAccess                 TruthValue,
    x25PLE-DCEcUGWithOutgoingAccess                 TruthValue,
    x25PLE-DCEdBitModification                      TruthValue,
    x25PLE-DCEdefaultThroughputClassesAssignment    DummySyntax,
    x25PLE-DCEextendedPacketSequenceNumbering       DummySyntax,
    x25PLE-DCEhuntGroup                             TruthValue,
    x25PLE-DCEincomingCallBarredWithinCUG           TruthValue,
    x25PLE-DCElocalChargingPrevention               TruthValue,
    x25PLE-DCEnonStandardDefaultPacketSizes         DummySyntax,
    x25PLE-DCEnonStandardDefaultWindowSizes         DummySyntax,
    x25PLE-DCEnUIOverride                           TruthValue,
    x25PLE-DCEnUISubscription                       TruthValue,
    x25PLE-DCEoneWayLogicalChannelIncoming          TruthValue,
    x25PLE-DCEonlineFacilityRegistration            TruthValue,
    x25PLE-DCEoutgoingCallBarredWithinCUG           TruthValue,
    x25PLE-DCEpacketRetransmission                  TruthValue,
    x25PLE-DCEreverseChargingAcceptance             TruthValue,
    x25PLE-DCErOASubscription                       TruthValue,
    x25PLE-DCEclearIndication                       TimeInterval,
    x25PLE-DCEincomingCall                          DummySyntax,
    x25PLE-DCEresetIndication                       DummySyntax,
    x25PLE-DCErestartIndication                     DummySyntax
}

x25PLE-DCEcallAttempts OBJECT-TYPE
    SYNTAX      Counter32
    MAX-ACCESS  read-only
    STATUS      current
    DESCRIPTION 
        "Provides a count of the number of call attempts."
    ::= { x25PLE-DCEEntry 1 }

x25PLE-DCEcallsConnected OBJECT-TYPE
    SYNTAX      Counter32
    MAX-ACCESS  read-only
    STATUS      current
    DESCRIPTION 
        "Provides a count of the number of calls connected."
    ::= { x25PLE-DCEEntry 2 }

x25PLE-DCEcUG OBJECT-TYPE
    SYNTAX      TruthValue
    MAX-ACCESS  read-only
    STATUS      current
    DESCRIPTION 
        "Specifies whether the DCE belongs to a closed user group."
    ::= { x25PLE-DCEEntry 3 }

x25PLE-DCEfastSelectAcceptance OBJECT-TYPE
    SYNTAX      TruthValue
    MAX-ACCESS  read-only
    STATUS      current
    DESCRIPTION 
        "Specifies whether fast select is accepted."
    ::= { x25PLE-DCEEntry 4 }

x25PLE-DCEincomingCallsBarred OBJECT-TYPE
    SYNTAX      TruthValue
    MAX-ACCESS  read-only
    STATUS      current
    DESCRIPTION 
        "Specifies whether incoming calls are barred."
    ::= { x25PLE-DCEEntry 5 }

x25PLE-DCEoneWayLogicalChannelOutgoing OBJECT-TYPE
    SYNTAX      TruthValue
    MAX-ACCESS  read-only
    STATUS      current
    DESCRIPTION 
        "Specifies whether one-way logical channel outgoing is provided."
    ::= { x25PLE-DCEEntry 6 }

x25PLE-DCEoutgoingCallsBarred OBJECT-TYPE
    SYNTAX      TruthValue
    MAX-ACCESS  read-only
    STATUS      current
    DESCRIPTION 
        "Specifies whether outgoing calls are barred."
    ::= { x25PLE-DCEEntry 7 }

-- dCECommonVirtualCircuitCounters-P conditional package
x25PLE-DCEdataPacketsReceived OBJECT-TYPE
    SYNTAX      Counter32
    MAX-ACCESS  read-only
    STATUS      current
    DESCRIPTION 
        "Provides a count of the number of data packets received."
    ::= { x25PLE-DCEEntry 8 }

x25PLE-DCEdataPacketsSent OBJECT-TYPE
    SYNTAX      Counter32
    MAX-ACCESS  read-only
    STATUS      current
    DESCRIPTION 
        "Provides a count of the number of data packets sent."
    ::= { x25PLE-DCEEntry 9 }

x25PLE-DCEinterruptPacketsReceived OBJECT-TYPE
    SYNTAX      Counter32
    MAX-ACCESS  read-only
    STATUS      current
    DESCRIPTION 
        "Provides a count of the number of interrupt packets received."
    ::= { x25PLE-DCEEntry 10 }

x25PLE-DCEinterruptPacketsSent OBJECT-TYPE
    SYNTAX      Counter32
    MAX-ACCESS  read-only
    STATUS      current
    DESCRIPTION 
        "Provides a count of the number of interrupt packets sent."
    ::= { x25PLE-DCEEntry 11 }

x25PLE-DCEinterruptTimerExpiries OBJECT-TYPE
    SYNTAX      Counter32
    MAX-ACCESS  read-only
    STATUS      current
    DESCRIPTION 
        "Provides a count of the number of interrupt timer expiries."
    ::= { x25PLE-DCEEntry 12 }

x25PLE-DCEoctetsReceivedCounter OBJECT-TYPE
    SYNTAX      Counter32
    MAX-ACCESS  read-only
    STATUS      current
    DESCRIPTION 
        "Provides a count of the number of octets received."
    ::= { x25PLE-DCEEntry 13 }

x25PLE-DCEoctetsSentCounter OBJECT-TYPE
    SYNTAX      Counter32
    MAX-ACCESS  read-only
    STATUS      current
    DESCRIPTION 
        "Provides a count of the number of octets sent."
    ::= { x25PLE-DCEEntry 14 }

x25PLE-DCEproviderInitiatedDisconnects OBJECT-TYPE
    SYNTAX      Counter32
    MAX-ACCESS  read-only
    STATUS      current
    DESCRIPTION 
        "Provides a count of the number of provider-initiated 
         disconnects."
    ::= { x25PLE-DCEEntry 15 }

x25PLE-DCEproviderInitiatedResets OBJECT-TYPE
    SYNTAX      Counter32
    MAX-ACCESS  read-only
    STATUS      current
    DESCRIPTION 
        "Provides a count of the number of provider-initiated resets."
    ::= { x25PLE-DCEEntry 16 }

x25PLE-DCEremotelyInitiatedRestarts OBJECT-TYPE
    SYNTAX      Counter32
    MAX-ACCESS  read-only
    STATUS      current
    DESCRIPTION 
        "Provides a count of the number of remotely-initiated restarts."
    ::= { x25PLE-DCEEntry 17 }

x25PLE-DCEremotelyInitiatedResets OBJECT-TYPE
    SYNTAX      Counter32
    MAX-ACCESS  read-only
    STATUS      current
    DESCRIPTION 
        "Provides a count of the number of remotely-initiated resets."
    ::= { x25PLE-DCEEntry 18 }

x25PLE-DCEresetTimeouts OBJECT-TYPE
    SYNTAX      Counter32
    MAX-ACCESS  read-only
    STATUS      current
    DESCRIPTION 
        "Provides a count of the number of reset timeouts."
    ::= { x25PLE-DCEEntry 19 }

x25PLE-DCEx25SegmentsReceived OBJECT-TYPE
    SYNTAX      Counter32
    MAX-ACCESS  read-only
    STATUS      current
    DESCRIPTION 
        "Provides a count of the number of X.25 segments received."
    ::= { x25PLE-DCEEntry 20 }

x25PLE-DCEx25SegmentsSent OBJECT-TYPE
    SYNTAX      Counter32
    MAX-ACCESS  read-only
    STATUS      current
    DESCRIPTION 
        "Provides a count of the number of X.25 segments sent."
    ::= { x25PLE-DCEEntry 21 }

-- dCEX25PLEFacilities-P conditional package
x25PLE-DCEbilateralCUG OBJECT-TYPE
    SYNTAX      TruthValue
    MAX-ACCESS  read-only
    STATUS      current
    DESCRIPTION 
        "Specifies whether bilateral CUG is subscribed."
    ::= { x25PLE-DCEEntry 22 }

x25PLE-DCEbilateralCUGWithOutgoingAccess OBJECT-TYPE
    SYNTAX      TruthValue
    MAX-ACCESS  read-only
    STATUS      current
    DESCRIPTION 
        "Provides bilateral CUG with outgoing access."
    ::= { x25PLE-DCEEntry 23 }

x25PLE-DCEcallDeflectionSubscription OBJECT-TYPE
    SYNTAX      TruthValue
    MAX-ACCESS  read-only
    STATUS      current
    DESCRIPTION 
        "Speciifes whether call deflection is subscribed."
    ::= { x25PLE-DCEEntry 24 }

x25PLE-DCEcallRedirection OBJECT-TYPE
    SYNTAX      TruthValue
    MAX-ACCESS  read-only
    STATUS      current
    DESCRIPTION 
        "Specifies whether call redirection is subscribed."
    ::= { x25PLE-DCEEntry 25 }

x25PLE-DCEchargingInformation OBJECT-TYPE
    SYNTAX      TruthValue
    MAX-ACCESS  read-only
    STATUS      current
    DESCRIPTION 
        "Specifies whether charging information is subscribed."
    ::= { x25PLE-DCEEntry 26 }

x25PLE-DCEcUGWithIncomingAccess OBJECT-TYPE
    SYNTAX      TruthValue
    MAX-ACCESS  read-only
    STATUS      current
    DESCRIPTION 
        "Specifies whether CUG with incoming access is subscribed."
    ::= { x25PLE-DCEEntry 27 }

x25PLE-DCEcUGWithOutgoingAccess OBJECT-TYPE
    SYNTAX      TruthValue
    MAX-ACCESS  read-only
    STATUS      current
    DESCRIPTION 
        "Specifies whether CUG with outgoing access is subscribed."
    ::= { x25PLE-DCEEntry 28 }

x25PLE-DCEdBitModification OBJECT-TYPE
    SYNTAX      TruthValue
    MAX-ACCESS  read-only
    STATUS      current
    DESCRIPTION 
        "Specifies wehther d-bit modification is subscribed."
    ::= { x25PLE-DCEEntry 29 }

x25PLE-DCEdefaultThroughputClassesAssignment OBJECT-TYPE
    SYNTAX      DummySyntax
    MAX-ACCESS  read-only
    STATUS      current
    DESCRIPTION 
        "Provides default throughput classes assignment."
    ::= { x25PLE-DCEEntry 30 }

x25PLE-DCEextendedPacketSequenceNumbering OBJECT-TYPE
    SYNTAX      DummySyntax
    MAX-ACCESS  read-only
    STATUS      current
    DESCRIPTION 
        "Provides extended packet sequence numbering."
    ::= { x25PLE-DCEEntry 31 }

x25PLE-DCEhuntGroup OBJECT-TYPE
    SYNTAX      TruthValue
    MAX-ACCESS  read-only
    STATUS      current
    DESCRIPTION 
        "Specifies whether hunt group is subscribed."
    ::= { x25PLE-DCEEntry 32 }

x25PLE-DCEincomingCallBarredWithinCUG OBJECT-TYPE
    SYNTAX      TruthValue
    MAX-ACCESS  read-only
    STATUS      current
    DESCRIPTION 
        "Specifies whether incoming calls are barred within CUG."
    ::= { x25PLE-DCEEntry 33 }

x25PLE-DCElocalChargingPrevention OBJECT-TYPE
    SYNTAX      TruthValue
    MAX-ACCESS  read-only
    STATUS      current
    DESCRIPTION 
        "Specifies local charging prevention."
    ::= { x25PLE-DCEEntry 34 }

x25PLE-DCEnonStandardDefaultPacketSizes OBJECT-TYPE
    SYNTAX      DummySyntax
    MAX-ACCESS  read-only
    STATUS      current
    DESCRIPTION 
        "Specifies non-standard default packet sizes."
    ::= { x25PLE-DCEEntry 35 }

x25PLE-DCEnonStandardDefaultWindowSizes OBJECT-TYPE
    SYNTAX      DummySyntax
    MAX-ACCESS  read-only
    STATUS      current
    DESCRIPTION 
        "Specifies non-standard default window sizes."
    ::= { x25PLE-DCEEntry 36 }

x25PLE-DCEnUIOverride OBJECT-TYPE
    SYNTAX      TruthValue
    MAX-ACCESS  read-only
    STATUS      current
    DESCRIPTION 
        "Specifies NUI override."
    ::= { x25PLE-DCEEntry 37 }

x25PLE-DCEnUISubscription OBJECT-TYPE
    SYNTAX      TruthValue
    MAX-ACCESS  read-only
    STATUS      current
    DESCRIPTION 
        "Speciifes NUI subscription."
    ::= { x25PLE-DCEEntry 38 }

x25PLE-DCEoneWayLogicalChannelIncoming OBJECT-TYPE
    SYNTAX      TruthValue
    MAX-ACCESS  read-only
    STATUS      current
    DESCRIPTION 
        "Specifies one-way logical channel incoming."
    ::= { x25PLE-DCEEntry 39 }

x25PLE-DCEonlineFacilityRegistration OBJECT-TYPE
    SYNTAX      TruthValue
    MAX-ACCESS  read-only
    STATUS      current
    DESCRIPTION 
        "Specifies online facility registration."
    ::= { x25PLE-DCEEntry 40 }

x25PLE-DCEoutgoingCallBarredWithinCUG OBJECT-TYPE
    SYNTAX      TruthValue
    MAX-ACCESS  read-only
    STATUS      current
    DESCRIPTION 
        "Specifies outgoing call barred within CUG."
    ::= { x25PLE-DCEEntry 41 }

x25PLE-DCEpacketRetransmission OBJECT-TYPE
    SYNTAX      TruthValue
    MAX-ACCESS  read-only
    STATUS      current
    DESCRIPTION 
        "Specifies packet retransmission."
    ::= { x25PLE-DCEEntry 42 }

x25PLE-DCEreverseChargingAcceptance OBJECT-TYPE
    SYNTAX      TruthValue
    MAX-ACCESS  read-only
    STATUS      current
    DESCRIPTION 
        "Specifies reverse charging acceptance."
    ::= { x25PLE-DCEEntry 43 }

x25PLE-DCErOASubscription OBJECT-TYPE
    SYNTAX      TruthValue
    MAX-ACCESS  read-only
    STATUS      current
    DESCRIPTION 
        "Specifies ROA subscription."
    ::= { x25PLE-DCEEntry 44 }

-- dCEX25PLETimers-P conditional package
x25PLE-DCEclearIndication OBJECT-TYPE
    SYNTAX      TimeInterval
    MAX-ACCESS  read-only
    STATUS      current
    DESCRIPTION 
        "Provides clear indication timer."
    ::= { x25PLE-DCEEntry 45 }

x25PLE-DCEincomingCall OBJECT-TYPE
    SYNTAX      DummySyntax
    MAX-ACCESS  read-only
    STATUS      current
    DESCRIPTION 
        "Provides incoming call timer."
    ::= { x25PLE-DCEEntry 46 }

x25PLE-DCEresetIndication OBJECT-TYPE
    SYNTAX      DummySyntax
    MAX-ACCESS  read-only
    STATUS      current
    DESCRIPTION 
        "Provides reset indication timer."
    ::= { x25PLE-DCEEntry 47 }

x25PLE-DCErestartIndication OBJECT-TYPE
    SYNTAX      DummySyntax
    MAX-ACCESS  read-only
    STATUS      current
    DESCRIPTION 
        "Provides restart indication timer."
    ::= { x25PLE-DCEEntry 48 }

x25PLEIVMO OBJECT IDENTIFIER
    ::= { osiTables 43 }

x25PLEIVMOTable OBJECT-TYPE
    SYNTAX      SEQUENCE OF X25PLEIVMOEntry
    MAX-ACCESS  not-accessible
    STATUS      current
    DESCRIPTION 
        "The X.25 PLE initial values managed object.
         
         This MO class is never instantiated. It serves as a generic 
         x25PLE IVMO from which both the x25PLEIVMO-DTE and 
         x25PLEIVMO-DCE MO classes are derived.
         
         Note that the values of the x25PLEIVMOId naming attribute are 
         required to be unique across all instances of MOs derived from 
         this, which have a common superior."
    REFERENCE   
        "ITU-T Rec. X.283 | ISO/IEC 10733 x25PLEIVMO MOC."
    ::= { x25PLEIVMO 1 }

x25PLEIVMOEntry OBJECT-TYPE
    SYNTAX      X25PLEIVMOEntry
    MAX-ACCESS  not-accessible
    STATUS      current
    DESCRIPTION 
        "Each row in this table is indexed by X.25 PLE IVMO identifier 
         (which is basically an initial value profile name).  Each row 
         contains initial values for the creation of X.25 packet-layer 
         entities."
    REFERENCE   
        "ITU-T Rec. X.283 | ISO/IEC 10733 x25PLEIVMO MO."
    INDEX       { x25PLEIVMOId }
    ::= { x25PLEIVMOTable 1 }

X25PLEIVMOEntry ::= SEQUENCE {
    x25PLEIVMOId                                SimpleNameType,
    x25PLEIVMOlocalDTEAddress                   DTEAddress,
    x25PLEIVMOlogicalChannelAssignments         DummySyntax,
    x25PLEIVMOsN-ServiceProvider                DummySyntax,
    x25PLEIVMOdefaultPacketSizes                DummySyntax,
    x25PLEIVMOdefaultThroughputClasses          DummySyntax,
    x25PLEIVMOdefaultWindowSizes                DummySyntax,
    x25PLEIVMOflowControlParameterNegotiation   DummySyntax,
    x25PLEIVMOthroughputClassNegotiation        DummySyntax,
    x25PLEIVMOx25PLEMode                        DummySyntax,
    x25PLEIVMOinterfaceMode                     X25PLEMode,
    x25PLEIVMOdefaultThroughputClass            DummySyntax,
    x25PLEIVMOflowControlNegotiationPermitted   DummySyntax,
    x25PLEIVMOcallDeflectionSubscription        TruthValue,
    x25PLEIVMOmaxActiveCircuits                 DummySyntax,
    x25PLEIVMOrestartTime                       DummySyntax,
    x25PLEIVMOdefaultPacketSize                 DummySyntax,
    x25PLEIVMOdefaultWindowSize                 DummySyntax,
    x25PLEIVMOminimumRecallTimer                DummySyntax,
    x25PLEIVMOrestartCount                      DummySyntax,
    x25PLEIVMOpacketSequencing                  DummySyntax,
    x25PLEIVMOregistrationRequestTime           DummySyntax,
    x25PLEIVMOregistrationRequestCount          DummySyntax,
    x25PLEIVMOregistrationPermitted             TruthValue,
    x25PLEIVMORowStatus                         RowStatus
}

x25PLEIVMOId OBJECT-TYPE
    SYNTAX      SimpleNameType
    MAX-ACCESS  not-accessible
    STATUS      current
    DESCRIPTION 
        "Provides a simple name for the protocol parameter profile that 
         is used as an index into this table."
    ::= { x25PLEIVMOEntry 1 }

-- X.283 or 10733
x25PLEIVMOlocalDTEAddress OBJECT-TYPE
    SYNTAX      DTEAddress
    MAX-ACCESS  read-only
    STATUS      current
    DESCRIPTION 
        "Provides the local DTE address."
    ::= { x25PLEIVMOEntry 2 }

x25PLEIVMOlogicalChannelAssignments OBJECT-TYPE
    SYNTAX      DummySyntax
    MAX-ACCESS  read-only
    STATUS      current
    DESCRIPTION 
        "Provides logical channel assignment."
    ::= { x25PLEIVMOEntry 3 }

x25PLEIVMOsN-ServiceProvider OBJECT-TYPE
    SYNTAX      DummySyntax
    MAX-ACCESS  read-only
    STATUS      current
    DESCRIPTION 
        "Profiles the subnetwork service provider."
    ::= { x25PLEIVMOEntry 4 }

-- X.283 only
x25PLEIVMOdefaultPacketSizes OBJECT-TYPE
    SYNTAX      DummySyntax
    MAX-ACCESS  read-only
    STATUS      current
    DESCRIPTION 
        "Provides default packet sizes."
    ::= { x25PLEIVMOEntry 5 }

x25PLEIVMOdefaultThroughputClasses OBJECT-TYPE
    SYNTAX      DummySyntax
    MAX-ACCESS  read-only
    STATUS      current
    DESCRIPTION 
        "Provides default throughput classes."
    ::= { x25PLEIVMOEntry 6 }

x25PLEIVMOdefaultWindowSizes OBJECT-TYPE
    SYNTAX      DummySyntax
    MAX-ACCESS  read-only
    STATUS      current
    DESCRIPTION 
        "Provides default window sizes."
    ::= { x25PLEIVMOEntry 7 }

x25PLEIVMOflowControlParameterNegotiation OBJECT-TYPE
    SYNTAX      DummySyntax
    MAX-ACCESS  read-only
    STATUS      current
    DESCRIPTION 
        "Provides flow control parameter negotiation."
    ::= { x25PLEIVMOEntry 8 }

x25PLEIVMOthroughputClassNegotiation OBJECT-TYPE
    SYNTAX      DummySyntax
    MAX-ACCESS  read-only
    STATUS      current
    DESCRIPTION 
        "Provides throughput class negotiation."
    ::= { x25PLEIVMOEntry 9 }

x25PLEIVMOx25PLEMode OBJECT-TYPE
    SYNTAX      DummySyntax
    MAX-ACCESS  read-only
    STATUS      current
    DESCRIPTION 
        "Provides the X.25 PLE mode."
    ::= { x25PLEIVMOEntry 10 }

-- ISO 10733 only
x25PLEIVMOinterfaceMode OBJECT-TYPE
    SYNTAX      X25PLEMode
    MAX-ACCESS  read-only
    STATUS      current
    DESCRIPTION 
        "Provides the interface mode."
    ::= { x25PLEIVMOEntry 11 }

x25PLEIVMOdefaultThroughputClass OBJECT-TYPE
    SYNTAX      DummySyntax
    MAX-ACCESS  read-only
    STATUS      current
    DESCRIPTION 
        "Provides the default throughput class."
    ::= { x25PLEIVMOEntry 12 }

x25PLEIVMOflowControlNegotiationPermitted OBJECT-TYPE
    SYNTAX      DummySyntax
    MAX-ACCESS  read-only
    STATUS      current
    DESCRIPTION 
        "Specifies whether flow control negotiation is permitted."
    ::= { x25PLEIVMOEntry 13 }

x25PLEIVMOcallDeflectionSubscription OBJECT-TYPE
    SYNTAX      TruthValue
    MAX-ACCESS  read-only
    STATUS      current
    DESCRIPTION 
        "Specifies call deflection subscription."
    ::= { x25PLEIVMOEntry 14 }

x25PLEIVMOmaxActiveCircuits OBJECT-TYPE
    SYNTAX      DummySyntax
    MAX-ACCESS  read-only
    STATUS      current
    DESCRIPTION 
        "Provides the maximum number of active circuits."
    ::= { x25PLEIVMOEntry 15 }

x25PLEIVMOrestartTime OBJECT-TYPE
    SYNTAX      DummySyntax
    MAX-ACCESS  read-only
    STATUS      current
    DESCRIPTION 
        "Provides the restart time."
    ::= { x25PLEIVMOEntry 16 }

x25PLEIVMOdefaultPacketSize OBJECT-TYPE
    SYNTAX      DummySyntax
    MAX-ACCESS  read-only
    STATUS      current
    DESCRIPTION 
        "Provides the default packet size."
    ::= { x25PLEIVMOEntry 17 }

x25PLEIVMOdefaultWindowSize OBJECT-TYPE
    SYNTAX      DummySyntax
    MAX-ACCESS  read-only
    STATUS      current
    DESCRIPTION 
        "Provides the default window size."
    ::= { x25PLEIVMOEntry 18 }

x25PLEIVMOminimumRecallTimer OBJECT-TYPE
    SYNTAX      DummySyntax
    MAX-ACCESS  read-only
    STATUS      current
    DESCRIPTION 
        "Provides the minimum recall timer."
    ::= { x25PLEIVMOEntry 19 }

x25PLEIVMOrestartCount OBJECT-TYPE
    SYNTAX      DummySyntax
    MAX-ACCESS  read-only
    STATUS      current
    DESCRIPTION 
        "Provides the restart count."
    ::= { x25PLEIVMOEntry 20 }

x25PLEIVMOpacketSequencing OBJECT-TYPE
    SYNTAX      DummySyntax
    MAX-ACCESS  read-only
    STATUS      current
    DESCRIPTION 
        "Specifies packet sequencing."
    ::= { x25PLEIVMOEntry 21 }

-- ISO 10733 only onlineRegistration-P conditional package
x25PLEIVMOregistrationRequestTime OBJECT-TYPE
    SYNTAX      DummySyntax
    MAX-ACCESS  read-only
    STATUS      current
    DESCRIPTION 
        "Provides the registration request time."
    ::= { x25PLEIVMOEntry 22 }

x25PLEIVMOregistrationRequestCount OBJECT-TYPE
    SYNTAX      DummySyntax
    MAX-ACCESS  read-only
    STATUS      current
    DESCRIPTION 
        "Provides the registration request count."
    ::= { x25PLEIVMOEntry 23 }

x25PLEIVMOregistrationPermitted OBJECT-TYPE
    SYNTAX      TruthValue
    MAX-ACCESS  read-only
    STATUS      current
    DESCRIPTION 
        "Specifies whether registration is permitted."
    ::= { x25PLEIVMOEntry 24 }

-- ISO 10733 only x25PLEIVMO-networkSubsystem name binding
x25PLEIVMORowStatus OBJECT-TYPE
    SYNTAX      RowStatus
    MAX-ACCESS  read-create
    STATUS      current
    DESCRIPTION 
        "Provides a mechanism whereby management stations may create and 
         delete rows in this table.  Entries must persist across agent 
         reboots."
    ::= { x25PLEIVMOEntry 25 }

x25PLEIVMO-DTE OBJECT IDENTIFIER
    ::= { osiTables 44 }

x25PLEIVMO-DTETable OBJECT-TYPE
    SYNTAX      SEQUENCE OF X25PLEIVMO-DTEEntry
    MAX-ACCESS  not-accessible
    STATUS      current
    DESCRIPTION 
        "Provides a table of initial values to be used when creating 
         X.25 PLE DTE's in the x25PLE-DTETable."
    REFERENCE   
        "ITU-T Rec. X.283 | ISO/IEC 10733 x25PLEIVMO-DTE MOC."
    ::= { x25PLEIVMO-DTE 1 }

x25PLEIVMO-DTEEntry OBJECT-TYPE
    SYNTAX      X25PLEIVMO-DTEEntry
    MAX-ACCESS  not-accessible
    STATUS      current
    DESCRIPTION 
        "Each row is indexed by the X.25 PLE IVMO identifier defined by 
         this table (which is basically a protocol profile name).  Each 
         row contains the initial values to use when creating rows in 
         the x25PLE-DTETable."
    REFERENCE   
        "ITU-T Rec. X.283 | ISO/IEC 10733 x25PLEIVMO-DTE MO."
    INDEX       { x25PLEIVMOId }
    ::= { x25PLEIVMO-DTETable 1 }

X25PLEIVMO-DTEEntry ::= SEQUENCE {
    x25PLEIVMO-DTEcallDeflectionSubscription                TruthValue,
    x25PLEIVMO-DTEcallRequestResponseTimer                  DummySyntax,
    x25PLEIVMO-DTEextendedPacketSequenceNumbering           DummySyntax,
    x25PLEIVMO-DTEmaxActiveCircuits                         DummySyntax,
    x25PLEIVMO-DTEminimumRecallTimer                        DummySyntax,
    x25PLEIVMO-DTEresetRequestResponseTimer                 DummySyntax,
    x25PLEIVMO-DTErestartRequestRetransmissionCount         DummySyntax,
    x25PLEIVMO-DTErestartRequestResponseTimer               DummySyntax,
    x25PLEIVMO-DTEclearRequestResponseTimer                 DummySyntax,
    x25PLEIVMO-DTEinterruptResponseTimer                    DummySyntax,
    x25PLEIVMO-DTEresetRequestRetransmissionCount           DummySyntax,
    x25PLEIVMO-DTEclearRequestRetransmissionCount           DummySyntax,
    x25PLEIVMO-DTEcallAttempts                              DummySyntax,
    x25PLEIVMO-DTEprotocolErrorsDetectedLocally             DummySyntax,
    x25PLEIVMO-DTEprotocolErrorsAccusedOf                   DummySyntax,
    x25PLEIVMO-DTEcallEstablishmentRetryCountsExceeded      DummySyntax,
    x25PLEIVMO-DTEoctetsReceivedCounter                     Counter32,
    x25PLEIVMO-DTEoctetsSentCounter                         Counter32,
    x25PLEIVMO-DTEcallTimeouts                              Counter32,
    x25PLEIVMO-DTEcallsConnected                            Counter32,
    x25PLEIVMO-DTEclearCountsExceeded                       Counter32,
    x25PLEIVMO-DTEclearTimeouts                             Counter32,
    x25PLEIVMO-DTEdataPacketsReceived                       Counter32,
    x25PLEIVMO-DTEdataPacketsSent                           Counter32,
    x25PLEIVMO-DTEdataRetransmissionTimerExpiries           Counter32,
    x25PLEIVMO-DTEproviderInitiatedResets                   Counter32,
    x25PLEIVMO-DTEproviderInitiatedDisconnects              Counter32,
    x25PLEIVMO-DTEremotelyInitiatedResets                   Counter32,
    x25PLEIVMO-DTEremotelyInitiatedRestarts                 Counter32,
    x25PLEIVMO-DTEresetTimeouts                             Counter32,
    x25PLEIVMO-DTErestartCountsExceeded                     Counter32,
    x25PLEIVMO-DTEwindowStatusTransmissionTimer             DummySyntax,
    x25PLEIVMO-DTEwindowRotationTimer                       DummySyntax,
    x25PLEIVMO-DTEdataPacketRetransmissionCount             DummySyntax,
    x25PLEIVMO-DTErejectResponseTimer                       DummySyntax,
    x25PLEIVMO-DTErejectRetransmissionCount                 DummySyntax,
    x25PLEIVMO-DTEregistrationRequestResponseTimer          DummySyntax,
    x25PLEIVMO-DTEregistrationRequestRetransmissionCount    DummySyntax,
    x25PLEIVMO-DTEregistrationPermitted                     TruthValue,
    x25PLEIVMO-DTERowStatus                                 RowStatus
}

x25PLEIVMO-DTEcallDeflectionSubscription OBJECT-TYPE
    SYNTAX      TruthValue
    MAX-ACCESS  read-only
    STATUS      current
    DESCRIPTION 
        "Specifies call deflection subscription."
    ::= { x25PLEIVMO-DTEEntry 1 }

x25PLEIVMO-DTEcallRequestResponseTimer OBJECT-TYPE
    SYNTAX      DummySyntax
    MAX-ACCESS  read-only
    STATUS      current
    DESCRIPTION 
        "Provides the call request response timer."
    ::= { x25PLEIVMO-DTEEntry 2 }

x25PLEIVMO-DTEextendedPacketSequenceNumbering OBJECT-TYPE
    SYNTAX      DummySyntax
    MAX-ACCESS  read-only
    STATUS      current
    DESCRIPTION 
        "Provides extended packet sequence numbering."
    ::= { x25PLEIVMO-DTEEntry 3 }

x25PLEIVMO-DTEmaxActiveCircuits OBJECT-TYPE
    SYNTAX      DummySyntax
    MAX-ACCESS  read-only
    STATUS      current
    DESCRIPTION 
        "Provides the maximum active circuits."
    ::= { x25PLEIVMO-DTEEntry 4 }

x25PLEIVMO-DTEminimumRecallTimer OBJECT-TYPE
    SYNTAX      DummySyntax
    MAX-ACCESS  read-only
    STATUS      current
    DESCRIPTION 
        "Provides the minimum recall timer."
    ::= { x25PLEIVMO-DTEEntry 5 }

x25PLEIVMO-DTEresetRequestResponseTimer OBJECT-TYPE
    SYNTAX      DummySyntax
    MAX-ACCESS  read-only
    STATUS      current
    DESCRIPTION 
        "Provides the reset request response timer."
    ::= { x25PLEIVMO-DTEEntry 6 }

x25PLEIVMO-DTErestartRequestRetransmissionCount OBJECT-TYPE
    SYNTAX      DummySyntax
    MAX-ACCESS  read-only
    STATUS      current
    DESCRIPTION 
        "Provides the restart request retransmission count."
    ::= { x25PLEIVMO-DTEEntry 7 }

x25PLEIVMO-DTErestartRequestResponseTimer OBJECT-TYPE
    SYNTAX      DummySyntax
    MAX-ACCESS  read-only
    STATUS      current
    DESCRIPTION 
        "Provides the restart request response timer."
    ::= { x25PLEIVMO-DTEEntry 8 }

x25PLEIVMO-DTEclearRequestResponseTimer OBJECT-TYPE
    SYNTAX      DummySyntax
    MAX-ACCESS  read-only
    STATUS      current
    DESCRIPTION 
        "Provides the clear request response timer."
    ::= { x25PLEIVMO-DTEEntry 9 }

x25PLEIVMO-DTEinterruptResponseTimer OBJECT-TYPE
    SYNTAX      DummySyntax
    MAX-ACCESS  read-only
    STATUS      current
    DESCRIPTION 
        "Provides the interrupt response timer."
    ::= { x25PLEIVMO-DTEEntry 10 }

x25PLEIVMO-DTEresetRequestRetransmissionCount OBJECT-TYPE
    SYNTAX      DummySyntax
    MAX-ACCESS  read-only
    STATUS      current
    DESCRIPTION 
        "Provides the reset request retransmission count."
    ::= { x25PLEIVMO-DTEEntry 11 }

x25PLEIVMO-DTEclearRequestRetransmissionCount OBJECT-TYPE
    SYNTAX      DummySyntax
    MAX-ACCESS  read-only
    STATUS      current
    DESCRIPTION 
        "Provides the clear request retransmission count."
    ::= { x25PLEIVMO-DTEEntry 12 }

x25PLEIVMO-DTEcallAttempts OBJECT-TYPE
    SYNTAX      DummySyntax
    MAX-ACCESS  read-only
    STATUS      current
    DESCRIPTION 
        "Provides a count of the number of call attempts."
    ::= { x25PLEIVMO-DTEEntry 13 }

x25PLEIVMO-DTEprotocolErrorsDetectedLocally OBJECT-TYPE
    SYNTAX      DummySyntax
    MAX-ACCESS  read-only
    STATUS      current
    DESCRIPTION 
        "Provides a count of the number of protocol errors detected 
         locally."
    ::= { x25PLEIVMO-DTEEntry 14 }

x25PLEIVMO-DTEprotocolErrorsAccusedOf OBJECT-TYPE
    SYNTAX      DummySyntax
    MAX-ACCESS  read-only
    STATUS      current
    DESCRIPTION 
        "Provides a count of the number of protocol errors accused of."
    ::= { x25PLEIVMO-DTEEntry 15 }

x25PLEIVMO-DTEcallEstablishmentRetryCountsExceeded OBJECT-TYPE
    SYNTAX      DummySyntax
    MAX-ACCESS  read-only
    STATUS      current
    DESCRIPTION 
        "Provides a count of the number of call establishment retry 
         counts exceeded."
    ::= { x25PLEIVMO-DTEEntry 16 }

-- dTEX25PLECounters-P conditional package
x25PLEIVMO-DTEoctetsReceivedCounter OBJECT-TYPE
    SYNTAX      Counter32
    MAX-ACCESS  read-only
    STATUS      current
    DESCRIPTION 
        "Provides a count of the number of octets received."
    ::= { x25PLEIVMO-DTEEntry 17 }

x25PLEIVMO-DTEoctetsSentCounter OBJECT-TYPE
    SYNTAX      Counter32
    MAX-ACCESS  read-only
    STATUS      current
    DESCRIPTION 
        "Provides a count of the number of octets sent."
    ::= { x25PLEIVMO-DTEEntry 18 }

x25PLEIVMO-DTEcallTimeouts OBJECT-TYPE
    SYNTAX      Counter32
    MAX-ACCESS  read-only
    STATUS      current
    DESCRIPTION 
        "Provides a count of the number of call timeouts."
    ::= { x25PLEIVMO-DTEEntry 19 }

x25PLEIVMO-DTEcallsConnected OBJECT-TYPE
    SYNTAX      Counter32
    MAX-ACCESS  read-only
    STATUS      current
    DESCRIPTION 
        "Provides a count of the number of calls connected."
    ::= { x25PLEIVMO-DTEEntry 20 }

x25PLEIVMO-DTEclearCountsExceeded OBJECT-TYPE
    SYNTAX      Counter32
    MAX-ACCESS  read-only
    STATUS      current
    DESCRIPTION 
        "Provides a count of the number of clear counts exceeded."
    ::= { x25PLEIVMO-DTEEntry 21 }

x25PLEIVMO-DTEclearTimeouts OBJECT-TYPE
    SYNTAX      Counter32
    MAX-ACCESS  read-only
    STATUS      current
    DESCRIPTION 
        "Provides a count of the number of clear timeouts."
    ::= { x25PLEIVMO-DTEEntry 22 }

x25PLEIVMO-DTEdataPacketsReceived OBJECT-TYPE
    SYNTAX      Counter32
    MAX-ACCESS  read-only
    STATUS      current
    DESCRIPTION 
        "Provides a count of the number of data packets received."
    ::= { x25PLEIVMO-DTEEntry 23 }

x25PLEIVMO-DTEdataPacketsSent OBJECT-TYPE
    SYNTAX      Counter32
    MAX-ACCESS  read-only
    STATUS      current
    DESCRIPTION 
        "Provides a count of the number of data packets sent."
    ::= { x25PLEIVMO-DTEEntry 24 }

x25PLEIVMO-DTEdataRetransmissionTimerExpiries OBJECT-TYPE
    SYNTAX      Counter32
    MAX-ACCESS  read-only
    STATUS      current
    DESCRIPTION 
        "Provides a count of the number of data retransmission timer 
         expiries."
    ::= { x25PLEIVMO-DTEEntry 25 }

x25PLEIVMO-DTEproviderInitiatedResets OBJECT-TYPE
    SYNTAX      Counter32
    MAX-ACCESS  read-only
    STATUS      current
    DESCRIPTION 
        "Provides a count of the number of provider-initiated resets."
    ::= { x25PLEIVMO-DTEEntry 26 }

x25PLEIVMO-DTEproviderInitiatedDisconnects OBJECT-TYPE
    SYNTAX      Counter32
    MAX-ACCESS  read-only
    STATUS      current
    DESCRIPTION 
        "Provides a count of the number of provider-initiated 
         disconnects."
    ::= { x25PLEIVMO-DTEEntry 27 }

x25PLEIVMO-DTEremotelyInitiatedResets OBJECT-TYPE
    SYNTAX      Counter32
    MAX-ACCESS  read-only
    STATUS      current
    DESCRIPTION 
        "Provides a count of the number of remotely-initiated resets."
    ::= { x25PLEIVMO-DTEEntry 28 }

x25PLEIVMO-DTEremotelyInitiatedRestarts OBJECT-TYPE
    SYNTAX      Counter32
    MAX-ACCESS  read-only
    STATUS      current
    DESCRIPTION 
        "Provides a count of the number of remotely-initiated restarts."
    ::= { x25PLEIVMO-DTEEntry 29 }

x25PLEIVMO-DTEresetTimeouts OBJECT-TYPE
    SYNTAX      Counter32
    MAX-ACCESS  read-only
    STATUS      current
    DESCRIPTION 
        "Provides a count of the number of reset timeouts."
    ::= { x25PLEIVMO-DTEEntry 30 }

x25PLEIVMO-DTErestartCountsExceeded OBJECT-TYPE
    SYNTAX      Counter32
    MAX-ACCESS  read-only
    STATUS      current
    DESCRIPTION 
        "Provides a count of the number of restart counts exceeded."
    ::= { x25PLEIVMO-DTEEntry 31 }

-- receivingWindowRotationRecoveryProcedures-P conditional package
x25PLEIVMO-DTEwindowStatusTransmissionTimer OBJECT-TYPE
    SYNTAX      DummySyntax
    MAX-ACCESS  read-only
    STATUS      current
    DESCRIPTION 
        "Provides the window status transmission timer."
    ::= { x25PLEIVMO-DTEEntry 32 }

-- transmittingWindowRotationRecoveryProcedures-P conditional package
x25PLEIVMO-DTEwindowRotationTimer OBJECT-TYPE
    SYNTAX      DummySyntax
    MAX-ACCESS  read-only
    STATUS      current
    DESCRIPTION 
        "Provides the window rotation timer."
    ::= { x25PLEIVMO-DTEEntry 33 }

x25PLEIVMO-DTEdataPacketRetransmissionCount OBJECT-TYPE
    SYNTAX      DummySyntax
    MAX-ACCESS  read-only
    STATUS      current
    DESCRIPTION 
        "Provides the data packet retransmission count."
    ::= { x25PLEIVMO-DTEEntry 34 }

-- packetRetransmissionProcedures-P conditional package
x25PLEIVMO-DTErejectResponseTimer OBJECT-TYPE
    SYNTAX      DummySyntax
    MAX-ACCESS  read-only
    STATUS      current
    DESCRIPTION 
        "Provides the reject response timer."
    ::= { x25PLEIVMO-DTEEntry 35 }

x25PLEIVMO-DTErejectRetransmissionCount OBJECT-TYPE
    SYNTAX      DummySyntax
    MAX-ACCESS  read-only
    STATUS      current
    DESCRIPTION 
        "Provides the reject retransmission count."
    ::= { x25PLEIVMO-DTEEntry 36 }

-- onlineRegistration-P conditional package
x25PLEIVMO-DTEregistrationRequestResponseTimer OBJECT-TYPE
    SYNTAX      DummySyntax
    MAX-ACCESS  read-only
    STATUS      current
    DESCRIPTION 
        "Provides the registration request response timer."
    ::= { x25PLEIVMO-DTEEntry 37 }

x25PLEIVMO-DTEregistrationRequestRetransmissionCount OBJECT-TYPE
    SYNTAX      DummySyntax
    MAX-ACCESS  read-only
    STATUS      current
    DESCRIPTION 
        "Provides the registration request retransmission count."
    ::= { x25PLEIVMO-DTEEntry 38 }

x25PLEIVMO-DTEregistrationPermitted OBJECT-TYPE
    SYNTAX      TruthValue
    MAX-ACCESS  read-only
    STATUS      current
    DESCRIPTION 
        "Specifies registration permitted."
    ::= { x25PLEIVMO-DTEEntry 39 }

--
x25PLEIVMO-DTERowStatus OBJECT-TYPE
    SYNTAX      RowStatus
    MAX-ACCESS  read-create
    STATUS      current
    DESCRIPTION 
        "Provides a mechanism whereby management stations may create and 
         delete rows in this table.  Entries must persist across agent 
         reboots."
    ::= { x25PLEIVMO-DTEEntry 40 }

x25PLEIVMO-DCE OBJECT IDENTIFIER
    ::= { osiTables 45 }

x25PLEIVMO-DCETable OBJECT-TYPE
    SYNTAX      SEQUENCE OF X25PLEIVMO-DCEEntry
    MAX-ACCESS  not-accessible
    STATUS      current
    DESCRIPTION 
        "The X.25 PLE DCE initial values managed object.
         
         There may be multiple instances of the x25PLEIVMO-DCE in a 
         system.  An x25PLEIVMO-DCE may be used to supply initial values 
         for the attributes of the x25PLE-DCE MO.  Different instances 
         of x25PLEIVMO-DCE may contain different initial values.
         
         Its definition permits it to be created and deleted explicitly 
         by management operation."
    REFERENCE   
        "ITU-T Rec. X.283 | ISO/IEC 10733 x25PLEIVMO-DCE MOC."
    ::= { x25PLEIVMO-DCE 1 }

x25PLEIVMO-DCEEntry OBJECT-TYPE
    SYNTAX      X25PLEIVMO-DCEEntry
    MAX-ACCESS  not-accessible
    STATUS      current
    DESCRIPTION 
        "Each row in this table is indexed by the X.25 PLE IVMO 
         identifier defined by this table (which is basically a protocol 
         profile name).  Each row contains initial values to be used 
         when creating X.25 PLE DCE entities (such as when creating rows 
         in the x25PLE-DCETable)."
    REFERENCE   
        "ITU-T Rec. X.283 | ISO/IEC 10733 x25PLEIVMO-DCE MO."
    INDEX       { x25PLEIVMOId }
    ::= { x25PLEIVMO-DCETable 1 }

X25PLEIVMO-DCEEntry ::= SEQUENCE {
    x25PLEIVMO-DCERowStatus     RowStatus
}

x25PLEIVMO-DCERowStatus OBJECT-TYPE
    SYNTAX      RowStatus
    MAX-ACCESS  read-create
    STATUS      current
    DESCRIPTION 
        "Provides a mechanism whereby management stations may create and 
         delete rows in this table.  Entries must persist across agent 
         reboots."
    ::= { x25PLEIVMO-DCEEntry 1 }

virtualCall OBJECT IDENTIFIER
    ::= { osiTables 46 }

virtualCallTable OBJECT-TYPE
    SYNTAX      SEQUENCE OF VirtualCallEntry
    MAX-ACCESS  not-accessible
    STATUS      current
    DESCRIPTION 
        "The Virtual Call Managed Object.  This MO Class is never 
         instantiated. It serves as a generic Virtual Call MO from which 
         both the Switched Virtual Call and the Permanent Virtual 
         Circuit MOs are derived.  Note that the values of the 
         virtualCallId naming attribute are required to be unique 
         accross all instances of MOs derived from this which have a 
         common superior."
    REFERENCE   
        "ISO/IEC 10733 virtualCall MOC."
    ::= { virtualCall 1 }

virtualCallEntry OBJECT-TYPE
    SYNTAX      VirtualCallEntry
    MAX-ACCESS  not-accessible
    STATUS      current
    DESCRIPTION 
        "Each row in this table is indexed by the virtual call 
         identifier defined in this table.  Each row contains 
         characteristics and operational status and measurements 
         associated with the virtual call."
    REFERENCE   
        "ISO/IEC 10733 virtualCall MO."
    INDEX       { virtualCallId }
    ::= { virtualCallTable 1 }

VirtualCallEntry ::= SEQUENCE {
    virtualCallId                               SimpleNameType,
    virtualCallChannel                          DummySyntax,
    virtualCallPacketSize                       DummySyntax,
    virtualCallWindowSize                       DummySyntax,
    virtualCallOctetsSentCounter                DummySyntax,
    virtualCallOctetsReceivedCounter            DummySyntax,
    virtualCallDataPacketsSent                  DummySyntax,
    virtualCallDataPacketsReceived              DummySyntax,
    virtualCallRemotelyInitiatedResets          DummySyntax,
    virtualCallDataRetransmissionTimerExpiries  DummySyntax,
    virtualCallProviderInitiatedResets          DummySyntax,
    virtualCallResetTimeouts                    DummySyntax,
    virtualCallInterruptPacketsSent             DummySyntax,
    virtualCallInterruptPacketsReceived         DummySyntax,
    virtualCallInterruptTimerExpiries           DummySyntax
}

virtualCallId OBJECT-TYPE
    SYNTAX      SimpleNameType
    MAX-ACCESS  not-accessible
    STATUS      current
    DESCRIPTION 
        "Provides a virtual call identifier for use as an index into 
         this table.  The value is of no other significance."
    ::= { virtualCallEntry 1 }

virtualCallChannel OBJECT-TYPE
    SYNTAX      DummySyntax
    MAX-ACCESS  read-only
    STATUS      current
    DESCRIPTION 
        "Identifies the channel on which the call exists."
    ::= { virtualCallEntry 2 }

virtualCallPacketSize OBJECT-TYPE
    SYNTAX      DummySyntax
    MAX-ACCESS  read-only
    STATUS      current
    DESCRIPTION 
        "Indicates the packet size."
    ::= { virtualCallEntry 3 }

virtualCallWindowSize OBJECT-TYPE
    SYNTAX      DummySyntax
    MAX-ACCESS  read-only
    STATUS      current
    DESCRIPTION 
        "Indicates the window size."
    ::= { virtualCallEntry 4 }

virtualCallOctetsSentCounter OBJECT-TYPE
    SYNTAX      DummySyntax
    MAX-ACCESS  read-only
    STATUS      current
    DESCRIPTION 
        "Provides count of the number of octets sent."
    ::= { virtualCallEntry 5 }

virtualCallOctetsReceivedCounter OBJECT-TYPE
    SYNTAX      DummySyntax
    MAX-ACCESS  read-only
    STATUS      current
    DESCRIPTION 
        "Provides a count of the number of octets received."
    ::= { virtualCallEntry 6 }

virtualCallDataPacketsSent OBJECT-TYPE
    SYNTAX      DummySyntax
    MAX-ACCESS  read-only
    STATUS      current
    DESCRIPTION 
        "Provides a count of the number of data packets sent."
    ::= { virtualCallEntry 7 }

virtualCallDataPacketsReceived OBJECT-TYPE
    SYNTAX      DummySyntax
    MAX-ACCESS  read-only
    STATUS      current
    DESCRIPTION 
        "Provides a count of the number of data packets received."
    ::= { virtualCallEntry 8 }

virtualCallRemotelyInitiatedResets OBJECT-TYPE
    SYNTAX      DummySyntax
    MAX-ACCESS  read-only
    STATUS      current
    DESCRIPTION 
        "Provides a count of the number of remotely initiated resets."
    ::= { virtualCallEntry 9 }

virtualCallDataRetransmissionTimerExpiries OBJECT-TYPE
    SYNTAX      DummySyntax
    MAX-ACCESS  read-only
    STATUS      current
    DESCRIPTION 
        "Provides a count of the number of retransmission timer 
         expiries."
    ::= { virtualCallEntry 10 }

virtualCallProviderInitiatedResets OBJECT-TYPE
    SYNTAX      DummySyntax
    MAX-ACCESS  read-only
    STATUS      current
    DESCRIPTION 
        "Provides a count of the number of provider-initiated resets."
    ::= { virtualCallEntry 11 }

virtualCallResetTimeouts OBJECT-TYPE
    SYNTAX      DummySyntax
    MAX-ACCESS  read-only
    STATUS      current
    DESCRIPTION 
        "Provides a count of the number of reset timeouts."
    ::= { virtualCallEntry 12 }

virtualCallInterruptPacketsSent OBJECT-TYPE
    SYNTAX      DummySyntax
    MAX-ACCESS  read-only
    STATUS      current
    DESCRIPTION 
        "Provides a count of the number of interrupt packets sent."
    ::= { virtualCallEntry 13 }

virtualCallInterruptPacketsReceived OBJECT-TYPE
    SYNTAX      DummySyntax
    MAX-ACCESS  read-only
    STATUS      current
    DESCRIPTION 
        "Provides a count of the number of interrupt packets received."
    ::= { virtualCallEntry 14 }

virtualCallInterruptTimerExpiries OBJECT-TYPE
    SYNTAX      DummySyntax
    MAX-ACCESS  read-only
    STATUS      current
    DESCRIPTION 
        "Provides a count of the number of interrupt timer expiries."
    ::= { virtualCallEntry 15 }

virtualCircuit OBJECT IDENTIFIER
    ::= { osiTables 47 }

virtualCircuitTable OBJECT-TYPE
    SYNTAX      SEQUENCE OF VirtualCircuitEntry
    MAX-ACCESS  not-accessible
    STATUS      current
    DESCRIPTION 
        "The virtual managed object.
         
         This MO Class is never instantiated. It serves as a generic 
         Virtual Circuit MO from which both the Virtual Circuit DTE and 
         Virtual Circuit DCE MOs are derived.  Note that the values of 
         the virtualCircuitId naming attribute are required to be unique 
         across all instances of MOs derived from this which have a 
         common superior."
    REFERENCE   
        "ITU-T Rec. X.283 | ISO/IEC 10733 virtualCircuit MOC."
    ::= { virtualCircuit 1 }

virtualCircuitEntry OBJECT-TYPE
    SYNTAX      VirtualCircuitEntry
    MAX-ACCESS  not-accessible
    STATUS      current
    DESCRIPTION 
        "Each row in this table is indexed by the virtual circuit 
         identifier defined in this table.  Each row contains 
         characteristics of the channel."
    REFERENCE   
        "ITU-T Rec. X.283 | ISO/IEC 10733 virtualCircuit MO."
    INDEX       { virtualCircuitId }
    ::= { virtualCircuitTable 1 }

VirtualCircuitEntry ::= SEQUENCE {
    virtualCircuitId                    SimpleNameType,
    virtualCircuitLogicalChannel        DummySyntax,
    virtualCircuitPacketSizes           DummySyntax,
    virtualCircuitThroughputClasses     DummySyntax,
    virtualCircuitWindowSizes           DummySyntax
}

virtualCircuitId OBJECT-TYPE
    SYNTAX      SimpleNameType
    MAX-ACCESS  not-accessible
    STATUS      current
    DESCRIPTION 
        "Provides a circuit identifier as an index into this table. "
    ::= { virtualCircuitEntry 1 }

virtualCircuitLogicalChannel OBJECT-TYPE
    SYNTAX      DummySyntax
    MAX-ACCESS  read-only
    STATUS      current
    DESCRIPTION 
        "provides the logical channel number."
    ::= { virtualCircuitEntry 2 }

virtualCircuitPacketSizes OBJECT-TYPE
    SYNTAX      DummySyntax
    MAX-ACCESS  read-only
    STATUS      current
    DESCRIPTION 
        "Provides the packet sizes."
    ::= { virtualCircuitEntry 3 }

virtualCircuitThroughputClasses OBJECT-TYPE
    SYNTAX      DummySyntax
    MAX-ACCESS  read-only
    STATUS      current
    DESCRIPTION 
        "Provides the throughput classes."
    ::= { virtualCircuitEntry 4 }

virtualCircuitWindowSizes OBJECT-TYPE
    SYNTAX      DummySyntax
    MAX-ACCESS  read-only
    STATUS      current
    DESCRIPTION 
        "Provides the window sizes."
    ::= { virtualCircuitEntry 5 }

virtualCircuit-DTE OBJECT IDENTIFIER
    ::= { osiTables 48 }

virtualCircuit-DTETable OBJECT-TYPE
    SYNTAX      SEQUENCE OF VirtualCircuit-DTEEntry
    MAX-ACCESS  not-accessible
    STATUS      current
    DESCRIPTION 
        "The virtual circuit DTE managed object.
         
         This MO Class is never instantiated. It serves as a generic 
         Virtual Circuit DTE MO from which both the Virtual Call DTE and 
         the Permanent Virtual Circuit DTE MOs are derived.  Note that 
         the values of the virtualCircuitId naming attribute are 
         required to be unique across all instances of MOs derived from 
         this which have a common superior."
    REFERENCE   
        "ITU-T Rec. X.283 | ISO/IEC 10733 virtualCircuit-DTE MOC."
    ::= { virtualCircuit-DTE 1 }

virtualCircuit-DTEEntry OBJECT-TYPE
    SYNTAX      VirtualCircuit-DTEEntry
    MAX-ACCESS  not-accessible
    STATUS      current
    DESCRIPTION 
        "Each row in this table is indexed by virtual circuit 
         identifier.  Each row contains DTE-specific information for 
         virtual circuits."
    REFERENCE   
        "ITU-T Rec. X.283 | ISO/IEC 10733 virtualCircuit-DTE MO."
    INDEX       { virtualCircuitId }
    ::= { virtualCircuit-DTETable 1 }

VirtualCircuit-DTEEntry ::= SEQUENCE {
    virtualCircuit-DTEoctetsSentCounter                 Counter32,
    virtualCircuit-DTEoctetsReceivedCounter             Counter32,
    virtualCircuit-DTEdataPacketsReceived               Counter32,
    virtualCircuit-DTEdataPacketsSent                   Counter32,
    virtualCircuit-DTEdataRetransmissionTimerExpiries   Counter32,
    virtualCircuit-DTEinterruptPacketsReceived          Counter32,
    virtualCircuit-DTEinterruptPacketsSent              Counter32,
    virtualCircuit-DTEinterruptTimerExpiries            Counter32,
    virtualCircuit-DTEproviderInitiatedResets           Counter32,
    virtualCircuit-DTEremotelyInitiatedResets           Counter32,
    virtualCircuit-DTEresetTimeouts                     Counter32
}

virtualCircuit-DTEoctetsSentCounter OBJECT-TYPE
    SYNTAX      Counter32
    MAX-ACCESS  read-only
    STATUS      current
    DESCRIPTION 
        "Provides a count of the number of octets sent."
    ::= { virtualCircuit-DTEEntry 1 }

virtualCircuit-DTEoctetsReceivedCounter OBJECT-TYPE
    SYNTAX      Counter32
    MAX-ACCESS  read-only
    STATUS      current
    DESCRIPTION 
        "Provides a count of the number of octets received."
    ::= { virtualCircuit-DTEEntry 2 }

virtualCircuit-DTEdataPacketsReceived OBJECT-TYPE
    SYNTAX      Counter32
    MAX-ACCESS  read-only
    STATUS      current
    DESCRIPTION 
        "Provides a count of the number of data packets received."
    ::= { virtualCircuit-DTEEntry 3 }

virtualCircuit-DTEdataPacketsSent OBJECT-TYPE
    SYNTAX      Counter32
    MAX-ACCESS  read-only
    STATUS      current
    DESCRIPTION 
        "Provides a count of the number of data packets sent."
    ::= { virtualCircuit-DTEEntry 4 }

virtualCircuit-DTEdataRetransmissionTimerExpiries OBJECT-TYPE
    SYNTAX      Counter32
    MAX-ACCESS  read-only
    STATUS      current
    DESCRIPTION 
        "Provides a count of the number of data retransmission timer 
         expiries."
    ::= { virtualCircuit-DTEEntry 5 }

virtualCircuit-DTEinterruptPacketsReceived OBJECT-TYPE
    SYNTAX      Counter32
    MAX-ACCESS  read-only
    STATUS      current
    DESCRIPTION 
        "Provides ac count of the number of interrupt packets received."
    ::= { virtualCircuit-DTEEntry 6 }

virtualCircuit-DTEinterruptPacketsSent OBJECT-TYPE
    SYNTAX      Counter32
    MAX-ACCESS  read-only
    STATUS      current
    DESCRIPTION 
        "Provides a count of the number of interrupt packets sent."
    ::= { virtualCircuit-DTEEntry 7 }

virtualCircuit-DTEinterruptTimerExpiries OBJECT-TYPE
    SYNTAX      Counter32
    MAX-ACCESS  read-only
    STATUS      current
    DESCRIPTION 
        "Provides a count of the number of interrupt timer expiries."
    ::= { virtualCircuit-DTEEntry 8 }

virtualCircuit-DTEproviderInitiatedResets OBJECT-TYPE
    SYNTAX      Counter32
    MAX-ACCESS  read-only
    STATUS      current
    DESCRIPTION 
        "Provides a count of the number of provider-initiated resets."
    ::= { virtualCircuit-DTEEntry 9 }

virtualCircuit-DTEremotelyInitiatedResets OBJECT-TYPE
    SYNTAX      Counter32
    MAX-ACCESS  read-only
    STATUS      current
    DESCRIPTION 
        "Provides a count of the number of remotely-initiated resets."
    ::= { virtualCircuit-DTEEntry 10 }

virtualCircuit-DTEresetTimeouts OBJECT-TYPE
    SYNTAX      Counter32
    MAX-ACCESS  read-only
    STATUS      current
    DESCRIPTION 
        "Provides a count of the number of reset timeouts."
    ::= { virtualCircuit-DTEEntry 11 }

virtualCircuit-DCE OBJECT IDENTIFIER
    ::= { osiTables 49 }

virtualCircuit-DCETable OBJECT-TYPE
    SYNTAX      SEQUENCE OF VirtualCircuit-DCEEntry
    MAX-ACCESS  not-accessible
    STATUS      current
    DESCRIPTION 
        "The virtual circuit DCE managed object.
         
         This MO class is never instantiated.  It serves as a generic 
         virtual circuit DCE MO from which both the virtual Call DCE and 
         the Permanent Virtual Call DCE MOs are derived.  Note that the 
         values of the virtualCircuitId naming attribute are required to 
         be unique across all instances of MOs derived from this which 
         have a common superior."
    REFERENCE   
        "ITU-T Rec. X.283 | ISO/IEC 10733 virtualCircuit-DCE MOC."
    ::= { virtualCircuit-DCE 1 }

virtualCircuit-DCEEntry OBJECT-TYPE
    SYNTAX      VirtualCircuit-DCEEntry
    MAX-ACCESS  not-accessible
    STATUS      current
    DESCRIPTION 
        "Each row in this table is indexed by virtual circuit 
         identifier.  Each row contains DCE-specific information for 
         virtual circuits.  A row that exists in this table will also 
         exist in the virtual circuit table and either the virtual call 
         DCE table or the permanent virtual circuit DCE table."
    REFERENCE   
        "ITU-T Rec. X.283 | ISO/IEC 10733 virtualCircuit-DCE MO."
    INDEX       { virtualCircuitId }
    ::= { virtualCircuit-DCETable 1 }

VirtualCircuit-DCEEntry ::= SEQUENCE {
    virtualCircuit-DCEdataPacketsReceived           Counter32,
    virtualCircuit-DCEdataPacketsSent               Counter32,
    virtualCircuit-DCEinterruptPacketsReceived      Counter32,
    virtualCircuit-DCEinterruptPacketsSent          Counter32,
    virtualCircuit-DCEinterruptTimerExpiries        Counter32,
    virtualCircuit-DCEoctetsReceivedCounter         Counter32,
    virtualCircuit-DCEoctetsSentCounter             Counter32,
    virtualCircuit-DCEproviderInitiatedDisconnects  Counter32,
    virtualCircuit-DCEproviderInitiatedResets       Counter32,
    virtualCircuit-DCEremotelyInitiatedRestarts     Counter32,
    virtualCircuit-DCEremotelyInitiatedResets       Counter32,
    virtualCircuit-DCEresetTimeouts                 Counter32,
    virtualCircuit-DCEx25SegmentsReceived           Counter32,
    virtualCircuit-DCEx25SegmentsSent               Counter32
}

virtualCircuit-DCEdataPacketsReceived OBJECT-TYPE
    SYNTAX      Counter32
    MAX-ACCESS  read-only
    STATUS      current
    DESCRIPTION 
        "Provides a count of the number of data packets received."
    ::= { virtualCircuit-DCEEntry 1 }

virtualCircuit-DCEdataPacketsSent OBJECT-TYPE
    SYNTAX      Counter32
    MAX-ACCESS  read-only
    STATUS      current
    DESCRIPTION 
        "Provides a count of the number of data packets sent."
    ::= { virtualCircuit-DCEEntry 2 }

virtualCircuit-DCEinterruptPacketsReceived OBJECT-TYPE
    SYNTAX      Counter32
    MAX-ACCESS  read-only
    STATUS      current
    DESCRIPTION 
        "Provides a count of the number of interrupt packets received."
    ::= { virtualCircuit-DCEEntry 3 }

virtualCircuit-DCEinterruptPacketsSent OBJECT-TYPE
    SYNTAX      Counter32
    MAX-ACCESS  read-only
    STATUS      current
    DESCRIPTION 
        "Provides a count of the number of interrupt packets sent."
    ::= { virtualCircuit-DCEEntry 4 }

virtualCircuit-DCEinterruptTimerExpiries OBJECT-TYPE
    SYNTAX      Counter32
    MAX-ACCESS  read-only
    STATUS      current
    DESCRIPTION 
        "Provides a count of the number of interrupt timer expiries."
    ::= { virtualCircuit-DCEEntry 5 }

virtualCircuit-DCEoctetsReceivedCounter OBJECT-TYPE
    SYNTAX      Counter32
    MAX-ACCESS  read-only
    STATUS      current
    DESCRIPTION 
        "Provides a count of the number of octets received."
    ::= { virtualCircuit-DCEEntry 6 }

virtualCircuit-DCEoctetsSentCounter OBJECT-TYPE
    SYNTAX      Counter32
    MAX-ACCESS  read-only
    STATUS      current
    DESCRIPTION 
        "Provides a count of the number of octets sent."
    ::= { virtualCircuit-DCEEntry 7 }

virtualCircuit-DCEproviderInitiatedDisconnects OBJECT-TYPE
    SYNTAX      Counter32
    MAX-ACCESS  read-only
    STATUS      current
    DESCRIPTION 
        "Provides a count of the number of provider-initiated 
         disconnects."
    ::= { virtualCircuit-DCEEntry 8 }

virtualCircuit-DCEproviderInitiatedResets OBJECT-TYPE
    SYNTAX      Counter32
    MAX-ACCESS  read-only
    STATUS      current
    DESCRIPTION 
        "Provides a count of the number of provider-initiated resets."
    ::= { virtualCircuit-DCEEntry 9 }

virtualCircuit-DCEremotelyInitiatedRestarts OBJECT-TYPE
    SYNTAX      Counter32
    MAX-ACCESS  read-only
    STATUS      current
    DESCRIPTION 
        "Provides a count of the number of remotely-initiated restarts."
    ::= { virtualCircuit-DCEEntry 10 }

virtualCircuit-DCEremotelyInitiatedResets OBJECT-TYPE
    SYNTAX      Counter32
    MAX-ACCESS  read-only
    STATUS      current
    DESCRIPTION 
        "Provides a count of the number of remotely-initiated resets."
    ::= { virtualCircuit-DCEEntry 11 }

virtualCircuit-DCEresetTimeouts OBJECT-TYPE
    SYNTAX      Counter32
    MAX-ACCESS  read-only
    STATUS      current
    DESCRIPTION 
        "Provides a count of the number of reset timeouts."
    ::= { virtualCircuit-DCEEntry 12 }

virtualCircuit-DCEx25SegmentsReceived OBJECT-TYPE
    SYNTAX      Counter32
    MAX-ACCESS  read-only
    STATUS      current
    DESCRIPTION 
        "Provides a count of the number of X.25 segments received."
    ::= { virtualCircuit-DCEEntry 13 }

virtualCircuit-DCEx25SegmentsSent OBJECT-TYPE
    SYNTAX      Counter32
    MAX-ACCESS  read-only
    STATUS      current
    DESCRIPTION 
        "Provides a count of the number of X.25 segments sent."
    ::= { virtualCircuit-DCEEntry 14 }

permanentVirtualCircuit OBJECT IDENTIFIER
    ::= { osiTables 50 }

permanentVirtualCircuitTable OBJECT-TYPE
    SYNTAX      SEQUENCE OF PermanentVirtualCircuitEntry
    MAX-ACCESS  not-accessible
    STATUS      current
    DESCRIPTION 
        "The Permanent Virtual Circuit Managed Object.  An instance of 
         this MO exists for each Permanent Virtual Circuit. It may be 
         both created and deleted by management."
    REFERENCE   
        "ISO/IEC 10733 permanentVirtualCircuit MOC."
    ::= { permanentVirtualCircuit 1 }

permanentVirtualCircuitEntry OBJECT-TYPE
    SYNTAX      PermanentVirtualCircuitEntry
    MAX-ACCESS  not-accessible
    STATUS      current
    DESCRIPTION 
        "When the MO is created, the protocol machine shall be 
         reinitialized and a reset PDU shall be transmitted."
    REFERENCE   
        "ISO/IEC 10733 permanentVirtualCircuit MO."
    INDEX       { x25PLEId, virtualCallId }
    ::= { permanentVirtualCircuitTable 1 }

PermanentVirtualCircuitEntry ::= SEQUENCE {
    permanentVirtualCircuitChannel      DummySyntax,
    permanentVirtualCircuitRowStatus    RowStatus
}

permanentVirtualCircuitChannel OBJECT-TYPE
    SYNTAX      DummySyntax
    MAX-ACCESS  read-only
    STATUS      current
    DESCRIPTION 
        "Specifies the logical channel used by the permanent virtual 
         circuit."
    ::= { permanentVirtualCircuitEntry 1 }

permanentVirtualCircuitRowStatus OBJECT-TYPE
    SYNTAX      RowStatus
    MAX-ACCESS  read-create
    STATUS      current
    DESCRIPTION 
        "Provides a mechanism whereby management stations may create and 
         delete rows in this table.  Entries must persist across agent 
         reboots."
    ::= { permanentVirtualCircuitEntry 2 }

permanentVirtualCircuit-DTE OBJECT IDENTIFIER
    ::= { osiTables 51 }

permanentVirtualCircuit-DTETable OBJECT-TYPE
    SYNTAX      SEQUENCE OF PermanentVirtualCircuit-DTEEntry
    MAX-ACCESS  not-accessible
    STATUS      current
    DESCRIPTION 
        "The permanent virtual circuit DTE managed object.
         
         An instance of this MO exists for each Permanent Virtual 
         Circuit.  It may be both created and deleted by management."
    REFERENCE   
        "ITU-T Rec. X.283 | ISO/IEC 10733 permanentVirtualCircuit-DTE 
         MOC."
    ::= { permanentVirtualCircuit-DTE 1 }

permanentVirtualCircuit-DTEEntry OBJECT-TYPE
    SYNTAX      PermanentVirtualCircuit-DTEEntry
    MAX-ACCESS  not-accessible
    STATUS      current
    DESCRIPTION 
        "When the MO is created, the protocol machine shall be 
         reinitialized and a reset PDU with a cause code of DTE 
         originated (encoded as 00000000) and a diagnostic code of DTE 
         operational (161) shall be transmitted. When the MO is deleted, 
         the protocol machine shall be reinitialized and a reset PDU 
         with a cause code of DTE originated (encoded as 00000000) and a 
         diagnostic code of DTE not operational (162) shall be 
         transmitted."
    REFERENCE   
        "ITU-T Rec. X.283 | ISO/IEC 10733 permanentVirtualCircuit-DTE 
         MO."
    INDEX       { x25PLEId, virtualCircuitId }
    ::= { permanentVirtualCircuit-DTETable 1 }

PermanentVirtualCircuit-DTEEntry ::= SEQUENCE {
    permanentVirtualCircuit-DTElogicalChannel       DummySyntax,
    permanentVirtualCircuit-DTEpacketSizes          DummySyntax,
    permanentVirtualCircuit-DTEthroughputClasses    DummySyntax,
    permanentVirtualCircuit-DTEwindowSizes          DummySyntax,
    permanentVirtualCircuit-DTERowStatus            RowStatus
}

permanentVirtualCircuit-DTElogicalChannel OBJECT-TYPE
    SYNTAX      DummySyntax
    MAX-ACCESS  read-only
    STATUS      current
    DESCRIPTION 
        "Provides the logical channel of the DTE PVC."
    ::= { permanentVirtualCircuit-DTEEntry 1 }

permanentVirtualCircuit-DTEpacketSizes OBJECT-TYPE
    SYNTAX      DummySyntax
    MAX-ACCESS  read-only
    STATUS      current
    DESCRIPTION 
        "Provides the packet sizes."
    ::= { permanentVirtualCircuit-DTEEntry 2 }

permanentVirtualCircuit-DTEthroughputClasses OBJECT-TYPE
    SYNTAX      DummySyntax
    MAX-ACCESS  read-only
    STATUS      current
    DESCRIPTION 
        "Provides the throughput classes."
    ::= { permanentVirtualCircuit-DTEEntry 3 }

permanentVirtualCircuit-DTEwindowSizes OBJECT-TYPE
    SYNTAX      DummySyntax
    MAX-ACCESS  read-only
    STATUS      current
    DESCRIPTION 
        "Provides the window sizes."
    ::= { permanentVirtualCircuit-DTEEntry 4 }

permanentVirtualCircuit-DTERowStatus OBJECT-TYPE
    SYNTAX      RowStatus
    MAX-ACCESS  read-create
    STATUS      current
    DESCRIPTION 
        "Provides a mechanism whereby management stations may create and 
         delete row in this table.  Entries must persist across agent 
         reboots."
    ::= { permanentVirtualCircuit-DTEEntry 5 }

permanentVirtualCircuit-DCE OBJECT IDENTIFIER
    ::= { osiTables 52 }

permanentVirtualCircuit-DCETable OBJECT-TYPE
    SYNTAX      SEQUENCE OF PermanentVirtualCircuit-DCEEntry
    MAX-ACCESS  not-accessible
    STATUS      current
    DESCRIPTION 
        "The permanent virtual circuit DCE managed object.
         
         An instance of this MO exists for each Permanent Virtual 
         Circuit. It may be both created and deleted by management."
    REFERENCE   
        "ITU-T Rec. X.283 | ISO/IEC 10733 permanentVirtualCircuit-DCE 
         MOC."
    ::= { permanentVirtualCircuit-DCE 1 }

permanentVirtualCircuit-DCEEntry OBJECT-TYPE
    SYNTAX      PermanentVirtualCircuit-DCEEntry
    MAX-ACCESS  not-accessible
    STATUS      current
    DESCRIPTION 
        "When the MO is created, the protocol machine shall be 
         re-initialized and a reset PDU shall be transmitted. A cause 
         code of remote DTE Operational (encoded as X000 1001) or 
         Network Operational (encoded as X000 1111) may, for example, be 
         included. When the MO is deleted the protocol machine shall be 
         reinitialized and a reset PDU shall be transmitted. A cause 
         code of Out of Order (encoded as X000 0001) or Network Out of 
         Order (encoded as X001 1101) may, for example, be included."
    REFERENCE   
        "ITU-T Rec. X.283 | ISO/IEC 10733 permanentVirtualCircuit-DCE MO."
    INDEX       { x25PLEId, virtualCircuitId }
    ::= { permanentVirtualCircuit-DCETable 1 }

PermanentVirtualCircuit-DCEEntry ::= SEQUENCE {
    permanentVirtualCircuit-DCEchargingDirection        DummySyntax,
    permanentVirtualCircuit-DCElogicalChannel           DummySyntax,
    permanentVirtualCircuit-DCEpacketSizes              DummySyntax,
    permanentVirtualCircuit-DCEthroughputClasses        DummySyntax,
    permanentVirtualCircuit-DCEwindowSizes              DummySyntax,
    permanentVirtualCircuit-DCEoperationalState         OperationalState,
    permanentVirtualCircuit-DCEremoteDTEAddress         DTEAddress,
    permanentVirtualCircuit-DCEremoteLogicalChannel     DummySyntax,
    permanentVirtualCircuit-DCERowStatus                RowStatus
}

permanentVirtualCircuit-DCEchargingDirection OBJECT-TYPE
    SYNTAX      DummySyntax
    MAX-ACCESS  read-only
    STATUS      current
    DESCRIPTION 
        "Provides the charging direction."
    ::= { permanentVirtualCircuit-DCEEntry 1 }

permanentVirtualCircuit-DCElogicalChannel OBJECT-TYPE
    SYNTAX      DummySyntax
    MAX-ACCESS  read-only
    STATUS      current
    DESCRIPTION 
        "Provides the logical channel for the DCE PVC."
    ::= { permanentVirtualCircuit-DCEEntry 2 }

permanentVirtualCircuit-DCEpacketSizes OBJECT-TYPE
    SYNTAX      DummySyntax
    MAX-ACCESS  read-only
    STATUS      current
    DESCRIPTION 
        "Provides the packet sizes."
    ::= { permanentVirtualCircuit-DCEEntry 3 }

permanentVirtualCircuit-DCEthroughputClasses OBJECT-TYPE
    SYNTAX      DummySyntax
    MAX-ACCESS  read-only
    STATUS      current
    DESCRIPTION 
        "Provides the throughput classes."
    ::= { permanentVirtualCircuit-DCEEntry 4 }

permanentVirtualCircuit-DCEwindowSizes OBJECT-TYPE
    SYNTAX      DummySyntax
    MAX-ACCESS  read-only
    STATUS      current
    DESCRIPTION 
        "Provides the window sizes."
    ::= { permanentVirtualCircuit-DCEEntry 5 }

permanentVirtualCircuit-DCEoperationalState OBJECT-TYPE
    SYNTAX      OperationalState
    MAX-ACCESS  read-only
    STATUS      current
    DESCRIPTION 
        "Provides the operational state of the PVC in accordance with 
         the OperationalState textual convention and X.721."
    ::= { permanentVirtualCircuit-DCEEntry 6 }

permanentVirtualCircuit-DCEremoteDTEAddress OBJECT-TYPE
    SYNTAX      DTEAddress
    MAX-ACCESS  read-only
    STATUS      current
    DESCRIPTION 
        "Provides the remote DTE address."
    ::= { permanentVirtualCircuit-DCEEntry 7 }

permanentVirtualCircuit-DCEremoteLogicalChannel OBJECT-TYPE
    SYNTAX      DummySyntax
    MAX-ACCESS  read-only
    STATUS      current
    DESCRIPTION 
        "Provides the remote logical channel."
    ::= { permanentVirtualCircuit-DCEEntry 8 }

permanentVirtualCircuit-DCERowStatus OBJECT-TYPE
    SYNTAX      RowStatus
    MAX-ACCESS  read-create
    STATUS      current
    DESCRIPTION 
        "Provides a mechanism whereby management stations may create and 
         delete rows in this table.  Entries must persist across agent 
         reboots."
    ::= { permanentVirtualCircuit-DCEEntry 9 }

virtualCallIVMO OBJECT IDENTIFIER
    ::= { osiTables 53 }

virtualCallIVMOTable OBJECT-TYPE
    SYNTAX      SEQUENCE OF VirtualCallIVMOEntry
    MAX-ACCESS  not-accessible
    STATUS      current
    DESCRIPTION 
        "The virtual call initial values managed object.
         
         There may be multiple instances of the virtualCallIVMO in a 
         system.  A virtualCallIVMO may be used to supply initial values 
         for the attributes of the virtualCall-DTE or virtualCall-DCE 
         MO.  Different instances of virtualCallIVMO may contain 
         different initial values.
         
         Its definition permits it to be created and deleted explicitly 
         by management operation."
    REFERENCE   
        "ITU-T Rec. X.283 | ISO/IEC 10733 virtualCallIVMO MOC."
    ::= { virtualCallIVMO 1 }

virtualCallIVMOEntry OBJECT-TYPE
    SYNTAX      VirtualCallIVMOEntry
    MAX-ACCESS  not-accessible
    STATUS      current
    DESCRIPTION 
        "Each row in this table is indexed by virtual call IVMO 
         identifier (which is basically a protocol profile name).  Each 
         row contains initial values for the creation of virtual calls 
         (e.g. rows in the virtualCallTable)."
    REFERENCE   
        "ITU-T Rec. X.283 | ISO/IEC 10733 virtualCallIVMO MO."
    INDEX       { x25PLEId, virtualCallIVMOId }
    ::= { virtualCallIVMOTable 1 }

VirtualCallIVMOEntry ::= SEQUENCE {
    virtualCallIVMOId                       SimpleNameType,
    virtualCallIVMOfastSelect               FastSelect,
    virtualCallIVMOpacketSizes              DummySyntax,
    virtualCallIVMOreverseCharging          TruthValue,
    virtualCallIVMOthroughputClasses        DummySyntax,
    virtualCallIVMOwindowSizes              DummySyntax,
    virtualCallIVMOproposedPacketSize       Integer32,
    virtualCallIVMOproposedWindowSize       Integer32,
    virtualCallIVMOacceptReverseCharging    TruthValue,
    virtualCallIVMOproposeReverseCharging   TruthValue,
    virtualCallIVMOcallTime                 TimeInterval,
    virtualCallIVMOresetTime                TimeInterval,
    virtualCallIVMOclearTime                TimeInterval,
    virtualCallIVMOinterruptTime            TimeInterval,
    virtualCallIVMOresetCount               Integer32,
    virtualCallIVMOclearCount               Integer32,
    virtualCallIVMOwindowTime               TimeInterval,
    virtualCallIVMOdataRetransmissionTime   TimeInterval,
    virtualCallIVMOdataRetransmissionCount  Integer32,
    virtualCallIVMOrejectTime               TimeInterval,
    virtualCallIVMOrejectCount              Integer32,
    virtualCallIVMORowStatus                RowStatus
}

virtualCallIVMOId OBJECT-TYPE
    SYNTAX      SimpleNameType
    MAX-ACCESS  not-accessible
    STATUS      current
    DESCRIPTION 
        "Provides a simple name for use as an index in this table.  The 
         value of the name has no other significance and can be chosen 
         at the convenience of the manager."
    ::= { virtualCallIVMOEntry 1 }

-- X.283 or ISO 10733
virtualCallIVMOfastSelect OBJECT-TYPE
    SYNTAX      FastSelect
    MAX-ACCESS  read-only
    STATUS      current
    DESCRIPTION 
        "Type of fast select used or to be used for call.  In the case 
         of an IVMO, this specifies that one of 'fast select', 'fast 
         select with restricted response', or 'no fast select' facility 
         is to be used for the call.  It includes a value 'not 
         specified' which indicates that no preference is expressed in 
         the IVMO.  In the case of non-IVMO MO, this specifies that one 
         of 'fast select' or 'no fast select' was used for the call."
    REFERENCE   
        "ITU-T Rec. X.283 | ISO/IEC 10733 fastSelect ATTRIBUTE."
    ::= { virtualCallIVMOEntry 2 }

-- X.283 only
virtualCallIVMOpacketSizes OBJECT-TYPE
    SYNTAX      DummySyntax
    MAX-ACCESS  read-only
    STATUS      current
    DESCRIPTION 
        "The packet sizes for this VC. In the case of an IVMO MO it is 
         the proposed value of the packet sizes (incoming and outgoing) 
         to be used when establishing the virtual call, expressed in 
         octets. The value of NULL indicates that the default packet 
         size for that direction (as indicated by the defaultPacketSizes 
         attribute of the containing X.25 PLE MO), is to be used. In the 
         case of a non-IVMO MO it is the actual packet sizes in use for 
         this VC."
    REFERENCE   
        "ITU-T Rec. X.283 | ISO/IEC 10733 packetSizes ATTRIBUTE."
    ::= { virtualCallIVMOEntry 3 }

virtualCallIVMOreverseCharging OBJECT-TYPE
    SYNTAX      TruthValue
    MAX-ACCESS  read-create
    STATUS      current
    DESCRIPTION 
        "Use of reverse charging. When 'True' for an outgoing call, it 
         shall be (for an IVMO), or was (for a non-IVMO), initiated 
         requesting reverse charging. When 'True' for an incoming call 
         associated with a virtualCall MO, it indicates that reverse 
         charging was accepted."
    REFERENCE   
        "ITU-T Rec. X.283 | ISO/IEC 10733 reverseCharging ATTRIBUTE."
    ::= { virtualCallIVMOEntry 4 }

virtualCallIVMOthroughputClasses OBJECT-TYPE
    SYNTAX      DummySyntax
    MAX-ACCESS  read-only
    STATUS      current
    DESCRIPTION 
        "Provides throughput classes."
    ::= { virtualCallIVMOEntry 5 }

virtualCallIVMOwindowSizes OBJECT-TYPE
    SYNTAX      DummySyntax
    MAX-ACCESS  read-only
    STATUS      current
    DESCRIPTION 
        "Provides window sizes."
    ::= { virtualCallIVMOEntry 6 }

-- ISO 10733 only
virtualCallIVMOproposedPacketSize OBJECT-TYPE
    SYNTAX      Integer32
    MAX-ACCESS  read-only
    STATUS      current
    DESCRIPTION 
        "The proposed value of the packet size parameter to be used when 
         establishing the virtual call, expressed in octets. The value 
         of NULL (zero) indicates that the default packet size (as 
         indicated by the defaultPacketSize attribute of the containing 
         X.25 PLE MO), is to be used."
    REFERENCE   
        "ISO/IEC 10733 proposedPacketSize ATTRIBUTE."
    ::= { virtualCallIVMOEntry 7 }

virtualCallIVMOproposedWindowSize OBJECT-TYPE
    SYNTAX      Integer32
    MAX-ACCESS  read-only
    STATUS      current
    DESCRIPTION 
        "The proposed value of the window size parameter to be used when 
         establishing the virtual call.  The value of NULL (zero) 
         indicates that the default window size (as indicated by the 
         defaultWindowSize attribute of the containing X.25 PLE MO), is 
         to be used."
    REFERENCE   
        "ISO/IEC 10733 proposedWindowSize ATTRIBUTE."
    ::= { virtualCallIVMOEntry 8 }

virtualCallIVMOacceptReverseCharging OBJECT-TYPE
    SYNTAX      TruthValue
    MAX-ACCESS  read-only
    STATUS      current
    DESCRIPTION 
        "When `False' an incoming call requesting reverse charging shall 
         not be accepted."
    REFERENCE   
        "ISO/IEC 10733: acceptReverseCharging ATTRIBUTE."
    ::= { virtualCallIVMOEntry 9 }

virtualCallIVMOproposeReverseCharging OBJECT-TYPE
    SYNTAX      TruthValue
    MAX-ACCESS  read-only
    STATUS      current
    DESCRIPTION 
        "Specifies whether to propose reverse charging on outgoing 
         calls.  When true(1), an outgoing call shall be initiated 
         requesting reverse charging; false(2), reverse charging will 
         not be requested."
    REFERENCE   
        "ISO/IEC 10733: proposeReverseCharging ATTRIBUTE."
    ::= { virtualCallIVMOEntry 10 }

virtualCallIVMOcallTime OBJECT-TYPE
    SYNTAX      TimeInterval
    UNITS       "seconds"
    MAX-ACCESS  read-only
    STATUS      current
    DESCRIPTION 
        "Value for Timer T21 (Call Request Response Timer) in seconds.  
         The default value from ISO/IEC 10733 is 20 seconds."
    REFERENCE   
        "ISO/IEC 10733: callTime ATTRIBUTE."
    DEFVAL      { 20000 }
    ::= { virtualCallIVMOEntry 11 }

virtualCallIVMOresetTime OBJECT-TYPE
    SYNTAX      TimeInterval
    UNITS       "seconds"
    MAX-ACCESS  read-only
    STATUS      current
    DESCRIPTION 
        "Value for Timer T22 (Reset Request Response Timer) in seconds.  
         The default value from ISO/IEC 10733 is 180 seconds."
    REFERENCE   
        "ISO/IEC 10733: resetTime ATTRIBUTE."
    DEFVAL      { 18000 }
    ::= { virtualCallIVMOEntry 12 }

virtualCallIVMOclearTime OBJECT-TYPE
    SYNTAX      TimeInterval
    UNITS       "seconds"
    MAX-ACCESS  read-only
    STATUS      current
    DESCRIPTION 
        "Value for Timer T23 (Clear Request Response Timer) in seconds.  
         The default value from ISO/IEC 10733 is 180 seconds."
    REFERENCE   
        "ISO/IEC 10733: clearTime ATTRIBUTE."
    DEFVAL      { 18000 }
    ::= { virtualCallIVMOEntry 13 }

virtualCallIVMOinterruptTime OBJECT-TYPE
    SYNTAX      TimeInterval
    UNITS       "seconds"
    MAX-ACCESS  read-only
    STATUS      current
    DESCRIPTION 
        "Value for Timer T26 (Interrupt Response Timer) in seconds.  The 
         default value from ISO/IEC 10733 is 180 seconds."
    REFERENCE   
        "ISO/IEC 10733: interruptTime ATTRIBUTE."
    DEFVAL      { 18000 }
    ::= { virtualCallIVMOEntry 14 }

virtualCallIVMOresetCount OBJECT-TYPE
    SYNTAX      Integer32
    UNITS       "reset request retransmissions"
    MAX-ACCESS  read-only
    STATUS      current
    DESCRIPTION 
        "Value for count R22 (Reset Request Retransmission Count).  The 
         default value from ISO/IEC 10733 is 1."
    REFERENCE   
        "ISO/IEC 10733: resetCount ATTRIBUTE."
    DEFVAL      { 1 }
    ::= { virtualCallIVMOEntry 15 }

virtualCallIVMOclearCount OBJECT-TYPE
    SYNTAX      Integer32
    MAX-ACCESS  read-only
    STATUS      current
    DESCRIPTION 
        "Value for count R23 (Clear Request Retransmission Count).  The 
         default value from ISO/IEC 10733 is 1."
    REFERENCE   
        "ISO/IEC 10733: clearCount ATTRIBUTE."
    DEFVAL      { 1 }
    ::= { virtualCallIVMOEntry 16 }

-- ISO 10733 only receivingWindowRotationRecoveryProcedures-P 
-- conditional package
--      Controls the operation of the optional window rotation recovery 
--      procedures at a receiving DTE as described in Clause 11.2.2 of 
--      ISO 8208 (2nd Edition).
virtualCallIVMOwindowTime OBJECT-TYPE
    SYNTAX      TimeInterval
    UNITS       "seconds"
    MAX-ACCESS  read-only
    STATUS      current
    DESCRIPTION 
        "Value for Timer T24 (Window Status Transmission Timer) in 
         seconds.  The default value from ISO/IEC 10733 is 60 seconds."
    REFERENCE   
        "ISO/IEC 10733: windowTime ATTRIBUTE."
    DEFVAL      { 6000 }
    ::= { virtualCallIVMOEntry 17 }

-- ISO 10733 only transmittingWindowRotationRecoveryProcedures-P 
-- conditional package
--      Controls the operation of the optional window rotation recovery 
--      procedures at a transmitting DTE as described in Clause 11.2.1 
--      of ISO 8208 (2nd Edition).
virtualCallIVMOdataRetransmissionTime OBJECT-TYPE
    SYNTAX      TimeInterval
    MAX-ACCESS  read-only
    STATUS      current
    DESCRIPTION 
        "Default for Timer T25 (Window Rotation Timer) in seconds.  The 
         default value from ISO/IEC 10733 is 200 seconds."
    REFERENCE   
        "ISO/IEC 10733: dataRetransmissionTime ATTRIBUTE."
    DEFVAL      { 20000 }
    ::= { virtualCallIVMOEntry 18 }

virtualCallIVMOdataRetransmissionCount OBJECT-TYPE
    SYNTAX      Integer32
    MAX-ACCESS  read-only
    STATUS      current
    DESCRIPTION 
        "Value for count R25 (Data Packet Retransmission Count).  The 
         default value from ISO/IEC 10733 is zero (0)."
    REFERENCE   
        "ISO/IEC 10733: dataRetransmissionCount ATTRIBUTE."
    DEFVAL      { 0 }
    ::= { virtualCallIVMOEntry 19 }

-- ISO 10733 only packetRetransmissionProcedures-P conditional package
--      Controls the operation of the optional packet retransmission 
--      procedures as described in Clause 13.4 of ISO 8208 (2nd 
--      Edition).
virtualCallIVMOrejectTime OBJECT-TYPE
    SYNTAX      TimeInterval
    UNITS       "seconds"
    MAX-ACCESS  read-only
    STATUS      current
    DESCRIPTION 
        "Value for Timer T27 (Reject Response Timer) in seconds.  The 
         default value from ISO/IEC 10733 is 60 seconds."
    REFERENCE   
        "ISO/IEC 10733: rejectTime ATTRIBUTE."
    DEFVAL      { 6000 }
    ::= { virtualCallIVMOEntry 20 }

virtualCallIVMOrejectCount OBJECT-TYPE
    SYNTAX      Integer32
    MAX-ACCESS  read-only
    STATUS      current
    DESCRIPTION 
        "Value for count R27 (Reject Retransmission Count).  The default 
         value from ISO/IEC 10733 is zero (0)."
    REFERENCE   
        "ISO/IEC 10733: rejectCount ATTRIBUTE."
    DEFVAL      { 0 }
    ::= { virtualCallIVMOEntry 21 }

-- both
virtualCallIVMORowStatus OBJECT-TYPE
    SYNTAX      RowStatus
    MAX-ACCESS  read-create
    STATUS      current
    DESCRIPTION 
        "Provides a mechanism whereby management stations may create and 
         delete rows in this table.  Entries must persist across agent 
         reboot."
    ::= { virtualCallIVMOEntry 22 }

switchedVirtualCall OBJECT IDENTIFIER
    ::= { osiTables 54 }

switchedVirtualCallTable OBJECT-TYPE
    SYNTAX      SEQUENCE OF SwitchedVirtualCallEntry
    MAX-ACCESS  not-accessible
    STATUS      current
    DESCRIPTION 
        "The Switched Virtual Call Managed Object.
         
         An instance of this MO exists for each Virtual Call. It is not 
         created by management, but by the operation of the protocol 
         state machine.  An existing instance may, however, be deleted 
         by management action, which will cause the associated VC to be 
         cleared.
         
         An instance of this MO is created and exists as long as real 
         resources are consumed by the existence of the virtual call.  
         It is an implementation matter to determine the point during 
         call establishement when reall resources are consumed, and 
         conversly, when during call clearing, when they are released."
    REFERENCE   
        "ISO/IEC 10733 switchedVirtualCall MOC."
    ::= { switchedVirtualCall 1 }

switchedVirtualCallEntry OBJECT-TYPE
    SYNTAX      SwitchedVirtualCallEntry
    MAX-ACCESS  not-accessible
    STATUS      current
    DESCRIPTION 
        "Each row in this table is indexed by X.25 packet-layer entity 
         and virtual call identifiers.  Each row contains 
         characteristics and operational status of a switched virtual 
         call."
    REFERENCE   
        "ISO/IEC 10733 switchedVirtualCall MO."
    INDEX       { x25PLEId, virtualCallId }
    ::= { switchedVirtualCallTable 1 }

SwitchedVirtualCallEntry ::= SEQUENCE {
    switchedVirtualCalldirection                INTEGER,
    switchedVirtualCallremoteDTEAddress         DTEAddress,
    switchedVirtualCallthroughputClass          Integer32,
    switchedVirtualCallredirectReason           Integer32,
    switchedVirtualCalloriginallyCalledAddress  DTEAddress,
    switchedVirtualCallcallingAddressExtension  NAddress,
    switchedVirtualCallcalledAddressExtension   NAddress,
    switchedVirtualCallRowStatus                RowStatus
}

switchedVirtualCalldirection OBJECT-TYPE
    SYNTAX      INTEGER { incoming(0), outgoing(1) }
    MAX-ACCESS  read-only
    STATUS      current
    DESCRIPTION 
        "The direction (incoming or outgoing) of the call."
    REFERENCE   
        "ISO/IEC 10733 direction ATTRIBUTE."
    ::= { switchedVirtualCallEntry 1 }

switchedVirtualCallremoteDTEAddress OBJECT-TYPE
    SYNTAX      DTEAddress
    MAX-ACCESS  read-only
    STATUS      current
    DESCRIPTION 
        "The DTE Address of the remote DTE. In the case of an outgoing 
         call, this is the remote DTE address from the called address of 
         the transmitted call request packet. In the case of an incoming 
         call, it is the calling address from the received call request 
         packet."
    REFERENCE   
        "ISO/IEC 10733 remoteDTEAddress ATTRIBUTE."
    ::= { switchedVirtualCallEntry 2 }

switchedVirtualCallthroughputClass OBJECT-TYPE
    SYNTAX      Integer32 (0..15)
    MAX-ACCESS  read-only
    STATUS      current
    DESCRIPTION 
        "The actual throughput class in use for the call. For SVCs this 
         is the result of negotiation."
    REFERENCE   
        "ISO/IEC 10733 throughputClass ATTRIBUTE."
    ::= { switchedVirtualCallEntry 3 }

switchedVirtualCallredirectReason OBJECT-TYPE
    SYNTAX      Integer32 (0..127)
    MAX-ACCESS  read-only
    STATUS      current
    DESCRIPTION 
        "The reason for call redirect. The zero value indicates that the 
         call was not redirected."
    REFERENCE   
        "ISO/IEC 10733 redirectReason ATTRIBUTE."
    ::= { switchedVirtualCallEntry 4 }

switchedVirtualCalloriginallyCalledAddress OBJECT-TYPE
    SYNTAX      DTEAddress
    MAX-ACCESS  read-only
    STATUS      current
    DESCRIPTION 
        "The originally called address."
    REFERENCE   
        "ISO/IEC 10733 originallyCalledAddress ATTRIBUTE."
    ::= { switchedVirtualCallEntry 5 }

switchedVirtualCallcallingAddressExtension OBJECT-TYPE
    SYNTAX      NAddress
    MAX-ACCESS  read-only
    STATUS      current
    DESCRIPTION 
        "The contents of the calling address extension field.  In the 
         OSI context this will always be an NSAP address but in other 
         uses it may not.  In any case it may be null, for example when 
         used by ISO 8473."
    REFERENCE   
        "ISO/IEC 10733 callingAddressExtension ATTRIBUTE."
    ::= { switchedVirtualCallEntry 6 }

switchedVirtualCallcalledAddressExtension OBJECT-TYPE
    SYNTAX      NAddress
    MAX-ACCESS  read-only
    STATUS      current
    DESCRIPTION 
        "The contents of the called address extension field.  In the OSI 
         context this will always be an NSAP address but in other uses 
         it may not.  In any case it may be null, for example when used 
         by ISO 8473."
    REFERENCE   
        "ISO/IEC 10733 calledAddressExtension ATTRIBUTE."
    ::= { switchedVirtualCallEntry 7 }

-- sVCMO-x25PLE name binding
switchedVirtualCallRowStatus OBJECT-TYPE
    SYNTAX      RowStatus
    MAX-ACCESS  read-create
    STATUS      current
    DESCRIPTION 
        "Provides a mechanism whereby management stations may create and 
         delete rows in this table.  Entries must persist across agent 
         reboot."
    REFERENCE   
        "ISO/IEC 10733 SVCMO-x25PLE NAME-BINDING."
    ::= { switchedVirtualCallEntry 8 }

virtualCall-DTE OBJECT IDENTIFIER
    ::= { osiTables 55 }

virtualCall-DTETable OBJECT-TYPE
    SYNTAX      SEQUENCE OF VirtualCall-DTEEntry
    MAX-ACCESS  not-accessible
    STATUS      current
    DESCRIPTION 
        "The virtual call DTE managed object.
         
         An instance of this MO exists for each Virtual Call. It is not 
         created by management, but by the operation of the protocol 
         state machine.  An existing instance may, however, be 
         deactivated by management action, which will cause the 
         associated VC to be cleared.
         
         An instance of this MO is created and exists as long as real 
         resources are consumed by the existence of the virtual call. It 
         is an implementation matter to determine the point during call 
         establishment when real resources are consumed, and conversely, 
         when during call clearing, when they are released."
    REFERENCE   
        "ITU-T Rec. X.283 | ISO/IEC 10733 virtualCall-DTE MOC."
    ::= { virtualCall-DTE 1 }

virtualCall-DTEEntry OBJECT-TYPE
    SYNTAX      VirtualCall-DTEEntry
    MAX-ACCESS  not-accessible
    STATUS      current
    DESCRIPTION 
        "Each row in this table is indexed by X.25 PLE and virtual 
         circuit identifiers.  Each row contains information concerning 
         a DTE virtual call."
    REFERENCE   
        "ITU-T Rec. X.283 | ISO/IEC 10733 virtualCall-DTE MO."
    INDEX       { x25PLEId, virtualCircuitId }
    ::= { virtualCall-DTETable 1 }

VirtualCall-DTEEntry ::= SEQUENCE {
    virtualCall-DTEcallingAddressExtension  NAddress,
    virtualCall-DTEcalledAddressExtension   NAddress,
    virtualCall-DTEdirection                INTEGER,
    virtualCall-DTEfastSelect               FastSelect,
    virtualCall-DTEoriginallyCalledAddress  DTEAddress,
    virtualCall-DTEredirectReason           Integer32,
    virtualCall-DTEremoteDTEAddress         DTEAddress,
    virtualCall-DTEreverseCharging          TruthValue,
    virtualCall-DTERowStatus                RowStatus
}

virtualCall-DTEcallingAddressExtension OBJECT-TYPE
    SYNTAX      NAddress
    MAX-ACCESS  read-only
    STATUS      current
    DESCRIPTION 
        "The contents of the calling address extension field.  In the 
         OSI context this will always be an NSAP address but in other 
         uses it may not. In any case it may be null, for example, when 
         used by ITU-T Rec. X.233 | ISO/IEC 8473-1."
    REFERENCE   
        "ITU-T Rec. X.283: callingAddressExtension ATTRIBUTE."
    ::= { virtualCall-DTEEntry 1 }

virtualCall-DTEcalledAddressExtension OBJECT-TYPE
    SYNTAX      NAddress
    MAX-ACCESS  read-only
    STATUS      current
    DESCRIPTION 
        "The contents of the called address extension field.  In the OSI 
         context this will always be an NSAP address but in other uses 
         it may not. In any case it may be null, for example, when used 
         by ITU-T Rec. X.233 | ISO/IEC 8473-1."
    REFERENCE   
        "ITU-T Rec. X.283: calledAddressExtension ATTRIBUTE."
    ::= { virtualCall-DTEEntry 2 }

virtualCall-DTEdirection OBJECT-TYPE
    SYNTAX      INTEGER { incoming(0), outgoing(1) }
    MAX-ACCESS  read-only
    STATUS      current
    DESCRIPTION 
        "The direction (incoming or outgoing) of the call."
    REFERENCE   
        "ITU-T Rec. X.283: direction ATTRIBUTE."
    ::= { virtualCall-DTEEntry 3 }

virtualCall-DTEfastSelect OBJECT-TYPE
    SYNTAX      FastSelect
    MAX-ACCESS  read-only
    STATUS      current
    DESCRIPTION 
        "Type of fast select used or to be used for call. In the case of 
         an IVMO, this specifies that one of 'fast select', 'fast select 
         with restricted response', or no fast select facility is to be 
         used for the call. It includes a value 'not specified' which 
         indicates that no preference is expressed in the IVMO. In the 
         case of a non-IVMO MO, this specifies that one of 'fast select' 
         or 'no fast select' was used for the call."
    REFERENCE   
        "ITU-T Rec. X.283: fastSelect ATTRIBUTE."
    ::= { virtualCall-DTEEntry 4 }

virtualCall-DTEoriginallyCalledAddress OBJECT-TYPE
    SYNTAX      DTEAddress
    MAX-ACCESS  read-only
    STATUS      current
    DESCRIPTION 
        "The originally called address."
    REFERENCE   
        "ITU-T Rec. X.283: originallyCalledAddress ATTRIBUTE."
    ::= { virtualCall-DTEEntry 5 }

virtualCall-DTEredirectReason OBJECT-TYPE
    SYNTAX      Integer32 (0..127)
    MAX-ACCESS  read-only
    STATUS      current
    DESCRIPTION 
        "The reason why the call has been redirected. This is the reason 
         why the call has been offered or has been connected to an 
         address different from the originally called address. That is, 
         the value of the first octet of the Facility Parameter Field of 
         the CRCDN or CLAMN facility, indicating the reason for call 
         redirection or call deflection. The zero value indicates that 
         the call was not redirected."
    REFERENCE   
        "ITU-T Rec. X.283: redirectReason ATTRIBUTE."
    ::= { virtualCall-DTEEntry 6 }

virtualCall-DTEremoteDTEAddress OBJECT-TYPE
    SYNTAX      DTEAddress
    MAX-ACCESS  read-only
    STATUS      current
    DESCRIPTION 
        "The DTE Address of the remote DTE. In the case of an outgoing 
         call, this is the remote DTE address from the called address of 
         the transmitted call request packet. In the case of an incoming 
         call, it is the calling address from the received call request 
         packet."
    REFERENCE   
        "ITU-T Rec. X.283: remoteDTEAddress ATTRIBUTE."
    ::= { virtualCall-DTEEntry 7 }

virtualCall-DTEreverseCharging OBJECT-TYPE
    SYNTAX      TruthValue
    MAX-ACCESS  read-only
    STATUS      current
    DESCRIPTION 
        "Use of reverse charging. When 'True' for an outgoing call, it 
         shall be (for an IVMO), or was (for a non-IVMO), initiated 
         requesting reverse charging. When 'True' for an incoming call 
         associated with a virtualCall MO, it indicates that reverse 
         charging was accepted."
    REFERENCE   
        "ITU-T Rec. X.283: reverseCharging ATTRIBUTE."
    ::= { virtualCall-DTEEntry 8 }

virtualCall-DTERowStatus OBJECT-TYPE
    SYNTAX      RowStatus
    MAX-ACCESS  read-create
    STATUS      current
    DESCRIPTION 
        "Provides a mechanism whereby management stations may create or 
         delete rows in this table.  Entries must persist across agent 
         reboot."
    ::= { virtualCall-DTEEntry 9 }

virtualCall-DCE OBJECT IDENTIFIER
    ::= { osiTables 56 }

virtualCall-DCETable OBJECT-TYPE
    SYNTAX      SEQUENCE OF VirtualCall-DCEEntry
    MAX-ACCESS  not-accessible
    STATUS      current
    DESCRIPTION 
        "The virtual call DCE managed object.
         
         An instance of this MO is created and exists as long as real 
         resources are consumed by the existence of the Virtual Call. It 
         is an implementation matter to determine the point during a 
         call establishment when real resources are consumed, and 
         conversely, when during call clearing, when they are released."
    REFERENCE   
        "ITU-T Rec. X.283 | ISO/IEC 10733 virtualCall-DCE MOC."
    ::= { virtualCall-DCE 1 }

virtualCall-DCEEntry OBJECT-TYPE
    SYNTAX      VirtualCall-DCEEntry
    MAX-ACCESS  not-accessible
    STATUS      current
    DESCRIPTION 
        "Each row in this table is indexed by X.25 PLE and virtual 
         circuit identifiers.  Each row contains the characteristics and 
         operational status of DCE virtual calls."
    REFERENCE   
        "ITU-T Rec. X.283 | ISO/IEC 10733 virtualCall-DCE MO."
    INDEX       { x25PLEId, virtualCircuitId }
    ::= { virtualCall-DCETable 1 }

VirtualCall-DCEEntry ::= SEQUENCE {
    virtualCall-DCEchargingDirection                        TruthValue,
    virtualCall-DCEcUGSelection                             TruthValue,
    virtualCall-DCEdirection                                INTEGER,
    virtualCall-DCEfastSelect                               FastSelect,
    virtualCall-DCEremoteDTEAddress                         DTEAddress,
    virtualCall-DCEtransitDelaySelectionAndIndication       TruthValue,
    virtualCall-DCEbilateralCUGSelection                    TruthValue,
    virtualCall-DCEcallRedirectionDeflectionNotification    TruthValue,
    virtualCall-DCEcalledLineAddressModifiedNotification    TruthValue,
    virtualCall-DCEcUGWithOutgoingAccessSelection           TruthValue,
    virtualCall-DCEnUISelection                             TruthValue,
    virtualCall-DCEreverseCharging                          TruthValue,
    virtualCall-DCErOASelection                             TruthValue,
    virtualCall-DCERowStatus                                RowStatus
}

virtualCall-DCEchargingDirection OBJECT-TYPE
    SYNTAX      TruthValue
    MAX-ACCESS  read-only
    STATUS      current
    DESCRIPTION 
        "Indicates the use of the charging direction facility for that 
         call."
    REFERENCE   
        "ITU-T Rec. X.283: chargingDirection ATTRIBUTE."
    ::= { virtualCall-DCEEntry 1 }

virtualCall-DCEcUGSelection OBJECT-TYPE
    SYNTAX      TruthValue
    MAX-ACCESS  read-only
    STATUS      current
    DESCRIPTION 
        "Indicates the use of the closed user group selection facility 
         for that call."
    REFERENCE   
        "ITU-T Rec. X.283: cUGSelection ATTRIBUTE."
    ::= { virtualCall-DCEEntry 2 }

virtualCall-DCEdirection OBJECT-TYPE
    SYNTAX      INTEGER { incoming(0), outgoing(1) }
    MAX-ACCESS  read-only
    STATUS      current
    DESCRIPTION 
        "The direction (incoming or outgoing) of the call."
    REFERENCE   
        "ITU-T Rec. X.283: direction ATTRIBUTE."
    ::= { virtualCall-DCEEntry 3 }

virtualCall-DCEfastSelect OBJECT-TYPE
    SYNTAX      FastSelect
    MAX-ACCESS  read-only
    STATUS      current
    DESCRIPTION 
        "Type of fast select used or to be used for call. In the case of 
         an IVMO, this specifies that one of 'fast select', 'fast select 
         with restricted response', or no fast select facility is to be 
         used for the call. It includes a value 'not specified' which 
         indicates that no preference is expressed in the IVMO. In the 
         case of a non-IVMO MO, this specifies that one of 'fast select' 
         or 'no fast select' was used for the call."
    REFERENCE   
        "ITU-T Rec. X.283: fastSelect ATTRIBUTE."
    ::= { virtualCall-DCEEntry 4 }

virtualCall-DCEremoteDTEAddress OBJECT-TYPE
    SYNTAX      DTEAddress
    MAX-ACCESS  read-only
    STATUS      current
    DESCRIPTION 
        "The DTE Address of the remote DTE. In the case of an outgoing 
         call, this is the remote DTE address from the called address of 
         the transmitted call request packet. In the case of an incoming 
         call, it is the calling address from the received call request 
         packet."
    REFERENCE   
        "ITU-T Rec. X.283: remoteDTEAddress ATTRIBUTE."
    ::= { virtualCall-DCEEntry 5 }

virtualCall-DCEtransitDelaySelectionAndIndication OBJECT-TYPE
    SYNTAX      TruthValue
    MAX-ACCESS  read-only
    STATUS      current
    DESCRIPTION 
        "Indicates the use of the transit delay selection and indication 
         facility for that call."
    REFERENCE   
        "ITU-T Rec. X.283: transitDelaySelectionAndIndication 
               ATTRIBUTE."
    ::= { virtualCall-DCEEntry 6 }

virtualCall-DCEbilateralCUGSelection OBJECT-TYPE
    SYNTAX      TruthValue
    MAX-ACCESS  read-only
    STATUS      current
    DESCRIPTION 
        "Indicates the use of the bilateral closed user group selection 
         facility for that call."
    REFERENCE   
        "ITU-T Rec. X.283: bilateralCUGSelection ATTRIBUTE."
    ::= { virtualCall-DCEEntry 7 }

virtualCall-DCEcallRedirectionDeflectionNotification OBJECT-TYPE
    SYNTAX      TruthValue
    MAX-ACCESS  read-only
    STATUS      current
    DESCRIPTION 
        "Indicates the use of the call redirection deflection 
         notification facility for that call."
    REFERENCE   
        "ITU-T Rec. X.283: callRedirectionDeflectionNotification ATTRIBUTE."
    ::= { virtualCall-DCEEntry 8 }

virtualCall-DCEcalledLineAddressModifiedNotification OBJECT-TYPE
    SYNTAX      TruthValue
    MAX-ACCESS  read-only
    STATUS      current
    DESCRIPTION 
        "Indicates the use of the called line address modified 
         notification facility for that call."
    REFERENCE   
        "ITU-T Rec. X.283: calledLineAddressModifiedNotification ATTRIBUTE."
    ::= { virtualCall-DCEEntry 9 }

virtualCall-DCEcUGWithOutgoingAccessSelection OBJECT-TYPE
    SYNTAX      TruthValue
    MAX-ACCESS  read-only
    STATUS      current
    DESCRIPTION 
        "Indicates the use of the Closed User Group With Outgoing Access 
         Selection facility for that call. It may only take the value 
         'True' if the DTE does not have a preferential closed user 
         group, as described in ITU-T Recommendation X.25 and ISO/IEC 
         8208."
    REFERENCE   
        "ITU-T Rec. X.283: cUGWithOutgoingAccessSelection ATTRIBUTE."
    ::= { virtualCall-DCEEntry 10 }

virtualCall-DCEnUISelection OBJECT-TYPE
    SYNTAX      TruthValue
    MAX-ACCESS  read-only
    STATUS      current
    DESCRIPTION 
        "Indicates the use of the network user identification selection 
         facility for that call."
    REFERENCE   
        "ITU-T Rec. X.283: nUISelection ATTRIBUTE."
    ::= { virtualCall-DCEEntry 11 }

virtualCall-DCEreverseCharging OBJECT-TYPE
    SYNTAX      TruthValue
    MAX-ACCESS  read-only
    STATUS      current
    DESCRIPTION 
        "Use of reverse charging. When 'True' for an outgoing call, it 
         shall be (for an IVMO), or was (for a non-IVMO), initiated 
         requesting reverse charging. When 'True' for an incoming call 
         associated with a virtualCall MO, it indicates that reverse 
         charging was accepted."
    REFERENCE   
        "ITU-T Rec. X.283: reverseCharging ATTRIBUTE."
    ::= { virtualCall-DCEEntry 12 }

virtualCall-DCErOASelection OBJECT-TYPE
    SYNTAX      TruthValue
    MAX-ACCESS  read-only
    STATUS      current
    DESCRIPTION 
        "Indicates the use of the registered operating agency selection 
         facility for that call."
    REFERENCE   
        "ITU-T Rec. X.283: rOASelection ATTRIBUTE."
    ::= { virtualCall-DCEEntry 13 }

virtualCall-DCERowStatus OBJECT-TYPE
    SYNTAX      RowStatus
    MAX-ACCESS  read-create
    STATUS      current
    DESCRIPTION 
        "Provides a mechanism whereby management stations may create and 
         delete rows in this table.  Entries must survive agent reboot."
    ::= { virtualCall-DCEEntry 14 }

dSeriesCounts OBJECT IDENTIFIER
    ::= { osiTables 57 }

dSeriesCountsTable OBJECT-TYPE
    SYNTAX      SEQUENCE OF DSeriesCountsEntry
    MAX-ACCESS  not-accessible
    STATUS      current
    DESCRIPTION 
        "The Recommendation D Series counts managed object.
         
         There is one instance of this MO created by management action 
         or automatically for each instance of a virtual call where the 
         Tariff Principles applying to Data Communications Services over 
         dedicated Public Data Networks are applicable. The provisions 
         of the tariff principles are defined in Recommendations D.10, 
         D.11 and D.12."
    REFERENCE   
        "ITU-T Rec. X.283 | ISO/IEC 10733 dSeriesCounts MOC."
    ::= { dSeriesCounts 1 }

dSeriesCountsEntry OBJECT-TYPE
    SYNTAX      DSeriesCountsEntry
    MAX-ACCESS  not-accessible
    STATUS      current
    DESCRIPTION 
        "Provides the set of packet and segment counts required to 
         collect the charges levied according to the tariff principles 
         contained in Recommendations D.10, D.11 and D.12 for 
         international packet switched public data communications 
         services. The values collected are reported at object 
         deletion."
    REFERENCE   
        "ITU-T Rec. X.283 | ISO/IEC 10733 dSeriesCounts MO."
    INDEX       { x25PLEId, virtualCircuitId, dSeriesId }
    ::= { dSeriesCountsTable 1 }

DSeriesCountsEntry ::= SEQUENCE {
    dSeriesId                               SimpleNameType,
    dSeriesResetRequestIndicationPackets    Counter32,
    dSeriesSegmentsSent                     Counter32,
    dSeriesSegmentsReceived                 Counter32,
    dSeriesRowStatus                        RowStatus
}

dSeriesId OBJECT-TYPE
    SYNTAX      SimpleNameType
    MAX-ACCESS  not-accessible
    STATUS      current
    DESCRIPTION 
        "The name of this instance of the dSeriesCounts MO."
    REFERENCE   
        "ITU-T Rec. X.286: dSeriesId ATTRIBUTE."
    ::= { dSeriesCountsEntry 1 }

dSeriesResetRequestIndicationPackets OBJECT-TYPE
    SYNTAX      Counter32
    MAX-ACCESS  read-only
    STATUS      current
    DESCRIPTION 
        "Value for count of Reset Request or Indication Packets with 
         restrictions defined in Recommendation D.11."
    REFERENCE   
        "ITU-T Rec. X.286: dSeriesResetRequestIndicationPackets ATTRIBUTE."
    ::= { dSeriesCountsEntry 2 }

dSeriesSegmentsSent OBJECT-TYPE
    SYNTAX      Counter32
    MAX-ACCESS  read-only
    STATUS      current
    DESCRIPTION 
        "Value for count of Segments Sent, in 64 octets, as per 
         Recommendation D.12."
    REFERENCE   
        "ITU-T Rec. X.286: dSeriesSegmentsSent ATTRIBUTE."
    ::= { dSeriesCountsEntry 3 }

dSeriesSegmentsReceived OBJECT-TYPE
    SYNTAX      Counter32
    MAX-ACCESS  read-only
    STATUS      current
    DESCRIPTION 
        "Value for count of Segments Received, in 64 octets, as per 
         Recommendation D.12."
    REFERENCE   
        "ITU-T Rec. X.286: dSeriesSegmentsReceived ATTRIBUTE."
    ::= { dSeriesCountsEntry 4 }

dSeriesRowStatus OBJECT-TYPE
    SYNTAX      RowStatus
    MAX-ACCESS  read-create
    STATUS      current
    DESCRIPTION 
        "Provides a mechanism whereby management stations may create and 
         delete rows in this table.  Entries must survive agent reboot."
    ::= { dSeriesCountsEntry 5 }

adjacency OBJECT IDENTIFIER
    ::= { osiTables 58 }

adjacencyTable OBJECT-TYPE
    SYNTAX      SEQUENCE OF AdjacencyEntry
    MAX-ACCESS  not-accessible
    STATUS      current
    DESCRIPTION 
        "Adjacency managed object.
         
         Created either through the adjacency-linkage Name binding for 
         adjacencies instantiated by protocol operation, or the 
         adjacency-linkage-management name binding for adjacencies 
         created via explicit system management operation."
    REFERENCE   
        "ISO/IEC 10589 adjacency MOC."
    ::= { adjacency 1 }

adjacencyEntry OBJECT-TYPE
    SYNTAX      AdjacencyEntry
    MAX-ACCESS  not-accessible
    STATUS      current
    DESCRIPTION 
        "This Managed Object imports the 10165-2 stateChange 
         notification. It is used to report changes to the 
         adjacencyState attribute. The value 'Down' shall be reported 
         when the adjacency is deleted. A single parameter set shall be 
         included in the State Change definition field. Only the 
         (mandatory) attributeId and newAttributeValue parameters shall 
         be used."
    REFERENCE   
        "ISO/IEC 10589 adjacency MO."
    INDEX       { communicationsEntityId, clProtocolMachineId, linkageId, 
                  adjacencyId }
    ::= { adjacencyTable 1 }

AdjacencyEntry ::= SEQUENCE {
    adjacencyId                 SimpleNameType,
    adjacencyState              INTEGER,
    neighbourSNPAAddress        SNPAAddress,
    neighbourSystemType         INTEGER,
    neighbourSystemIds          OCTET STRING,
    adjacencyUsage              INTEGER,
    areaAddressesOfNeighbour    AreaAddresses,
    holdingTimer                TimeInterval,
    priorityOfNeighbour         Integer32,
    adjacencyRowStatus          RowStatus
}

adjacencyId OBJECT-TYPE
    SYNTAX      SimpleNameType
    MAX-ACCESS  not-accessible
    STATUS      current
    DESCRIPTION 
        "A string which is the Identifier for the Adjacency and which is 
         unique amongst the set of Adjacencies maintained for this 
         linkage. If this is an adjacency created by system management, 
         it is set by the System Manager when the Adjacency is created, 
         otherwise it is generated by the implementation such that it is 
         unique.  The set of identifiers containing the leading string 
         'Auto' are reserved for Automatic Adjacencies. An attempt by 
         system management to create an adjacency with such an 
         identifier will cause a reserved name violation."
    REFERENCE   
        "ISO/IEC 10589, adjacencyId attribute."
    ::= { adjacencyEntry 1 }

adjacencyState OBJECT-TYPE
    SYNTAX      INTEGER { initializing(0), up(1), failed(2), down(3) }
    MAX-ACCESS  read-only
    STATUS      current
    DESCRIPTION 
        "The state of the adjacency."
    REFERENCE   
        "ISO/IEC 10589, adjacencyState attribute."
    ::= { adjacencyEntry 2 }

neighbourSNPAAddress OBJECT-TYPE
    SYNTAX      SNPAAddress
    MAX-ACCESS  read-create
    STATUS      current
    DESCRIPTION 
        "The SNPA address of the neighbour system.
         
         Value is supplied either by the protocol machine if the MO is 
         automatically created, or supplied via the CREATE Operation. 
         The value cannot be changed thereafter."
    REFERENCE   
        "ISO/IEC 10589, neighboursSNPAAddress attribute."
    ::= { adjacencyEntry 3 }

neighbourSystemType OBJECT-TYPE
    SYNTAX      INTEGER { unknown(0), endSystem(1), 
                    intermediateSystem(2), l1IntermediateSystem(3), 
                    l2IntermeidateSystem(4) }
    MAX-ACCESS  read-only
    STATUS      current
    DESCRIPTION 
        "The type of the neighbour system one of: Unknown, End system, 
         Intermediate system, L1 Intermediate system, L2 Intermediate 
         system"
    REFERENCE   
        "ISO/IEC 10589, neighbourSystemType attribute."
    ::= { adjacencyEntry 4 }

neighbourSystemIds OBJECT-TYPE
    SYNTAX      OCTET STRING
    MAX-ACCESS  read-create
    STATUS      current
    DESCRIPTION 
        "For Intermediate system neighbours: Contains the single 
         SystemId of the neighbouring Intermediate system obtained from 
         the Source ID field of the neighbour's IIH PDU. For End system 
         neighbours: Contains the set of system ID(s) of a neighbour End 
         system.
         
         Each systemId is formatted as an octet string of size 
         0..8 preceded by a single length octet.
         
         Value is supplied either by the protocol machine if the MO is 
         automatically created, or supplied via the CREATE Operation. 
         The value cannot be changed thereafter."
    REFERENCE   
        "ISO/IEC 10589, neighbourSystemIds attribute."
    ::= { adjacencyEntry 5 }

-- iSAdjacency-P conditional package
--
-- IS adjacency package of the adjacency managed object.  Used when the 
-- adjacency is to an IS (i.e the neighbourSystemType is Intermediate 
-- System, L1 Intermediate System or L2 Intermediate System).
--
adjacencyUsage OBJECT-TYPE
    SYNTAX      INTEGER { undefined(0), level1(1), level2(2), 
                    level1and2(3) }
    MAX-ACCESS  read-only
    STATUS      current
    DESCRIPTION 
        "The usage of the Adjacency. An Adjacency of type Level 
         1 will be used for Level 1 traffic only. An adjacency of type 
           Level 2 will be used for Level 2 traffic only.  An adjacency 
           of type Level 1 and 2 will be used for both Level 1 and Level 
           2 traffic. There may be two adjacencies (of types Level 1 and 
             Level 2 between the same pair of Intermediate Systems."
    REFERENCE   
        "ISO/IEC 10589 adjacencyUsage attribute."
    DEFVAL      { undefined }
    ::= { adjacencyEntry 6 }

areaAddressesOfNeighbour OBJECT-TYPE
    SYNTAX      AreaAddresses
    MAX-ACCESS  read-only
    STATUS      current
    DESCRIPTION 
        "This contains the Area Addresses of a neighbour Intermediate 
         System from the IIH PDU."
    REFERENCE   
        "ISO/IEC 10589 areaAddressesOfNeighbor attribute."
    ::= { adjacencyEntry 7 }

holdingTimer OBJECT-TYPE
    SYNTAX      TimeInterval
    MAX-ACCESS  read-only
    STATUS      current
    DESCRIPTION 
        "Holding time for this adjacency updated from the IIH PDUs."
    REFERENCE   
        "ISO/IEC 10589 holdingTimer attribute."
    ::= { adjacencyEntry 8 }

-- broadcastISAdjacency-P conditional package
priorityOfNeighbour OBJECT-TYPE
    SYNTAX      Integer32 (1..127)
    MAX-ACCESS  read-only
    STATUS      current
    DESCRIPTION 
        "Priority of neighbour on this adjacency for becoming LAN Level 
         1 Designated Intermediate System if adjacencyType is L1 
         Intermediate System or LAN Level 2 Designated Intermediate 
         System if adjacencyType is L2 Intermediate System."
    REFERENCE   
        "ISO/IEC 10589 priorityOfNeighbour attribute."
    ::= { adjacencyEntry 9 }

-- adjacency-linkage name binding
-- adjacency-linkage-management name binding
adjacencyRowStatus OBJECT-TYPE
    SYNTAX      RowStatus
    MAX-ACCESS  read-create
    STATUS      current
    DESCRIPTION 
        "Provides a mechanism whereby management stations, following the 
         RowStatus textual convention of the SNMPv2-TC module, may 
         create or delete conceptual rows from this table.
         
         The adjacency-linkage name binding is used for adjacencies 
         created automatically by operation of the ISO/IEC 10589 
         protocol machine.
         
         The adjacency-linkage-management name binding is used for 
         adjacencies created by system management."
    REFERENCE   
        "ISO/IEC 10589 adjacency-linkage, adjacency-linkage-management, 
         STD 58, SNMPv2-TC RowStatus."
    ::= { adjacencyEntry 10 }

virtualAdjacency OBJECT IDENTIFIER
    ::= { osiTables 59 }

virtualAdjacencyTable OBJECT-TYPE
    SYNTAX      SEQUENCE OF VirtualAdjacencyEntry
    MAX-ACCESS  not-accessible
    STATUS      current
    DESCRIPTION 
        "The virtual adjacency managed object class.  Instances of this 
         class only exist if the containing cLNS is a Level 2 
         Intermediate System.
         
         The virtualAdjacency-cLNS name binding is only applicable where 
         the superior object has an iSType of Level2.
         
         Virtual adjacencies cannot be created or deleted explicitly by 
         mangement stations and are created or deleted as a part of 
         system operation."
    REFERENCE   
        "ISO/IEC 10589 virtualAdjacency MOC."
    ::= { virtualAdjacency 1 }

virtualAdjacencyEntry OBJECT-TYPE
    SYNTAX      VirtualAdjacencyEntry
    MAX-ACCESS  not-accessible
    STATUS      current
    DESCRIPTION 
        "Each row in this table is indexed by communications entity, 
         connectionless protocol machine and virtual adjacency network 
         entity title. Each row contains a network entity title."
    REFERENCE   
        "ISO/IEC 10589 virtualAdjacency MO."
    INDEX       { communicationsEntityId, clProtocolMachineId, 
                  virtualAdjacencyNetworkEntityTitle }
    ::= { virtualAdjacencyTable 1 }

VirtualAdjacencyEntry ::= SEQUENCE {
    virtualAdjacencyNetworkEntityTitle  NAddress,
    virtualAdjacencyMetric              PathMetric
}

virtualAdjacencyNetworkEntityTitle OBJECT-TYPE
    SYNTAX      NAddress
    MAX-ACCESS  not-accessible
    STATUS      current
    DESCRIPTION 
        "Provides the adjacency network entity title."
    REFERENCE   
        "ISO/IEC 10589 networkEntityTitle attribute."
    ::= { virtualAdjacencyEntry 1 }

virtualAdjacencyMetric OBJECT-TYPE
    SYNTAX      PathMetric
    MAX-ACCESS  read-only
    STATUS      current
    DESCRIPTION 
        "Cost of least cost L2 path(s) to destination area based on the 
         default metric."
    REFERENCE   
        "ISO/IEC 10589 metric attribute."
    ::= { virtualAdjacencyEntry 2 }

destinationMOC OBJECT IDENTIFIER
    ::= { osiTables 60 }

destinationTable OBJECT-TYPE
    SYNTAX      SEQUENCE OF DestinationEntry
    MAX-ACCESS  not-accessible
    STATUS      current
    DESCRIPTION 
        "Destination managed object.  This MO class is never 
         instantiated. It exists only to allow the destinationSystem and 
         destinationArea MO classes to be derived from it."
    REFERENCE   
        "ISO/IEC 10589 destination MOC."
    ::= { destinationMOC 1 }

destinationEntry OBJECT-TYPE
    SYNTAX      DestinationEntry
    MAX-ACCESS  not-accessible
    STATUS      current
    DESCRIPTION 
        "Each entry in this table is indexed by communications entity, 
         connectionless protocol machine and destination address prefix.  
         Each row contains information about destinations."
    REFERENCE   
        "ISO/IEC 10589 destination MO."
    INDEX       { communicationsEntityId, clProtocolMachineId, 
                  destinationAddressPrefix }
    ::= { destinationTable 1 }

DestinationEntry ::= SEQUENCE {
    destinationAddressPrefix                    AddressPrefix,
    destinationDefaultMetricPathCost            PathMetric,
    destinationDefaultMetricOutputAdjacencies   DummySyntax,
    destinationDelayMetricPathCost              PathMetric,
    destinationDelayMetricOutputAdjacencies     DummySyntax,
    destinationExpenseMetricPathCost            PathMetric,
    destinationExpenseMetricOutputAdjacencies   DummySyntax,
    destinationErrorMetricPathCost              PathMetric,
    destinationErrorMetricOutputAdjacencies     DummySyntax
}

destinationAddressPrefix OBJECT-TYPE
    SYNTAX      AddressPrefix
    MAX-ACCESS  not-accessible
    STATUS      current
    DESCRIPTION 
        "Provides an index for this and the destinationSystem and 
         destinationArea tables."
    REFERENCE   
        "ISO/IEC 10589 networkEntityTitle and addressPrefix attributes."
    ::= { destinationEntry 1 }

destinationDefaultMetricPathCost OBJECT-TYPE
    SYNTAX      PathMetric
    MAX-ACCESS  read-write
    STATUS      current
    DESCRIPTION 
        "Cost of least cost path(s) using the default metric to 
         destination."
    ::= { destinationEntry 2 }

destinationDefaultMetricOutputAdjacencies OBJECT-TYPE
    SYNTAX      DummySyntax
    MAX-ACCESS  read-write
    STATUS      current
    DESCRIPTION 
        "The set of Adjacency (or Reachable Address) managed object 
         identifiers representing the forwarding decisions based upon 
         the default metric for the destination."
    ::= { destinationEntry 3 }

destinationDelayMetricPathCost OBJECT-TYPE
    SYNTAX      PathMetric
    MAX-ACCESS  read-write
    STATUS      current
    DESCRIPTION 
        "Cost of least cost path(s) using the delay metric to 
         destination."
    ::= { destinationEntry 4 }

destinationDelayMetricOutputAdjacencies OBJECT-TYPE
    SYNTAX      DummySyntax
    MAX-ACCESS  read-write
    STATUS      current
    DESCRIPTION 
        "The set of Adjacency (or Reachable Address) managed object 
         identifiers representing the forwarding decisions based upon 
         the delay metric for the destination."
    ::= { destinationEntry 5 }

destinationExpenseMetricPathCost OBJECT-TYPE
    SYNTAX      PathMetric
    MAX-ACCESS  read-write
    STATUS      current
    DESCRIPTION 
        "Cost of least cost path(s) using the expense metric to 
         destination."
    ::= { destinationEntry 6 }

destinationExpenseMetricOutputAdjacencies OBJECT-TYPE
    SYNTAX      DummySyntax
    MAX-ACCESS  read-write
    STATUS      current
    DESCRIPTION 
        "The set of Adjacency (or Reachable Address) managed object 
         identifiers representing the forwarding decisions based upon 
         the expense metric for the destination."
    ::= { destinationEntry 7 }

destinationErrorMetricPathCost OBJECT-TYPE
    SYNTAX      PathMetric
    MAX-ACCESS  read-write
    STATUS      current
    DESCRIPTION 
        "Cost of least cost path(s) using the error metric to 
         destination."
    ::= { destinationEntry 8 }

destinationErrorMetricOutputAdjacencies OBJECT-TYPE
    SYNTAX      DummySyntax
    MAX-ACCESS  read-write
    STATUS      current
    DESCRIPTION 
        "The set of Adjacency (or Reachable Address) managed object 
         identifiers representing the forwarding decisions based upon 
         the expense metric for the destination."
    ::= { destinationEntry 9 }

destinationSystem OBJECT IDENTIFIER
    ::= { osiTables 61 }

destinationSystemTable OBJECT-TYPE
    SYNTAX      SEQUENCE OF DestinationSystemEntry
    MAX-ACCESS  not-accessible
    STATUS      current
    DESCRIPTION 
        "Provides a table of destination systems."
    REFERENCE   
        "ISO/IEC 10589 destinationSystem MOC."
    ::= { destinationSystem 1 }

destinationSystemEntry OBJECT-TYPE
    SYNTAX      DestinationSystemEntry
    MAX-ACCESS  not-accessible
    STATUS      current
    DESCRIPTION 
        "Each row in this table is indexed by communications entity, 
         connectionless protocol machine and destination system network 
         entity title.  Each row contains characteristics of the 
         destination system."
    REFERENCE   
        "ISO/IEC 10589 destinationSystem MO."
    INDEX       { communicationsEntityId, clProtocolMachineId, 
                  destinationSystemNetworkEntityTitle }
    ::= { destinationSystemTable 1 }

DestinationSystemEntry ::= SEQUENCE {
    destinationSystemNetworkEntityTitle     NAddress,
    destinationSystemMetricType             INTEGER,
    desintationSystemMetric                 PathMetric,
    destinationSystemAdjacency              RowPointer
}

destinationSystemNetworkEntityTitle OBJECT-TYPE
    SYNTAX      NAddress
    MAX-ACCESS  not-accessible
    STATUS      current
    DESCRIPTION 
        "Provides the network entity title used as an index."
    REFERENCE   
        "ISO/IEC 10589 networkEntityTitle attribute."
    ::= { destinationSystemEntry 1 }

destinationSystemMetricType OBJECT-TYPE
    SYNTAX      INTEGER { default(0), delay(1), expense(2), error(3) }
    MAX-ACCESS  not-accessible
    STATUS      current
    DESCRIPTION 
        "Provides the metric type."
    ::= { destinationSystemEntry 2 }

desintationSystemMetric OBJECT-TYPE
    SYNTAX      PathMetric
    MAX-ACCESS  read-only
    STATUS      current
    DESCRIPTION 
        "Provides the metric."
    ::= { destinationSystemEntry 3 }

destinationSystemAdjacency OBJECT-TYPE
    SYNTAX      RowPointer
    MAX-ACCESS  not-accessible
    STATUS      current
    DESCRIPTION 
        "Provides the system adjacency."
    ::= { destinationSystemEntry 4 }

destinationArea OBJECT IDENTIFIER
    ::= { osiTables 62 }

destinationAreaTable OBJECT-TYPE
    SYNTAX      SEQUENCE OF DestinationAreaEntry
    MAX-ACCESS  not-accessible
    STATUS      current
    DESCRIPTION 
        "Provides a table of destination areas."
    REFERENCE   
        "ISO/IEC 10589 destinationArea MOC."
    ::= { destinationArea 1 }

destinationAreaEntry OBJECT-TYPE
    SYNTAX      DestinationAreaEntry
    MAX-ACCESS  not-accessible
    STATUS      current
    DESCRIPTION 
        "Each row in this table is indexed by and defines the 
         destination area identifier.   Aside for indicating membership, 
         rows are empty."
    REFERENCE   
        "ISO/IEC 10589 destinationArea MO."
    INDEX       { destinationAreaId }
    ::= { destinationAreaTable 1 }

DestinationAreaEntry ::= SEQUENCE {
    destinationAreaId   SimpleNameType
}

destinationAreaId OBJECT-TYPE
    SYNTAX      SimpleNameType
    MAX-ACCESS  read-only
    STATUS      current
    DESCRIPTION 
        "Provides the destination area identifier used as an index for 
         this table."
    ::= { destinationAreaEntry 1 }

reachableAddress OBJECT IDENTIFIER
    ::= { osiTables 63 }

reachableAddressTable OBJECT-TYPE
    SYNTAX      SEQUENCE OF ReachableAddressEntry
    MAX-ACCESS  not-accessible
    STATUS      current
    DESCRIPTION 
        "Reachable address managed object.  Created either through the 
         reachableAddress-linkage-imported Name binding for reachable 
         addresses instantiated by the importation of routeing 
         information from another routeing protocol (such as the 
         interdomain routeing protocol), or the 
         reachableAddress-linkage-management name binding for 
         adjacencies created via explicit system management operation.
         
         The table issues an objectCreation notification when entries 
         are created and added to the table.  The table issues an 
         objectDeletion notification when entries are deleted from the 
         table."
    REFERENCE   
        "ISO/IEC 10589 reachableAddress MOC."
    ::= { reachableAddress 1 }

reachableAddressEntry OBJECT-TYPE
    SYNTAX      ReachableAddressEntry
    MAX-ACCESS  not-accessible
    STATUS      current
    DESCRIPTION 
        "
         Each entry issues a stateChange notification should the 
         operationalState change indicating that the operationalState 
         has changed.
         
         Each entry supports an activate action and a deactivate action.  
         These actions are emulated in SNMP using the 
         administrativeState column."
    REFERENCE   
        "ISO/IEC 10589 reachableAddress MO."
    INDEX       { reachableAddressId }
    ::= { reachableAddressTable 1 }

ReachableAddressEntry ::= SEQUENCE {
    reachableAddressId                      SimpleNameType,
    reachableAddressPrefix                  AddressPrefix,
    reachableAddressMappingType             INTEGER,
    reachableAddressDefaultMetric           HopMetric,
    reachableAddressDelayMetric             HopMetric,
    reachableAddressExpenseMetric           HopMetric,
    reachableAddressErrorMetric             HopMetric,
    reachableAddressDefaultMetricType       MetricType,
    reachableAddressDelayMetricType         MetricType,
    reachableAddressExpenseMetricType       MetricType,
    reachableAddressErrorMetricType         MetricType,
    reachableAddressOperationalState        OperationalState,
    reachableAddressAdministrativeState     AdministrativeState,
    reachableAddressSNPAAddresses           SNPAAddresses,
    reachableAddressSNPAMask                NAddress,
    reachableAddressSNPAPrefix              SNPAPrefix,
    reachableAddressRowStatus               RowStatus
}

reachableAddressId OBJECT-TYPE
    SYNTAX      SimpleNameType
    MAX-ACCESS  not-accessible
    STATUS      current
    DESCRIPTION 
        "A string which is the Identifier for the ReachableAddress and 
         which is unique amongst the set of reachable addresses 
         maintained for this linkage. If this is a reachableAddress 
         created by system management, it is set by the System Manager 
         when the ReachableAddress is created, otherwise it is generated 
         by the implementation such that it is unique. The set of 
         identifiers containing the leading string 'Auto' are reserved 
         for reachable addresses imported from other routeing protocols. 
         An attempt by system management to create a reachableAddress 
         with such an identifier will cause a reserved name violation."
    REFERENCE   
        "ISO/IEC 10589 reachableAddressId."
    ::= { reachableAddressEntry 1 }

reachableAddressPrefix OBJECT-TYPE
    SYNTAX      AddressPrefix
    MAX-ACCESS  read-create
    STATUS      current
    DESCRIPTION 
        "An Area Address of a destination area or a prefix for a 
         reachable address.
         
         Value is supplied either by the protocol machine if the MO is 
         automatically created, or supplied via the CREATE Operation. 
         The value cannot be changed thereafter."
    REFERENCE   
        "ISO/IEC 10589 addressPrefix."
    ::= { reachableAddressEntry 2 }

reachableAddressMappingType OBJECT-TYPE
    SYNTAX      INTEGER { none(0), explicit(1), extractIDI(2), 
                    extractDSP(3) }
    MAX-ACCESS  read-create
    STATUS      current
    DESCRIPTION 
        "The type of mapping to be employed to ascertain the SNPA 
         Address which should be used in forwarding NPDUs for this 
         Reachable Address Prefix. The following values of mappingType 
         are defined:
         
         none: The mapping is null because the neighbour SNPA is 
         implicit by nature of the subnetwork (e.g. a point-to-point 
         linkage).
         
         explicit: The set of subnetwork addresses in the sNPAAddresses 
         attribute are to be used.
         
         extractIDI: The SNPA is embedded in the IDI of the destination 
         NSAP address. The mapping algorithm extracts the SNPA to be 
         used according to the format and encoding rules of 
         ISO8348/Add2. This SNPA extraction algorithm can be used in 
         conjunction with Reachable Address Prefixes from the X.121, 
         F.69, E.163, and E.164 addressing subdomains.
         
         extractDSP: All, or a suffix, of the SNPA is embedded in the 
         DSP of the destination address. This SNPA extraction algorithm 
         extracts the embedded subnetwork addressing information by 
         performing a logical AND of the sNPAMask attribute with the 
         destinaition address. The part of the SNPA extracted from the 
         destination NSAP is appended to the sNPAPrefix to form the next 
         hop subnetwork addressing information.
         
         Value is supplied either by the protocol machine if the MO is 
         automatically created, or supplied via the CREATE Operation. 
         The value cannot be changed thereafter."
    REFERENCE   
        "ISO/IEC 10589 mappingType."
    ::= { reachableAddressEntry 3 }

reachableAddressDefaultMetric OBJECT-TYPE
    SYNTAX      HopMetric (1..63)
    MAX-ACCESS  read-create
    STATUS      current
    DESCRIPTION 
        "The default metric value for reaching the specified prefix over 
         this Circuit. If this attribute is changed while both the 
         Reachable Address and the linkage are Enabled (i.e. state On), 
         the actions described in clause 8.3.5.4 must be taken."
    REFERENCE   
        "ISO/IEC 10589 defaultMetric."
    DEFVAL      { 20 }
    ::= { reachableAddressEntry 4 }

reachableAddressDelayMetric OBJECT-TYPE
    SYNTAX      HopMetric
    MAX-ACCESS  read-create
    STATUS      current
    DESCRIPTION 
        "The delay metric value for reaching the specified prefix over 
         this Circuit. If this attribute is changed while both the 
         Reachable Address and the linkage are Enabled (i.e. state On), 
         the actions described in clause 8.3.5.4 must be taken.  The 
         value of zero is reserved to indicate that this metric is not 
         supported."
    REFERENCE   
        "ISO/IEC 10589 delayMetric."
    DEFVAL      { 0 }
    ::= { reachableAddressEntry 5 }

reachableAddressExpenseMetric OBJECT-TYPE
    SYNTAX      HopMetric
    MAX-ACCESS  read-create
    STATUS      current
    DESCRIPTION 
        "The expense metric value for reaching the specified prefix over 
         this Circuit. If this attribute is changed while both the 
         Reachable Address and the linkage are Enabled (i.e. state On), 
         the actions described in clause 8.3.5.4 must be taken.  The 
         value of zero is reserved to indicate that this metric is not 
         supported."
    REFERENCE   
        "ISO/IEC 10589 expenseMetric."
    DEFVAL      { 0 }
    ::= { reachableAddressEntry 6 }

reachableAddressErrorMetric OBJECT-TYPE
    SYNTAX      HopMetric
    MAX-ACCESS  read-create
    STATUS      current
    DESCRIPTION 
        "The error metric value for reaching the specified prefix over 
         this Circuit. If this attribute is changed while both the 
         Reachable Address and the linkage are Enabled (i.e. state On), 
         the actions described in clause 8.3.5.4 must be taken.  The 
         value of zero is reserved to indicate that this metric is not 
         supported."
    REFERENCE   
        "ISO/IEC 10589 errorMetric."
    DEFVAL      { 0 }
    ::= { reachableAddressEntry 7 }

reachableAddressDefaultMetricType OBJECT-TYPE
    SYNTAX      MetricType
    MAX-ACCESS  read-create
    STATUS      current
    DESCRIPTION 
        "Indicates whether the default metric is internal or external."
    REFERENCE   
        "ISO/IEC 10589 defaultMetricType."
    DEFVAL      { internal }
    ::= { reachableAddressEntry 8 }

reachableAddressDelayMetricType OBJECT-TYPE
    SYNTAX      MetricType
    MAX-ACCESS  read-create
    STATUS      current
    DESCRIPTION 
        "Indicates whether the delay metric is internal or external."
    REFERENCE   
        "ISO/IEC 10589 delayMetricType."
    DEFVAL      { internal }
    ::= { reachableAddressEntry 9 }

reachableAddressExpenseMetricType OBJECT-TYPE
    SYNTAX      MetricType
    MAX-ACCESS  read-create
    STATUS      current
    DESCRIPTION 
        "Indicates whether the expense metric is internal or external."
    REFERENCE   
        "ISO/IEC 10589 expenseMetricType."
    DEFVAL      { internal }
    ::= { reachableAddressEntry 10 }

reachableAddressErrorMetricType OBJECT-TYPE
    SYNTAX      MetricType
    MAX-ACCESS  read-create
    STATUS      current
    DESCRIPTION 
        "Indicates whether the error metric is internal or external."
    REFERENCE   
        "ISO/IEC 10589 errorMetricType."
    DEFVAL      { internal }
    ::= { reachableAddressEntry 11 }

reachableAddressOperationalState OBJECT-TYPE
    SYNTAX      OperationalState
    MAX-ACCESS  read-only
    STATUS      current
    DESCRIPTION 
        "Provides the operational state of the reachable address in 
         accordance with the OperationalState textual convention from 
         the OPENSS7-TMN-TC module."
    REFERENCE   
        "ITU-T Rec. X.721 | ISO/IEC 10165-2 operationalState."
    ::= { reachableAddressEntry 12 }

reachableAddressAdministrativeState OBJECT-TYPE
    SYNTAX      AdministrativeState
    MAX-ACCESS  read-create
    STATUS      current
    DESCRIPTION 
        "Provides the emulation of activate and deactivate actions using 
         the AdministrativeState texutal convention from the 
         OPENSS7-TMN-TC module."
    REFERENCE   
        "ITU-T Rec. X.721 | ISO/IEC 10165-2 administrativeState."
    ::= { reachableAddressEntry 13 }

-- explicitSNPA-P conditional package
--
-- This package is applicablew when the value of mappingType is 
-- 'explicit'.
--
reachableAddressSNPAAddresses OBJECT-TYPE
    SYNTAX      SNPAAddresses
    MAX-ACCESS  read-create
    STATUS      current
    DESCRIPTION 
        "A set of SNPA addresses to which pdu may be forwarded in order 
         to reach an address which matches the address prefix of the 
         Reachable Address."
    REFERENCE   
        "ISO/IEC 10589 sNPAAddresses."
    ::= { reachableAddressEntry 14 }

-- extractDSP-P conditional package
--
-- This package is applicable when the value of mappingType is 
-- 'extractDSP'.  When present, the remote SNPA address is determined by 
-- extracting the bits from the effective NSAP address indicated by 1's 
-- in the sNPAMask and concatenating them to the sNPAPrefix.
--
reachableAddressSNPAMask OBJECT-TYPE
    SYNTAX      NAddress
    MAX-ACCESS  read-create
    STATUS      current
    DESCRIPTION 
        "A Bit mask with 1 bits indicating the positions in the 
         effective destination address from which embedded SNPA 
         information is to be extracted. For the extraction the first 
         octect of the sNPAMask is aligned with the first octet (AFI) of 
         the NSAP Address. If the sNPAMask and NSAP Address are of 
         different lengths, the shorter of the two is logically padded 
         with zeros before performing the extraction."
    REFERENCE   
        "ISO/IEC 10589 sNPAMask."
    DEFVAL      { "" }
    ::= { reachableAddressEntry 15 }

reachableAddressSNPAPrefix OBJECT-TYPE
    SYNTAX      SNPAPrefix
    MAX-ACCESS  read-create
    STATUS      current
    DESCRIPTION 
        "A fixed SNPA prefix manually configured as an attribute of a 
         Reachable Address with mappingType extractDSP. The SNPA address 
         to use is formed by concatenating the fixed sNPAPrefix with a 
         variable SNPA part that is extracted from the effective 
         destination address. For Reachable Address Prefixes in which 
         then entire SNPA is embedded in the DSP the sNPAPrefix shall be 
         null."
    REFERENCE   
        "ISO/IEC 10589 sNPAPrefix."
    DEFVAL      { "" }
    ::= { reachableAddressEntry 16 }

-- reachableAddress-linkage-imported name binding
--
-- This name binding is only applicable where the superior object of the 
-- linkage instance is an object with iSType level2IS It is used for the 
-- automatic creation of reachable address MOs. This is useful when 
-- injecting intra-domain routes obtained through the operation of an 
-- interdomain routeing protocol.
--
-- reachableAddress-linkage-management name binding
--
-- This name binding is only applicable where the superior object of the 
-- linkage instance is an object with iSType level2IS It is used for the 
-- manual creation of reachable address MOs by system management.
--
reachableAddressRowStatus OBJECT-TYPE
    SYNTAX      RowStatus
    MAX-ACCESS  read-create
    STATUS      current
    DESCRIPTION 
        "Provides a mechanism whereby management stations, following the 
         RowStatust textual convention of the SNMPv2-TC module, may 
         create or delete conceptual rows in this table.
         
         The reachableAddress-linkage-imported name binding is only 
         applicable where the superior object of the linkage instance is 
         an object with iSType level2IS It is used for the automatic 
         creation of reachable address MOs. This is useful when 
         injecting intra-domain routes obtained through the operation of 
         an interdomain routeing protocol.
         
         The reachableAddress-linkage-management name binding is only 
         applicable where the superior object of the linkage instance is 
         an object with iSType level2IS It is used for the manual 
         creation of reachable address MOs by system management."
    REFERENCE   
        "ISO/IEC 10589 reachableAddress-linkage-imported, 
         reachableAddress-linkage-management, STD 58, SNMPv2-TC 
         RowStatus."
    ::= { reachableAddressEntry 17 }

osiScalars OBJECT IDENTIFIER
    ::= { osiObjects 2 }

osiGlobals OBJECT IDENTIFIER
    ::= { osiScalars 1 }

llcDiscontinuityTime OBJECT-TYPE
    SYNTAX      TimeStamp
    MAX-ACCESS  read-only
    STATUS      current
    DESCRIPTION 
        "Provides the time since the last reboot at which a 
         discontinuity in counters and gauges occurred possibly 
         resulting in the reset of counters and gauges to zero."
    REFERENCE   
        "SMIv2"
    ::= { osiGlobals 1 }

osiDefaults OBJECT IDENTIFIER
    ::= { osiScalars 2 }

sLPConnectionDefaults OBJECT IDENTIFIER
    ::= { osiDefaults 1 }

sLPConnectionDefaultInterfaceType OBJECT-TYPE
    SYNTAX      INTEGER { dTE(0), dCE(1) }
    MAX-ACCESS  read-write
    STATUS      current
    DESCRIPTION 
        "Sets the default initial value for the 
         sLPConnectionInterfaceType element of the sLPConnectionTable 
         and the default value for the sLPConnectionIVMOinterfaceType 
         element of the sLPConnectionIVMOTable.  When set by a 
         management station, the value set should persist across agent 
         and system reboots.  The DEFVAL, therefore, is only applicable 
         when this default has never been set by a management station."
    REFERENCE   
        "ITU-T Rec. X.282 | ISO/IEC 10742."
    DEFVAL      { dTE }
    ::= { sLPConnectionDefaults 1 }

sLPConnectionDefaultK OBJECT-TYPE
    SYNTAX      Integer32
    MAX-ACCESS  read-write
    STATUS      current
    DESCRIPTION 
        "Sets the default initial value for the sLPConnectionK element 
         of the sLPConnectionTable and the default value for the 
         sLPConnectionIVMOk element of the sLPConnectionIVMOTable.  When 
         set by a management station, the value set should persist 
         across agent and system reboots.  The DEFVAL, therefore, is 
         only applicable when this default has never been set by a 
         management station."
    REFERENCE   
        "ITU-T Rec. X.282 | ISO/IEC 10742."
    ::= { sLPConnectionDefaults 2 }

sLPConnectionDefaultN1 OBJECT-TYPE
    SYNTAX      Integer32
    MAX-ACCESS  read-write
    STATUS      current
    DESCRIPTION 
        "Sets the default initial value for the sLPConnectionN1 element 
         of the sLPConnectionTable and a default value for the 
         sLPConnectionIVMOn1 element of the sLPConnectionIVMOTable.  
         When set by a management station, the value set should persist 
         across agent and system reboots.  The DEFVAL, therefore, is 
         only applicable when this default has never been set by a 
         management station."
    REFERENCE   
        "ITU-T Rec. X.282 | ISO/IEC 10742."
    ::= { sLPConnectionDefaults 3 }

sLPConnectionDefaultN2 OBJECT-TYPE
    SYNTAX      Integer32
    MAX-ACCESS  read-write
    STATUS      current
    DESCRIPTION 
        "Sets the default initial value for the sLPConnectionN2 element 
         of the sLPConnectionTable and the default value for the 
         sLPConnectionIVMOn2 element of the sLPConnectionIVMOTable.  
         When set by a management station, the value set should persist 
         across agent and system reboots.  The DEFVAL, therefore, is 
         only applicable when this default has never been set by a 
         management station."
    REFERENCE   
        "ITU-T Rec. X.282 | ISO/IEC 10742."
    ::= { sLPConnectionDefaults 4 }

sLPConnectionDefaultSequenceModulus OBJECT-TYPE
    SYNTAX      Integer32 (8 | 128)
    MAX-ACCESS  read-write
    STATUS      current
    DESCRIPTION 
        "Sets the default initial value for the sLPConnectionModulus 
         element of the sLPConnectionTable and the default value for the 
         sLPConnectionIVMOModulus element of the sLPConnectionIVMOTable.  
         When set by a management station, the value set should persist 
         across agent and system reboots.  The DEFVAL, therefore, is 
         only applicable when this default has never been set by a 
         management station."
    REFERENCE   
        "ITU-T Rec. X.282 | ISO/IEC 10742."
    ::= { sLPConnectionDefaults 5 }

sLPConnectionDefaultT1Timer OBJECT-TYPE
    SYNTAX      TimeInterval
    MAX-ACCESS  read-write
    STATUS      current
    DESCRIPTION 
        "Sets the default initial value for the sLPConnectionT1Timer 
         element of the sLPConnectionTable and the default value for the 
         sLPConnectionIVMOt1Timer element of the sLPConnectionIVMOTable.  
         When set by a management station, the value set should persist 
         across agent and system reboots.  The DEFVAL, therefore, is 
         only applicable when this default has never been set by a 
         management station."
    REFERENCE   
        "ITU-T Rec. X.282 | ISO/IEC 10742."
    ::= { sLPConnectionDefaults 6 }

sLPConnectionDefaultT2Timer OBJECT-TYPE
    SYNTAX      TimeInterval
    MAX-ACCESS  read-write
    STATUS      current
    DESCRIPTION 
        "Sets the default initial value for the sLPConnectionT2Timer 
         element of the sLPConnectionTable and the default value of the 
         sLPConnectionIVMOt2Timer element of the sLPConnectionIVMOTable.  
         When set by a management station, the value set should persist 
         across agent and system reboots.  The DEFVAL, therefore, is 
         only applicable when this default has never been set by a 
         management station."
    REFERENCE   
        "ITU-T Rec. X.282 | ISO/IEC 10742."
    ::= { sLPConnectionDefaults 7 }

sLPConnectionDefaultT3Timer OBJECT-TYPE
    SYNTAX      TimeInterval
    MAX-ACCESS  read-write
    STATUS      current
    DESCRIPTION 
        "Sets the default initial value for the sLPConnectionT3Timer 
         element of the sLPConnectionTable and the default value of the 
         sLPConnectionIVMOt3Timer element of the sLPConnectionIVMOTable.  
         When set by a management station, the value set should persist 
         across agent and system reboots.  The DEFVAL, therefore, is 
         only applicable when this default has never been set by a 
         management station."
    REFERENCE   
        "ITU-T Rec. X.282 | ISO/IEC 10742."
    ::= { sLPConnectionDefaults 8 }

sLPConnectionDefaultT4Timer OBJECT-TYPE
    SYNTAX      TimeInterval
    MAX-ACCESS  read-write
    STATUS      current
    DESCRIPTION 
        "Sets the default initial value for the sLPConnectionT4Timer 
         element of the sLPConnectionTable and the default value of the 
         sLPConnectionIVMOt4Timer element of the sLPConnectionIVMOTable.  
         When set by a management station, the value set should persist 
         across agent and system reboots.  The DEFVAL, therefore, is 
         only applicable when this default has never been set by a 
         management station."
    REFERENCE   
        "ITU-T Rec. X.282 | ISO/IEC 10742."
    ::= { sLPConnectionDefaults 9 }

lLCConnection2Defaults OBJECT IDENTIFIER
    ::= { osiDefaults 2 }

lLCConnection2DefaultMaximumRetransmissions OBJECT-TYPE
    SYNTAX      Integer32
    MAX-ACCESS  read-write
    STATUS      current
    DESCRIPTION 
        "Sets the default value for the 
         lLCConnection2MaximumRetransmissions element of the 
         lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 1 }

lLCConnection2DefaultReceivedWindowSize OBJECT-TYPE
    SYNTAX      Integer32
    MAX-ACCESS  read-write
    STATUS      current
    DESCRIPTION 
        "Sets the default value for the lLCConnection2ReceivedWindowSize 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 2 }

lLCConnection2DefaultSendWindowSize OBJECT-TYPE
    SYNTAX      Integer32
    MAX-ACCESS  read-write
    STATUS      current
    DESCRIPTION 
        "Sets the default value for the lLCConnection2SendWindowSize 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 3 }

lLCConnection2DefaultAcknowledgeTimeoutValue OBJECT-TYPE
    SYNTAX      TimeInterval
    MAX-ACCESS  read-write
    STATUS      current
    DESCRIPTION 
        "Sets the default value for the 
         lLCConnection2AcknowleTimeoutValue element of the 
         lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 4 }

lLCConnection2DefaultBusyStateTimeoutValue OBJECT-TYPE
    SYNTAX      TimeInterval
    MAX-ACCESS  read-write
    STATUS      current
    DESCRIPTION 
        "Sets the default value for the 
         lLCConnection2BusyStateTimeoutValue element of the 
         lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 5 }

lLCConnection2DefaultPBitTimeoutValue OBJECT-TYPE
    SYNTAX      TimeInterval
    MAX-ACCESS  read-write
    STATUS      current
    DESCRIPTION 
        "Sets the default value for the lLCConnection2BitTImeoutValue 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 6 }

lLCConnection2DefaultRejectTimeoutValue OBJECT-TYPE
    SYNTAX      TimeInterval
    MAX-ACCESS  read-write
    STATUS      current
    DESCRIPTION 
        "Sets the default value for the lLCConnection2RejectTimeoutValue 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 7 }

lLCConnection2DefaultRoute OBJECT-TYPE
    SYNTAX      OCTET STRING
    MAX-ACCESS  read-write
    STATUS      current
    DESCRIPTION 
        "Sets the default value for the lLCConnection2Route element of 
         the lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 8 }

lLCConnection2DefaultKStep OBJECT-TYPE
    SYNTAX      Integer32
    MAX-ACCESS  read-write
    STATUS      current
    DESCRIPTION 
        "Sets the default value for the lLCConnection2KStep element of 
         the lLCConnection2Table.  When set by a management station, the 
         value set should persist across agent and system reboots.  The 
         DEFVAL, therefore, is only applicable when this default has 
         never been set by a  managements station."
    REFERENCE   
        "IEEE 802.2 (ISO/IEC 8802-2)."
    ::= { lLCConnection2Defaults 9 }

lLCConnection2DefaultMaxSendWindowSize OBJECT-TYPE
    SYNTAX      Integer32
    MAX-ACCESS  read-write
    STATUS      current
    DESCRIPTION 
        "Sets the default value for the lLCConnection2MaxSendWindowSize 
         element of the lLCConnection2Table.  When set by a management 
         station, the value set should persist across agent and system 
         reboots.  The DEFVAL, therefore, is only applicable when this 
         default has never been set by a  managements station."
    REFERENCE   
        "IEEE 802.2 (ISO/IEC 8802-2)."
    ::= { lLCConnection2Defaults 10 }

lLCConnection2DefaultOptionalTolerationIPDUs OBJECT-TYPE
    SYNTAX      TruthValue
    MAX-ACCESS  read-write
    STATUS      current
    DESCRIPTION 
        "Sets the default value for the 
         lLCConnection2OptionalTolerationIPDUs element of the 
         lLCConnection2Table.  When set by a management station, the 
         value set should persist across agent and system reboots.  The 
         DEFVAL, therefore, is only applicable when this default has 
         never been set by a  management station."
    REFERENCE   
        "IEEE 802.2 (ISO/IEC 8802-2)."
    ::= { lLCConnection2Defaults 11 }

lLCConnectionlessAckDefaults OBJECT IDENTIFIER
    ::= { osiDefaults 3 }

lLCConnectionlessAckDefaultMaximumLLCInformationFieldSize OBJECT-TYPE
    SYNTAX      Integer32
    MAX-ACCESS  read-write
    STATUS      current
    DESCRIPTION 
        "Set the default value for the 
         lLCConnectionlessAckMaximumLLCInformationFieldSize element of 
         the lLCConnectionlessAckTable.  When set by a management 
         station, the value set should persist across the agen and 
         system reboots.  The DEFVAL, therefore, is only applicable when 
         this default has never been set by a management station."
    REFERENCE   
        "IEEE 802.2 (ISO/IEC 8802-2)"
    ::= { lLCConnectionlessAckDefaults 1 }

lLCConnectionlessAckDefaultMaximumRetransmissions OBJECT-TYPE
    SYNTAX      Integer32
    MAX-ACCESS  read-write
    STATUS      current
    DESCRIPTION 
        "Set the default value for the 
         lLCConnectionlessAckMaximumRetransmissions element of the 
         lLCConnectionlessAckTable.  When set by a management station, 
         the value set should persist across the agen and system 
         reboots.  The DEFVAL, therefore, is only applicable when this 
         default has never been set by a management station."
    REFERENCE   
        "IEEE 802.2 (ISO/IEC 8802-2)"
    ::= { lLCConnectionlessAckDefaults 2 }

osiNotifs OBJECT IDENTIFIER
    ::= { osiObjects 3 }

physicalBitErrorThresholdReached OBJECT-TYPE
    SYNTAX      OCTET STRING
    MAX-ACCESS  accessible-for-notify
    STATUS      current
    DESCRIPTION 
        "This parameter is used with a qualityofServiceAlarm 
         notification from the OPENSS7-TMN-SMI module indicating the row 
         in the dataCircuitTable to which the qualityofServiceAlarm 
         applies.  This parameter, then, indicates that the bit error 
         threshold has been surpassed."
    REFERENCE   
        "ITU-T Rec. X.281 | ISO/IEC 13642 bitErrorThresholdReached."
    ::= { osiNotifs 1 }

physicalConnectionError OBJECT-TYPE
    SYNTAX      OCTET STRING
    MAX-ACCESS  accessible-for-notify
    STATUS      current
    DESCRIPTION 
        "This parameter is used with the communicationsAlarm 
         notification from the OPENSS7-TMN-SMI module indicating the row 
         in the dataCircuitTable to which the communicationsAlarm 
         applies.  This parameter, then, indicates the connection error 
         that occurred."
    REFERENCE   
        "ITU-T Rec. X.281 | ISO/IEC 13642 connectionError."
    ::= { osiNotifs 2 }

phsyicalConnectionEstablished OBJECT-TYPE
    SYNTAX      OCTET STRING
    MAX-ACCESS  accessible-for-notify
    STATUS      current
    DESCRIPTION 
        "This parameter is used with the communicationsInformation 
         notification from the OPENSS7-TMN-SMI module indicating the row 
         in the dataCircuitTable to which the communicationsInformation  
         applies.  This parameter, then, indicates that the connection 
         has been established."
    REFERENCE   
        "ITU-T Rec. X.281 | ISO/IEC 13642 connectionEstablished."
    ::= { osiNotifs 3 }

physicalLossOfSignal OBJECT-TYPE
    SYNTAX      OCTET STRING
    MAX-ACCESS  accessible-for-notify
    STATUS      current
    DESCRIPTION 
        "This parameter is used with the communicationsAlarm 
         notification from the OPENSS7-TMN-SMI module indicating the row 
         in the dataCircuitTable to which the communicationsAlarm 
         applies.  This parameter, then, indicates that a loss of signal 
         error occured."
    REFERENCE   
        "ITU-T Rec. X.281 | ISO/IEC 13642 lossOfSignal."
    ::= { osiNotifs 4 }

physicalLossOfSynchronization OBJECT-TYPE
    SYNTAX      OCTET STRING
    MAX-ACCESS  accessible-for-notify
    STATUS      current
    DESCRIPTION 
        "This parameter is used with the communicationsAlarm 
         notification from the OPENSS7-TMN-SMImodule indicating the row 
         in the dataCircuitTable to which the communicationsAlarm 
         applies.  This parameter, then, indcates that a loss of 
         syncrhonization error occured."
    REFERENCE   
        "ITU-T Rec. X.281 | ISO/IEC 13642 lossOfSynchronization."
    ::= { osiNotifs 5 }

fRMR OBJECT-TYPE
    SYNTAX      OCTET STRING
    MAX-ACCESS  accessible-for-notify
    STATUS      current
    DESCRIPTION 
        "Provides a parameter containing the FRMR frame for use as 
         additional information with the communicationsAlarm issued for 
         an sLPConnection table entry when specificProblems has the 
         value fRMRReceived."
    REFERENCE   
        "ITU-T Rec. X.282 | ISO/IEC 10742 ASN.1 fRMR."
    ::= { osiNotifs 6 }

pdusDiscarded1 OBJECT-TYPE
    SYNTAX      Counter32
    MAX-ACCESS  accessible-for-notify
    STATUS      current
    DESCRIPTION 
        "Parameter for use with the lLCConnection2Event notification."
    REFERENCE   
        "IEEE 802.2 (ISO/IEC 8802-2) ASN.1, pdusDiscarded1."
    ::= { osiNotifs 7 }

pdusDiscarded2 OBJECT-TYPE
    SYNTAX      Counter32
    MAX-ACCESS  accessible-for-notify
    STATUS      current
    DESCRIPTION 
        "Parameter for use with the lLCConnection2Event notification."
    REFERENCE   
        "IEEE 802.2 (ISO/IEC 8802-2) ASN.1, pdusDiscarded2."
    ::= { osiNotifs 8 }

pduRetransmissions OBJECT-TYPE
    SYNTAX      Counter32
    MAX-ACCESS  accessible-for-notify
    STATUS      current
    DESCRIPTION 
        "Parameter for use with the lLCConnection2Event notification."
    REFERENCE   
        "IEEE 802.2 (ISO/IEC 8802-2) ASN.1, pduRetransmissions."
    ::= { osiNotifs 9 }

acknowledgeTimeout OBJECT-TYPE
    SYNTAX      TimeInterval
    MAX-ACCESS  accessible-for-notify
    STATUS      current
    DESCRIPTION 
        "Parameter for use with the lLCConnection2Event notification."
    REFERENCE   
        "IEEE 802.2 (ISO/IEC 8802-2) ASN.1, acknowledgeTimeout."
    ::= { osiNotifs 10 }

busyStateTimeout OBJECT-TYPE
    SYNTAX      TimeInterval
    MAX-ACCESS  accessible-for-notify
    STATUS      current
    DESCRIPTION 
        "Parameter for use with the lLCConnection2Event notification."
    REFERENCE   
        "IEEE 802.2 (ISO/IEC 8802-2) ASN.1, busyStateTimeout."
    ::= { osiNotifs 11 }

rejectTimeout OBJECT-TYPE
    SYNTAX      TimeInterval
    MAX-ACCESS  accessible-for-notify
    STATUS      current
    DESCRIPTION 
        "Parameter for use with the lLCConnection2Event notification."
    REFERENCE   
        "IEEE 802.2 (ISO/IEC 8802-2) ASN.1, rejectTimeout."
    ::= { osiNotifs 12 }

pBitTimeout OBJECT-TYPE
    SYNTAX      TimeInterval
    MAX-ACCESS  accessible-for-notify
    STATUS      current
    DESCRIPTION 
        "Parameter for use with the lLCConnection2Event notification."
    REFERENCE   
        "IEEE 802.2 (ISO/IEC 8802-2) ASN.1, pBitTimeout."
    ::= { osiNotifs 13 }

type2Violation OBJECT-TYPE
    SYNTAX      Counter32
    MAX-ACCESS  accessible-for-notify
    STATUS      current
    DESCRIPTION 
        "Parameter for use with the lLCConnection2Event notification."
    REFERENCE   
        "IEEE 802.2 (ISO/IEC 8802-2) ASN.1, type2Violation."
    ::= { osiNotifs 14 }

retranmissions OBJECT-TYPE
    SYNTAX      Counter32
    MAX-ACCESS  accessible-for-notify
    STATUS      current
    DESCRIPTION 
        "Parameter for use with the lLCConnection2Event or 
         lLCClessACKEvent notifications."
    REFERENCE   
        "IEEE 802.2 (ISO/IEC 8802-2) ASN.1, retransmissions."
    ::= { osiNotifs 15 }

type3Violation OBJECT-TYPE
    SYNTAX      Counter32
    MAX-ACCESS  accessible-for-notify
    STATUS      current
    DESCRIPTION 
        "Parameter for use with the lLCClessACKEvent notification."
    REFERENCE   
        "IEEE 802.2 (ISO/IEC 8802-2) ASN.1, 
         LLCClessACKEvent.type3Violation."
    ::= { osiNotifs 16 }

noResponse OBJECT-TYPE
    SYNTAX      Counter32
    MAX-ACCESS  accessible-for-notify
    STATUS      current
    DESCRIPTION 
        "Parameter for use with the lLCClessACKEvent notification."
    REFERENCE   
        "IEEE 802.2 (ISO/IEC 8802-2) ASN.1, 
         LLCClessACKEvent.noResponse."
    ::= { osiNotifs 17 }

pdusDiscarded OBJECT-TYPE
    SYNTAX      Counter32
    MAX-ACCESS  accessible-for-notify
    STATUS      current
    DESCRIPTION 
        "Parameter for use with the lLCStationEvent notification."
    REFERENCE   
        "IEEE 802.2 (ISO/IEC 8802-2) ASN.1, 
         LLCStationEvent.pdusDiscarded."
    ::= { osiNotifs 18 }

bufferProblems OBJECT-TYPE
    SYNTAX      Counter32
    MAX-ACCESS  accessible-for-notify
    STATUS      current
    DESCRIPTION 
        "Parameter for use with the lLCStationEvent notification."
    REFERENCE   
        "IEEE 802.2 (ISO/IEC 8802-2) ASN.1, 
         LLCStationEvent.bufferProblems."
    ::= { osiNotifs 19 }

notificationPDUHeader OBJECT-TYPE
    SYNTAX      OCTET STRING
    MAX-ACCESS  accessible-for-notify
    STATUS      current
    DESCRIPTION 
        "The header of the data NPDU header which caused this event.  
         This parmaeter is sused was an additional parameter of the 
         communicationsAlarm notification issued by the cLNS object when 
         the cLNS8473-P package is present."
    REFERENCE   
        "ITU-T Rec. X.283 | ISO/IEC 10733 notificationPDUHeader."
    ::= { osiNotifs 20 }

reachabilityChange OBJECT-TYPE
    SYNTAX      OCTET STRING
    MAX-ACCESS  accessible-for-notify
    STATUS      current
    DESCRIPTION 
        "Parameter for reporting reachability changes.  This parameter 
         is used as an additional parameter of the 
         communicationsInformation notification issued by the linkage 
         object when the linkage-ISO9542ES-P or linkage-ISO9542IS-P 
         package is present."
    REFERENCE   
        "ITU-T Rec. X.283 | ISO/IEC 10733 reachabilityChange."
    ::= { osiNotifs 21 }

notificationData OBJECT-TYPE
    SYNTAX      OCTET STRING
    MAX-ACCESS  accessible-for-notify
    STATUS      current
    DESCRIPTION 
        "Information relating to the call which resulted in the 
         notification.  This parameter is used as an additional 
         parameter of the communicationsAlarm notification issued by the 
         x25PLE object."
    REFERENCE   
        "ITU-T Rec. X.283 | ISO/IEC 10733 notificationData."
    ::= { osiNotifs 22 }

constraintViolation OBJECT-TYPE
    SYNTAX      TruthValue
    MAX-ACCESS  accessible-for-notify
    STATUS      current
    DESCRIPTION 
        "The specific error returned on failure of a REPLACE operation 
         when the MO prohibits such operations under certain conditions, 
         for example while the MO is in the disabled operational state."
    REFERENCE   
        "ISO/IEC 10589 constraintViolation."
    ::= { osiNotifs 23 }

notificationReceivingAdjacency OBJECT-TYPE
    SYNTAX      RowPointer
    MAX-ACCESS  accessible-for-notify
    STATUS      current
    DESCRIPTION 
        "The local managed object name of the adjacency upon which the 
         NPDU was received."
    REFERENCE   
        "ISO/IEC 10589 notificationReceivingAdjacency ."
    ::= { osiNotifs 24 }

notificationIDLength OBJECT-TYPE
    SYNTAX      Integer32 (0..8)
    MAX-ACCESS  accessible-for-notify
    STATUS      current
    DESCRIPTION 
        "The IDLength specified in the ignored PDU."
    REFERENCE   
        "ISO/IEC 10589 notificationIDLength ."
    ::= { osiNotifs 25 }

notificationAreaAddress OBJECT-TYPE
    SYNTAX      AreaAddress
    MAX-ACCESS  accessible-for-notify
    STATUS      current
    DESCRIPTION 
        "The Area Address which caused MaximumAreaAddresses to be 
         exceeded."
    REFERENCE   
        "ISO/IEC 10589 notificationAreaAddress ."
    ::= { osiNotifs 26 }

notificationAreaAddresses OBJECT-TYPE
    SYNTAX      AreaAddresses
    MAX-ACCESS  accessible-for-notify
    STATUS      current
    DESCRIPTION 
        "The set of Area Address from the neighbour's IIH PDU."
    REFERENCE   
        "ISO/IEC 10589 notificationAreaAddresses."
    ::= { osiNotifs 27 }

notificationSourceId OBJECT-TYPE
    SYNTAX      OCTET STRING (SIZE(1..10))
    MAX-ACCESS  accessible-for-notify
    STATUS      current
    DESCRIPTION 
        "The source ID of the LSP."
    REFERENCE   
        "ISO/IEC 10589 notificationSourceId."
    ::= { osiNotifs 28 }

notificationMaximumAreaAddresses OBJECT-TYPE
    SYNTAX      Integer32 (0..254)
    MAX-ACCESS  accessible-for-notify
    STATUS      current
    DESCRIPTION 
        "The maximum area addresses field of the received PDU."
    REFERENCE   
        "ISO/IEC 10589 notificationMaximumAreaAddresses."
    ::= { osiNotifs 29 }

notificationVirtualLinkChange OBJECT-TYPE
    SYNTAX      INTEGER { deleted(0), created(1) }
    MAX-ACCESS  accessible-for-notify
    STATUS      current
    DESCRIPTION 
        "This indicates whether the event was generated as a result of 
         the creation or deletion of a Virtual Link between two Level 2 
         Intermediate Systems."
    REFERENCE   
        "ISO/IEC 10589 notificationVirtualLinkChange."
    ::= { osiNotifs 30 }

notificationVirtualLinkAddress OBJECT-TYPE
    SYNTAX      NAddress
    MAX-ACCESS  accessible-for-notify
    STATUS      current
    DESCRIPTION 
        "The Network Entity Title of the Level 2 Intermediate System at 
         the remote end of the virtual link."
    REFERENCE   
        "ISO/IEC 10589 notificationVirtualLinkAddress ."
    ::= { osiNotifs 31 }

notificationSystemId OBJECT-TYPE
    SYNTAX      OCTET STRING (SIZE(0..8))
    MAX-ACCESS  accessible-for-notify
    STATUS      current
    DESCRIPTION 
        "The system ID of the source system generating the 
         notification."
    REFERENCE   
        "ISO/IEC 10589 notificationSystemId."
    ::= { osiNotifs 32 }

notificationVersion OBJECT-TYPE
    SYNTAX      DisplayString
    MAX-ACCESS  accessible-for-notify
    STATUS      current
    DESCRIPTION 
        "The version number reported by the other system."
    REFERENCE   
        "ISO/IEC 10589 notificationVersion."
    ::= { osiNotifs 33 }

notificationDesignatedIntermediateSystemChange OBJECT-TYPE
    SYNTAX      INTEGER { resigned(0), elected(1) }
    MAX-ACCESS  accessible-for-notify
    STATUS      current
    DESCRIPTION 
        "The direction of the change in Designated Intermediate System 
         status of this system."
    REFERENCE   
        "ISO/IEC 10589 ."
    ::= { osiNotifs 34 }

notificationOverloadStateChange OBJECT-TYPE
    SYNTAX      INTEGER { on(0), waiting(1) }
    MAX-ACCESS  accessible-for-notify
    STATUS      current
    DESCRIPTION 
        "The direction of the change in Overload status."
    REFERENCE   
        "ISO/IEC 10589 notificationOverloadStateChange."
    ::= { osiNotifs 35 }

reservedName OBJECT-TYPE
    SYNTAX      TruthValue
    MAX-ACCESS  accessible-for-notify
    STATUS      current
    DESCRIPTION 
        "The specific error returned on failure of a create operation 
         using a name reserved for other purposes."
    REFERENCE   
        "ISO/IEC 10589 reservedName."
    ::= { osiNotifs 36 }

notificationLSPHeader OBJECT-TYPE
    SYNTAX      OCTET STRING
    MAX-ACCESS  accessible-for-notify
    STATUS      current
    DESCRIPTION 
        "The header of the LSP."
    REFERENCE   
        "ISO/IEC 10589 notificationLSPHeader ."
    ::= { osiNotifs 37 }

osiOids OBJECT IDENTIFIER
    ::= { osiObjects 4 }

osiConformance OBJECT IDENTIFIER
    ::= { dlMIB 2 }

osiGroups OBJECT IDENTIFIER
    ::= { osiConformance 1 }

osiCompliances OBJECT IDENTIFIER
    ::= { osiConformance 2 }

se OBJECT IDENTIFIER
    ::= { 2 13 0 1 0 3 }

areaMismatch OBJECT-IDENTITY
    STATUS      current
    DESCRIPTION 
        "A communicationsAlarm notification is used to report an 
         areaMismatch event.  The notification is generated by a cLNS 
         managed object when an attempt to initialise with an adjacent 
         system fails as a result of two level 1 ISs not sharing any 
         area addresses in common.  The AREA ADDRESSES field and the ID 
         field of the received PDU are reported in the 
         additionalInformation field using the notificationAreaAddresses 
         and notificationSystemId parameters respectively. The 
         significance sub-parameter of each item of 
         additionalInformation shall be set to the value 'false' (i.e. 
         not significant) so that a managing system receiving the event 
         report will be less likely to reject it.  The value 
         areaMismatch shall be reported in the specificProblems 
         parameter.  The probableCause shall be set to the 
         configurationOrCustomizationError OBJECT IDENTIFIER from the 
         OPENSS7-TMN-SMI module.  The perceivedSeverity shall be set to 
         'Major'.  A subsequent communicationsAlarm with a 
         perceivedSeverity value of 'Cleared' shall not be generated. No 
         other fields or parameters shall be used, with the exception of 
         further parameters in the additionalInformation field. The 
         occurrence of this event is counted by the 
         linkageISISinitialisationFailures counter."
    ::= { se 0 }

attemptToExceedMaximumSequenceNumber OBJECT-IDENTITY
    STATUS      current
    DESCRIPTION 
        "A communicationsAlarm notification is used to report an 
         attemptToExceedMaximumSequenceNumber event.  The notificaion is 
         generated by a cLNS managed object when an attempt is made to 
         increment the sequence number of an LSP beyond the maximum 
         sequence number. The value attemptToExceedMaximumSequenceNumber 
         shall be reported in the specificProblems parameter. The 
         probableCause shall be set to communicationsProtocolError from 
         the OPENSS7-TMN-SMI module. The perceivedSeverity shall be set 
         to 'Major'.  A subsequent communicationsAlarm with a 
         perceivedSeverity value of 'Cleared' shall not be generated. No 
         other fields or parameters shall be used, with the exception of 
         further parameters in the additionalInformation field. The 
         occurrence of this event is counted by the 
         cLNSISISattemptsToExceedMaximumSequenceNumber
         counter."
    ::= { se 1 }

authenticationFailure OBJECT-IDENTITY
    STATUS      current
    DESCRIPTION 
        "A communicationsAlarm notification is used to report an 
         authenticationFailure event.  The notification is generated by 
         a cLNS managed object when a PDU is received with an incorrect 
         Authentication information field. The SystemId of the source 
         system shall be reported in the additionalInformation field 
         using the notificationSystemId parameter. The significance 
         sub-parameter of each item of additionalInformation shall be 
         set to the value 'false' (i.e. not significant) so that a 
         managing system receiving the event report will be less likely 
         to reject it. The value authenticationFailure shall be reported 
         in the specificProblems parameter.  The probableCause shall be 
         set to configurationOrCustomizationError from the 
         OPENSS7-TMN-SMI module.  The perceivedSeverity shall be set to 
         'Major'. A subsequent communicationsAlarm with a 
         perceivedSeverity value of 'Cleared' shall not be generated. No 
         other fields or parameters shall be used, with the exception of 
         further parameters in the additionalInformation field. The 
         occurrence of this event is counted by the 
         cLNSISISauthenticationFailures counter."
    ::= { se 2 }

corruptedLSPDetected OBJECT-IDENTITY
    STATUS      current
    DESCRIPTION 
        "A communicationsAlarm notification is used to report a 
         corruptedLSPDetected event.  The notification is generated when 
         a corrupted Link State PDU is detected in memory. The value 
         corruptedLSPDetected shall be reported in the specificProblems 
         parameter. The probableCause shall be set to corruptData from 
         the OPENSS7-TMN-SMI module.  The perceivedSeverity shall be set 
         to 'Minor'. A subsequent communicationsAlarm with a 
         perceivedSeverity value of 'Cleared' shall not be generated. No 
         other fields or parameters shall be used, with the exception of 
         further parameters in the additionalInformation field. The 
         occurrence of this event is counted by the 
         cLNSISIScorruptedLSPsDetected counter."
    ::= { se 3 }

iDFieldLengthMismatch OBJECT-IDENTITY
    STATUS      current
    DESCRIPTION 
        "A communicationsAlarm notification is used to report a 
         iDFieldLengthMismatch event.  The notification is generated by 
         a cLNS managed object instance when a PDU is received with a 
         different value for ID field length to that of the receiving 
         Intermediate system. The received ID LENGTH and SOURCE ID are 
         reported in the additionalInformation field using the 
         notificationIDLength and notificationSourceId parameters 
         respectively. The significance sub-parameter of each item of 
         additionalInformation shall be set to the value 'false' (i.e. 
         not significant) so that a managing system receiving the event 
         report will be less likely to reject it. The value 
         iDFieldLengthMismatch shall be reported in the specificProblems 
         parameter.  The probableCause shall be set to 
         configurationOrCustomizationError. The perceivedSeverity shall 
         be set to 'Major'. A subsequent communicationsAlarm with a 
         perceivedSeverity value of 'Cleared' shall not be generated. No 
         other fields or parameters shall be used, with the exception of 
         further parameters in the additionalInformation field. The 
         occurence of this event is counted by the 
         iDFieldLengthMismatches counter."
    ::= { se 4 }

lanL1DesignatedIntermediateSystemChange OBJECT-IDENTITY
    STATUS      current
    DESCRIPTION 
        "A communicationsInformation notification is used to report a 
         lanL1DesignatedIntermediateSystemChange event.  The 
         notification is generated by a linkage managed object instance 
         when the local system either elects itself or resigns as being 
         the LAN L1 Designated Intermediate System on this circuit. The 
         direction of the change is reported in the communicationData 
         field using the notificationDesignatedIntermediateSystemChange 
         parameter. The value lanL1DesignatedIntermediateSystemChange 
         shall be reported in the informationType parameter. No other 
         fields or parameters shall be used, with the exception of 
         further parameters in the informationData field. The relative 
         order of these events must be preserved. The occurrence of this 
         event is counted by the 
         lanL1DesignatedIntermediateSystemChanges counter."
    ::= { se 5 }

lSPL1DatabaseOverload OBJECT-IDENTITY
    STATUS      current
    DESCRIPTION 
        "A communicationsAlarm notification is used to report a 
         lSPL1DatabaseOverload event.  The notification is generated by 
         a cLSN managed object instance when the l1State of the system 
         changes between On and Waiting or Waiting and On. The resulting 
         state, shall be reported in the additionalInformation field 
         using the notificationOverloadStateChange parameter and in the 
         case of Waiting the SourceId of the LSP which precipitated the 
         overload shall be reported in the additionalInformation field 
         using the notificationSourceId parameter. The significance 
         sub-parameter of each item of additionalInformation shall be 
         set to the value 'false' (i.e. not significant) so that a 
         managing system receiving the event report will be less likely 
         to reject it. The value lSPL1DatabaseOverload shall be reported 
         in the specificProblems parameter. The probableCause shall be 
         set to resourceAtOrNearingCapacity from the OPENSS7-TMN-SMI 
         module. The perceivedSeverity shall be set to 'Major'.  A 
         subsequent communicationsAlarm with a perceivedSeverity value 
         of 'Cleared' shall not be generated. No other fields or 
         parameters shall be used, with the exception of further 
         parameters in the additionalInformation field. The occurrence 
         of this event shall be counted by the 
         cLNSISISlSPL1DatabaseOverloads counter."
    ::= { se 6 }

lSPL2DatabaseOverload OBJECT-IDENTITY
    STATUS      current
    DESCRIPTION 
        "A communicationsAlarm notification is used to report a 
         lSPL2DatabaseOverload event.  The notification is generated by 
         a cLNS managed object instance when the l2State of the system 
         changes between On and Waiting or Waiting and On. The resulting 
         state, shall be reported in the additionalInformation field 
         using the notificationOverloadStateChange parameter and in the 
         case of Waiting the SourceId of the LSP which precipitated the 
         overload shall be reported in the additionalInformation field 
         using the notificationSourceId parameter. The significance 
         sub-parameter of each item of additionalInformation shall be 
         set to the value 'false' (i.e. not significant) so that a 
         managing system receiving the event report will be less likely 
         to reject it. The value lSPL2DatabaseOverload shall be reported 
         in the specificProblems parameter. The probableCause shall be 
         set to resourceAtOrNearingCapacity from the OPENSS7-TMN-SMI 
         module. The perceivedSeverity shall be set to 'Major'.  A 
         subsequent communicationsAlarm with a perceivedSeverity value 
         of 'Cleared' shall not be generated. No other fields or 
         parameters shall be used, with the exception of further 
         parameters in the additionalInformation field. The occurence of 
         this event shall be counted by the 
         cLNSISISLevel2lSPL2DatabaseOverloads counter."
    ::= { se 7 }

manualAddressDroppedFromArea OBJECT-IDENTITY
    STATUS      current
    DESCRIPTION 
        "A communicationsAlarm notiification is used to report a 
         manualAddressDroppedFromArea event.  The notification is 
         generated by a cLNS managed object instance when one of the 
         manualAreaAddresses assigned to this system is ignored when 
         computing partitionAreaAddresses or areaAddresses because there 
         are more than MaximumAreaAddresses distinct Area Addresses. The 
         ignored Area Address shall be reported in the 
         additionalInformation field using the notificationAreaAddress 
         parameter. The significance sub-parameter of each item of 
         additionalInformation shall be set to the value 'false' (i.e. 
         not significant) so that a managing system receiving the event 
         report will be less likely to reject it. The event is generated 
         once for each Area Address in manualAreaAddresses which is 
         dropped. It is not generated again for that Area Address until 
         after it has been reinstated into areaAddresses (i.e. it is 
         only the action of dropping the Area Address and not the state 
         of being dropped, which causes the event to be generated). The 
         value manualAddressDroppedFromArea shall be reported in the 
         specificProblems parameter.  The probableCause shall be set to 
         configurationOrCustomizationError from the OPENSS7-TMN-SMI 
         module. The perceivedSeverity shall be set to 'Major'. A 
         subsequent communicationsAlarm with a perceivedSeverity value 
         of 'Cleared' shall not be generated. No other fields or 
         parameters shall be used, with the exception of further 
         parameters in the additionalInformation field. The occurrence 
         of this event shall be counted by the 
         cLNSISISmanualAddressesDroppedFromAreas counter."
    ::= { se 8 }

maximumAreaAddressesMismatch OBJECT-IDENTITY
    STATUS      current
    DESCRIPTION 
        "A communicationsAlarm notification is used to report a 
         maximumAreaAddressesMismatch event.  The notification is 
         generated by a cLNS managed object instance when a PDU is 
         received with a different value for maximumAreaAddresses from 
         that of the receiving Intermediate system.  The received 
         Maximum Area Addresses and Source ID are reported in the 
         additionalInformation field using the 
         notificationMaximumAreaAddresses and notificationSourceId 
         parameters respectively. The significance sub-parameter of each 
         item of additionalInformation shall be set to the value 'false' 
         (i.e. not significant) so that a managing system receiving the 
         event report will be less likely to reject it. The value 
         maximumAreaAddressesMismatch shall be reported in the 
         specificProblems parameter.  The probableCause shall be set to 
         configurationOrCustomizationError from the OPENSS7-TMN-SMI 
         module. The perceivedSeverity shall be set to 'Major'. A 
         subsequent communicationsAlarm with a perceivedSeverity value 
         of 'Cleared' shall not be generated. No other fields or 
         parameters shall be used, with the exception of further 
         parameters in the additionalInformation field. The occurence of 
         this event is counted by the 
         cLNSISISmaximumAreaAddressesMismatches counter."
    ::= { se 9 }

ownLSPPurge OBJECT-IDENTITY
    STATUS      current
    DESCRIPTION 
        "A communicationsAlarm notification is used to report a 
         ownLSPPurge event.  This notification is genrated by a cLNS 
         managed object instance when a zero aged copy of a system's own 
         LSP is received from some other system.  This represents an 
         erroneous attempt to purge the local system's LSP. The value 
         ownLSPPurge shall be reported in the specificProblems 
         parameter. The probableCause shall be set to 
         communicationsProtocolError from the OPENSS7-TMN-SMI module. 
         The perceivedSeverity shall be set to 'Minor'.  A subsequent 
         communicationsAlarm with a perceivedSeverity value of 'Cleared' 
         shall not be generated. No other fields or parameters shall be 
         used, with the exception of further parameters in the 
         additionalInformation field. The occurrence of this event is 
         counted by the cLNSISISownLSPPurges counter."
    ::= { se 10 }

partitionVirtualLinkChange OBJECT-IDENTITY
    STATUS      current
    DESCRIPTION 
        "A communicationsInformation notification is used to report a 
         partitionVirtualLinkChange event.  This notification is 
         generated by a cLNS managed object instance when a virtual link 
         (for the purposes of Level 1 partition repair) is either 
         created or deleted. The direction of the change and the 
         networkEntityTitle of the corresponding virtual adjacency 
         managed object are reported in the communicationData field 
         using the notificationVirtualLinkChange and 
         notificationVirtualLinkAddress parameters respectively.  The 
         value partitionVirtualLinkChange shall be reported in the 
         informationType parameter. No other fields or parameters shall 
         be used, with the exception of further parameters in the 
         informationData field. The relative order of events relating to 
         the same Virtual Link must be preserved. The occurrence of this 
         event is counted by the 
         cLNSISISLevel2partitionVirtualLinkChanges counter."
    ::= { se 11 }

rejectedAdjacency OBJECT-IDENTITY
    STATUS      current
    DESCRIPTION 
        "A communicationsAlarm notification is used to report a 
         rejectedAdjacency event.  This notification is generated by a 
         linkage managed object instance when an attempt to create a new 
         adjacency is rejected, because of a lack of resources. The ID 
         field of the received PDU is reported in the additionaldata 
         field using the notificationSystemId parameter.  The value 
         rejectedAdjacency shall be reported in the specificProblems 
         parameter. The probableCause shall be set to 
         resourceAtOrNearingCapacity from the OPENSS7-TMN-SMI module.  
         The perceivedSeverity shall be set to 'Major'. A subsequent 
         communicationsAlarm with a perceivedSeverity value of 'Cleared' 
         shall not be generated. No other fields or parameters shall be 
         used, with the exception of further parameters in the 
         additionalInformation field. The occurrence of this event is 
         counted by the linkageISISrejectedAdjacencies counter."
    ::= { se 12 }

sequenceNumberSkip OBJECT-IDENTITY
    STATUS      current
    DESCRIPTION 
        "A communicationsInformation notification is used to report a 
         sequenceNumberSkip event.  This notificiation  is generated by 
         a cLNS managed object instance when the sequence number of an 
         LSP is incremented by more than one. The value 
         sequenceNumberSkip shall be reported in the informationType 
         parameter. No other fields or parameters shall be used, with 
         the exception of parameters in the informationData field. The 
         occurrence of this event is counted by the 
         cLNSISISsequenceNumberSkips counter."
    ::= { se 13 }

versionSkew OBJECT-IDENTITY
    STATUS      current
    DESCRIPTION 
        "A communicationsAlarm notification is used to report a 
         versionSkew event.  The notification is generated by a linkage 
         managed object instance  when an attempt to initialise with an 
         adjacent system fails as a result of the versions of the 
         protocol are not compatible. The protocol version field from 
         the received PDU shall be reported in the additionalInformation 
         field using the notificationVersion parameter. The significance 
         sub-parameter of each item of additionalInformation shall be 
         set to the value 'false' (i.e. not significant) so that a 
         managing system receiving the event report will be less likely 
         to reject it. The value ISIS.versionSkew shall be reported in 
         the specificProblems parameter. The probableCause shall be set 
         to versionMismatch from the OPENSS7-TMN-SMI module.  The 
         perceivedSeverity shall be set to 'Major'. A subsequent 
         communicationsAlarm with a perceivedSeverity value of 'Cleared' 
         shall not be generated. No other fields or parameters shall be 
         used, with the exception of further parameters in the 
         additionalInformation field. The occurrence of this event is 
         counted by the linkageISISinitialisationFailures counter."
    ::= { se 14 }

originatingLSPBufferSizeMismatch OBJECT-IDENTITY
    STATUS      current
    DESCRIPTION 
        "A communicationsAlarm notification is used to report a 
         originatingLSPBufferSizeMismatch event.  The notification is 
         generated by a cLNS managed object instance when a Level 1 LSP 
         or Level 2 LSP is received which is larger than the local value 
         for originatingL1LSPBufferSize or originatingL2LSPBufferSize 
         respectively or when a Level 1 LSP or Level2 LSP is received 
         containing the originatingLSPBufferSize option and the value in 
         the PDU option field does not match the local value for 
         originatingL1LSPBufferSize or originatingL2LSPBufferSize 
         respectively. The contents of the LSP header are reported in 
         the additionalInformation field using the notificationLSPHeader 
         parameter. The significance sub-parameter of each item of 
         additionalInformation shall be set to False (i.e. not 
         significant) so that a managing system receiving the event 
         report will be less likely to reject it.  The value 
         originatingLSPBufferSizeMismatch shall be reported in the 
         specificProblems parameter. The probable cause shall be set to 
         configurationOrCustomizationError.  The perceivedSeverity shall 
         be set to 'Minor'. A subsequent communicationsAlarm with a 
         perceivedSeverity value of Cleared shall not be generated. No 
         other fields or parameters shall be used, with the exception of 
         further parameters in the additionalInformation field. The 
         occurrence of this event is counted by the 
         cLNSISISoriginatingLSPBufferSizeMismatches counter."
    ::= { se 15 }

lSPTooLargeToPropagate OBJECT-IDENTITY
    STATUS      current
    DESCRIPTION 
        "A communicationsAlarm notification is used to report a 
         lSPTooLargeToPropagate event.  The notification is generated by 
         a cLNS managed object instance when an attempt is made to 
         propagate an LSP PDU which is larger than the dataLinkBlockSize 
         for a circuit. The contents of the LSP header are reported in 
         the additionalInformation field using the notificationLSPHeader 
         parameter. The significance sub-parameter of each item of 
         additionalInformation shall be set to False (i.e. not 
         significant) so that a managing system receiving the event 
         report will be less likely to reject it. The value 
         lSPTooLargeToPropagate shall be reported in the 
         specificProblems parameter. The probable cause shall be set to 
         configurationOrCustomizationError. The perceivedSeverity shall 
         be set to 'Major'. A subsequent communicationsAlarm with a 
         preceivedSeverity value of Cleared shall not be generated. No 
         other fields or parameters shall be used, with the exception of 
         further parameters in the additionalInformation field. The 
         occurrence of this event is counted by the 
         cLNSISISlSPTooLargeToPropagate counter."
    ::= { se 16 }

sseoi OBJECT IDENTIFIER
    ::= { 2 13 0 2 0 }

spoi OBJECT IDENTIFIER
    ::= { sseoi 3 }

pDUDiscard OBJECT-IDENTITY
    STATUS      current
    DESCRIPTION 
        "The communicationsAlarm notification is use to report a 
         pDUDiscard event.
         
         The notification is generated by a cLNS managed object instance 
         when an 8473 data PDU is discarded. In addition to the 
         parameters specified by ISO/IEC 10733, the local adjacencyId of 
         the adjacency upon which the NPDU was received shall be 
         reported in the additionalInformation field using the 
         notificationReceivingAdjacency parameter. The significance 
         sub-parameter of each item of additionalInformation shall be 
         set to the value 'false' (i.e. not significant) so that a 
         managing system receiving the event report will be less likely 
         to reject it.
         
         The notification is generated by a cLNS managed object  
         instance when when a data NPDU is discarded due to any of the 
         reasons specified in ITU-T Rec. X.233 | ISO/IEC 8473-1 Table 7, 
         with the exception of 'PDU Discarded due to Congestion' The 
         header of the PDU in error shall be reported as a parameter in 
         the additionalInformation field of the communicationsAlarm, 
         using the notificationPDUHeader parameter.
         
         The significance sub-parameter of each item of 
         additionalInformation shall be set to the value 'False' (i.e.  
         not significant) so that a managing system receiving the event 
         report will be less likely to reject it. The value pDUDiscard 
         and that corresponding to the Reason For Discard shall both be 
         reported in the specificProblems parameter.
         
         The probableCause shall be set to communicationsProtocolError 
         from the OPENSS7-TMN-SMI module.
         
         The perceivedSeverity shall be set to 'Minor'.  A subsequent 
         communicationsAlarm with a perceivedSeverity value of 'Cleared' 
         shall not be generated. No other fields or parameters shall be 
         used, with the exception of further parameters in the 
         AdditionalInformation field.  A PDU which does not contain one 
         of the protocol identifiers defined in ITU-T Rec. X.233 | 
         ISO/IEC 8473-1 shall not cause this event.
         
         A PDU with a protocol ID 1000 0001 shall not cause this event 
         if it does not also contain the Version/Protocol Identifier 
         extension in 7.2.4 of ITU-T Rec.  X.233 | ISO/IEC 8473-1. If an 
         error report PDU is generated, the PDU header and Discard 
         Reason in the error report shall be the same as those in the 
         corresponding notification."
    ::= { spoi 1 }

pDUDiscardReasonNotSpecified OBJECT-IDENTITY
    STATUS      current
    DESCRIPTION 
        "Used as an additional specificProblem in a communicationsAlarm 
         with pDUDiscard."
    ::= { pDUDiscard 0 }

pDUDiscardProtocolProcedureError OBJECT-IDENTITY
    STATUS      current
    DESCRIPTION 
        "Used as an additional specificProblem in a communicationsAlarm 
         with pDUDiscard."
    ::= { pDUDiscard 1 }

pDUDiscardIncorrectChecksum OBJECT-IDENTITY
    STATUS      current
    DESCRIPTION 
        "Used as an additional specificProblem in a communicationsAlarm 
         with pDUDiscard."
    ::= { pDUDiscard 2 }

pDUDiscardHeaderSyntaxError OBJECT-IDENTITY
    STATUS      current
    DESCRIPTION 
        "Used as an additional specificProblem in a communicationsAlarm 
         with pDUDiscard."
    ::= { pDUDiscard 4 }

pDUDiscardSegmentationNeededButNotPermitted OBJECT-IDENTITY
    STATUS      current
    DESCRIPTION 
        "Used as an additional specificProblem in a communicationsAlarm 
         with pDUDiscard."
    ::= { pDUDiscard 5 }

pDUDiscardIncompletePDUReceived OBJECT-IDENTITY
    STATUS      current
    DESCRIPTION 
        "Used as an additional specificProblem in a communicationsAlarm 
         with pDUDiscard."
    ::= { pDUDiscard 6 }

pDUDiscardDuplicateOption OBJECT-IDENTITY
    STATUS      current
    DESCRIPTION 
        "Used as an additional specificProbelm in a communicationsAlarm 
         with pDUDiscard."
    ::= { pDUDiscard 7 }

pDUDiscardDestinationAddressUnreachable OBJECT-IDENTITY
    STATUS      current
    DESCRIPTION 
        "Used as an additional specificProblem in a communicationsAlarm 
         with pDUDiscard."
    ::= { pDUDiscard 128 }

pDUDiscardDestinationaAddressUnknown OBJECT-IDENTITY
    STATUS      current
    DESCRIPTION 
        "Used as an additional specificProblem in a communicationsAlarm 
         with pDUDiscard."
    ::= { pDUDiscard 129 }

pDUDiscardUnspecifiedSourceRouteingError OBJECT-IDENTITY
    STATUS      current
    DESCRIPTION 
        "Used as an additional specificProblem in a communicationsAlarm 
         with pDUDiscard."
    ::= { pDUDiscard 144 }

pDUDiscardSyntaxErrorInSourceRouteingField OBJECT-IDENTITY
    STATUS      current
    DESCRIPTION 
        "Used as an additional specificProblem in a communicationsAlarm 
         with pDUDiscard."
    ::= { pDUDiscard 145 }

pDUDiscardUnknownAddressInSourceRouteingField OBJECT-IDENTITY
    STATUS      current
    DESCRIPTION 
        "Used as an additional specificProblem in a communicationsAlarm 
         with pDUDiscard."
    ::= { pDUDiscard 146 }

pDUDiscardPathNotAcceptable OBJECT-IDENTITY
    STATUS      current
    DESCRIPTION 
        "Used as an additional specificProblem in a communicationsAlarm 
         with pDUDiscard."
    ::= { pDUDiscard 147 }

pDUDiscardLifetimeExpiredWhileDataUnitInTransit OBJECT-IDENTITY
    STATUS      current
    DESCRIPTION 
        "Used as an additional specificProblem in a communicationsAlarm 
         with pDUDiscard."
    ::= { pDUDiscard 160 }

pDUDiscardLifetimeExpiredDuringReassembly OBJECT-IDENTITY
    STATUS      current
    DESCRIPTION 
        "Used as an additional specificProblem in a communicationsAlarm 
         with pDUDiscard."
    ::= { pDUDiscard 161 }

pDUDiscardUnsupportedOptionNotSpecified OBJECT-IDENTITY
    STATUS      current
    DESCRIPTION 
        "Used as an additional specificProblem in a communicationsAlarm 
         with pDUDiscard."
    ::= { pDUDiscard 176 }

pDUDiscardUnsupportedProtocolVersion OBJECT-IDENTITY
    STATUS      current
    DESCRIPTION 
        "Used as an additional specificProblem in a communicationsAlarm 
         with pDUDiscard."
    ::= { pDUDiscard 177 }

pDUDiscardUnsupportedSecurityOption OBJECT-IDENTITY
    STATUS      current
    DESCRIPTION 
        "Used as an additional specificProblem in a communicationsAlarm 
         with pDUDiscard."
    ::= { pDUDiscard 178 }

pDUDiscardUnsupportedSourceRouteingOption OBJECT-IDENTITY
    STATUS      current
    DESCRIPTION 
        "Used as an additional specificProblem in a communicationsAlarm 
         with pDUDiscard."
    ::= { pDUDiscard 179 }

pDUDiscardUnsupportedRecordingOfRouteOption OBJECT-IDENTITY
    STATUS      current
    DESCRIPTION 
        "Used as an additional specificProblem in a communicationsAlarm 
         with pDUDiscard."
    ::= { pDUDiscard 180 }

pDUDiscardReassemblyInterference OBJECT-IDENTITY
    STATUS      current
    DESCRIPTION 
        "Used as an additional specificProblem in a communicationsAlarm 
         with pDUDiscard."
    ::= { pDUDiscard 181 }

iSO9542PDUDiscard OBJECT-IDENTITY
    STATUS      current
    DESCRIPTION 
        "The communicationsAlarm notification is used to report an 
         invalid9542PDU event.  This notification is generated by a 
         linkage managed object instance when an ISO 9542 PDU is 
         received which is discarded as result of the PDU Header Error 
         Detection or Protocol Error Processing Functions specified in 
         ISO 9542.
         
         The significance sub-parameter of each item of 
         additionalInformation shall be set to the value `False' (i.e. 
         not significant) so that a managing system receiving the event 
         report will be less likely to reject it.
         
         The value iSO9542PDUDiscard shall be reported in the 
         specificProblems parameter. The probableCause shall be set to 
         communicationsProtocolError from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field."
    ::= { spoi 2 }

providerInitiatedDisconnect OBJECT-IDENTITY
    STATUS      current
    DESCRIPTION 
        "The communicationsAlarm notification is used to report a 
         providerInitiatedDisconnect event.  This alarm is issued by a 
         x25PLE managed object instance upon receipt of a clear packet 
         with a cause code other than `DTE initiated'.
         
         The information relating to the packet shall be reported as a 
         parameter in the additionalInformation field of the 
         communicationsAlarm, using the notificationData parameter.
         
         The significance sub-parameter of each item of 
         additionalInformation shall be set to the value `False' (i.e. 
         not significant) so that a managing system receiving the event 
         report will be less likely to reject it. The value 
         providerInitiatedDisconnect shall be reported in the 
         specificProblems parameter.  The probableCause shall be set to 
         communicationsProtocolError from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field.
         
         This event is counted by the 
         x25PLEproviderInitiatedDisconnects, 
         x25PLE-DTEproviderInitiatedDisconnects or 
         x25PLE-DCEproviderInitiatedDisconnects counters."
    ::= { spoi 3 }

remotelyInitiatedReset OBJECT-IDENTITY
    STATUS      current
    DESCRIPTION 
        "The communicationsAlarm notification is used to report a 
         remotelyInitiatedReset event.  This notification is issued by a 
         x25PLE managed object instance upon occurance of a remotely 
         initiated reset.  This event is issued in lieu of a 
         'providerInitiatedReset' when operating in a DTE-DXE 
         environment. The information relating to the packet shall be 
         reported as a parameter in the additionalInformation field of 
         the communicationsAlarm, using the notificationData parameter.
         
         The significance sub-parameter of each item of 
         additionalInformation shall be set to the value `False' (i.e. 
         not significant) so that a managing system receiving the event 
         report will be less likely to reject it. The value 
         remotelyInitiatedDisconnect shall be reported in the 
         specificProblems parameter.  The probableCause shall be set to 
         communicationsProtocolError from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field.
         
         This event is counted by the x25PLEremotelyInitiatedResets, 
         x25PLE-DTEremotelyInitiatedResets or 
         x25PLE-DCEremotelyInitiatedResets counters."
    ::= { spoi 4 }

providerInitiatedReset OBJECT-IDENTITY
    STATUS      current
    DESCRIPTION 
        "The communicationsAlarm notification is used to report a 
         providerInitiatedReset event.  The alarm is issued by an x25PLE 
         managed object instance upon occurance of a provider initiated 
         reset.  This event is issued when operating in a DTE-DCE 
         environment. The information relating to the packet shall be 
         reported as a parameter in the additionalInformation field of 
         the communicationsAlarm, using the notificationData parameter.
         
         The significance sub-parameter of each item of 
         additionalInformation shall be set to the value `False' (i.e. 
         not significant) so that a managing system receiving the event 
         report will be less likely to reject it. The value 
         providerInitiatedReset shall be reported in the 
         specificProblems parameter.  The probableCause shall be set to 
         communicationsProtocolError from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field.
         
         This event is counted by the x25PLEproviderInitiatedResets, 
         x25PLE-DTEproviderInitiatedResets or 
         x25PLE-DCEproviderInitiatedResets counters."
    ::= { spoi 5 }

remotelyInitiatedRestart OBJECT-IDENTITY
    STATUS      current
    DESCRIPTION 
        "The communicationsAlarm notification is used to report a 
         remotelyInitiatedRestart event.  The alarm is issued by an 
         x25PLE managed object instance upon receipt of a remotely 
         (including provider) initiated restart.
         
         The information relating to the packet shall be reported as a 
         parameter in the additionalInformation field of the 
         communicationsAlarm, using the notificationData parameter.
         
         The significance sub-parameter of each item of 
         additionalInformation shall be et to the value `False' (i.e. 
         not significant) so that a managing system s8 receiving the 
         event report will be less likely to reject it. The value 
         remotelyInitiatedRestart shall be reported in the 
         specificProblems parameter. The probableCause shall be set to 
         communicationsProtocolError from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field.
         
         This event is counted by the x25PLEremotelyInitiatedRestarts, 
         x25PLE-DTEremotelyInitiatedRestarts or 
         x25PLE-DCEremotelyInitiatedRestarts counters."
    ::= { spoi 6 }

restartCountExceeded OBJECT-IDENTITY
    STATUS      current
    DESCRIPTION 
        "The communicationsAlarm notification is used to report a 
         restartCountExceeded event.  The alarm is issued by an x25PLE 
         managed object instance on restart failure due to restart count 
         (R20) exceeded. The information relating to the packet shall be 
         reported as a parameter in the additionalInformation field of 
         the communicationsAlarm, using the notificationData parameter.
         
         The significance sub-parameter of each item of 
         additionalInformation shall be set to the value `False' (i.e. 
         not significant) so that a managing system receiving the event 
         report will be less likely to reject it.
         
         The value restartCountExceeded shall be reported in the 
         specificProblems parameter. The probableCause shall be set to 
         communicationsProtocolError from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field.
         
         This event is counted by the x25PLErestartCountsExceeded, 
         x25PLE-DTErestartCountsExceeded or 
         x25PLEIVMO-DTErestartCountsExceeded counters."
    ::= { spoi 7 }

protocolErrorDetectedLocally OBJECT-IDENTITY
    STATUS      current
    DESCRIPTION 
        "The communicationsAlarm notification is used to report a 
         protocolErrorDetectedLocally event.  The alarm is issued by an 
         x25PLE managed object instance upon receipt of a packet which 
         causes the 'A=Error' action in the ISO 8208 state tables to be 
         taken.
         
         The information relating to the packet shall be reported as a 
         parameter in the additionalInformation field of the 
         communicationsAlarm, using the notificationData parameter..
         
         The values of cause diagnosand diagnostic codes shall be those 
         which would have been placed in a diagnostic packet had one 
         been generated by the DTE (i.e. as if it were a DTE). The 
         actual generation of such a packet is not required.
         
         The significance sub-parameter of each item of 
         additionalInformation shall be set to the value `False' (i.e. 
         not significant) so that a managing system receiving the event 
         report will be less likely to reject it. The value 
         communicationsProtocolErrorDetectedLocally shall be reported in 
         the specificProblems parameter.
         
         The probableCause shall be set to communicationsProtocolError 
         from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field.
         
         This event is counted by the 
         x25PLEprotocolErrorsDetectedLocally, 
         x25PLE-DTEprotocolErrorsDetectedLocally or 
         x25PLEIVMO-DTEprotocolErrorsDetectedLocally counts."
    ::= { spoi 8 }

accusedOfProtocolError OBJECT-IDENTITY
    STATUS      current
    DESCRIPTION 
        "The communicationsAlarm notification is used to report a 
         accusedOfProtocolError event.  The alarm is issued by an x25PLE 
         managed object instance upon receipt of a diagnostic packet or 
         a clear, reset or restart packet with a cause code equal to 
         `protocol error'. No other x25PLE communication alarm shall be 
         generated as a result of this particular instance of packet.
         
         The information relating to the packet shall be reported as a 
         parameter in the additionalInformation field of the 
         communicationsAlarm, using the notificationData parameter.
         
         The significance sub-parameter of each item of 
         additionalInformation shall be set to the value `False' (i.e. 
         not significant) so that a managing system receiving the event 
         report will be less likely to reject it. The value 
         accusedOfProtocolError shall be reported in the 
         specificProblems parameter.  The probableCause shall be set to 
         communicationsProtocolError from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field.
         
         This event is counted by the x25PLEprotocolErrorsAccusedOf or 
         x25PLE-DTEprotocolErrorsAccusedOf counters."
    ::= { spoi 9 }

callEstablishmentRetryCountExceeded OBJECT-IDENTITY
    STATUS      current
    DESCRIPTION 
        "The communicationsAlarm notification is used to report a 
         callEstablishmentRetryCountExceeded event.  The alarm is issued 
         by an x25PLE managed object instance on retry failure during 
         call establishment due to retry limit exceeded.
         
         The information relating to the call shall be reported as a 
         parameter in the additionalInformation field of the 
         communicationsAlarm, using the notificationData parameter.
         
         The significance sub-parameter of each item of 
         additionalInformation shall be set to the value `False' (i.e. 
         not significant) so that a managing system receiving the event 
         report will be less likely to reject it. The value 
         callEstablishmentRetryCountExceeded shall be reported in the 
         specificProblems parameter.
         
         The probableCause shall be set to communicationsProtocolError 
         from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field.
         
         This event is counted by the 
         x25PLEcallEstablishmentRetryCountsExceeded or 
         x25PLE-DTEcallEstablishmentRetryCountsExceeded counts."
    ::= { spoi 10 }

clearCountExceeded OBJECT-IDENTITY
    STATUS      current
    DESCRIPTION 
        "The communicationsAlarm notification is used to report a 
         clearCountExceeded event.  The alarm is issued by an x25PLE 
         managed object instance on retry failure due to clear limit 
         (R23) exceeded.  The information relating to the call shall be 
         reported as a parameter in the additionalInformation field of 
         the communicationsAlarm, using the notificationData parameter.
         
         The significance sub-parameter of each item of 
         additionalInformation shall be set to the value `False' (i.e. 
         not significant) so that a managing system receiving the event 
         report will be less likely to reject it.
         
         The value clearCountExceeded shall be reported in the 
         specificProblems parameter. The probableCause shall be set to 
         communicationsProtocolError from the OPENSS7-TMN-SMI module.
         
         The perceivedSeverity shall be set to `Minor'. A subsequent 
         communicationsAlarm with a perceivedSeverity value of `Cleared' 
         shall not be generated. No other fields or parameters shall be 
         used, with the exception of further parameters in the 
         AdditionalInformation field.
         
         This event is counted by the x25PLEclearCountsExceeded or 
         x25PLE-DTEclearCountsExceeded counts."
    ::= { spoi 11 }

iSReachabilityChange OBJECT-IDENTITY
    STATUS      current
    DESCRIPTION 
        "This notification is used to report a change in intermediate 
         system reachability."
    ::= { sseoi 4 1 }

eSReachabilityChange OBJECT-IDENTITY
    STATUS      current
    DESCRIPTION 
        "This notification is used to report a change in end system 
         reachability."
    ::= { sseoi 4 2 }

successfulConnectionEstablishment OBJECT-IDENTITY
    STATUS      current
    DESCRIPTION 
        "This notification is used to report successful connection 
         establishment."
    ::= { sseoi 4 3 }

sNPADTEAddress OBJECT-IDENTITY
    STATUS      current
    DESCRIPTION 
        "This identifier is used to report an SNPA DTE address."
    ::= { sseoi 5 1 }

sNPAMACAddress OBJECT-IDENTITY
    STATUS      current
    DESCRIPTION 
        "This identifier is used to report an SNPA MAC address."
    ::= { sseoi 5 2 }

protocol8473 OBJECT-IDENTITY
    STATUS      current
    DESCRIPTION 
        "This identifier is used to identify ISO/IEC 8473."
    ::= { sseoi 6 1 }

protocol9542ES OBJECT-IDENTITY
    STATUS      current
    DESCRIPTION 
        "This identifier is used to identify ISO/IEC 9542 for 
         end-systems."
    ::= { sseoi 6 2 }

protocol9542IS OBJECT-IDENTITY
    STATUS      current
    DESCRIPTION 
        "This identifier is used to identify ISO/IEC 9542 for 
         intermediate-systems."
    ::= { sseoi 6 3 }

lapbErrors OBJECT IDENTIFIER
    ::= { 2 15 0 9 1 1 }

activateFailure OBJECT-IDENTITY
    STATUS      current
    DESCRIPTION 
        "This object identity is used as the value of the probableCause 
         parameter in the processingErrorAlarm notification issued for 
         an sLPConnection table entry.  It indicates that the processing 
         error was a failure to activate the sLPConnection.  The 
         perceivedSeverity for the processingErrorAlarm is Minor."
    ::= { lapbErrors 1 }

activateFailureInsufficientResources OBJECT-IDENTITY
    STATUS      current
    DESCRIPTION 
        "This object identity is used as the value of the 
         specificProblems parameter in the processingErrorAlarm 
         notification issued for an sLPConnection table entry.  It 
         indicates that the reason for the activation failure was 
         insufficient resources."
    ::= { activateFailure 1 }

activateFailureProviderDoesNotExist OBJECT-IDENTITY
    STATUS      current
    DESCRIPTION 
        "This object identity is used as the value of the 
         specificProblems parameter in the processingErrorAlarm 
         notification issued for an sLPConnection table entry.  It 
         indicates that the reason for the activation failure was that 
         the specified provider does not exist."
    ::= { activateFailure 2 }

activateFailureProviderNotAvailable OBJECT-IDENTITY
    STATUS      current
    DESCRIPTION 
        "This object identity is used as the value of the 
         specificProblems parameter in the processingErrorAlarm 
         notification issued for an sLPConnection table entry.  It 
         indicates that the reason for the activation failure was that 
         the specified provider is not available for activation."
    ::= { activateFailure 3 }

activateFailureRequiredServiceNotAvailable OBJECT-IDENTITY
    STATUS      current
    DESCRIPTION 
        "This object identity is used as the value of the 
         specificProblems parameter in the processingErrorAlarm 
         notification issued for an sLPConnection table entry.  It 
         indicates that the reason for the activation failure was that 
         an underlying service required for activation is not 
         available."
    ::= { activateFailure 4 }

activateFailureSystemSpecific OBJECT-IDENTITY
    STATUS      current
    DESCRIPTION 
        "This object identity is used as the value of the 
         specificProblems parameter in the processingErrorAlarm 
         notification issued for an sLPConnection table entry.  It 
         indicates that the reason for the activation is system 
         specific."
    ::= { activateFailure 5 }

lapbSpecificProblems OBJECT IDENTIFIER
    ::= { 2 15 0 11 }

fRMRReceived OBJECT-IDENTITY
    STATUS      current
    DESCRIPTION 
        "This object identity is used as the value of the 
         specificProblems parameter in the communicationsAlarm 
         notification issued for an sLPConnection or lLCConnection2 
         table entry.  It indicates that an FRMR was received.  The FRMR 
         frame itself is include in the fRMR parameter provided as 
         additional information for the communicationsAlarm 
         notification.
         
         A FRMR frame was received.  The received FRMR frame is reported 
         as additionalInformation in the notification, using the fRMR 
         parameter.  THe significance sub-parameter shall be set as 
         described above.
         
         The probableCause parameter is set to 
         communicationsProtocolError.  This value, fRMRReceived, shall 
         be reported in the specificProblems parameter.  In addition, 
         the reason why the frame was sent is also returned in 
         specificProblems.
         
         The perceivedSeverity parameter is set to the value Minor.  A 
         subsequent communicationsAlarm with a preceivedSeverity of 
         Cleared is not generated.  No other parameters are used."
    REFERENCE   
        "ITU-T Rec. X.282 | ISO/IEC 10742 ASN.1 fRMRReceived."
    ::= { lapbSpecificProblems 5 }

fRMRReasons OBJECT IDENTIFIER
    ::= { lapbSpecificProblems 6 }

fRMRReasonsControlFieldUndefinedOrUnimplemented OBJECT-IDENTITY
    STATUS      current
    DESCRIPTION 
        "This object identity is used as an additional value of the 
         specificProblems parameter in the communicationsAlarm 
         notification issued for an sLPConnection or lLCConnection2 
         table entry.  It indicates that the reason for receiving the 
         FRMR was an undefined or unimplemented control field."
    REFERENCE   
        "ITU-T Rec. X.282 | ISO/IEC 10742 ASN.1 
         fRMRReasonsControlFieldUndefinedOrUnimplemented."
    ::= { fRMRReasons 1 }

fRMRReasonsFormatError OBJECT-IDENTITY
    STATUS      current
    DESCRIPTION 
        "This object identity is used as an additional value of the 
         specificProblems parameter in the communicationsAlarm 
         notification issued for an sLPConnection or lLCConnection2 
         table entry.  It indicates that the reason for receiving the 
         FRMR was a format error."
    REFERENCE   
        "ITU-T Rec. X.282 | ISO/IEC 10742 ASN.1 fRMRReasonsFormatError."
    ::= { fRMRReasons 2 }

fRMRReasonsInfoFieldLengthGreaterThanMaximum OBJECT-IDENTITY
    STATUS      current
    DESCRIPTION 
        "This object identity is used as an additional value of the 
         specificProblems parameter in the communicationsAlarm 
         notification issued for an sLPConnection or lLCConnection2 
         table entry.  It indicates that the reason for receiving the 
         FRMR was that the information field length was greater than the 
         maximum."
    REFERENCE   
        "ITU-T Rec. X.282 | ISO/IEC 10742 ASN.1 
         fRMRReasonsInfoFieldLengthGreaterThanMaximum."
    ::= { fRMRReasons 3 }

fRMRReasonsInvalidNR OBJECT-IDENTITY
    STATUS      current
    DESCRIPTION 
        "This object identity is used as an additional value of the 
         specificProblems parameter in the communicationsAlarm 
         notification issued for an sLPConnection or lLCConnection2 
         table entry.  It indicates that the reason for receiving the 
         FRMR was that the NR included in the command was invalid."
    REFERENCE   
        "ITU-T Rec. X.282 | ISO/IEC 10742 ASN.1 fRMRReasonsInvalidNR."
    ::= { fRMRReasons 4 }

fRMRReasonsNonSpecific OBJECT-IDENTITY
    STATUS      current
    DESCRIPTION 
        "This object identity is used as an additional value of the 
         specificProblems parameter in the communicationsAlarm 
         notification issued for an sLPConnection or lLCConnection2 
         table entry.  It indicates that the reason for receiving the 
         FRMR was unknown or unspecified."
    REFERENCE   
        "ITU-T Rec. X.282 | ISO/IEC 10742 ASN.1 fRMRReasonsNonSpecific."
    ::= { fRMRReasons 5 }

lLCConnection2Event NOTIFICATION-TYPE
    OBJECTS     { tmnObjectInstance }
    STATUS      current
    DESCRIPTION 
        "This event will be sent for the following condtions: DupIPDUs 
         Received, PDUs Discarded1, PDUs Discarded2, PDU 
         Retransmissions, Type2 Violation, Type2 Acknowledgement Timeout 
         Value, Type2 Reject Timeout Value, Type2 Busy-State, Timeout 
         Value Type2, P-Bit Timeout Value, Retranmissions.  Fr each 
         condition there is an appropriate parameter to be included in 
         the notification.
         
         Additional parameters of importance that may be included are:
         
             - pdusDiscarded1
             - pdusDiscarded2
             - pduRetransmissions
             - acknowledgeTimeout
             - busyStateTimeout
             - rejectTimeout
             - pBitTimeout
             - type2Violation
             - retransmissions"
    REFERENCE   
        "IEEE 802.2 (ISO/IEC 8802-3), lLCConnection2Event-N."
    ::= { osiNotifications 1 }

lLCClessACKEvent NOTIFICATION-TYPE
    OBJECTS     { tmnObjectInstance }
    STATUS      current
    DESCRIPTION 
        "This event will be sent for the following conditions: 
         Retransmission, NoResponse, Type3 Violation.  For each 
         condition, there is an appropriate parameter to be included in 
         the notification.
         
         Additional parameters of importance that may be included are:
         
            - type3Violation
            - retransmissions
            - noResponse"
    REFERENCE   
        "IEEE 802.2 (ISO/IEC 8802-3), lLCClessACKEvent-N."
    ::= { osiNotifications 2 }

lLCStationEvent NOTIFICATION-TYPE
    OBJECTS     { tmnObjectInstance }
    STATUS      current
    DESCRIPTION 
        "This notification will be sent ofr either pdusdiscarded, buffer 
         problems, or Type 3 retransmissions.
         
         Additional parameters of importance that may be included are:
         
            - pdusDiscarded
            - bufferProblems
            - ?? retransmissions"
    REFERENCE   
        "IEEE 802.2 (ISO/IEC 8802-3), lLCStationEvent-N."
    ::= { osiNotifications 3 }

osiObjectGroup OBJECT-GROUP
    OBJECTS     { physicalBitErrorThresholdReached, 
                  physicalConnectionError, phsyicalConnectionEstablished, 
                  physicalLossOfSignal, physicalLossOfSynchronization, 
                  fRMR, pdusDiscarded1, pdusDiscarded2, 
                  pduRetransmissions, acknowledgeTimeout, 
                  busyStateTimeout, rejectTimeout, pBitTimeout, 
                  type2Violation, retranmissions, type3Violation, 
                  noResponse, pdusDiscarded, bufferProblems, 
                  notificationPDUHeader, reachabilityChange, 
                  notificationData, constraintViolation, 
                  notificationReceivingAdjacency, notificationIDLength, 
                  notificationAreaAddress, notificationAreaAddresses, 
                  notificationSourceId, notificationMaximumAreaAddresses, 
                  notificationVirtualLinkChange, 
                  notificationVirtualLinkAddress, notificationSystemId, 
                  notificationVersion, 
                  notificationDesignatedIntermediateSystemChange, 
                  notificationOverloadStateChange, reservedName, 
                  notificationLSPHeader, llcDiscontinuityTime, 
                  sLPConnectionDefaultInterfaceType, 
                  sLPConnectionDefaultK, sLPConnectionDefaultN1, 
                  sLPConnectionDefaultN2, 
                  sLPConnectionDefaultSequenceModulus, 
                  sLPConnectionDefaultT1Timer, 
                  sLPConnectionDefaultT2Timer, 
                  sLPConnectionDefaultT3Timer, 
                  sLPConnectionDefaultT4Timer, 
                  lLCConnection2DefaultMaximumRetransmissions, 
                  lLCConnection2DefaultReceivedWindowSize, 
                  lLCConnection2DefaultSendWindowSize, 
                  lLCConnection2DefaultAcknowledgeTimeoutValue, 
                  lLCConnection2DefaultBusyStateTimeoutValue, 
                  lLCConnection2DefaultPBitTimeoutValue, 
                  lLCConnection2DefaultRejectTimeoutValue, 
                  lLCConnection2DefaultRoute, lLCConnection2DefaultKStep, 
                  lLCConnection2DefaultMaxSendWindowSize, 
                  lLCConnection2DefaultOptionalTolerationIPDUs, 
                  lLCConnectionlessAckDefaultMaximumLLCInformationFieldSize, 
                  lLCConnectionlessAckDefaultMaximumRetransmissions, 
                  communicationsEntityLocalSapNames, 
                  communicationsEntityOperationalState, sap1Address, 
                  sap1UserEntityNames, sap2Address, sap2UserEntityNames, 
                  sap2ProviderEntityNames, 
                  clProtocolMachineOperationalState, 
                  clProtocolMachineTotalRemoteSAPs, 
                  coProtocolMachineOperationalState, 
                  underlyingConnectionNames, suppportedConnectionNames, 
                  physicalEntityPhysicalEntityTitles, 
                  dataCircuitBitErrorsReceived, 
                  dataCircuitBitErrorsTransmitted, 
                  dataCircuitBitErrorsThreshold, dataCircuitType, 
                  dataCircuitPhysicalMediaNames, 
                  dataCircuitPhysicalInterfaceType, 
                  dataCircuitPhysicalInterfaceStandard, 
                  dataCircuitSynchronizationMode, 
                  dataCircuitTransmissionCoding, 
                  dataCircuitTransmissionMode, 
                  dataCircuitTransmissionRate, dataCircuitRowStatus, 
                  physicalConnectionEndpointIdentifier, 
                  physicalConnectionPortNumber, 
                  physicalConnectionRowStatus, 
                  datalinkEntityProviderEntityNames, 
                  datalinkEntityRowStatus, dLSAPRowStatus, 
                  lAPBDLEmT1Timer, lAPBDLEmT3Timer, lAPBDLEmW, 
                  lAPBDLEmXSend, lAPBDLEmXReceive, lAPBDLEmT2Timer, 
                  lAPBDLEreceivedMlpResets, lAPBDLEtimesMT1Expired, 
                  lAPBDLEIframesReassignments, lAPBDLEmlpFramesReceived, 
                  lAPBDLEmlpFramesSent, 
                  lAPBDLEmlpFramesOutsideWindowGuard, 
                  lAPBDLEreceivedMlpFramesInGuardRegion, 
                  lAPBDLERowStatus, sLPPMadministrativeState, 
                  sLPPMRowStatus, sLPConnectionInterfaceType, 
                  sLPConnectionK, sLPConnectionN1, sLPConnectionN2, 
                  sLPConnectionSequenceModulus, sLPConnectionT1Timer, 
                  sLPConnectionT2Timer, sLPConnectionFCSErrorsReceived, 
                  sLPConnectionFRMRsReceived, sLPConnectionFRMRsSent, 
                  sLPConnectionIFrameDataOctetsReceived, 
                  sLPConnectionIFrameDataOctetsSent, 
                  sLPConnectionIFramesReceived, sLPConnectionIFramesSent, 
                  sLPConnectionPollsReceived, sLPConnectionREJsReceived, 
                  sLPConnectionREJsSent, sLPConnectionRNRsReceived, 
                  sLPConnectionRNRsSent, sLPConnectionSABMsReceived, 
                  sLPConnectionSABMsSent, sLPConnectionProtocolState, 
                  sLPConnectionTimesT1Expired, sLPConnectionT3Timer, 
                  sLPConnectionTimesT3Expired, sLPConnectionT4Timer, 
                  sLPConnectionTimesT4Expired, 
                  sLPConnectionAbnormalLinkDisconnectsReceived, 
                  sLPConnectionAbnormalLinkDisconnectsSent, 
                  sLPConnectionLinkResetsReceived, 
                  sLPConnectionLinkResetsSent, 
                  sLPConnectionTimesN2Reached, 
                  sLPConnectionAdministrativeState, 
                  sLPConnectionOperationalState, sLPConnectionUsageState, 
                  sLPConnectionProceduralStatus, 
                  sLPConnectionAlarmStatus, sLPConnectionRowStatus, 
                  sLPConnectionIVMOinterfaceType, sLPConnectionIVMOk, 
                  sLPConnectionIVMOn1, sLPConnectionIVMOn2, 
                  sLPConnectionIVMOsequenceModulus, 
                  sLPConnectionIVMOt1Timer, sLPConnectionIVMOt2Timer, 
                  sLPConnectionIVMOt3Timer, sLPConnectionIVMOt4Timer, 
                  sLPConnectionIVMORowStatus, mACDLERowStatus, 
                  mACOperationalState, mACRowStatus, lLCDLERowStatus, 
                  lLCCLPMRowStatus, lLCCOPMRowStatus, resourceTypeIdName, 
                  resourceInfoManufacturerOUI, 
                  resourceInfoManufacturerName, 
                  resourceInfoManufacturerProductName, 
                  resourceInfoManufacturerProductVersion, 
                  lLCStationLLCName, lLCStationMaximumLSAPsConfigured, 
                  lLCStationNumberOfActiveLSAPs, 
                  lLCStationSupportedServicesTypes, lLCStationStatus, 
                  lLCStationType1AcknowledgeTimeoutValue, 
                  lLCStationType1MaximumRetryCount, 
                  lLCStationMaximumPDUN3, 
                  lLCStationMaximumRetransmissions4, 
                  lLCStationReceiveVariableLifetime, 
                  lLCStationTransmitVariableLifetime, 
                  lLCStationType3AcknowledgeTimeoutValue, 
                  lLCStationType3Retransmissions, 
                  lLCStationAvgBufferUseSize, lLCStationBufferProblems, 
                  lLCStationBufferSize, lLCStationMaxBufferUseSize, 
                  lLCStationInactiveLSAP, lLCStationPDUsDiscard, 
                  lLCStationSTRIndicator, lLCStationVersionNumber, 
                  lLCStationType1AcknowledgmentTimerTimeouts, 
                  lLCSAPAddress, lLCSAPRDE, rDESetupAgingEnabled, 
                  rDESetupAgingValue, rDESetupEnableType2Reset, 
                  rDESetupMaximumRouteDescriptors, 
                  rDESetupMaximumResponseTime, rDESetupMinimumPDUSize, 
                  rDESetupRDEHold, rDESetupRDEReplace, rDESetupName, 
                  rDESetupResetOnTestEnabled, rDEPairDiscardCounter, 
                  rDEPairNSRPDUCounter, rDEPairNSRSelectedCounter, 
                  rDEPairRIF, rDEPairSRFPDUCounter, rDEPairQueryCounter, 
                  lLCConnectionlessName, 
                  lLCConnectionlessMaximumLLCInformationFieldSize, 
                  lLCConnectionlessTESTReceivedABBResponse, 
                  lLCConnectionlessTESTReceivedCommand, 
                  lLCConnectionlessTESTReceivedResponse, 
                  lLCConnectionlessTESTSentABBResponse, 
                  lLCConnectionlessTESTSentCommand, 
                  lLCConnectionlessTESTSentResponse, 
                  lLCConnectionlessUIReceived, lLCConnectionlessUISent, 
                  lLCConnectionlessXIDReceivedCommand, 
                  lLCConnectionlessXIDReceivedResponse, 
                  lLCConnectionlessXIDSentCommand, 
                  lLCConnectionlessXIDSentResponse, lLCConnection2Name, 
                  lLCConnection2MaximumRetransmissions, 
                  lLCConnection2ReceivedWindowSize, 
                  lLCConnection2SendWindowSize, 
                  lLCConnection2AcknowledgeTimeoutValue, 
                  lLCConnection2BusyStateTimeoutValue, 
                  lLCConnection2PBitTimeoutValue, 
                  lLCConnection2RejectTimeoutValue, 
                  lLCConnection2LocalBusy, lLCConnection2RemoteBusy, 
                  lLCConnection2RemoteReset, lLCConnection2LocalReset, 
                  lLCConnection2ProviderReset, lLCConnection2Route, 
                  lLCConnection2KStep, lLCConnection2MaxSendWindowSize, 
                  lLCConnection2ReceivedI, lLCConnection2SentI, 
                  lLCConnection2SentAcks, lLCConnection2ReceivedAcks, 
                  lLCConnection2ReceivedFRMR, lLCConnection2SentFRMR, 
                  lLCConnection2ReceivedRR, lLCConnection2SentRR, 
                  lLCConnection2ReceivedRNR, lLCConnection2SentRNR, 
                  lLCConnection2ReceivedREJ, lLCConnection2SentREJ, 
                  lLCConnection2ReceivedSABME, lLCConnection2SentSABME, 
                  lLCConnection2ReceivedUA, lLCConnection2SentUA, 
                  lLCConnection2ReceivedDISC, lLCConnection2SentDISC, 
                  lLCConnection2ReceivedDM, lLCConnection2SentDM, 
                  lLCConnection2PDUsDiscarded1, 
                  lLCConnection2PDUsDiscarded2, 
                  lLCConnection2PDURetransmissions, 
                  lLCConnection2OptionalTolerationIPDUs, 
                  lLCConnection2DuplicateIPDUsReceived, 
                  lLCConnection2Violation, lLCConnection2ProtocolState, 
                  lLCConnection2AdministrativeState, 
                  lLCConnection2OperationalState, 
                  lLCConnection2UsageState, 
                  lLCConnection2ProceduralStatus, 
                  lLCConnection2AlarmStatus, 
                  lLCConnection2IVMOMaximumRetransmissions, 
                  lLCConnection2IVMOReceivedWindowSize, 
                  lLCConnection2IVMOSendWindowSize, 
                  lLCConnection2IVMOAcknowledgeTimeoutValue, 
                  lLCConnection2IVMOBusyStateTimeoutValue, 
                  lLCConnection2IVMOBitTimeoutValue, 
                  lLCConnection2IVMORejectTimeoutValue, 
                  lLCConnection2IVMORoute, lLCConnection2IVMOKStep, 
                  lLCConnection2IVMOMaxSendWindowSize, 
                  lLCConnection2IVMOOptionalTolerationIPDUs, 
                  lLCConnectionlessAckMaximumLLCInformationFieldSize, 
                  lLCConnectionlessAckMaximumRetransmissions, 
                  lLCConnectionlessAckTESTReceivedABBResponse, 
                  lLCConnectionlessAckTESTReceivedCommand, 
                  lLCConnectionlessAckTESTReceivedResponse, 
                  lLCConnectionlessAckTESTSentABBResponse, 
                  lLCConnectionlessAckTESTSentCommand, 
                  lLCConnectionlessAckTESTSentResponse, 
                  lLCConnectionlessAckReceiveResources, 
                  lLCConnectionlessAckUIReceived, 
                  lLCConnectionlessAckUISent, 
                  lLCConnectionlessAckXIDReceivedCommand, 
                  lLCConnectionlessAckXIDReceivedResponse, 
                  lLCConnectionlessAckXIDSentCommand, 
                  lLCConnectionlessAckXIDSentResponse, 
                  lLCConnectionlessAckRetransmissions, 
                  lLCConnectionlessAckNoResponse, 
                  lLCConnectionlessAckCommandIP, 
                  lLCConnectionlessAckCommandIT, 
                  lLCConnectionlessAckCommandOK, 
                  lLCConnectionlessAckCommandPE, 
                  lLCConnectionlessAckCommandRS, 
                  lLCConnectionlessAckCommandUE, 
                  lLCConnectionlessAckCommandUN, 
                  lLCConnectionlessAckReceivedACCommand, 
                  lLCConnectionlessAckSentACCommand, 
                  lLCConnectionlessAckResponseIP, 
                  lLCConnectionlessAckResponseIT, 
                  lLCConnectionlessAckResponseNE, 
                  lLCConnectionlessAckResponseNR, 
                  lLCConnectionlessAckResponseOK, 
                  lLCConnectionlessAckResponseRS, 
                  lLCConnectionlessAckResponseUE, 
                  lLCConnectionlessAckResponseUN, 
                  lLCConnectionlessAckViolation, 
                  lLCConnectionlessAckIVMOMaximumLLCInformationFieldSize, 
                  lLCConnectionlessAckIVMOMaximumRetransmissions, 
                  lLCConnectionlessAckIVMORowStatus, networkEntityTitles, 
                  networkEntitySystemTypes, networkEntityRowStatus, 
                  nSAPRowStatus, cLNSAdministrativeState, 
                  cLNSSupportedProtocols, cLNSOperationalSystemType, 
                  cLNSOctetsSentCounter, cLNSOctetsReceivedCounter, 
                  cLNSSegmentsReceived, cLNSSegmentsDiscarded, 
                  cLNSAssemblingSegmentsDiscarded, 
                  cLNSErrorReportsReceived, cLNSpDUDiscards, 
                  cLNSCongestionDiscards, cLNSMaximumLifetime, 
                  cLNSEnableChecksum, cLNSRowStatus, cLNSISISversion, 
                  cLNSISISiSType, cLNSISISsystemId, 
                  cLNSISISmaximumPathSplits, 
                  cLNSISISminimumLSPTransmissionInterval, 
                  cLNSISISmaximumLSPGenerationInterval, 
                  cLNSISISminimumBroadcastLSPTransmissionInterval, 
                  cLNSISIScompleteSNPInterval, 
                  cLNSISISoriginatingL1LSPBufferSize, 
                  cLNSISISmanualAreaAddresses, 
                  cLNSISISmaximumAreaAddresses, 
                  cLNSISISminimumLSPGenerationInterval, 
                  cLNSISISpollESHelloRate, cLNSISISpartialSNPInterval, 
                  cLNSISISwaitingTime, cLNSISISdRISISHelloTimer, 
                  cLNSISISl1State, cLNSISISareaAddresses, 
                  cLNSISIScorruptedLSPsDetected, 
                  cLNSISISlSPL1DatabaseOverloads, 
                  cLNSISISmanualAddressesDroppedFromAreas, 
                  cLNSISISattemptsToExceedMaximumSequenceNumber, 
                  cLNSISISsequenceNumberSkips, cLNSISISownLSPPurges, 
                  cLNSISISiDFieldLengthMismatches, 
                  cLNSISISmaximumAreaAddressesMismatches, 
                  cLNSISISoriginatingLSPBufferSizeMismatches, 
                  cLNSISISlSPTooLargeToPropagate, 
                  cLNSISISareaTransmitPassword, 
                  cLNSISISareaReceivePasswords, 
                  cLNSISISauthenticationFailures, cLNSISISRowStatus, 
                  cLNSISISLevel2maximumVirtualAdjacencies, 
                  cLNSISISLevel2partitionAreaAddresses, 
                  cLNSISISLevel2partitionDesignatedL2IntermediateSystem, 
                  cLNSISISLevel2partitionVirtualLinkChanges, 
                  cLNSISISLevel2originatingL2LSPBufferSize, 
                  cLNSISISLevel2l2State, 
                  cLNSISISLevel2lSPL2DatabaseOverloads, 
                  cLNSISISLevel2domainTransmitPassword, 
                  cLNSISISLevel2domainReceivePasswords, 
                  cLNSISISLevel2RowStatus, linkageOperationalState, 
                  linkageAdministrativeState, linkageSnServiceProvider, 
                  linkageSnSAP, linkageOperationalProtocols, 
                  linkageISiSO9542OperationalSubsets, 
                  linkageISHoldingTimerMultiplier, 
                  linkageISISConfigurationTimer, 
                  linkageISSuggestedEsConfigurationTimer, 
                  linkageISRedirectHoldingTime, 
                  linkageISESReachabilityChanges, 
                  linkageISInvalid9542PDUs, 
                  linkageESiSO9542OperationalSubsets, 
                  linkageESHoldingTimerMultiplier, 
                  linkageESManualISSNPAAddress, 
                  linkageESDefaultESConfigTimer, 
                  linkageESActiveESConfigTimer, 
                  linkageESISReachabilityChanges, 
                  linkageESInvalid9542PDUs, linkageEnableChecksum, 
                  linkageInitialMinimumTimer, linkageReserveTimer, 
                  linkageIdleTimer, linkageSNDCFCallsPlaced, 
                  linkageSNDCFCallsFailed, linkageCODLCallsPlaced, 
                  linkageCODLCallsFailed, linkageISISType, 
                  linkageISISiSISHelloTimer, linkageISISl1DefaultMetric, 
                  linkageISISl1DelayMetric, linkageISISl1ExpenseMetric, 
                  linkageISISl1ErrorMetric, linkageISISexternalDomain, 
                  linkageISISchangedInAdjacencyState, 
                  linkageISISinitialisationFailures, 
                  linkageISISrejectedAdjacencies, 
                  linkageISISiSISControlPDUsSent, 
                  linkageISISiSISControlPDUsReceived, 
                  linkageISISiDFieldLengthMismatches, 
                  linkageISISmaximumAreaAddressesMismatches, 
                  linkageISIScircuitTransmitPassword, 
                  linkageISIScircuitReceivedPasswords, 
                  linkageISISauthenticationFailures, 
                  linkageISISl1IntermediateSystemPriority, 
                  linkageISISl1CircuitID, 
                  linkageISISl1DesignatedIntermediateSystem, 
                  linkageISISlanL1DesignatedIntermediateSystemChanges, 
                  linkageISIScallEstablishmentDefaultMetricIncrement, 
                  linkageISIScallEstablishmentDelayMetricIncrement, 
                  linkageISIScallEstablishmentExpenseMetricIncrement, 
                  linkageISIScallEstablishmentErrorMetricIncrement, 
                  linkageISISptPtCircuitID, linkageISISoutgoingCallIVMO, 
                  linkageISISneighborSNPAAddress, 
                  linkageISISl2DefaultMetric, linkageISISl2DelayMetric, 
                  linkageISISl2ExpenseMetric, linkageISISl2ErrorMetric, 
                  linkageISISmanualL2OnlyMode, 
                  linkageISISl2IntermediateSystemPriority, 
                  linkageISISl2CircuitID, 
                  linkageISISl2DesignatedIntermediateSystem, 
                  linkageISISlanL2DesignatedIntermediateSystemChanges, 
                  linkageRowStatus, cONSAdministrativeState, 
                  cONSOperationalSystemType, cONSRowStatus, 
                  networkConnectionLocalNSAPMO, 
                  networkConnectionRemoteNSAPAddress, 
                  networkConnectionRowStatus, x25PLEoperationalState, 
                  x25PLEadministrativeState, 
                  x25PLEprotocolVersionSupported, x25PLElocalDTEAddress, 
                  x25PLEMode, x25PLEdefaultThroughputClasses, 
                  x25PLEflowControlParameterNegotiation, 
                  x25PLEdefaultPackageSizes, 
                  x25PLEthroughputClassNegotiation, 
                  x25PLEsNserviceProvider, x25PLEsNsAP, 
                  x25PElogicalChannelAssignments, x25PLEinterfaceMode, 
                  x25PLEdefaultThroughputClass, 
                  x25PLEflowControlNegotiationPermitted, 
                  x25PLEcallDeflectionSubscription, 
                  x25PLEmaxActiveCircuits, x25PLErestartTime, 
                  x25PLEdefaultPacketSize, x25PLEdefaultWindowSize, 
                  x25PLEminimumRecallTimer, x25PLErestartCount, 
                  x25PLEsN-ServiceProvider, x25PLEsN-SA-P, 
                  x25PLElogicalChannelAssignments, 
                  x25PLEpacketSequencing, x25PLEoctetsSentCounter, 
                  x25PLEoctetsReceivedCounter, x25PLEdataPacketsSent, 
                  x25PLEdataPacketsReceived, x25PLEcallAttempts, 
                  x25PLEcallsConnected, 
                  x25PLEproviderInitiatedDisconnects, x25PLEcallTimeouts, 
                  x25PLEclearTimeouts, x25PLEremotelyInitiatedResets, 
                  x25PLEdataRetransmissionTimerExpiries, 
                  x25PLEproviderInitiatedResets, x25PLEresetTimeouts, 
                  x25PLEremotelyInitiatedRestarts, 
                  x25PLErestartCountsExceeded, 
                  x25PLEprotocolErrorsDetectedLocally, 
                  x25PLEprotocolErrorsAccusedOf, 
                  x25PLEcallEstablishmentRetryCountsExceeded, 
                  x25PLEclearCountsExceeded, x25PLEpLEClientMOName, 
                  x25PLEregistrationRequestTime, 
                  x25PLEregistrationRequestCount, 
                  x25PLEregistrationPermitted, x25PLERowStatus, 
                  x25PLE-DTEcallDeflectionSubscription, 
                  x25PLE-DTEcallRequestResponseTimer, 
                  x25PLE-DTEextendedPacketSequenceNumbering, 
                  x25PLE-DTEmaxActiveCircuits, 
                  x25PLE-DTEminimumRecallTimer, 
                  x25PLE-DTEresetRequestResponseTimer, 
                  x25PLE-DTErestartRequestRetransmissionCount, 
                  x25PLE-DTErestartRequestResponseTimer, 
                  x25PLE-DTEclearRequestResponseTimer, 
                  x25PLE-DTEinterruptResponseTimer, 
                  x25PLE-DTEresetRequestRetransmissionCount, 
                  x25PLE-DTEclearRequestRetransmissionCount, 
                  x25PLE-DTEcallAttempts, 
                  x25PLE-DTEprotocolErrorsDetectedLocally, 
                  x25PLE-DTEprotocolErrorsAccusedOf, 
                  x25PLE-DTEcallEstablishmentRetryCountsExceeded, 
                  x25PLE-DTEoctetsReceivedCounter, 
                  x25PLE-DTEoctetsSentCounter, x25PLE-DTEcallTimeouts, 
                  x25PLE-DTEcallsConnected, 
                  x25PLE-DTEclearCountsExceeded, x25PLE-DTEclearTimeouts, 
                  x25PLE-DTEdataPacketsReceived, 
                  x25PLE-DTEdataPacketsSent, 
                  x25PLE-DTEdataRetransmissionTimerExpiries, 
                  x25PLE-DTEproviderInitiatedResets, 
                  x25PLE-DTEproviderInitiatedDisconnects, 
                  x25PLE-DTEremotelyInitiatedResets, 
                  x25PLE-DTEremotelyInitiatedRestarts, 
                  x25PLE-DTEresetTimeouts, 
                  x25PLE-DTErestartCountsExceeded, 
                  x25PLE-DTEwindowStatusTransmissionTimer, 
                  x25PLE-DTEwindowRotationTimer, 
                  x25PLE-DTEdataPacketRetransmissionCount, 
                  x25PLE-DTErejectResponseTimer, 
                  x25PLE-DTErejectRetransmissionCount, 
                  x25PLE-DTEregistrationRequestResponseTimer, 
                  x25PLE-DTEregistrationRequestRetransmissionCount, 
                  x25PLE-DTEregistrationPermitted, 
                  x25PLE-DCEcallAttempts, x25PLE-DCEcallsConnected, 
                  x25PLE-DCEcUG, x25PLE-DCEfastSelectAcceptance, 
                  x25PLE-DCEincomingCallsBarred, 
                  x25PLE-DCEoneWayLogicalChannelOutgoing, 
                  x25PLE-DCEoutgoingCallsBarred, 
                  x25PLE-DCEdataPacketsReceived, 
                  x25PLE-DCEdataPacketsSent, 
                  x25PLE-DCEinterruptPacketsReceived, 
                  x25PLE-DCEinterruptPacketsSent, 
                  x25PLE-DCEinterruptTimerExpiries, 
                  x25PLE-DCEoctetsReceivedCounter, 
                  x25PLE-DCEoctetsSentCounter, 
                  x25PLE-DCEproviderInitiatedDisconnects, 
                  x25PLE-DCEproviderInitiatedResets, 
                  x25PLE-DCEremotelyInitiatedRestarts, 
                  x25PLE-DCEremotelyInitiatedResets, 
                  x25PLE-DCEresetTimeouts, x25PLE-DCEx25SegmentsReceived, 
                  x25PLE-DCEx25SegmentsSent, x25PLE-DCEbilateralCUG, 
                  x25PLE-DCEbilateralCUGWithOutgoingAccess, 
                  x25PLE-DCEcallDeflectionSubscription, 
                  x25PLE-DCEcallRedirection, 
                  x25PLE-DCEchargingInformation, 
                  x25PLE-DCEcUGWithIncomingAccess, 
                  x25PLE-DCEcUGWithOutgoingAccess, 
                  x25PLE-DCEdBitModification, 
                  x25PLE-DCEdefaultThroughputClassesAssignment, 
                  x25PLE-DCEextendedPacketSequenceNumbering, 
                  x25PLE-DCEhuntGroup, 
                  x25PLE-DCEincomingCallBarredWithinCUG, 
                  x25PLE-DCElocalChargingPrevention, 
                  x25PLE-DCEnonStandardDefaultPacketSizes, 
                  x25PLE-DCEnonStandardDefaultWindowSizes, 
                  x25PLE-DCEnUIOverride, x25PLE-DCEnUISubscription, 
                  x25PLE-DCEoneWayLogicalChannelIncoming, 
                  x25PLE-DCEonlineFacilityRegistration, 
                  x25PLE-DCEoutgoingCallBarredWithinCUG, 
                  x25PLE-DCEpacketRetransmission, 
                  x25PLE-DCEreverseChargingAcceptance, 
                  x25PLE-DCErOASubscription, x25PLE-DCEclearIndication, 
                  x25PLE-DCEincomingCall, x25PLE-DCEresetIndication, 
                  x25PLE-DCErestartIndication, x25PLEIVMOlocalDTEAddress, 
                  x25PLEIVMOlogicalChannelAssignments, 
                  x25PLEIVMOsN-ServiceProvider, 
                  x25PLEIVMOdefaultPacketSizes, 
                  x25PLEIVMOdefaultThroughputClasses, 
                  x25PLEIVMOdefaultWindowSizes, 
                  x25PLEIVMOflowControlParameterNegotiation, 
                  x25PLEIVMOthroughputClassNegotiation, 
                  x25PLEIVMOx25PLEMode, x25PLEIVMOinterfaceMode, 
                  x25PLEIVMOdefaultThroughputClass, 
                  x25PLEIVMOflowControlNegotiationPermitted, 
                  x25PLEIVMOcallDeflectionSubscription, 
                  x25PLEIVMOmaxActiveCircuits, x25PLEIVMOrestartTime, 
                  x25PLEIVMOdefaultPacketSize, 
                  x25PLEIVMOdefaultWindowSize, 
                  x25PLEIVMOminimumRecallTimer, x25PLEIVMOrestartCount, 
                  x25PLEIVMOpacketSequencing, 
                  x25PLEIVMOregistrationRequestTime, 
                  x25PLEIVMOregistrationRequestCount, 
                  x25PLEIVMOregistrationPermitted, x25PLEIVMORowStatus, 
                  x25PLEIVMO-DTEcallDeflectionSubscription, 
                  x25PLEIVMO-DTEcallRequestResponseTimer, 
                  x25PLEIVMO-DTEextendedPacketSequenceNumbering, 
                  x25PLEIVMO-DTEmaxActiveCircuits, 
                  x25PLEIVMO-DTEminimumRecallTimer, 
                  x25PLEIVMO-DTEresetRequestResponseTimer, 
                  x25PLEIVMO-DTErestartRequestRetransmissionCount, 
                  x25PLEIVMO-DTErestartRequestResponseTimer, 
                  x25PLEIVMO-DTEclearRequestResponseTimer, 
                  x25PLEIVMO-DTEinterruptResponseTimer, 
                  x25PLEIVMO-DTEresetRequestRetransmissionCount, 
                  x25PLEIVMO-DTEclearRequestRetransmissionCount, 
                  x25PLEIVMO-DTEcallAttempts, 
                  x25PLEIVMO-DTEprotocolErrorsDetectedLocally, 
                  x25PLEIVMO-DTEprotocolErrorsAccusedOf, 
                  x25PLEIVMO-DTEcallEstablishmentRetryCountsExceeded, 
                  x25PLEIVMO-DTEoctetsReceivedCounter, 
                  x25PLEIVMO-DTEoctetsSentCounter, 
                  x25PLEIVMO-DTEcallTimeouts, 
                  x25PLEIVMO-DTEcallsConnected, 
                  x25PLEIVMO-DTEclearCountsExceeded, 
                  x25PLEIVMO-DTEclearTimeouts, 
                  x25PLEIVMO-DTEdataPacketsReceived, 
                  x25PLEIVMO-DTEdataPacketsSent, 
                  x25PLEIVMO-DTEdataRetransmissionTimerExpiries, 
                  x25PLEIVMO-DTEproviderInitiatedResets, 
                  x25PLEIVMO-DTEproviderInitiatedDisconnects, 
                  x25PLEIVMO-DTEremotelyInitiatedResets, 
                  x25PLEIVMO-DTEremotelyInitiatedRestarts, 
                  x25PLEIVMO-DTEresetTimeouts, 
                  x25PLEIVMO-DTErestartCountsExceeded, 
                  x25PLEIVMO-DTEwindowStatusTransmissionTimer, 
                  x25PLEIVMO-DTEwindowRotationTimer, 
                  x25PLEIVMO-DTEdataPacketRetransmissionCount, 
                  x25PLEIVMO-DTErejectResponseTimer, 
                  x25PLEIVMO-DTErejectRetransmissionCount, 
                  x25PLEIVMO-DTEregistrationRequestResponseTimer, 
                  x25PLEIVMO-DTEregistrationRequestRetransmissionCount, 
                  x25PLEIVMO-DTEregistrationPermitted, 
                  x25PLEIVMO-DTERowStatus, x25PLEIVMO-DCERowStatus, 
                  virtualCallChannel, virtualCallPacketSize, 
                  virtualCallWindowSize, virtualCallOctetsSentCounter, 
                  virtualCallOctetsReceivedCounter, 
                  virtualCallDataPacketsSent, 
                  virtualCallDataPacketsReceived, 
                  virtualCallRemotelyInitiatedResets, 
                  virtualCallDataRetransmissionTimerExpiries, 
                  virtualCallProviderInitiatedResets, 
                  virtualCallResetTimeouts, 
                  virtualCallInterruptPacketsSent, 
                  virtualCallInterruptPacketsReceived, 
                  virtualCallInterruptTimerExpiries, 
                  virtualCircuitLogicalChannel, 
                  virtualCircuitPacketSizes, 
                  virtualCircuitThroughputClasses, 
                  virtualCircuitWindowSizes, 
                  virtualCircuit-DTEoctetsSentCounter, 
                  virtualCircuit-DTEoctetsReceivedCounter, 
                  virtualCircuit-DTEdataPacketsReceived, 
                  virtualCircuit-DTEdataPacketsSent, 
                  virtualCircuit-DTEdataRetransmissionTimerExpiries, 
                  virtualCircuit-DTEinterruptPacketsReceived, 
                  virtualCircuit-DTEinterruptPacketsSent, 
                  virtualCircuit-DTEinterruptTimerExpiries, 
                  virtualCircuit-DTEproviderInitiatedResets, 
                  virtualCircuit-DTEremotelyInitiatedResets, 
                  virtualCircuit-DTEresetTimeouts, 
                  virtualCircuit-DCEdataPacketsReceived, 
                  virtualCircuit-DCEdataPacketsSent, 
                  virtualCircuit-DCEinterruptPacketsReceived, 
                  virtualCircuit-DCEinterruptPacketsSent, 
                  virtualCircuit-DCEinterruptTimerExpiries, 
                  virtualCircuit-DCEoctetsReceivedCounter, 
                  virtualCircuit-DCEoctetsSentCounter, 
                  virtualCircuit-DCEproviderInitiatedDisconnects, 
                  virtualCircuit-DCEproviderInitiatedResets, 
                  virtualCircuit-DCEremotelyInitiatedRestarts, 
                  virtualCircuit-DCEremotelyInitiatedResets, 
                  virtualCircuit-DCEresetTimeouts, 
                  virtualCircuit-DCEx25SegmentsReceived, 
                  virtualCircuit-DCEx25SegmentsSent, 
                  permanentVirtualCircuitChannel, 
                  permanentVirtualCircuitRowStatus, 
                  permanentVirtualCircuit-DTElogicalChannel, 
                  permanentVirtualCircuit-DTEpacketSizes, 
                  permanentVirtualCircuit-DTEthroughputClasses, 
                  permanentVirtualCircuit-DTEwindowSizes, 
                  permanentVirtualCircuit-DTERowStatus, 
                  permanentVirtualCircuit-DCEchargingDirection, 
                  permanentVirtualCircuit-DCElogicalChannel, 
                  permanentVirtualCircuit-DCEpacketSizes, 
                  permanentVirtualCircuit-DCEthroughputClasses, 
                  permanentVirtualCircuit-DCEwindowSizes, 
                  permanentVirtualCircuit-DCEoperationalState, 
                  permanentVirtualCircuit-DCEremoteDTEAddress, 
                  permanentVirtualCircuit-DCEremoteLogicalChannel, 
                  permanentVirtualCircuit-DCERowStatus, 
                  virtualCallIVMOfastSelect, virtualCallIVMOpacketSizes, 
                  virtualCallIVMOreverseCharging, 
                  virtualCallIVMOthroughputClasses, 
                  virtualCallIVMOwindowSizes, 
                  virtualCallIVMOproposedPacketSize, 
                  virtualCallIVMOproposedWindowSize, 
                  virtualCallIVMOacceptReverseCharging, 
                  virtualCallIVMOproposeReverseCharging, 
                  virtualCallIVMOcallTime, virtualCallIVMOresetTime, 
                  virtualCallIVMOclearTime, virtualCallIVMOinterruptTime, 
                  virtualCallIVMOresetCount, virtualCallIVMOclearCount, 
                  virtualCallIVMOwindowTime, 
                  virtualCallIVMOdataRetransmissionTime, 
                  virtualCallIVMOdataRetransmissionCount, 
                  virtualCallIVMOrejectTime, virtualCallIVMOrejectCount, 
                  virtualCallIVMORowStatus, switchedVirtualCalldirection, 
                  switchedVirtualCallremoteDTEAddress, 
                  switchedVirtualCallthroughputClass, 
                  switchedVirtualCallredirectReason, 
                  switchedVirtualCalloriginallyCalledAddress, 
                  switchedVirtualCallcallingAddressExtension, 
                  switchedVirtualCallcalledAddressExtension, 
                  switchedVirtualCallRowStatus, 
                  virtualCall-DTEcallingAddressExtension, 
                  virtualCall-DTEcalledAddressExtension, 
                  virtualCall-DTEdirection, virtualCall-DTEfastSelect, 
                  virtualCall-DTEoriginallyCalledAddress, 
                  virtualCall-DTEredirectReason, 
                  virtualCall-DTEremoteDTEAddress, 
                  virtualCall-DTEreverseCharging, 
                  virtualCall-DTERowStatus, 
                  virtualCall-DCEchargingDirection, 
                  virtualCall-DCEcUGSelection, virtualCall-DCEdirection, 
                  virtualCall-DCEfastSelect, 
                  virtualCall-DCEremoteDTEAddress, 
                  virtualCall-DCEtransitDelaySelectionAndIndication, 
                  virtualCall-DCEbilateralCUGSelection, 
                  virtualCall-DCEcallRedirectionDeflectionNotification, 
                  virtualCall-DCEcalledLineAddressModifiedNotification, 
                  virtualCall-DCEcUGWithOutgoingAccessSelection, 
                  virtualCall-DCEnUISelection, 
                  virtualCall-DCEreverseCharging, 
                  virtualCall-DCErOASelection, virtualCall-DCERowStatus, 
                  dSeriesResetRequestIndicationPackets, 
                  dSeriesSegmentsSent, dSeriesSegmentsReceived, 
                  dSeriesRowStatus, adjacencyState, neighbourSNPAAddress, 
                  neighbourSystemType, neighbourSystemIds, 
                  adjacencyUsage, areaAddressesOfNeighbour, holdingTimer, 
                  priorityOfNeighbour, adjacencyRowStatus, 
                  virtualAdjacencyMetric, 
                  destinationDefaultMetricPathCost, 
                  destinationDefaultMetricOutputAdjacencies, 
                  destinationDelayMetricPathCost, 
                  destinationDelayMetricOutputAdjacencies, 
                  destinationExpenseMetricPathCost, 
                  destinationExpenseMetricOutputAdjacencies, 
                  destinationErrorMetricPathCost, 
                  destinationErrorMetricOutputAdjacencies, 
                  desintationSystemMetric, destinationAreaId, 
                  reachableAddressPrefix, reachableAddressMappingType, 
                  reachableAddressDefaultMetric, 
                  reachableAddressDelayMetric, 
                  reachableAddressExpenseMetric, 
                  reachableAddressErrorMetric, 
                  reachableAddressDefaultMetricType, 
                  reachableAddressDelayMetricType, 
                  reachableAddressExpenseMetricType, 
                  reachableAddressErrorMetricType, 
                  reachableAddressOperationalState, 
                  reachableAddressAdministrativeState, 
                  reachableAddressSNPAAddresses, 
                  reachableAddressSNPAMask, reachableAddressSNPAPrefix, 
                  reachableAddressRowStatus, physicalSAPRowStatus }
    STATUS      current
    DESCRIPTION 
        "A collection of all accessible OSI objects in this module."
    ::= { osiGroups 1 }

osiNotificationGroup NOTIFICATION-GROUP
    NOTIFICATIONS { lLCConnection2Event, lLCClessACKEvent, 
                  lLCStationEvent }
    STATUS      current
    DESCRIPTION 
        "A collection of all OSI notifications in this module."
    ::= { osiGroups 2 }

osiTotalCompliance MODULE-COMPLIANCE
    STATUS      current
    DESCRIPTION 
        "This compliance profile specifies complete complicance."

    MODULE      -- this module

        MANDATORY-GROUPS        { osiObjectGroup, osiNotificationGroup }

    ::= { osiCompliances 1 }

END -- end of module OPENSS7-DL-MIB.
