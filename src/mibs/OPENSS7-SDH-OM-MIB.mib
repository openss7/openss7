-- vim: ft=mib comments=\f\:\",\b\:\-\-,\:\-\-,\f\b\:- fo+=tcqlornw tw=72 nocin nosi sts=4 sw=4
-- =============================================================================
-- 
-- @(#) src/mibs/OPENSS7-SDH-OM-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-SDH-OM-MIB DEFINITIONS ::= BEGIN

IMPORTS
    openss7G774
	FROM OPENSS7-SMI
    AdministrativeState, AlarmStatus, AvailabilityStatus, ControlStatus, 
    GnmAlarmStatus, OperationalState, ProceduralStatus, SimpleNameType, 
    StandbyStatus, SystemTimingSource, tmnObjectInstance, 
    tmnPerceivedSeverity, tmnProbableCause, UsageState
	FROM OPENSS7-SMI-MIB
    CircuitCode, CircuitIdentificationCode, CommonLanguageName, 
    MilliSeconds
	FROM OPENSS7-TC
    SnmpAdminString
	FROM SNMP-FRAMEWORK-MIB
    MODULE-COMPLIANCE, NOTIFICATION-GROUP, OBJECT-GROUP
	FROM SNMPv2-CONF
    Gauge32, Integer32, MODULE-IDENTITY, NOTIFICATION-TYPE, 
    OBJECT-IDENTITY, OBJECT-TYPE, Unsigned32, zeroDotZero
	FROM SNMPv2-SMI
    AutonomousType, RowPointer, RowStatus, TEXTUAL-CONVENTION, 
    TimeInterval, TruthValue
	FROM SNMPv2-TC;

sdhOmMIB MODULE-IDENTITY
    LAST-UPDATED "201004150620Z"
    ORGANIZATION
	"The OpenSS7 Project"
    CONTACT-INFO 
	"Brian Bidulock
	 OpenSS7 Corporation
	 1469 Jefferys Crescent
	 Edmonton, Alberta T6L 6T1
	 CANADA
	 Tel: +1 780 490 1141
	 Fax: +1 780 490 1241
	 Mob: +1 780 953 0557
	 E-mail: bidulock@openss7.org"
    DESCRIPTION
	"This is a MIB providing management information in accordance 
	 with ITU-T Rec. G.774.1 : 2001.

         Copyright (c) 2008-2015  Monavacon Limited
         Copyright (c) 2001-2008  OpenSS7 Corporation
         Copyright (c) 1997-2001  Brian F. G. Bidulock

         All Rights Reserved.

         This program is free software; you can redistribute it and/or 
         modify it under the terms of the GNU Affero General Public 
         License as published by the Free Software Foundation; version 3 
         of the License.

         This program is distributed in the hope that it will be useful, 
         but WITHOUT ANY WARRANTY; without even the implied warranty of 
         MERCHANTABILITY or FITNESS FOR A PARTICULAR PURPOSE.  See the 
         GNU Affero General Public License for more details.

         You should have received a copy of the GNU Affero General 
         Public License along with this program.  If not, see 
         <http://www.gnu.org/licenses/>, or write to the Free Software 
         Foundation, Inc., 675 Mass Ave, Cambridge, MA 02139, USA.

         Note well: notwithstanding this AGPL license, you are not 
         permitted to make modifications under the OpenSS7 project's 
         enterprise object identifier arc: 1.3.6.1.4.1.29591.  
         Modifications must be made only within an object identifier arc 
         under your control."
    REVISION "201004150620Z"
    DESCRIPTION
	"First release of this module."
    ::= { openss7G774 1 }

sdhOmNotifications	OBJECT IDENTIFIER ::= { sdhOmMIB	 0 }
sdhOmObjects		OBJECT IDENTIFIER ::= { sdhOmMIB	 1 }
sdhOmConformance	OBJECT IDENTIFIER ::= { sdhOmMIB	 2 }

sdhOmTables		OBJECT IDENTIFIER ::= { sdhOmObjects	 1 }
sdhOmScalars		OBJECT IDENTIFIER ::= { sdhOmObjects	 2 }
sdhOmNotifs		OBJECT IDENTIFIER ::= { sdhOmObjects	 3 }
sdhOmOids		OBJECT IDENTIFIER ::= { sdhOmObjects	 4 }

sdhOmCompliance		OBJECT IDENTIFIER ::= { sdhOmConformance 1 }
sdhOmGroups		OBJECT IDENTIFIER ::= { sdhOmConformance 2 }

sdhOmDefaults		OBJECT IDENTIFIER ::= { sdhOmScalars	 1 }

sdhOmProtocols		OBJECT IDENTIFIER ::= { sdhOmOids	 1 }
sdhOmProbableCauses	OBJECT IDENTIFIER ::= { sdhOmOids	 2 }
sdhOmSpecificProblems	OBJECT IDENTIFIER ::= { sdhOmOids	 3 }
sdhOmSpecificExtensions	OBJECT IDENTIFIER ::= { sdhOmOids	 4 }
sdhOmProbableCauses2	OBJECT IDENTIFIER ::= { sdhOmOids	 5 }

sdhOmCurrentData	OBJECT IDENTIFIER ::= { sdhOmTables	 1 }
sdhOmPathTermCurrData	OBJECT IDENTIFIER ::= { sdhOmTables	 2 }
sdhOmPathTermHistData	OBJECT IDENTIFIER ::= { sdhOmTables	 3 }

-- =================================================================

sdhOmCurrentDataTable OBJECT-TYPE
    SYNTAX SEQUENCE OF SdhOmCurrentDataEntry
    MAX-ACCESS not-accessible
    STATUS current
    DESCRIPTION
	"The sdhCurrentData class is used to define generic 
	 characteristic for SDH performance monitoring from which 
	 subclasses are defined in order to hold performance event 
	 counts for a specific monitoring point. Subclasses of this 
	 class are used in order to support performance monitoring of 
	 SDH paths at various layers as described in Recommendation 
	 G.803. The performance monitoring events ES, SES and BBE which 
	 are monitored by some of the subclasses of this subclass are 
	 defined in 4.1.1/G.826. The granularityPeriod attribute can 
	 only be assigned a value at creation time.

	 This class can only contain one reference to an instance of the 
	 thresholdData object class in the thresholdDataInstance 
	 attribute.

	 The 15' and 24 hours granularity period must be supported 
	 fully. If a threshold is reached or crossed then the 
	 currentProblemList attribute shall indicate it with the 
	 probable cause 'Threshold crossed'. Subclass of this class is 
	 used to monitor the near end of the path in case of 
	 bidirectional path the far end of the path shall be supported 
	 additionaly. In case of monitoring of a bidirectional path and 
	 Far End unavailability is monitored, an unavailable period 
	 starts if either the near end or the far end is in an 
	 unavailable condition. In case of monitoring of a 
	 unidirectional path only the near end is considered.

	 An unavailable condition starts when 10 consecutive severely 
	 errored seconds have been detected; these 10 seconds belong to 
	 the unavailable time. An unavailable condition ends when 10 
	 consecutive seconds with no severely errored second are 
	 detected. These 10 seconds belong to the available time. The 
	 unavailable period entry/exit criteria are described in Annex 
	 A/G.826.

	 For threshold reset subclasses of this object class the 
	 following rules apply:

	 - No more than one QOS alarm shall be generated until there has 
	   been a 15-minute rectangular fixed window with less error 
	   count than the low error count threshold and no unavailable 
	   period exists.

	 - To provision the high and low threshold value, the 
	   counterThresholdAttributList attribute of the 
	   Q.822-ThresholdDataInstance is used.

	 In this attribute all the thresholds (high and low) for each 
	 necessary counter are stored in a list. This means for example, 
	 that the high threshold for ES and the low threshold for ES are 
	 individually stored in the same list. It is up to the network 
	 element to recognize which is the high and which is the low 
	 one.

	 If the unavailableTimeAlarmPackage is present and if an 
	 unavailable period starts, then a communication alarm shall be 
	 sent with a probable cause of 'Unavailable' and the presence of 
	 this unavailable condition is indicated by the 
	 currentProblemList attribute. If an unavailable period is 
	 ending, then a communication alarm shall be sent with a 
	 probable cause of 'Unavailable' and a severity of 'Cleared'. An 
	 available condition is indicated by the absence of the 
	 unavailable condition in the current problem list. The 
	 unavailable condition has no effect on the operationalState. 
	 Each subclass of this class shall define the performance 
	 attributes required to hold the mandatory or optional 
	 performance events. These performance event counts are 
	 inhibited during unavailable time.  Attributes which are 
	 defined in a subclass of this class shall be included in 
	 history information using the historyData, or one of its 
	 subclass, unless it is explicitly specified in the subclass of 
	 this class that a particular attribute be not included. Each 
	 subclass of this class shall indicate which subclass of the 
	 history data is used for history retention. The following 
	 conditional packages are not used in this class: 
	 filterSuppressionPkg, observedManagedObjectPkg.

	 Concerning the subclasses of this class the following rule 
	 applies:

	 If a subclass of this class has a granularity period of 15 
	 minutes, it should be either an instance with the threshold 
	 reset functionality or an instance without this functionality 
	 instantiated (per termination point), but not both.

	 historyPackage: At the end of each performance interval an 
	 instance of historyData or one of its subclass shall be created 
	 if history retention was not suppressed by other means such as 
	 zero suppression. The values of the historyData object or one 
	 of its subclass is the copy of the values of the corresponding 
	 attributes of the currentData or one of its subclass at the end 
	 of each performance interval. Once the new historyData instance 
	 is created or one of its subclass this instance shall be 
	 retained in the Network Element at least for 16 periods of 15 
	 minutes for 15' performance interval and 1 period of 1 day for 
	 1 day performance interval. The storing of history data is 
	 described in 5.3.2/G.784.

	 uavailableTimeAlarmPackage: This package is used when a 
	 Communication Alarm Notification with the probable cause.  
	 Unavailable is to be emitted to indicate the beginning of an 
	 unavailable time period. The end of an unavailable time period 
	 shall be indicated by the clearing of this alarm."
    REFERENCE
	"ITU-T Rec. G.774.1 (02/2001) : sdhCurrentData MOC."
    ::= { sdhOmCurrentData 1 }

sdhOmCurrentDataEntry OBJECT-TYPE
    SYNTAX SdhOmCurrentDataEntry
    MAX-ACCESS not-accessible
    STATUS current
    DESCRIPTION
	""
    REFERENCE
	"ITU-T Rec. G.774.1 (02/2001) : sdhCurrentData MO."
    INDEX {
	sdhOmCurrentDataId -- index
    }
    ::= { sdhOmCurrentDataTable 1 }

SdhOmCurrentDataEntry ::= SEQUENCE {
    sdhOmCurrentDataId
	Unsigned32
	-- DERIVED FROM "Recommendation Q.822":currentData;
	-- CHARACTERIZED BY
	--	"Recommendation Q.822":zeroSuppressionPkg,
	--	"Recommendation Q.822":thresholdPkg,
	-- ATTRIBUTES
	--	"Recommendation M.3100":currentProblemList GET;;;
	-- CONDITIONAL PACKAGES
	--	historyPackage
	--	unavailableTimeAlarmPackage
}

sdhOmCurrentDataId OBJECT-TYPE
    SYNTAX Unsigned32
    MAX-ACCESS not-accessible -- index
    STATUS current
    DESCRIPTION
	""
    REFERENCE
	""
    ::= { sdhOmCurrentDataEntry 1 }


-- =================================================================

-- =================================================================

-- =================================================================


-- sdhCurrentData MANAGED OBJECT CLASS
-- pathTerminationCurrentData MANAGED OBJECT CLASS
-- pathTerminationHistoryData MANAGED OBJECT CLASS



END -- OPENSS7-SDH-OM-MIB
