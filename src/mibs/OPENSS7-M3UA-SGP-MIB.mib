-- vim: ft=mib comments=\f\b\:\"ITU\-T,\f\b\:ITU\-T,\f\:\",\b\:\-\-,\:\-\-,\f\b\:\- fo+=tcqlornw12 tw=64 ai nocin nosi sts=4 sw=4 et
-- =============================================================================
-- 
-- @(#) src/mibs/OPENSS7-M3UA-SGP-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-M3UA-SGP-MIB DEFINITIONS ::= BEGIN

IMPORTS
    InetAddress, InetAddressType, InetPortNumber
        FROM INET-ADDRESS-MIB
    AspIdPolicy, AspState, ProtocolVersion, RegistrationPolicy, 
    SigtranOptions, interoperableVersion
        FROM OPENSS7-SIGTRAN-TC
    openss7Modules
        FROM OPENSS7-SMI
    AdministrativeState, AlarmStatus, AvailabilityStatus, ControlStatus, 
    OperationalState, ProceduralStatus, StandbyStatus, UsageState
        FROM OPENSS7-SMI-MIB
    CommonLanguageName
        FROM OPENSS7-TC
    MODULE-COMPLIANCE, OBJECT-GROUP
        FROM SNMPv2-CONF
    Integer32, MODULE-IDENTITY, OBJECT-IDENTITY, OBJECT-TYPE, Unsigned32, 
    zeroDotZero
        FROM SNMPv2-SMI
    DisplayString, RowPointer, RowStatus
        FROM SNMPv2-TC;

m3uaSgpMIB MODULE-IDENTITY
    LAST-UPDATED "201112101120Z"
    ORGANIZATION 
        "OpenSS7 Corporation"
    CONTACT-INFO 
        "Brian Bidulock
         1469 Jefferys Crescent
         Edmonton, Alberta  T6L 6T1
         Canada
         Tel: +1 780 490 1141
         Fax: +1 780 490 1241
         Mob: +1 780 953 0557
         E-Mail: bidulock@openss7.org"
    DESCRIPTION 
        "MIB Module for SIGTRAN M3UA SGP management.
         
         In the containment model for the SGP side, the 
         correspondences to SS7 MTP entities is different than 
         the ASP side.
         
         - ASPs serving an AS within an SP correspond to routes.  
           There is no correspondence for route lists; i.e., 
           there is only one route list containing all routes.  
           For each SP which has AS served to ASPs there is one 
           route set containing this single route list.  A route 
           in a route list corresponds to a load selection.  If 
           LOADSEL is supported, the ASP may conttrol its load 
           selection membership.  Each load selection is 
           organized into a load group.  Route Sets on the SGP 
           side are finer than on the ASP side.
         
         Note that the underlying MTP implementation must be 
         smart enough to properly route 'Alias' signalling 
         points.  The use of Alias point codes for SCCP GTT 
         function in ANSI MTP networks at STPs is described in 
         ANSI T1.111.4/2000.  When assigning an M3UA point code 
         to an STP pair, that point code needs to be declared as 
         an Alias point code.  In extension to the ANSI 
         T1.111.4/2000 SCCP Alias behaviour, the MTP 
         implementation must also permit other SI values (other 
         than SCCP) as well as multiple SI values to be active.  
         If a given SI value is unavailable on the local STP, it 
         should be routed, if possible, to the associated STP 
         (note that the transfer-prohibited procedures of 13.2.2 
         apply).  If is is not possible to route the message to 
         the associated STP (perhaps because a 
         transfer-prohibited message with regard to the 
         signalling point has been received), the message is 
         given UPU treatment.  If all SI values are inaccessble 
         at the STP, trasnfer-prohibited procedures will be 
         invoked for the entire point code.
         
         Copyright (c) 2008-2015  Monavacon Limited
         Copyright (c) 2001-2008  OpenSS7 Corporation
         Copyright (c) 1997-2001  Brian F. G. Bidulock
         
         All Rights Reserved.
         
         This program is free software; you can redistribute it and/or 
         modify it under the terms of the GNU Affero General Public 
         License as published by the Free Software Foundation; version 3 
         of the License.
         
         This program is distributed in the hope that it will be useful, 
         but WITHOUT ANY WARRANTY; without even the implied warranty of 
         MERCHANTABILITY or FITNESS FOR A PARTICULAR PURPOSE.  See the 
         GNU Affero General Public License for more details.
         
         You should have received a copy of the GNU Affero General 
         Public License along with this program.  If not, see 
         <http://www.gnu.org/licenses/>, or write to the Free Software 
         Foundation, Inc., 675 Mass Ave, Cambridge, MA 02139, USA.
         
         Note well: notwithstanding this AGPL license, you are not 
         permitted to make modifications under the OpenSS7 project's 
         enterprise object identifier arc: 1.3.6.1.4.1.29591.  
         Modifications must be made only within an object identifier arc 
         under your control."
    REVISION    "201112101120Z"
    DESCRIPTION 
        "Corrections an smilint workup."
    REVISION    "200709300000Z"
    DESCRIPTION 
        "First release of this MIB."
    ::= { openss7Modules 321 }


m3uaSgpNotifications OBJECT IDENTIFIER
    ::= { m3uaSgpMIB 0 }

m3uaSgpObjects OBJECT IDENTIFIER
    ::= { m3uaSgpMIB 1 }

m3uaSgpScalars OBJECT IDENTIFIER
    ::= { m3uaSgpObjects 1 }

m3uaSgpTables OBJECT IDENTIFIER
    ::= { m3uaSgpObjects 2 }

m3uaSgpAg OBJECT IDENTIFIER
    ::= { m3uaSgpTables 1 }

m3uaSgpAgNextIndex OBJECT-TYPE
    SYNTAX      Unsigned32
    MAX-ACCESS  read-only
    STATUS      current
    DESCRIPTION 
        "Provides the next available index into the AG table.  
         The value returned is zero if there are no more 
         available entries in the table (i.e. the table is 
         exahausted)."
    ::= { m3uaSgpAg 1 }

m3uaSgpAgTable OBJECT-TYPE
    SYNTAX      SEQUENCE OF M3uaSgpAgEntry
    MAX-ACCESS  not-accessible
    STATUS      current
    DESCRIPTION 
        "Provides the access group (AG) table.  Each entry in 
         the AG table represents and access group.  An access 
         group is a group of signalling gateways (SG) to which 
         ASPs route messages with equal route priority (and thus 
         loadhsharing)."
    ::= { m3uaSgpAg 2 }

m3uaSgpAgEntry OBJECT-TYPE
    SYNTAX      M3uaSgpAgEntry
    MAX-ACCESS  not-accessible
    STATUS      current
    DESCRIPTION 
        "Provides an entry in the access group (AG) table.  Each 
         entry in the AG table represents an access group which 
         consists of a number of signalling gateways (SGs).  As 
         an access group is a logical concept, access groups can 
         be added to and removed from this table by management 
         stations.  The contents of this table must survive an 
         agent reboot."
    INDEX       { m3uaSgpAgIndex }
    ::= { m3uaSgpAgTable 1 }

M3uaSgpAgEntry ::= SEQUENCE {
    m3uaSgpAgIndex                  Unsigned32,
    m3uaSgpAgName                   CommonLanguageName,
    m3uaSgpAgProtocolVersion        ProtocolVersion,
    m3uaSgpAgOptions                SigtranOptions,
    m3uaSgpAgRegistrationPolicy     RegistrationPolicy,
    m3uaSgpAgAspIdPolicy            AspIdPolicy,
    m3uaSgpAgProtocolPayloadId      Integer32,
    m3uaSgpAgIpPort                 InetPortNumber,
    m3uaSgpAgMinOstreams            Integer32,
    m3uaSgpAgMaxIstreams            Integer32,
    m3uaSgpAgStatus                 RowStatus
}

m3uaSgpAgIndex OBJECT-TYPE
    SYNTAX      Unsigned32
    MAX-ACCESS  not-accessible
    STATUS      current
    DESCRIPTION 
        "Provides an index into the AG table as well as an 
         identifier for referring to groupsings of SG into AG 
         (access groups)."
    ::= { m3uaSgpAgEntry 1 }

m3uaSgpAgName OBJECT-TYPE
    SYNTAX      CommonLanguageName
    MAX-ACCESS  read-create
    STATUS      current
    DESCRIPTION 
        "Provides the name of the access group following COMMON 
         LANGUAGE procedures and the CommonLanguageName textual 
         convention.  The COMMON LANGUAGE name of each access 
         group should be formed by taking the CLLI of the 
         managed element and appending the two characters 'AG' 
         followed by the two digits 'NN', where the two digits 
         'NN' are the ordinal of the m3uaSgpAgIndex.  So, for 
         example, if the host CLLI is EDTNAB99CG7, and this is 
         the 3rd entry in the AG table, the name should be 
         EDTNAB99CG7AG03."
    REFERENCE   
        "OPENSS7-TC"
    ::= { m3uaSgpAgEntry 2 }

m3uaSgpAgProtocolVersion OBJECT-TYPE
    SYNTAX      ProtocolVersion
    MAX-ACCESS  read-create
    STATUS      current
    DESCRIPTION 
        "Provides the protocol version supported by all 
         signalling gateways in the access group.  The version 
         is an object identifier and autonomous type.  It is set 
         to interoperableVersion when the implementation claims 
         to support all versions.  Otherwise it is set to one of 
         the versions defined by this MIB, or defined in another 
         document or MIB, including an enterprise MIB for 
         private or prorprietary protocol variations.  Protocol 
         versions can be interoperableVersion, 
         indicating that the implementations in the AG 
         interoperate with all protocol versions; 
         m3uaRfc3332ProtocolVersion, indicating that the 
         implementation supports RFC 3332 version of the 
         protocol; m3uaTs102142ProtocolVersion, indication that 
         the implementation supports ETSI TS 102 142 version of 
         the protocol; or, m3uaRfc4666ProtocolVersion, 
         indicataing that the implementation supports RFC 4666 
         version of the protocol.
         
         Whether this value may be changed on an active entry is 
         implementation dependent, and the effects when changed 
         on an active entry is also implementation dependent."
    REFERENCE   
        "OPENSS7-SIGTRAN-TC"
    DEFVAL      { interoperableVersion }
    ::= { m3uaSgpAgEntry 3 }

m3uaSgpAgOptions OBJECT-TYPE
    SYNTAX      SigtranOptions
    MAX-ACCESS  read-create
    STATUS      current
    DESCRIPTION 
        "Provides the options supported within the access group 
         following the SigtranOptions textual convention.  
         Options that are not pertinent to M3UA may be ignored.  
         If the access group supports ASPEXT, these options will 
         be reported to the ASPs when they execute the ASP Up 
         procedure.
         
         If this value is modified on an active entry, it will 
         not take effect until an SGP in the Access Group 
         engages in the ASP Up procedure with an ASP."
    REFERENCE   
        "OPENSS7-SIGTRAN-TC"
    ::= { m3uaSgpAgEntry 4 }

m3uaSgpAgRegistrationPolicy OBJECT-TYPE
    SYNTAX      RegistrationPolicy
    MAX-ACCESS  read-create
    STATUS      current
    DESCRIPTION 
        "Provides the registration policy of the SG in the 
         Access Group following the RegistrationPolicy textual 
         convention.  The registration policy may be unknown(1), 
         where the registration policy is left to the 
         implementation, forbidden(2), where the registration 
         procedures will not be used, required(4), where the 
         registration procedures will always be used, and 
         permitted(3), where the registration procedures will be 
         used if configured and not otherwise.  
         
         Changing this value on an active entry will not affect 
         the effective regsitration policy until an ASP has 
         cycled through the ASP Down state following the setting 
         to a new value.  The new value will be in force for the 
         next ASP Up procedure invoked by the ASP that has 
         cycled through the ASP Down procedure."
    REFERENCE   
        "OPENSS7-SIGTRAN-TC"
    DEFVAL      { unknown }
    ::= { m3uaSgpAgEntry 5 }

m3uaSgpAgAspIdPolicy OBJECT-TYPE
    SYNTAX      AspIdPolicy
    MAX-ACCESS  read-create
    STATUS      current
    DESCRIPTION 
        "Provides the ASP Identifier policy of the access group 
         following the AspIdPolicy textual convention.  This 
         convention describes whether SG in the Access Group 
         have no set ASP Identifier policy, or permit, require 
         or forbid the use of ASP Identifiers.
         
         If this value is modified on an active entry, it will 
         not take effect until an SGP in the Access Group 
         engages in the ASP Up procedure with an ASP."
    REFERENCE   
        "OPENSS7-SIGTRAN-TC"
    DEFVAL      { unknown }
    ::= { m3uaSgpAgEntry 6 }

m3uaSgpAgProtocolPayloadId OBJECT-TYPE
    SYNTAX      Integer32 (0 | 3)
    MAX-ACCESS  read-create
    STATUS      current
    DESCRIPTION 
        "Provides the SCTP Payload Protocol Identifier to be 
         used in DATA chunks containing M3uA messages sent 
         between SGP in this Access Group and ASPs.  This value 
         must either be zero (0) or three (3).
         
         When changed on an active entry, the PPI value set will 
         take effect on the next DATA chunk sent."
    DEFVAL      { 3 }
    ::= { m3uaSgpAgEntry 7 }

m3uaSgpAgIpPort OBJECT-TYPE
    SYNTAX      InetPortNumber
    MAX-ACCESS  read-create
    STATUS      current
    DESCRIPTION 
        "Provides the IP port number on which SGP in this Access 
         Group will listen.  This largely assumes that each SGP 
         in the Access Group is on a separate host.  For the 
         case where multiple SG are provided for one or more 
         hosts, set this value to zero (0) to indicate that the 
         port number is specified in the m3uaSgp table.  The 
         default is to have all SGP listen on the well-known 
         M3UA server port number as assigned by IANA, 2905.
         
         When changed on an active entry that results in a 
         change in the port on which an active SGP should be 
         listening, the SGP stops listening on the old port 
         immediately and starts listening on the new port 
         immediately.  What actions are performed with regard to 
         outstanding connection attempts at the time of the 
         change are implementation dependent."
    DEFVAL      { 2905 }
    ::= { m3uaSgpAgEntry 8 }

m3uaSgpAgMinOstreams OBJECT-TYPE
    SYNTAX      Integer32 (2..16384)
    MAX-ACCESS  read-create
    STATUS      current
    DESCRIPTION 
        "Provides the minimum number of outbound streams to 
         request from SGP in this Access Group.  The minimum 
         value is 2 per RFC 4666.  For ITU-T or ETSI newtorks, a 
         reasonable default is 17 (one stream for the control 
         stream (0) and 16 data streams for the 16 possible SLS 
         values); for ANSI newtorks, 33 or 257 (one stream for 
         the control stream (0) and 32 (5-bit SLS) or 256 (8-bit 
         SLS) data streams for the  32 or 256 possible SLS 
         values).   The default value is set to 33 to handle 
         most cases without an excessive number of streams."
    DEFVAL      { 33 }
    ::= { m3uaSgpAgEntry 9 }

m3uaSgpAgMaxIstreams OBJECT-TYPE
    SYNTAX      Integer32 (2..16384)
    MAX-ACCESS  read-create
    STATUS      current
    DESCRIPTION 
        "Proivdes the maximum number of inbound streams that 
         will be reported when forming a connection to SGP in 
         this access group.  The minimum value to support RFC 
         4666 is 2.  The value of 33 is amore reasonable 
         default.  See the analysis for the number of default 
         streanms in the description in the same table as this, 
         m3uaSgpAg, table for the m3uaSgpAgMinOstreams column in 
         the same entry."
    DEFVAL      { 33 }
    ::= { m3uaSgpAgEntry 10 }

m3uaSgpAgStatus OBJECT-TYPE
    SYNTAX      RowStatus
    MAX-ACCESS  read-create
    STATUS      current
    DESCRIPTION 
        "Provides a mechanism whereby management stations may 
         create and destroy rows in this table, according to the 
         RowStatus textual convention of the SNMPv2-TC MIB."
    REFERENCE
        "STD 58"
    ::= { m3uaSgpAgEntry 11 }

m3uaSgpSg OBJECT IDENTIFIER
    ::= { m3uaSgpTables 2 }

m3uaSgpSgTable OBJECT-TYPE
    SYNTAX      SEQUENCE OF M3uaSgpSgEntry
    MAX-ACCESS  not-accessible
    STATUS      current
    DESCRIPTION 
        "Provides a table of Signalling Gateways (SG) that are 
         known to the Signalling Gateway Process (SG)."
    ::= { m3uaSgpSg 1 }

m3uaSgpSgEntry OBJECT-TYPE
    SYNTAX      M3uaSgpSgEntry
    MAX-ACCESS  not-accessible
    STATUS      current
    DESCRIPTION 
        "Each row in this table is indexed by the pairing of 
         Application Gateway (AG) and Signalling Gateway (SG) as 
         viewed by the Signalling Gateway Process (SGP).  Each 
         rown contains the name of the Signalling Gateway (SG)."
    INDEX       { m3uaSgpAgIndex, m3uaSgpSgIndex }
    ::= { m3uaSgpSgTable 1 }

M3uaSgpSgEntry ::= SEQUENCE {
    m3uaSgpSgIndex      Unsigned32,
    m3uaSgpSgName       CommonLanguageName,
    m3uaSgpSgStatus     RowStatus
}

m3uaSgpSgIndex OBJECT-TYPE
    SYNTAX      Unsigned32
    MAX-ACCESS  not-accessible
    STATUS      current
    DESCRIPTION 
        "Provides an ordinal index into the SG Table."
    ::= { m3uaSgpSgEntry 1 }

m3uaSgpSgName OBJECT-TYPE
    SYNTAX      CommonLanguageName
    MAX-ACCESS  read-create
    STATUS      current
    DESCRIPTION 
        "Provides the common language name of the SG (Signalling 
         Gateway)."
    ::= { m3uaSgpSgEntry 2 }

m3uaSgpSgStatus OBJECT-TYPE
    SYNTAX      RowStatus
    MAX-ACCESS  read-create
    STATUS      current
    DESCRIPTION 
        "Provides a mechanism whereby management stations may 
         create and destroy rows in this table, according to the 
         RowStatus textual convention of the SNMPv2-TC MIB."
    REFERENCE
        "STD 58"
    ::= { m3uaSgpSgEntry 3 }

m3uaSgpAsp OBJECT IDENTIFIER
    ::= { m3uaSgpTables 3 }

m3uaSgpAspTable OBJECT-TYPE
    SYNTAX      SEQUENCE OF M3uaSgpAspEntry
    MAX-ACCESS  not-accessible
    STATUS      current
    DESCRIPTION 
        "Provides the ASP table for this host.  The ASP table 
         contains an entry for each ASP known to the host."
    ::= { m3uaSgpAsp 1 }

m3uaSgpAspEntry OBJECT-TYPE
    SYNTAX      M3uaSgpAspEntry
    MAX-ACCESS  not-accessible
    STATUS      current
    DESCRIPTION 
        "Provides an ASP table entry.  Each entry in the ASP 
         table describes an ASP known to this host."
    INDEX       { m3uaSgpAspIndex }
    ::= { m3uaSgpAspTable 1 }

M3uaSgpAspEntry ::= SEQUENCE {
    m3uaSgpAspIndex                 Unsigned32,
    m3uaSgpAspName                  CommonLanguageName,
    m3uaSgpAspOperationalState      OperationalState,
    m3uaSgpAspUsageState            UsageState,
    m3uaSgpAspAdministrativeState   AdministrativeState,
    m3uaSgpAspAlarmStatus           AlarmStatus,
    m3uaSgpAspProceduralStatus      ProceduralStatus,
    m3uaSgpAspAvailabilityStatus    AvailabilityStatus,
    m3uaSgpAspAspState              AspState,
    m3uaSgpAspSctpProfile           RowPointer,
    m3uaSgpAspStatus                RowStatus
}

m3uaSgpAspIndex OBJECT-TYPE
    SYNTAX      Unsigned32
    MAX-ACCESS  not-accessible
    STATUS      current
    DESCRIPTION 
        "Provides an index into the ASP table and also provides 
         an unsigned integer handle to an entry in the table 
         that may be used as a shorthand for the equivalent 
         RowPointer."
    ::= { m3uaSgpAspEntry 1 }

m3uaSgpAspName OBJECT-TYPE
    SYNTAX      CommonLanguageName
    MAX-ACCESS  read-create
    STATUS      current
    DESCRIPTION 
        "Provides the name of the ASP using COMMON LANGUAGE 
         procedures and the CommonLanguageName textual 
         convention.  This value is persistent across an agent 
         reboot."
    ::= { m3uaSgpAspEntry 2 }

m3uaSgpAspOperationalState OBJECT-TYPE
    SYNTAX      OperationalState
    MAX-ACCESS  read-only
    STATUS      current
    DESCRIPTION 
        "Provides the overall operational state of the ASP as 
         viewed by the managed element using the 
         OperationalState textual convention.  The overall 
         operational state is the most operable state of all of 
         the SGP-ASP associations that are configured for this 
         managed element."
    DEFVAL      { disabled }
    ::= { m3uaSgpAspEntry 3 }

m3uaSgpAspUsageState OBJECT-TYPE
    SYNTAX      UsageState
    MAX-ACCESS  read-only
    STATUS      current
    DESCRIPTION 
        "Provides the overall usage status of the ASP as viewd 
         by the managed element using the UsageState textual 
         convention.  The overall usage state is the most 
         utilized state of each of the AS served by each SGP-ASP 
         associaiton that is configured for this managed 
         element."
    DEFVAL      { idle }
    ::= { m3uaSgpAspEntry 4 }

m3uaSgpAspAdministrativeState OBJECT-TYPE
    SYNTAX      AdministrativeState
    MAX-ACCESS  read-create
    STATUS      current
    DESCRIPTION 
        "Provides the adminstrative state of the ASP as viewd by 
         the managed element using the AdministrativeState 
         textual convention.  When locked(0), no SGP-ASP 
         association related to this ASP is permitted to be 
         formed.  When unlocked(1), the SGP-ASP associations to 
         this ASP may form and the ASP may activate AS for the 
         association.  When shuttingDown(2), no new SGP-ASP 
         association to this ASP may form and no new AS may 
         activate for any association; any AS served will be 
         issued an unsolicited ASP Inactive Ack to deactivate 
         the AS.  The value represents current conditions and is 
         not guaranteed peristent across an agent reboot."
    DEFVAL      { locked }
    ::= { m3uaSgpAspEntry 5 }

m3uaSgpAspAlarmStatus OBJECT-TYPE
    SYNTAX      AlarmStatus
    MAX-ACCESS  read-create
    STATUS      current
    DESCRIPTION 
        "Provides the alarm status for the ASP as viewed by the 
         managed element using the AlarmStatus textual 
         convention.  The value reflects current conditions and 
         is not guaranteed persistent across an agent reboot."
    DEFVAL      { {} }
    ::= { m3uaSgpAspEntry 6 }

m3uaSgpAspProceduralStatus OBJECT-TYPE
    SYNTAX      ProceduralStatus
    MAX-ACCESS  read-only
    STATUS      current
    DESCRIPTION 
        "Provides the overall procedureal status for the ASP 
         using the ProceduralStatus textual convention.  The 
         overall procedural status is the set-union (logical OR) 
         of the procedural status of all SGP-ASP associations 
         configured for this ASP."
    DEFVAL      { {} }
    ::= { m3uaSgpAspEntry 7 }

m3uaSgpAspAvailabilityStatus OBJECT-TYPE
    SYNTAX      AvailabilityStatus
    MAX-ACCESS  read-only
    STATUS      current
    DESCRIPTION 
        "Provides the overal availability status for the ASP 
         using the AvailabilityStatus textual convention.  The 
         overal availablity status is the set-union (logical OR) 
         of the availability status of all SGP-ASP associations 
         configured for this ASP."
    DEFVAL      { {} }
    ::= { m3uaSgpAspEntry 8 }

m3uaSgpAspAspState OBJECT-TYPE
    SYNTAX      AspState
    MAX-ACCESS  read-create
    STATUS      current
    DESCRIPTION 
        "Provides the overall ASP state for the ASP using the 
         AspState textual convention.  The overall ASP state is 
         the most active state of the individual SGP-ASP 
         associations configured for this ASP.  Setting a stable 
         state value (up or down) will cause all of the SGP-ASP 
         associations configured to transition to that state by 
         invoking the appropriate procedures.  Note that this is 
         not a persistent state change as autonomous actions may 
         be performed to return the ASP to its previous state.  
         This value reflects current conditions and is not 
         guaranteed persistent across an agent reboot."
    DEFVAL      { down }
    ::= { m3uaSgpAspEntry 9 }

m3uaSgpAspSctpProfile OBJECT-TYPE
    SYNTAX      RowPointer
    MAX-ACCESS  read-create
    STATUS      current
    DESCRIPTION 
        "Provides a row pointer into the sigtranSctpProfileTable 
         or an SCTP protocol parameter profile table known to 
         the agent, or zeroDotZero for an implementation 
         dependent default profile.  The referenced profile 
         entry provides SCTP parameters that will be used when 
         forming associations to this ASP.  The value is 
         persistent accross agent reboots.  When set on an 
         active entry, the values will not be effective util the 
         next time that an SCTP association is formed with the 
         ASP.  Management stations can force a new association 
         to be formed with this ASP using the 
         m3uaSgpAspAdministrativeState column."
    DEFVAL      { zeroDotZero }
    ::= { m3uaSgpAspEntry 10 }

m3uaSgpAspStatus OBJECT-TYPE
    SYNTAX      RowStatus
    MAX-ACCESS  read-create
    STATUS      current
    DESCRIPTION 
        "Provides a mechanism whereby management stations may 
         create and destroy rows in this table, according to the 
         RowStatus textual convention of the SNMPv2-TC MIB."
    REFERENCE
        "STD 58"
    ::= { m3uaSgpAspEntry 11 }

m3uaSgp OBJECT IDENTIFIER
    ::= { m3uaSgpTables 4 }

m3uaSgpNextIndex OBJECT-TYPE
    SYNTAX      Unsigned32
    MAX-ACCESS  read-only
    STATUS      current
    DESCRIPTION 
        "Provides the next available indes in the SGP table.  
         The value returned is zero if there are no more entries 
         available in the table."
    ::= { m3uaSgp 1 }

m3uaSgpTable OBJECT-TYPE
    SYNTAX      SEQUENCE OF M3uaSgpEntry
    MAX-ACCESS  not-accessible
    STATUS      current
    DESCRIPTION 
        "Provides the SGP Table.  The SGP Table contains an 
         instance of every signalling gateway process (SGP) 
         defined for the host, by the signalling gateway (SG) 
         and access group (AG) to which they belong."
    ::= { m3uaSgp 2 }

m3uaSgpEntry OBJECT-TYPE
    SYNTAX      M3uaSgpEntry
    MAX-ACCESS  not-accessible
    STATUS      current
    DESCRIPTION 
        "Provides an entry in the SGP Table.  Each entry 
         contains information about the characteristics of the 
         SGP.  Because SGP are logical entities, the may be 
         created or destroyed by management stations by adding 
         or deleting them from this table.  All entries in this 
         table must survive an agent reboot."
    INDEX       { m3uaSgpAgIndex, m3uaSgpSgIndex, m3uaSgpIndex }
    ::= { m3uaSgpTable 1 }

M3uaSgpEntry ::= SEQUENCE {
    m3uaSgpIndex                Unsigned32,
    m3uaSgpName                 CommonLanguageName,
    m3uaSgpOperationalState     OperationalState,
    m3uaSgpUsageState           UsageState,
    m3uaSgpAdministrativeState  AdministrativeState,
    m3uaSgpAlarmStatus          AlarmStatus,
    m3uaSgpProceduralStatus     ProceduralStatus,
    m3uaSgpAvailabiltiyStatus   AvailabilityStatus,
    m3uaSgpControlStatus        ControlStatus,
    m3uaSgpStandbyStatus        StandbyStatus,
    m3uaSgpPrimaryAddressType   InetAddressType,
    m3uaSgpPrimaryAddress       InetAddress,
    m3uaSgpHostName             DisplayString,
    m3uaSgpStatus               RowStatus
}

m3uaSgpIndex OBJECT-TYPE
    SYNTAX      Unsigned32
    MAX-ACCESS  not-accessible
    STATUS      current
    DESCRIPTION 
        "Provides an ordinal index into the SGP table."
    ::= { m3uaSgpEntry 1 }

m3uaSgpName OBJECT-TYPE
    SYNTAX      CommonLanguageName
    MAX-ACCESS  read-create
    STATUS      current
    DESCRIPTION 
        "Provides a common language name for this SGP 
         (Signalling Gateway Process)."
    ::= { m3uaSgpEntry 2 }

m3uaSgpOperationalState OBJECT-TYPE
    SYNTAX      OperationalState
    MAX-ACCESS  read-only
    STATUS      current
    DESCRIPTION 
        "Provides the operational state of the SGP in accordance 
         with the OperationalState textual convention of the 
         OPENSS7-SMI-MIB."
    ::= { m3uaSgpEntry 3 }

m3uaSgpUsageState OBJECT-TYPE
    SYNTAX      UsageState
    MAX-ACCESS  read-only
    STATUS      current
    DESCRIPTION 
        "Provides the usage state of the SGP in accordance with 
         the UsageState textual convention of the 
         OPENSS7-SMI-MIB."
    ::= { m3uaSgpEntry 4 }

m3uaSgpAdministrativeState OBJECT-TYPE
    SYNTAX      AdministrativeState
    MAX-ACCESS  read-create
    STATUS      current
    DESCRIPTION 
        "Provides the administrative state of the SGP in 
         accordance with the AdministrativeState textual 
         convention of the OPENSS7-SMI-MIB."
    ::= { m3uaSgpEntry 5 }

m3uaSgpAlarmStatus OBJECT-TYPE
    SYNTAX      AlarmStatus
    MAX-ACCESS  read-create
    STATUS      current
    DESCRIPTION 
        "Provides the alarm status of the SGP in accordance with 
         the AlarmStatus textual convention of the 
         OPENSS7-SMI-MIB."
    ::= { m3uaSgpEntry 6 }

m3uaSgpProceduralStatus OBJECT-TYPE
    SYNTAX      ProceduralStatus
    MAX-ACCESS  read-only
    STATUS      current
    DESCRIPTION 
        "Provides the procedural status of the SGP in accordance 
         with the ProceduralStatus textual convention of the 
         OPENSS7-SMI-MIB."
    ::= { m3uaSgpEntry 7 }

m3uaSgpAvailabiltiyStatus OBJECT-TYPE
    SYNTAX      AvailabilityStatus
    MAX-ACCESS  read-only
    STATUS      current
    DESCRIPTION 
        "Provides the availability status of the SGP in 
         accordance with the AvailabilityStatus textual 
         convention of the OPENSS7-SMI-MIB."
    ::= { m3uaSgpEntry 8 }

m3uaSgpControlStatus OBJECT-TYPE
    SYNTAX      ControlStatus
    MAX-ACCESS  read-create
    STATUS      current
    DESCRIPTION 
        "Provides the control status of the SGP in accordance 
         with the ControlStatus textual convention of the 
         OPENSS7-SMI-MIB."
    ::= { m3uaSgpEntry 9 }

m3uaSgpStandbyStatus OBJECT-TYPE
    SYNTAX      StandbyStatus
    MAX-ACCESS  read-only
    STATUS      current
    DESCRIPTION 
        "Provides the standby status of the SGP in accordance 
         with the StandbyStatus textual convention of the 
         OPENSS7-SMI-MIB."
    ::= { m3uaSgpEntry 10 }

m3uaSgpPrimaryAddressType OBJECT-TYPE
    SYNTAX      InetAddressType
    MAX-ACCESS  read-create
    STATUS      current
    DESCRIPTION 
        "Provides the type of primary Inet Address for the SGP 
         in accordance with the InetAddressType textual 
         convention of the INET-ADDRESS-MIB."
    ::= { m3uaSgpEntry 11 }

m3uaSgpPrimaryAddress OBJECT-TYPE
    SYNTAX      InetAddress
    MAX-ACCESS  read-create
    STATUS      current
    DESCRIPTION 
        "Provides the primary Inet Address of the SGP in 
         accordance with the InetAddress textual convention of 
         the INET-ADDRESS-MIB.  This address is of the type 
         specified in the m3uaSgpPrimaryAddressType column."
    ::= { m3uaSgpEntry 12 }

m3uaSgpHostName OBJECT-TYPE
    SYNTAX      DisplayString
    MAX-ACCESS  read-create
    STATUS      current
    DESCRIPTION 
        "Provides the hostname of the SGP."
    ::= { m3uaSgpEntry 13 }

m3uaSgpStatus OBJECT-TYPE
    SYNTAX      RowStatus
    MAX-ACCESS  read-create
    STATUS      current
    DESCRIPTION 
        "Provides a mechanism whereby management stations may 
         create and destroy rows in this table, according to the 
         RowStatus textual convention of the SNMPv2-TC MIB."
    REFERENCE
        "STD 58"
    ::= { m3uaSgpEntry 14 }

m3uaSgpNotifObjects OBJECT IDENTIFIER
    ::= { m3uaSgpObjects 3 }

m3uaSgpOids OBJECT IDENTIFIER
    ::= { m3uaSgpObjects 4 }

m3uaProtocolVersions OBJECT IDENTIFIER
    ::= { m3uaSgpOids 1 }

m3uaRfc3332ProtocolVersion OBJECT-IDENTITY
    STATUS      current
    DESCRIPTION 
        "Provides an object identifier which identifies the RFC 
         3332 version of the M3UA protocol, for use with the 
         ProtocolVersion textual convention from 
         OPENSS7-SIGTRAN-TC."
    REFERENCE   
        "RFC 3332"
    ::= { m3uaProtocolVersions 1 }

m3uaTs102142ProtocolVersion OBJECT-IDENTITY
    STATUS      current
    DESCRIPTION 
        "Provides an object identifier which identifies the ETSI 
         TS 102 142 version of the M3UA protocol, for use with 
         the ProtocolVersion textual convention from 
         OPENSS7-SIGTRAN-TC."
    REFERENCE   
        "RFC 3332 and ETSI TS 102 142"
    ::= { m3uaProtocolVersions 2 }

m3uaRfc4666ProtocolVersion OBJECT-IDENTITY
    STATUS      current
    DESCRIPTION 
        "Provides an object identifier which identifies the RFC 
         4666 version of the M3UA protocol, for use with the 
         ProtocolVersion textual convention from 
         OPENSS7-SIGTRAN-TC."
    REFERENCE   
        "RFC 4666"
    ::= { m3uaProtocolVersions 3 }

m3uaSgpConformance OBJECT IDENTIFIER
    ::= { m3uaSgpMIB 2 }

m3uaSgpGroups OBJECT IDENTIFIER
    ::= { m3uaSgpConformance 1 }

m3uaSgpCompliances OBJECT IDENTIFIER
    ::= { m3uaSgpConformance 2 }

m3uaSgpCapabilities OBJECT IDENTIFIER
    ::= { m3uaSgpConformance 3 }

m3uaSgpObjectGroup OBJECT-GROUP
    OBJECTS     { m3uaSgpAgNextIndex, m3uaSgpAgName, 
                  m3uaSgpAgProtocolVersion, m3uaSgpAgOptions, 
                  m3uaSgpAgRegistrationPolicy, m3uaSgpAgAspIdPolicy, 
                  m3uaSgpAgProtocolPayloadId, m3uaSgpAgIpPort, 
                  m3uaSgpAgMinOstreams, m3uaSgpAgMaxIstreams, 
                  m3uaSgpAgStatus, m3uaSgpSgName, m3uaSgpSgStatus, 
                  m3uaSgpAspName, m3uaSgpAspOperationalState, 
                  m3uaSgpAspUsageState, m3uaSgpAspAdministrativeState, 
                  m3uaSgpAspAlarmStatus, m3uaSgpAspProceduralStatus, 
                  m3uaSgpAspAvailabilityStatus, m3uaSgpAspAspState, 
                  m3uaSgpAspSctpProfile, m3uaSgpAspStatus, 
                  m3uaSgpNextIndex, m3uaSgpName, m3uaSgpOperationalState, 
                  m3uaSgpUsageState, m3uaSgpAdministrativeState, 
                  m3uaSgpAlarmStatus, m3uaSgpProceduralStatus, 
                  m3uaSgpAvailabiltiyStatus, m3uaSgpControlStatus, 
                  m3uaSgpStandbyStatus, m3uaSgpPrimaryAddressType, 
                  m3uaSgpPrimaryAddress, m3uaSgpHostName, m3uaSgpStatus }
    STATUS      current
    DESCRIPTION 
        "This group contains, for now, all of the conformance 
         applicable objects."
    ::= { m3uaSgpGroups 1 }

m3uaSgpGeneralCompliance MODULE-COMPLIANCE
    STATUS      current
    DESCRIPTION 
        "This conformance provides general compliance for this 
         module."

    MODULE      -- this module

        MANDATORY-GROUPS        { m3uaSgpObjectGroup }

    ::= { m3uaSgpCompliances 1 }

END -- end of module OPENSS7-M3UA-SGP-MIB.
