-- vim: ft=mib comments=\f\:\",\b\:\-\-,\:\-\-,\f\b\:- fo+=tcqlornw tw=72 nocin nosi sts=4 sw=4
-- =============================================================================
-- 
-- @(#) src/mibs/ATM-FORUM-SRVC-REG.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

ATM-FORUM-SRVC-REG DEFINITIONS ::= BEGIN

IMPORTS
        atmfSrvcRegTypes,
        atmfSrvcRegistryGroup,
        AtmAddress                      FROM ATM-FORUM-TC-MIB
        OBJECT-TYPE                     FROM RFC-1212;


--              Object Identifier definitions

-- The following values are defined for use as possible values
-- of the atmfSrvcRegServiceID object.

-- LAN Emulation Configuration Server (LECS)
atmfSrvcRegLecs         OBJECT IDENTIFIER ::= { atmfSrvcRegTypes 1 }
-- When atmfSrvcRegServiceID has a value of atmfSrvcRegLecs,
-- the value of atmfSrvcRegParm1 is ignored.

-- ATM Name Server (ANS)
atmfSrvcRegAns         OBJECT IDENTIFIER ::= { atmfSrvcRegTypes 2 }
-- When atmfSrvcRegServiceID has a value of atmfSrvcRegAns,
-- the value of atmfSrvcRegParm1 is ignored.


--          The Service Registry Table
--
-- The Service Registry Table is implemented by the network-side IME

atmfSrvcRegTable OBJECT-TYPE
        SYNTAX  SEQUENCE OF AtmfSrvcRegEntry
        ACCESS  not-accessible
        STATUS  mandatory
        DESCRIPTION
                "The table implemented by the IME on the network side of
                the ATM UNI port contains all of the services that are
                available to the user-side IME indexed by service
                identifier."
        ::= { atmfSrvcRegistryGroup 1 }

atmfSrvcRegEntry OBJECT-TYPE
        SYNTAX  AtmfSrvcRegEntry
        ACCESS  not-accessible
        STATUS  mandatory
        DESCRIPTION
                "Information about a single service provider that is 
                available to the user-side IME."
        INDEX   { atmfSrvcRegPort, atmfSrvcRegServiceID, 
                  atmfSrvcRegAddressIndex }
        ::= { atmfSrvcRegTable 1 }

AtmfSrvcRegEntry ::=
        SEQUENCE {
                atmfSrvcRegPort
                        INTEGER,
                atmfSrvcRegServiceID
                        OBJECT IDENTIFIER,
                atmfSrvcRegATMAddress
                        AtmAddress,
                atmfSrvcRegAddressIndex
                        INTEGER,
                atmfSrvcRegParm1
                        OCTET STRING
        }

atmfSrvcRegPort OBJECT-TYPE
        SYNTAX  INTEGER (0..2147483647)
        ACCESS  not-accessible
        STATUS  mandatory
        DESCRIPTION
                "The value of 0 which has the special meaning of
                identifying the ATM Interface over which this message
                was received."
       ::= { atmfSrvcRegEntry 1 }

atmfSrvcRegServiceID OBJECT-TYPE
        SYNTAX  OBJECT IDENTIFIER
        ACCESS  not-accessible
        STATUS  mandatory
        DESCRIPTION
                "This is the service identifier which uniquely identifies
                the type of service at the address provided in the table."
        ::= { atmfSrvcRegEntry 2 }

atmfSrvcRegATMAddress OBJECT-TYPE
        SYNTAX  AtmAddress
        ACCESS  read-only
        STATUS  mandatory
        DESCRIPTION
                "This is the full address of the service.  The user-side
                IME may use this address to establish a connection
                with the service."
        ::= { atmfSrvcRegEntry 3 }

atmfSrvcRegAddressIndex OBJECT-TYPE
        SYNTAX INTEGER (1..2147483647)
        ACCESS  not-accessible
        STATUS  mandatory
        DESCRIPTION
                "An arbitrary integer to differentiate multiple rows
                containing different ATM addresses for the same service
                on the same port."
        ::= { atmfSrvcRegEntry 4 }

atmfSrvcRegParm1 OBJECT-TYPE
        SYNTAX  OCTET STRING (SIZE (1..255))
        ACCESS  read-only
        STATUS  mandatory
        DESCRIPTION
                "An octet string whose size and meaning is determined
                by the value of atmfSrvcRegServiceID."
        ::= { atmfSrvcRegEntry 5 }
END
-- vim: ft=mib comments=\f\:\",\b\:\-\-,\:\-\-,\f\b\:- fo+=tcqlornw tw=72 nocin nosi sts=4 sw=4
