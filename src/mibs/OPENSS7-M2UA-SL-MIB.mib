-- vim: ft=mib comments=\f\:\",\b\:\-\-,\:\-\-,\f\b\:- fo+=tcqlornw tw=72 nocin nosi sts=4 sw=4
-- =============================================================================
-- 
-- @(#) src/mibs/OPENSS7-M2UA-SL-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-M2UA-SL-MIB DEFINITIONS ::= BEGIN

IMPORTS
    MODULE-IDENTITY, OBJECT-IDENTITY, OBJECT-TYPE, NOTIFICATION-TYPE, 
    Unsigned32, zeroDotZero
	    FROM SNMPv2-SMI

    RowPointer, RowStatus, TimeInterval, TruthValue
	FROM SNMPv2-TC

    MODULE-COMPLIANCE, NOTIFICATION-GROUP, OBJECT-GROUP
	FROM SNMPv2-CONF

    MtpResultOfAction, MtpCongestionLevel, NetworkPointCode, 
    MtpTransmissionRate
	FROM OPENSS7-MTP-MIB

    Ss7ProtocolVariant
	FROM OPENSS7-SS7-MIB

    AdministrativeState, AvailabilityStatus, OperationalState, 
    ProceduralStatus, SimpleNameType, UsageState
	FROM OPENSS7-SMI-MIB

    CircuitCode, CircuitIdentificationCode, MilliSeconds, 
    CommonLanguageName
	FROM OPENSS7-TC

    openss7Q751
	FROM OPENSS7-SMI;

m2slMIB MODULE-IDENTITY
    LAST-UPDATED	"200901080108Z"
    ORGANIZATION	"The OpenSS7 Project"
    CONTACT-INFO
	"Brian Bidulock
	 OpenSS7 Corporation
	 1469 Jefferys Crescent
	 Edmonton, Alberta  T6L 6T1
	 CANADA
	 Tel: +1 780 490 1141
	 Fax: +1 780 490 1241
	 Mob: +1 780 953 0557
	 mailto:bidulock@openss7.org"
    DESCRIPTION	
	"

         Copyright (c) 2008-2015  Monavacon Limited
         Copyright (c) 2001-2008  OpenSS7 Corporation
         Copyright (c) 1997-2001  Brian F. G. Bidulock

         All Rights Reserved.

         This program is free software; you can redistribute it and/or 
         modify it under the terms of the GNU Affero General Public 
         License as published by the Free Software Foundation; version 3 
         of the License.

         This program is distributed in the hope that it will be useful, 
         but WITHOUT ANY WARRANTY; without even the implied warranty of 
         MERCHANTABILITY or FITNESS FOR A PARTICULAR PURPOSE.  See the 
         GNU Affero General Public License for more details.

         You should have received a copy of the GNU Affero General 
         Public License along with this program.  If not, see 
         <http://www.gnu.org/licenses/>, or write to the Free Software 
         Foundation, Inc., 675 Mass Ave, Cambridge, MA 02139, USA.

         Note well: notwithstanding this AGPL license, you are not 
         permitted to make modifications under the OpenSS7 project's 
         enterprise object identifier arc: 1.3.6.1.4.1.29591.  
         Modifications must be made only within an object identifier arc 
         under your control."
    REVISION	"200901080108Z"
    DESCRIPTION
	"First release of this module."
    ::= { openss7Q751 33 }

 -- top level organization of the MIB

m2slNotifications	OBJECT IDENTIFIER ::= { m2slMIB		 0 }
m2slObjects		OBJECT IDENTIFIER ::= { m2slMIB		 1 }
m2slConformance		OBJECT IDENTIFIER ::= { m2slMIB		 2 }

m2slTables		OBJECT IDENTIFIER ::= { m2slObjects	 1 }
m2slScalars		OBJECT IDENTIFIER ::= { m2slObjects	 2 }
m2slNotifs		OBJECT IDENTIFIER ::= { m2slObjects	 3 }
m2slOids		OBJECT IDENTIFIER ::= { m2slObjects	 4 }

m2slGroups		OBJECT IDENTIFIER ::= { m2slConformance	 1 }
m2slCompliance		OBJECT IDENTIFIER ::= { m2slConformance	 2 }
m2slCapabilities	OBJECT IDENTIFIER ::= { m2slConformance	 3 }

m2slDefaults		OBJECT IDENTIFIER ::= { m2slScalars	 1 }

m2slProtocols		OBJECT IDENTIFIER ::= { m2slOids	 1 }
m2slProbableCauses	OBJECT IDENTIFIER ::= { m2slOids	 2 }
m2slSpecificProblems	OBJECT IDENTIFIER ::= { m2slOids	 3 }
m2slExtensions		OBJECT IDENTIFIER ::= { m2slOids	 4 }

m2uaSl			OBJECT IDENTIFIER ::= { m2slTables	 1 }
m2uaSdt			OBJECT IDENTIFIER ::= { m2slTables	 2 }
m2uaSdl			OBJECT IDENTIFIER ::= { m2slTables	 3 }
m2uaSctp		OBJECT IDENTIFIER ::= { m2slTables	 4 }

-- =============================================================================

-- (1.3.6.1.4.1.29591.17.751.1.3) m2slMIB
-- |__(0) m2slNotifications
-- |
-- |__(1) m2slObjects
-- |  |__(1) m2slTables
-- |  |  |__( 1) m2uaSl
-- |  |  |  |__( 1) m2uaSlTable
-- |  |  |
-- |  |  |__( 1) m2uaSdt
-- |  |  |  |__( 1) m2uaSdtTable
-- |  |  |
-- |  |  |__( 1) m2uaSdl
-- |  |  |  |__( 1) m2uaSdlTable
-- |  |  |
-- |  |  |__( 1) m2uaSctp
-- |  |
-- |  |__(2) m2slScalars
-- |  |  |__(1) m2slDefaults
-- |  |
-- |  |__(3) m2slNotifs
-- |  |
-- |  |__(4) m2slOids
-- |     |__(1) m2slProtocols
-- |     |
-- |     |__(2) m2slProbableCauses
-- |     |
-- |     |__(3) m2slSpecificProblems
-- |     |
-- |     |__(4) m2slExtensions
-- |
-- |__(2) m2slConformance
--    |__(1) m2slGroups
--    |
--    |__(2) m2slCompliance
--    |
--    |__(3) m2slCapabilities

-- =============================================================================

END -- OPENSS7-M2UA-SL-MIB

-- vim: ft=mib comments=\f\:\",\b\:\-\-,\:\-\-,\f\b\:- fo+=tcqlornw tw=72 nocin nosi sts=4 sw=4
