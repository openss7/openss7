-- vim: ft=mib comments=\f\:\",\b\:\-\-,\:\-\-,\f\b\:- fo+=tcqlornw tw=72 nocin nosi sts=4 sw=4
-- =============================================================================
-- 
-- @(#) src/mibs/OPENSS7-SCCP2-MIB.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-SCCP2-MIB DEFINITIONS ::= BEGIN

IMPORTS
    MODULE-IDENTITY, OBJECT-TYPE, enterprises, Unsigned32
	FROM SNMPv2-SMI
    RowStatus, RowPointer, AutonomousType, 
    TimeInterval, DisplayString, TruthValue, TEXTUAL-CONVENTION
	FROM SNMPv2-TC
    MODULE-COMPLIANCE, OBJECT-GROUP
	FROM SNMPv2-CONF
    CommonLanguageName
	FROM OPENSS7-TC
    AdministrativeState, OperationalState, ProceduralStatus, 
    AvailabilityStatus, AlarmStatus, SimpleNameType, UsageState
	FROM OPENSS7-SMI-MIB
    NEntitySystemTypes, NEntitySystemType
	FROM OPENSS7-CLNS-MIB
    Ss7ProtocolVariant
	FROM OPENSS7-SS7-MIB
    mtpMsId, MtpSapAddress, MtpUserPart, MtpUserPartStatus, 
    MtpCongestedState, MtpCongestionLevel
	FROM OPENSS7-MTP-MIB
    SubSystemNumber, PointCodeList
	FROM OPENSS7-SCCP-MIB
    openss7, openss7Q, openss7Q751
	FROM OPENSS7-SMI;

sccp2MIB MODULE-IDENTITY
    LAST-UPDATED "200903032246Z"
    ORGANIZATION
	"The OpenSS7 Project"
    CONTACT-INFO
        "Brian Bidulock
         OpenSS7 Corporation
         1469 Jefferys Crescent
         Edmonton, Alberta T6L 6T1
         CANADA
         Tel: +1 780 490 1141
         Fax: +1 780 490 1241
         Mob: +1 780 953 0557
         E-mail: bidulock@openss7.org"
    DESCRIPTION 
        "This is a MIB providing management information is 
         accordance with ITU-T Rec. Q.751.1, ITU-T Rec. 
         Q.2751.1, ANSI T1.116.1.

         Copyright (c) 2008-2015  Monavacon Limited
         Copyright (c) 2001-2008  OpenSS7 Corporation
         Copyright (c) 1997-2001  Brian F. G. Bidulock

         All Rights Reserved.

         This program is free software; you can redistribute it and/or 
         modify it under the terms of the GNU Affero General Public 
         License as published by the Free Software Foundation; version 3 
         of the License.

         This program is distributed in the hope that it will be useful, 
         but WITHOUT ANY WARRANTY; without even the implied warranty of 
         MERCHANTABILITY or FITNESS FOR A PARTICULAR PURPOSE.  See the 
         GNU Affero General Public License for more details.

         You should have received a copy of the GNU Affero General 
         Public License along with this program.  If not, see 
         <http://www.gnu.org/licenses/>, or write to the Free Software 
         Foundation, Inc., 675 Mass Ave, Cambridge, MA 02139, USA.

         Note well: notwithstanding this AGPL license, you are not 
         permitted to make modifications under the OpenSS7 project's 
         enterprise object identifier arc: 1.3.6.1.4.1.29591.  
         Modifications must be made only within an object identifier arc 
         under your control."
    REVISION "200903032246Z"
    DESCRIPTION
	"First release of this module."
    ::= { openss7Q751 22 }

sccpNotifications OBJECT IDENTIFIER
    ::= { sccp2MIB 0 }

sccpDefaults OBJECT IDENTIFIER
    ::= { sccp2MIB 1 }

sccpTables OBJECT IDENTIFIER
    ::= { sccp2MIB 2 }

-- =============================================================================

-- This object should not be necessary and any references to this object 
-- should be replaced with a row pointer to an mtpNaTable entry.

sccpNetwork OBJECT IDENTIFIER
    ::= { sccpTables 1 }

-- =============================================================================

-- This object should not be necessary and any reference to this object 
-- should be replaced with a row pointer to an mtpMsTable, mtpSpTable  
-- or mtpL3Table entry.

sccpSignallingPoint OBJECT IDENTIFIER
    ::= { sccpTables 2 }

-- =============================================================================

-- This object corresponds to an instance of an sccpAccessPoint 
-- invocation.  That is, it corresponds to an upper stream on the SCCP 
-- STREAMS driver.

sccpUser OBJECT IDENTIFIER
    ::= { sccpTables 3 }

-- =============================================================================

-- This is an SCCP entity set.  It models a group of subsystems that, in 
-- concert, provided an SCCP entity service.

sccpEntitySet OBJECT IDENTIFIER
    ::= { sccpTables 4 }

-- =============================================================================

-- This is a signalling relation that is a relationship between the 
-- local SCCP (sccpSignallingPoint) and a remote SCCP.  It tracks the 
-- status of remote signalling points reachable from the local 
-- signalling point via the associated linkages.

sccpSignallingRelation OBJECT IDENTIFIER
    ::= { sccpTables 5 }

-- =============================================================================

-- This is a local SCCP subsystem or SCCP-SAP.  It corresponds to the 
-- local version of the sccpAccessPoint MOC defined in Q.752.2.

sccpSubsystem OBJECT IDENTIFIER
    ::= { sccpTables 6 }

sccpSubsystemTable OBJECT-TYPE
    SYNTAX SEQUENCE OF SccpSubsystemEntry
    MAX-ACCESS not-accessible
    STATUS current
    DESCRIPTION
	""
    REFERENCE
	""
    ::= { sccpSubsystem 1 }

sccpSubsystemEntry OBJECT-TYPE
    SYNTAX SccpSubsystemEntry
    MAX-ACCESS not-accessible
    STATUS current
    DESCRIPTION
	""
    REFERENCE
	""
    INDEX {
	sccpSubsystemSapId
    }
    ::= { sccpSubsystemTable 1 }

SccpSubsystemEntry ::=
    SEQUENCE {
	-- sap2 attributes
	sccpSubsystemSapId			Unsigned32,
	sccpSubsystemAlarmStatus		AlarmStatus,
	sccpSubsystemSap2Address		SubSystemNumber,
	sccpSubsystemUserEntityNames		OCTET STRING,
	sccpSubsystemProviderEntityNames	PointCodeList,
	-- nSAP attributes: (none)
	-- sccpAccessPoint attributes
	sccpSubsystemAvailabilityStatus		AvailabilityStatus,
	sccpSubsystemConcernedAreaPointer	Unsigned32,
	sccpSubsystemLinkagePointer		Unsigned32,
	-- ssAvailableAfterRestartPackage
	sccpSubsystemSsAvailableAfterRestart	TruthValue,
	sccpSubsystemAsaProfilePointer		RowPointer,
	sccpSubsystemName			CommonLanguageName,
	sccpSubsystemRowStatus			RowStatus
    }

-- sap2 attributes
sccpSubsystemSapId OBJECT-TYPE
    SYNTAX	Unsigned32
    MAX-ACCESS	not-accessible
    STATUS	current
    DESCRIPTION	
	"..."
    ::= { sccpSubsystemEntry 1 }

sccpSubsystemAlarmStatus OBJECT-TYPE
    SYNTAX	AlarmStatus
    MAX-ACCESS	read-create
    STATUS	current
    DESCRIPTION
	"..."
    ::= { sccpSubsystemEntry 2 }

sccpSubsystemSap2Address OBJECT-TYPE
    SYNTAX	SubSystemNumber
    MAX-ACCESS	read-create
    STATUS	current
    DESCRIPTION
	"..."
    ::= { sccpSubsystemEntry 3 }

sccpSubsystemUserEntityNames OBJECT-TYPE
    SYNTAX	OCTET STRING
    MAX-ACCESS	read-create
    STATUS	current
    DESCRIPTION
	"..."
    ::= { sccpSubsystemEntry 4 }

sccpSubsystemProviderEntityNames OBJECT-TYPE
    SYNTAX	PointCodeList
    MAX-ACCESS	read-create
    STATUS	current
    DESCRIPTION
	"..."
    ::= { sccpSubsystemEntry 5 }

-- nSAP attributes: (none)
-- sccpAccessPoint attributes
sccpSubsystemAvailabilityStatus OBJECT-TYPE
    SYNTAX	AvailabilityStatus
    MAX-ACCESS	read-create
    STATUS	current
    DESCRIPTION
	"..."
    ::= { sccpSubsystemEntry 6 }

sccpSubsystemConcernedAreaPointer OBJECT-TYPE
    SYNTAX	Unsigned32
    MAX-ACCESS	read-create
    STATUS	current
    DESCRIPTION
	"..."
    ::= { sccpSubsystemEntry 7 }

sccpSubsystemLinkagePointer OBJECT-TYPE
    SYNTAX	Unsigned32
    MAX-ACCESS	read-create
    STATUS	current
    DESCRIPTION
	"..."
    ::= { sccpSubsystemEntry 8 }

-- ssAvailableAfterRestartPackage
sccpSubsystemSsAvailableAfterRestart OBJECT-TYPE
    SYNTAX	TruthValue
    MAX-ACCESS	read-create
    STATUS	current
    DESCRIPTION
	"..."
    ::= { sccpSubsystemEntry 9 }

sccpSubsystemAsaProfilePointer OBJECT-TYPE
    SYNTAX	RowPointer
    MAX-ACCESS	read-create
    STATUS	current
    DESCRIPTION
	"..."
    ::= { sccpSubsystemEntry 10 }

sccpSubsystemName OBJECT-TYPE
    SYNTAX	CommonLanguageName
    MAX-ACCESS	read-create
    STATUS	current
    DESCRIPTION
	"..."
    ::= { sccpSubsystemEntry 11 }

sccpSubsystemRowStatus OBJECT-TYPE
    SYNTAX	RowStatus
    MAX-ACCESS	read-create
    STATUS	current
    DESCRIPTION
	"..."
    ::= { sccpSubsystemEntry 12 }


-- =============================================================================

-- This is a remote SCCP subsystem or SCCP-SAP.  It corresponds to the
-- remote version of the sccpAccessPoint MOC defined in Q.752.2.

sccpRemoteSubsystem OBJECT IDENTIFIER
    ::= { sccpTables 7 }

sccpRemoteSubsystemTable OBJECT-TYPE
    SYNTAX SEQUENCE OF SccpRemoteSubsystemEntry
    MAX-ACCESS not-accessible
    STATUS current
    DESCRIPTION
	""
    REFERENCE
	""
    ::= { sccpRemoteSubsystem 1 }

sccpRemoteSubsystemEntry OBJECT-TYPE
    SYNTAX SccpRemoteSubsystemEntry
    MAX-ACCESS not-accessible
    STATUS current
    DESCRIPTION
	""
    REFERENCE
	""
    INDEX {
	sccpRemoteSubsystemSapId
    }
    ::= { sccpRemoteSubsystemTable 1 }

SccpRemoteSubsystemEntry ::=
    SEQUENCE {
	-- sap2 attributes
	sccpRemoteSubsystemSapId		Unsigned32,
	sccpRemoteSubsystemAlarmStatus		AlarmStatus,
	sccpRemoteSubsystemSap2Address		SubSystemNumber,
	sccpRemoteSubsystemUserEntityNames	OCTET STRING,
	sccpRemoteSubsystemProviderEntityNames	PointCodeList,
	-- nSAP attributes: (none)
	-- sccpAccessPoint attributes
	sccpRemoteSubsystemAvailabilityStatus	AvailabilityStatus,
	sccpRemoteSubsystemConcernedAreaPointer	Unsigned32,
	sccpRemoteSubsystemLinkagePointer	Unsigned32,
	-- ssAvailableAfterRestartPackage
	sccpRemoteSubsystemSsAvailableAfterRestart TruthValue,
	sccpRemoteSubsystemAsaProfilePointer	RowPointer,
	sccpRemoteSubsystemName			CommonLanguageName,
	sccpRemoteSubsystemRowStatus		RowStatus
    }

-- sap2 attributes
sccpRemoteSubsystemSapId OBJECT-TYPE
    SYNTAX	Unsigned32
    MAX-ACCESS	not-accessible
    STATUS	current
    DESCRIPTION	
	"..."
    ::= { sccpRemoteSubsystemEntry 1 }

sccpRemoteSubsystemAlarmStatus OBJECT-TYPE
    SYNTAX	AlarmStatus
    MAX-ACCESS	read-create
    STATUS	current
    DESCRIPTION	
	"..."
    ::= { sccpRemoteSubsystemEntry 2 }

sccpRemoteSubsystemSap2Address OBJECT-TYPE
    SYNTAX	SubSystemNumber
    MAX-ACCESS	read-create
    STATUS	current
    DESCRIPTION	
	"..."
    ::= { sccpRemoteSubsystemEntry 3 }

sccpRemoteSubsystemUserEntityNames OBJECT-TYPE
    SYNTAX	OCTET STRING
    MAX-ACCESS	read-create
    STATUS	current
    DESCRIPTION	
	"..."
    ::= { sccpRemoteSubsystemEntry 4 }

sccpRemoteSubsystemProviderEntityNames OBJECT-TYPE
    SYNTAX	PointCodeList
    MAX-ACCESS	read-create
    STATUS	current
    DESCRIPTION	
	"..."
    ::= { sccpRemoteSubsystemEntry 5 }

-- nSAP attributes: (none)
-- sccpAccessPoint attributes
sccpRemoteSubsystemAvailabilityStatus OBJECT-TYPE
    SYNTAX	AvailabilityStatus
    MAX-ACCESS	read-create
    STATUS	current
    DESCRIPTION	
	"..."
    ::= { sccpRemoteSubsystemEntry 6 }

sccpRemoteSubsystemConcernedAreaPointer OBJECT-TYPE
    SYNTAX	Unsigned32
    MAX-ACCESS	read-create
    STATUS	current
    DESCRIPTION	
	"..."
    ::= { sccpRemoteSubsystemEntry 7 }

sccpRemoteSubsystemLinkagePointer OBJECT-TYPE
    SYNTAX	Unsigned32
    MAX-ACCESS	read-create
    STATUS	current
    DESCRIPTION	
	"..."
    ::= { sccpRemoteSubsystemEntry 8 }

-- ssAvailableAfterRestartPackage
sccpRemoteSubsystemSsAvailableAfterRestart OBJECT-TYPE
    SYNTAX	TruthValue
    MAX-ACCESS	read-create
    STATUS	current
    DESCRIPTION	
	"..."
    ::= { sccpRemoteSubsystemEntry 9 }

sccpRemoteSubsystemAsaProfilePointer OBJECT-TYPE
    SYNTAX	RowPointer
    MAX-ACCESS	read-create
    STATUS	current
    DESCRIPTION	
	"..."
    ::= { sccpRemoteSubsystemEntry 10 }

sccpRemoteSubsystemName OBJECT-TYPE
    SYNTAX	CommonLanguageName
    MAX-ACCESS	read-create
    STATUS	current
    DESCRIPTION	
	"..."
    ::= { sccpRemoteSubsystemEntry 11 }

sccpRemoteSubsystemRowStatus OBJECT-TYPE
    SYNTAX	RowStatus
    MAX-ACCESS	read-create
    STATUS	current
    DESCRIPTION	
	"..."
    ::= { sccpRemoteSubsystemEntry 12 }


-- =============================================================================


sccpConcernedArea OBJECT IDENTIFIER
    ::= { sccpTables 8 }

-- =============================================================================


sccpLinkage OBJECT IDENTIFIER
    ::= { sccpTables 9 }

-- =============================================================================


sccpCoupling OBJECT IDENTIFIER
    ::= { sccpTables 10 }

-- =============================================================================


END -- OPENSS7-SCCP2-MIB

-- vim: ft=mib comments=\f\:\",\b\:\-\-,\:\-\-,\f\b\:- fo+=tcqlornw tw=72 nocin nosi sts=4 sw=4
