-- vim: ft=mib comments=\f\:\",\b\:\-\-,\:\-\-,\f\b\:- fo+=tcqlornw tw=72 nocin nosi sts=4 sw=4
-- =============================================================================
-- 
-- @(#) src/mibs/x25-1.mib
--
-- -----------------------------------------------------------------------------
--
-- Copyright (c) 2008-2015  Monavacon Limited <http://www.monavacon.com/>
-- Copyright (c) 2001-2008  OpenSS7 Corporation <http://www.openss7.com/>
-- Copyright (c) 1997-2001  Brian F. G. Bidulock <bidulock@openss7.org>
--
-- All Rights Reserved.
--
-- This program is free software; you can redistribute it and/or modify it under 
-- the terms of the GNU Affero General Public License as published by the Free 
-- Software Foundation; version 3 of the License.
--
-- This program is distributed in the hope that it will be useful, but WITHOUT 
-- ANY WARRANTY; without even the implied warranty of MERCHANTABILITY or  
-- FITNESS FOR A PARTICULAR PURPOSE.  See the GNU Affero General Public License 
-- for more details.
--
-- You should have received a copy of the GNU Affero General Public License 
-- along with this program.  If not, see <http://www.gnu.org/licenses/>, or 
-- write to the Free Software Foundation, Inc., 675 Mass Ave, Cambridge, MA 
-- 02139, USA.
--
-- -----------------------------------------------------------------------------
--
-- Note well: notwithstanding this AGPL license, you are not permitted to make 
-- modifications under the OpenSS7 project's enterprise object identifier arc: 
-- 1.3.6.1.4.1.29591.  Modifications must be made only within an object 
-- identifier arc under your control.
--
-- -----------------------------------------------------------------------------
--
-- U.S. GOVERNMENT RESTRICTED RIGHTS.  If you are licensing this Software on
-- behalf of the U.S. Government ("Government"), the following provisions apply
-- to you.  If the Software is supplied by the Department of Defense ("DoD"), it
-- is classified as "Commercial Computer Software" under paragraph 252.227-7014
-- of the DoD Supplement to the Federal Acquisition Regulations ("DFARS") (or any
-- successor regulations) and the Government is acquiring only the license rights
-- granted herein (the license rights customarily provided to non-Government
-- users).  If the Software is supplied to any unit or agency of the Government
-- other than DoD, it is classified as "Restricted Computer Software" and the
-- Government's rights in the Software are defined in paragraph 52.227-19 of the
-- Federal Acquisition Regulations ("FAR") (or any successor regulations) or, in
-- the cases of NASA, in paragraph 18.52.227-86 of the NASA Supplement to the FAR
-- (or any successor regulations).
--
-- -----------------------------------------------------------------------------
--
-- Commercial licensing and support of this software is available from OpenSS7
-- Corporation at a fee.  See http://www.openss7.com/
--
-- =============================================================================

OPENSS7-X25-PLP-1-MIB DEFINITIONS ::= BEGIN

IMPORTS
    openss7Modules
	FROM OPENSS7-SMI
    MODULE-IDENTITY,
    NOTIFICATION-TYPE,
    OBJECT-TYPE, 
    enterprises
	FROM SNMPv2-SMI
    TEXTUAL-CONVENTION,
    Counter64,
    Counter32,
    Integer32,
    DisplayString,
    Gauge32,
    RowPointer,
    RowStatus, 
    TimeInterval,
    TimeStamp,
    TruthValue, 
    Unsigned32
	FROM SNMPv2-TC
    attributeValueChange,
    communicationsAlarm,
    objectCreation,
    objectDeletion,
    tmnObjectInstance
	FROM OPENSS7-SMI-MIB
    AdministrativeState, 
    OperationalState,
    SimpleNameType,
    UsageState
	FROM OPENSS7-TMN-TC
    MODULE-COMPLIANCE,
    OBJECT-GROUP
	FROM SNMPv2-CONF;

x25PLPMIB1 MODULE-IDENTITY
    LAST-UPDATED "200807121128Z"
    ORGANIZATION
	"The OpenSS7 Project"
    CONTACT-INFO
	"Brian Bidulock
	 OpenSS7 Corporation
	 1469 Jefferys Crescent
	 Edmonton, Alberta T6L 6T1
	 CANADA
	 Tel: +1 780 490 1141
	 Fax: +1 780 490 1241
	 Mob: +1 780 953 0557
	 E-mail: bidulock@openss7.org"
    DESCRIPTION
	"This is an enhanced MIB module that provides definition 
	 of an array of X.25 Packet Layer Protocol (PLP) 
	 subsystem managed objects in accordance with ITU-T Rec. 
	 X.25 | ISO/IEC 8208 and the managed object classes of 
	 ITU-T Rec.  X.283 | ISO/IEC 10733."
    REVISION	"200807121128Z"
    DESCRIPTION
	"First release of this module."
    ::= { openss7Modules 103 }

ProtocolVersion ::= TEXTUAL-CONVENTION
    STATUS	current
    DESCRIPTION
	"This textual convention is used to specify the 
	 supported protocol versions of an X.25 Packet Layer 
	 Entity (PLE).  It is set-valued and can contain one or 
	 more of the following values:
	
	 - x2580(8), the 1980 CCITT Yelow Book text of 
	   Recommendation X.25.
	
	 - x2584(2), the 1984 CCITT Red Book text of 
	   Recommendation X.25.
	
	 - iso8208V1(0), the first edition of ISO/IEC 8208 was 
	   based on the 1984 CCITT Red Book text of 
	   Recommendation X.25.  It also contained the necessary 
	   provisions for compatibility with the earlier 1980 
	   CCITT Yellow Book text of Recommendation X.25.
	
	 - x2588(3), the 1988 CCITT Blue Book text of 
	   Recommendation X.25.
	
	 - iso8208V2(2), the second edition of ISO/IEC 8208 wsa 
	   based on the 1988 CCITT Blue Book text of 
	   Recommendation X.25, and retained the necessary 
	   provisions for compatibility with the 1984 and 1980 
	   versions of X.25.
	
	 - x2593(4), the 1993 text of ITU-T Recommendation X.25.
	
	 - iso8208V3(3), the third edition of ISO/IEC 8208 was 
	   based on the 1993 text of ITU-T Recommendation X.25, 
	   and retained the necessary provisions for 
	   compatibility with the 1988, 1984 and 1980 versions 
	   of X.25.
	
	 - x2596(6), the 1996 text of ITU-T Recommendation X.25. 
	
	 - iso8208V4(7), the fourth edition of ISO/IEC 8208 was 
	   based on the 1996 text of ITU-T Recommendation X.25, 
	   and retained the necessary provisions for 
	   compatibility with the 1993, 1988, 1984 and 1980 
	   versions of X.25.
	
	 When used to specify a single version (e.g. the current 
	 operational version), only one value may be contained 
	 in the set."
    SYNTAX	BITS {
		    iSO8208V1(0), iSO8208V2(1), x2584(2), 
		    x2588(3), x2593(4), iSO8208V3(5), x2596(6), 
		    iSO8208V4(7), x2580(8)
		}

InterfaceMode ::= TEXTUAL-CONVENTION
    STATUS	current
    DESCRIPTION
	"This textual convention is use to specify the interface 
	 mode of an X.25 Packet Layer Entity (PLE).  It can have 
	 one of the following values:
	
	 - dTE(0), specifies that the interface is Data Terminal 
	   Equipment (DTE) and is valid for either ITU-T X.25 or 
	   ISO/IEC 8208 operation.
	
	 - dCE(1), specifies that the interface is Data 
	   Circuit-terminating Equiment (DCE) and is valid only 
	   for ITU-T X.25 operation.
	
	 - dTEasDCE(2), specifies that the interface is Data 
	   Terminal Equipment (DTE) behaving as Data 
	   Circuit-termnating equipment (DCE) and is valid only 
	   for ISO/IEC 8208 operation.
	"
    REFERENCE
	"ITU-T Rec. X.25, ITU-T Rec. X.75, ISO/IEC 8208."
    SYNTAX	INTEGER {
	dTE(0),
	dCE(1),
	dTEasDCE(2)
    }

FastSelect ::= TEXTUAL-CONVENTION
    STATUS	current
    DESCRIPTION
	"T"
    SYNTAX	INTEGER {
		    notSpecified(0), fastSelect(1), 
		    fastSelectWithRestrictedResponse(2), 
		    noFastSelect(3)
		}

Modulo ::= TEXTUAL-CONVENTION
    STATUS	current
    DESCRIPTION
	"This textual convention is used to specify the packet 
	 sequence numbering format for an X.25 Packet Layer 
	 Entity (PLE).  It can have one of the following values:
	
	 - default(0), specifies the default packet sequence 
	   numbering.  For X.25, the default packet sequence 
	   numbering is modulo8(1).
	
	 - modulo8(1), specifies packet sequence numbering with 
	   3-bit sequence numbers.
	
	 - modulo128(2), specifies extended packet sequence 
	   numbering with 7-bits sequence numbers.
	
	 - modulo32768(3), specifies super extended packet 
	   sequence numbering with 15-bit sequence numbers.  
	   Only x2596(6) and iso8208V4(7) protocol version 
	   support super extended packet sequence numbering.
	 "
    SYNTAX	INTEGER {
		    default(0), modulo8(1), modulo128(2), 
		    modulo32768(3)
		}

MaxActiveCircuits ::= TEXTUAL-CONVENTION
    STATUS	current
    DESCRIPTION
	"T"
    SYNTAX	INTEGER (0..4096)

DTEAddress ::= TEXTUAL-CONVENTION
    STATUS      current
    DESCRIPTION 
        "This is the full DTE address represented as an octet 
	 string. The first octet of the string is a 
	 numberingPlanId that has one of the following values:
	
	 unknown('0'), TOA/NPI format, address SIZE(2..17)
	 x121('1'), X.121 DTE format, address SIZE(1..15)
	 e164('2'), E.164 DTE format, address SIZE(1..15)
	
	 - unknown('0') indicates TOA/NPI address formatting and 
	   the next two octets in the address field contain the 
	   TOA and NPI values (in ASCII | ITU-T T.501 | ISO/IEC 
	   646), following by 1..40 octets in the address field 
	   that contain the address (in ACSII | ITU-T T.501 | 
	   ISO/IEC 646).
	
	 - x121('1'), indicates X.121 DTE address formatting and 
	   the following 1..15 octets in the address field 
	   contain the X.121 address (in ASCII | ITU-T T.501 | 
	   ISO/IEC 646).
	
	 - e164('2'), indicates E.164 DTE adresss formatting and 
	   the following 1..15 octets in the address field 
	   contain the E.164 address (in ASCII | ITU-T T.501 | 
	   ISO/IEC 646).
	
	 The remaining octets in the octet string contain the 
	 address digits (in ASCII | ITU-T T.501 | ISO/IEC 646 
	 format), containing characters FROM('0'|'1'|'2'|'3'| 
	 '4'|'5'|'6'|'7'|'8'|'9'|'A'|'B'|'C'|'D'|'E'|'F'), each 
	 representing a 4-bit BCD or hexadecimal position in the 
	 DTE address.
	
	 An address containing zero or one octet, or three 
	 octets beginning with unknown('0'), is a NULL address 
	 of the type otherwise indicated."
    REFERENCE
	"ISO/IEC 10733 : NLM.DTEAddress which is defined as a 
	     NumericString(SIZE(0..15)).
	 ITU-T Rec. X.283 : NLM.DTEAddress which is defeined as 
	     a complex type."
    SYNTAX      OCTET STRING (SIZE(0..18))

LogicalChannelNumber ::= TEXTUAL-CONVENTION
    DISPLAY-HINT "d-0"
    STATUS      current
    DESCRIPTION 
        "This textual convention is used to specify a logical 
	 channel number for an X.25 virtual circuit.  It may 
	 specify a logical channel 1..4095, or it can have the 
	 special value zero(0), which specifies no logical 
	 channel."
    REFERENCE
	"ITU-T Rec. X.238 | ISO/IEC 10733 : 
	     NLM.LogicalChannelNumber.
	 ITU-T Rec. X.25 | ISO/IEC 8208."
    SYNTAX      Integer32 (0..4095)

ThroughputClass ::= TEXTUAL-CONVENTION
    DISPLAY-HINT "d-0"
    STATUS      current
    DESCRIPTION 
	"This textual convention is used to specify both ITU-T 
	 Rec.  X.25 | ISO/IEC 8208 basic and extended throughput 
	 classes.  The integer value of the object using this 
	 textual convention is the rate of the X.25 interface in 
	 bits per second.
	
	 The values 0, 1 and 2 are reserved, but this textual 
	 convention uses the special value default(0) to 
	 represent the default throughput class.  Values between 
	 3 and 11 (inclusive) are power of two products of 75 
	 bits per second, or (75*(2**(n-3))) bits per second.  
	 The value of 12 is 48000 bits per second.  Values 
	 between 13 and 44 (inclusive) are a rate of 
	 ((n-1)*64000).
	
	 Values between 3 and 15 (inclusive) are supported by 
	 the basic throughput class negotiation facility of 
	 ITU-T Rec.  X.25 | ISO/IEC 8208.  Values between 16 and 
	 44 (inclusive) are supported by the extended throughput 
	 class negotiation facility of ITU-T Rec. X.25 | 
	 ISO/IEC 8208.
	
	 Note that ITU-T Rec. X.25 (1988) and ISO/IEC 8208 2nd 
	 Edition added b64000(13) basic throughput class.
	
	 Note that ITU-T Rec. X.25 (11/93) and ISO/IEC 8208 3rd 
	 Edition added b12800(14) and b192000(15) throughput 
	 classes, as well as extended throughput classes from 
	 b75(3) through b2048000(44).
	"
    REFERENCE
	"ITU-T Rec. X.283 | ISO/IEC 10733 : ThoughputClasses
	 ITU-T Rec. X.25 | ISO/IEC 8208"
    SYNTAX      INTEGER {
		    default(0), b75(3), b150(4), b300(5), 
		    b600(6), b1200(7), b2400(8), b4800(9), 
		    b9600(10), b19200(11), b48000(12), 
		    b64000(13), b128000(14), b192000(15), 
		    b256000(16), b320000(17), b384000(18), 
		    b448000(19), b512000(20), b576000(21), 
		    b640000(22), b704000(23), b768000(24), 
		    b832000(25), b896000(26), b960000(27), 
		    b1024000(28), b1088000(29), b1152000(30), 
		    b1216000(31), b1280000(32), b1344000(33), 
		    b1408000(34), b1472000(35), b1536000(36), 
		    b1600000(37), b1664000(38), b1728000(39), 
		    b1792000(30), b1856000(41), b1920000(42), 
		    b1984000(43), b2048000(44)
		}


PacketSize ::= TEXTUAL-CONVENTION
    STATUS	current
    DESCRIPTION
	"This textual convention is used to specify X.25 Packet 
	 Sizes.  These can be any power of 2 value between 16 
	 and 4096 (4 through 12, inclusive) for ITU-T Rec. X.25 
	 | ISO/IEC 8208 operation.  When used to express the 
	 maximum packet size accepted, only power of 2 values 
	 between 128 and 4096 (7 through 12, inclusive) are 
	 allowed.
	
	 Note that for ITU-T Rec. X.25 (1980) operation, 
	 x2580(8), the maximum packet size is psize1024(1024).
	 "
    REFERENCE
	"ITU-T Rec. X.283 | ISO/IEC 10733 : PacketSizes
	 ITU-T Rec. X.25 | ISO/IEC 8208"
    SYNTAX	INTEGER {
		    default(0), psize16(16), psize32(32), 
		    psize64(64), psize128(128), psize256(256), 
		    psize512(512), psize1024(1024), 
		    psize2048(2048), psize4096(4096)
		}

Subscription ::= TEXTUAL-CONVENTION
    STATUS	current
    DESCRIPTION
	"This textual convention is used to specify X.25 
	 facility subscription.  There are a number of X.25 
	 facilities that provide both a basic and an extended 
	 form.  The PLE can either be subscribed to the basic or 
	 the extended form or not subscribed at all.  Also, 
	 sometimes the subscription is unknown.  This leads to 
	 the following four values, indicating the level of 
	 subscription:
	
	 - unknown(0), unknown
	 - basic(1), basic
	 - notsubscribed(2), not subscribed
	 - extended(3), extended
	
	 The extended(3) level of subscription is does not 
	 always need to be valid for all uses of this textual 
	 convention.  Common default values are likely 
	 unknown(0) or notsubscribed(2).
	
	 Note that ITU-T Rec. X.283 and ISO/IEC 10733 only make 
	 provisions for true or false; however, at the time that 
	 they were last released, extended facilities did not 
	 exist in ITU-T Rec. X.25 and ISO/IEC 8208."
    REFERENCE
	"ITU-T Rec. X.283 | ISO/IEC 10733
	 ITU-T Rec. X.25 Clause 7.3."
    SYNTAX	INTEGER {
		    unknown(0), basic(1), notsubscribed(2), 
		    extended(3)
		}



WindowSize ::= TEXTUAL-CONVENTION
    STATUS	current
    DESCRIPTION
	""
    SYNTAX	Integer32 (1..32768)

FacilityNonNegotiable ::= TEXTUAL-CONVENTION
    STATUS	current
    DESCRIPTION
	"These are facilities that a non-negotiable but are 
	 indicated to the DTE in a registration confirmation.

	 Objects using this textual convention are set-valued. 
	 When a value is included in the set (the corresponding 
	 bit is set) in a registration confirmation, it 
	 indicates that the corresponding facility is 
	 subscribed; when absent, non-subscribed.

	 - lCP(0), Local Charging Prevention is an optional user 
	   facility requiring subscription only [X.7 6.5.2].
	
	 Objects using this textual convention as their syntax 
	 have a status of read-write or read-create.  For a DTE 
	 that is subscribed and permitted to user the On-line 
	 Facility Registration facility, the set is the set 
	 returned by the DCE or DXE in a registration 
	 confirmation packet.  For a DTE when the On-line 
	 Facility Registration facility is non-subscribed or not 
	 permitted, the value represents the agreement on 
	 subscription between the DTE and the DCE or DXE.

	 For a DCE or DXE, this value represents the 
	 subscription of the DTE to the contained facilities.  
	 When the DTE is subscribed to the On-line Registation 
	 facility, these values will be reported to the DTE in a 
	 registration confirmation packet.  Otherwise, they 
	 refelect the subscription, agreed for a time, between 
	 the DCE or DXE and the DTE."
    SYNTAX	BITS {
		    lCP(0)
		}


FacilityAvailability ::= TEXTUAL-CONVENTION
    STATUS	current
    DESCRIPTION
	"These are facilities whose availability is indicated in 
	 a two-octet parameter in a registration confirmation. 
	
	 This is set-valued.  When a value is included in the 
	 set (the corresponding bit is set) in a registration 
	 confirmation, it indicates that the corresponding 
	 facility is available; when absent, unavailable.

	 When the On-line Faciltiy Registration facility is 
	 subscribed, this value reflects the subscriptions 
	 available at the DCE or DXE.  When the On-line 
	 Factility Registration is non-subscribed, this value 
	 reflects the subscriptions agreed for a time between 
	 the DTE and the DCE or DXE.
	
	 - ePSN(0), Extended Packet Sequence Numbering is an 
	   optional user facility requiring subscription 
	   followed by dynamic invocation [X.7 6.1.3.1].

	 - pR(1), Packet Retransmission is an optional user 
	   facility requiring subscription Followed by dynamic 
	   invocation.

	 - dM(2), D-bit Modification is an optional user 
	   facility that requires subscription only [X.7 6.1.5].

	 - cLAMN(3), Called Line Address Modification 
	   Notification is an optional user facility requiring 
	   subscription followed by dynamic invocation [X.7 
	   6.3.9].

	 - cIPI(4), Charging Information Per Interface
	 - cIPVC(5), Charging Information Per Virtual Call
	 - rCA(6), Reverse Charging Acceptance
	 - rC(7), Reverse Charging
	 - dTCA(8), Default Throughput Classes Assignment
	 - nDWSB(9), Non-standard Default Window Sizes Basic
	 - nDPS(10), Non-standard Default Packet Sizes
	 - lCTR(11), Logical Channel Type Ranges
	 - rOAS(12), ROA Selection
	 - eTCN(13), Extended Throughput Class Negotiation

	 - sPSN(14), Super Extended Packet Sequence Numbering is 
	   an optional user facility requiring subscription 
	   followed by dynamic invocation [X.7 6.1.3.2].

	 - nDWSSE(15), Non-standard Default Window Sizes Super Extended
	
	 When indicated as available, the facility is subscribed 
	 and no futher negotatiaion is required for the 
	 cLAMN(3), cIPVC(5), rC(7) or rOAS(12) facilities.
	
	 Columnar objects that use this textual convention have 
	 a STATUS of read-only.  Reading the parameter has the 
	 effect of a registration confirmation.  When the online 
	 registration facility is subscribed, reading the value 
	 may indeed invoke a registration request and 
	 confirmation exchange."
    SYNTAX	BITS {
		    ePSN(0), pR(1), dM(2), cLAMN(3), cIPI(4), 
		    cIPVC(5), rCA(6), rC(7), dTCA(8), nDWSB(9), 
		    nDPS(10), lCTR(11), rOAS(12), eTCN(13), 
		    sPSN(14), nDWSSE(15)
		}

FacilityNegotiation ::= TEXTUAL-CONVENTION
    STATUS	current
    DESCRIPTION
	"These are facilities whose negotiation is specified in 
	 a two-octet parameter in a registration request or 
	 confirmation.  These faciltiies can be negotiated at 
	 any time.
	
	 This is set-valued.  When a value is included in the 
	 set (the corresponding bit is set) in a registration 
	 request, it requests that the corresponding facility be 
	 invoked; when absent, revoked.  In a registration 
	 confirmation, it indicates that the facility is invoked 
	 (present), or revoked (absent).  The following values 
	 may be present:
	
	 - iCB(0), Incoming Calls Barred facility; this is an 
	   optional user facility that requires subscription 
	   only.
	
	 - oCB(1), Outgoing Calls Barred faciltiy; this is an 
	   optional user facility that requries subscription 
	   only.
	
	 - fSA(2), Fast Select Acceptance facility; this is an 
	   optional user facility that requires subscription 
	   only.
	
	 - rCA(3), Reverse Charging Acceptance facility; this is 
	   an optional user facility that requires subscription 
	   only.
	
	 - fCPN(4), Flow Control Parameter Negotiation facility; 
	   this is an optional user facility that requires 
	   subscription followed by dynamic invocation.
	
	 - bTCN(5), Basic Throughput Class Negotiation facility; 
	   this is an optional user faciltiy that requires 
	   subscription folloed by dynamic invocation.  It 
	   cannot be present when eTCN(15) is present.
	
	 - cIPI(6), Charging Information (Per-Interface) 
	   facility; this is an  optional user facility that 
	   requires subscription only.
	
	 - eTCN(15), Extended Throughput Class Negotiation 
	   facility; this is an optional user faciltiy that 
	   requries subscription only.  It cannot be present 
	   when bTCN(5) is present.
	
	 Only one of basicThroughputClassNegotiation(5) and 
	 extendedThroughputClassNegotitation(15) may be present: 
	 both cannot be present at the same time.

	 Columnar object that use this textual convention have a 
	 STATUS of read-write or read-create.  Writing a value 
	 to the object has the same effect as a registration 
	 request; reading the value, the same as a registration 
	 confirmation.
	 "
    SYNTAX	BITS {
		    iCB(0), oCB(1), fSA(2), rCA(3), fCPN(4), 
		    bTCN(5), cIPI(6), eTCN(15)
		}

FacilityWhileIdle ::= TEXTUAL-CONVENTION
    STATUS	current
    DESCRIPTION
	"These are facilities whose negotiation is specified in 
	 a one-octet parameter in a registration request or 
	 confirmation.  These facilities can be negotiated only 
	 while all logical channels are idle.
	
	 This is set-valued.  When a value is included in the 
	 set (the corresponding bit is set), in a registration 
	 request, it requests that the corresponding facility be 
	 invoked; hwen absent, revoked.  In a registration 
	 confirmation, it indicates that the faciltiy is invoked 
	 (present), or revoked (absent).

	 - ePSN(0),  Extended Packet Sequence Numbering is an 
	   optional user facility that requires subscription 
	   followed by dynamic invocation.

	 - pR(1), Packet Retransmission

	 - dM(2), D-bit Modification

	 - sPSN(3), Super Extended Packet Sequence Numbering

	 - tNAS(4), TOA/NPI Address Subscription

	 "
    SYNTAX	BITS {
		    extendedPacketSequenceNumbering(0), 
		    packetRetransmission(1), 
		    dBitModification(2), 
		    superExtendedPacketSequenceNumbering(3), 
		    tOANPIAddressSubscription(4),
		}

RedirectReason ::= TEXTUAL-CONVENTION
    DISPLAY-HINT "d-0"
    STATUS      current
    DESCRIPTION
	"The reason why the call has been redirected. This is 
	 the reason why the call has been offered or has been 
	 connected to an address different from the originally 
	 called address. That is, the value of the first octet 
	 of the Facility Parameter Field of the Call Redirection 
	 or Call Deflection Notification (CRCDN) or Called Line 
	 Address Modified Notification (CLAMN) facility, 
	 indicating the reason for call redirection or call 
	 deflection. The zero value indicates that the call was 
	 not redirected.
	
	 Call Redirection or Call Deflection Notification is an 
	 optional user facility that requires dynamic invocation 
	 on an packet switched network.
	
	 Note that Call Redireaction and Call Deflection 
	 Notification (CRCDN) and Called Line Address Modified 
	 Notification (CLAMN) facilities are not supported by 
	 the 1980 version of X.25, x2580(8)."
    REFERENCE
	"ITU-T Rec. X.25 Table 7-5/X.25.
	 ITU-T Rec. X.7, Clause 6.3.9., 6.4.4."
    SYNTAX      Integer32 (0..127)

NetworkAddress ::= TEXTUAL-CONVENTION
    STATUS      current
    DESCRIPTION
        ""
    SYNTAX      OCTET STRING (SIZE(0..20))

Direction ::= TEXTUAL-CONVENTION
    STATUS	current
    DESCRIPTION
	""
    SYNTAX	INTEGER {
	incoming(0),
	outgoing(1)
    }

ThroughputClassSupport ::= TEXTUAL-CONVENTION
    STATUS	current
    DESCRIPTION
	"Note that ITU-T Rec. X.25 (1988) and ISO/IEC 8208 2nd 
	 Edition added b64000(13) basic throughput class.
	
	 Note that ITU-T Rec. X.25 (11/93) and ISO/IEC 8208 3rd 
	 Edition added b12800(14) and b192000(15) throughput 
	 classes, as well as extended throughput classes from 
	 b75(3) through b2048000(44).
	 "
    SYNTAX	BITS {
		    b0(0), b1(1), b2(2), b75(3), b150(4), 
		    b300(5), b600(6), b1200(7), b2400(8), 
		    b4800(9), b9600(10), b19200(11), b48000(12), 
		    b64000(13), b128000(14), b192000(15), 
		    b256000(16), b320000(17), b384000(18), 
		    b448000(19), b512000(20), b576000(21), 
		    b640000(22), b704000(23), b768000(24), 
		    b832000(25), b896000(26), b960000(27), 
		    b1024000(28), b1088000(29), b1152000(30), 
		    b1216000(31), b1280000(32), b1344000(33), 
		    b1408000(34), b1472000(35), b1536000(36), 
		    b1600000(37), b1664000(38), b1728000(39), 
		    b1792000(30), b1856000(41), b1920000(42), 
		    b1984000(43), b2048000(44)
		}

x25PLPNotifications OBJECT IDENTIFIER
    ::= { x25PLPMIB1 0 }

x25PLPObjects OBJECT IDENTIFIER
    ::= { x25PLPMIB1 1 }

x25PLPTables OBJECT IDENTIFIER
    ::= { x25PLPObjects 1 }

x25PLE OBJECT IDENTIFIER
    ::= { x25PLPTables 1 }

x25PLETable OBJECT-TYPE
    SYNTAX	SEQUENCE OF X25PLEEntry
    MAX-ACCESS	not-accessible
    STATUS	current
    DESCRIPTION
	"Provides a table of X.25 Packet Layer Entities (PLE).  
	 Each X.25 Packet Layer Entity (PLE) corresponds to an 
	 X.25 DTE, X.25 DCE, X.25 DXE, or X.75 STX, over which 
	 permanent virtual circuits exist or virtual calls can 
	 be placed.
	
	 Entries in this table generate stateChange, 
	 objectCreation and objectDeletion notifications.
	
	 Entries in this table support 'activate' and 
	 'deactivate' actions."
    REFERENCE
	"ITU-T Rec. X.283 | ISO/IEC 10733 : x25PLE MOC."
    ::= { x25PLE 1 }

x25PLEEntry OBJECT-TYPE
    SYNTAX	X25PLEEntry
    MAX-ACCESS	not-accessible
    STATUS	current
    DESCRIPTION
	"Provides an entry in the x25PLETable.  Each entry 
	 corresponds to an instance of an x25PLE managed object, 
	 which represents a DTE, DCE or DXE X.25 packet layer 
	 entity, or an X.75 STX, from which permanent virtual 
	 circuits are formed or virtual calls are established.
	
	 This MO class is never instantiated.  It serves as a 
	 generic x25PLE MO from which both the x25PLE-DTE and 
	 x25PLE-DCE MO classes are derived.  Note that the 
	 values of the x25PLEId naming attribute are required to 
	 be unique across all instances of MOs derived from 
	 this, which have a common superior.
	
	 Whenever a derived MO is created an instance of this 
	 MOC is also created.  That is, creating a row in the 
	 x25PLEDTE, x25PLEDCE or x25PLEDXE tables results in the 
	 creation of a row in this table with the same index.
	
	 This MO provides for the following facilities, for an 
	 agreed period of time, between the DTE and the DCE:
	
	 - Extended Packet Sequence Numbering
	 - Super-extended Packet Sequence Numbering
	 - D-bit Modification
	 - Packet Retransmission
	 - Incoming Calls Barred
	 - Outgoing Calls Barred
	 - One-way Logical Channel Outgoing
	 - One-way Logical Channel Incoming
	 - Non-standard Default Packet Sizes
	 - Non-standard Default Window Sizes
	 - Default Throughput Classes Assignment
	 - Flow Control Parameter Negotiation
	 - Basic Throughput Class Negotiation
	 - Exended Throughput Class Negotiation
	 
	 "
    REFERENCE
	"ITU-T Rec. X.283 | ISO/IEC 10733 : x25PLE MO."
    INDEX	{
		    x25PLEId	    -- (BASE CLASS INSTANCE)
		}
    ::= { x25PLETable 1 }

X25PLEEntry ::= SEQUENCE {
    x25PLEId					SimpleNameType,
    x25PLEOperationalState			OperationalState,
    x25PLEAdministrativeState			AdministrativeState,
    x25PLEProtocolVersionsSupported		ProtocolVersion,
    x25PLELocalDTEAddress			DTEAddress,
    x25PLEInterfaceMode				InterfaceMode,
    x25PLEFacilityNonNegotiable			FacilityNonNegotiable,
    x25PLEFacilityAvailability			FacilityAvailability,
    x25PLEFacilityNegotiation			FacilityNegotiation,
    x25PLEFacilityWhileIdle			FacilityWhileIdle,
    x25PLEPacketSequenceNumbering		Modulo,
    x25PLEDefaultPacketSizeIncoming		PacketSize,
    x25PLEDefaultPacketSizeOutgoing		PacketSize,
    x25PLEDefaultWindowSizeIncoming		WindowSize,
    x25PLEDefaultWindowSizeOutgoing		WindowSize,
    x25PLEDefaultThroughputClassIncoming	ThroughputClass,
    x25PLEDefaultThroughputClassOutgoing	ThroughputClass,
    x25PLELogicalChannelAssignmentHIC		LogicalChannelNumber,
    x25PLELogicalChannelAssignmentLIC		LogicalChannelNumber,
    x25PLELogicalChannelAssignmentHTC		LogicalChannelNumber,
    x25PLELogicalChannelAssignmentLTC		LogicalChannelNumber,
    x25PLELogicalChannelAssignmentHOC		LogicalChannelNumber,
    x25PLELogicalChannelAssignmentLOC		LogicalChannelNumber,
    x25PLESNServiceProvider			RowPointer,
    x25PLESNSAP					RowPointer,
}

x25PLEId OBJECT-TYPE
    SYNTAX	SimpleNameType
    MAX-ACCESS	not-accessible
    STATUS	current
    DESCRIPTION
	"This object provides an index for the table."
    REFERENCE
	"ITU-T Rec. X.283 | ISO/IEC 10733 : x25PLE.x25PLEId"
    ::= { x25PLEEntry 1 }

x25PLEOperationalState OBJECT-TYPE
    SYNTAX	OperationalState
    MAX-ACCESS	read-only
    STATUS	current
    DESCRIPTION
	"Indicates the operational state of the X.25 packet 
	 layer entity following the OperationalState textual 
	 convention from the OPENSS7-SMI-MIB module.  This 
	 object can have one of two values:
	
	 - disabled(0), the X.25 packet layer entity is 
	   non-operational.
	
	 - enabled(1), the X.25 packet layer entity is 
	   operational.
	
	 Changes on some of the columnar objects in this table 
	 may not be effected when the X.25 packet layer entity 
	 is in the operational state."
    REFERENCE
        "ITU-T Rec. X.721 (1992) | ISO/IEC 10165-2 : 1992, 
	     Attribute-ASN1Module.OperationalState.
         ITU-T Rec. X.731 (1992) | ISO/IEC 10164-2 : 1993, 
	     Section 8.1.1.1.
	 ITU-T Rec. X.283 | ISO/IEC 10733 : x25PLE."
    ::= { x25PLEEntry 2 }

x25PLEAdministrativeState OBJECT-TYPE
    SYNTAX	AdministrativeState
    MAX-ACCESS	read-write
    STATUS	current
    DESCRIPTION
	"Provides the administrative state of the X.25 packet 
	 layer entity following the AdministrativeState textual 
	 convention from the OPENSS7-SMI-MIB module.  This 
	 object can have one of the following values:
	
	 - locked(0), the X.25 packet layer entity is 
	   administratively prohibited from providing service.
	   Setting this value results in the immediate, 
	   distruptive removal from service of the X.25 PLE.  
	   All virtual calls are abortively disconnected and 
	   permanent virtual circuits are disabled.
	
	 - unlocked(1), the X.25 packet layer entity is 
	   administratively permitted to provide service.
	   Setting this value results in the placement back into 
	   service of all virtual Calls and PVC still associated 
	   with the X.25 PLE.
	
	 - shuttingDown(2), the X.25 packet layer entity is 
	   shutting down and will soon no longer be 
	   administratively permitted to provide service.  
	   Setting this value results in the graceful removal 
	   from service of the X.25 PLE.  All virtual calls will 
	   be allowed to terminated and PVC allowed to detach 
	   before the X.25 PLE is taken out of service; however, 
	   new virtual calls or PVC attachments will not be 
	   permitted.
	
	 The ability to make changes to columnar objects does 
	 not depend directly on this state."
    REFERENCE
        "ITU-T Rec. X.721 (1992) | ISO/IEC 10165-2 : 1992, 
	     Attribute-ASN1Module.AdministrativeState.
         ITU-T Rec. X.731 (1992) | ISO/IEC 10164-2 : 1993, 
	     Section 8.1.1.3.
	 ITU-T Rec. X.283 | ISO/IEC 10733 : x25PLE."
    ::= { x25PLEEntry 3 }

x25PLEProtocolVersionsSupported OBJECT-TYPE
    SYNTAX	ProtocolVersion
    MAX-ACCESS	read-only
    STATUS	current
    DESCRIPTION
	"Indicates the protocol versions supported by this X.25 
	 Packet Layer Entity using the ProtocolVersion textual 
	 convention.  This columnar object is set-valued and can 
	 have one or more of the following values:
	
	 - x2580(8), ITU-T Rec. X.25 (1980) - Yellow Book
	 - x2584(2), ITU-T Rec. X.25 (1984) - Red Book
	 - x2588(3), ITU-T Rec. X.25 (1988) - Blue Book
	 - x2593(4), ITU-T Rec. X.25 (1993) - White Book
	 - x2597(6), ITU-T Rec. X.25 (1997) - Grey Book
	
	 - iso8208V1(0), ISO/IEC 8208 Edition 1
	 - iso8208V2(1), ISO/IEC 8208 Edition 2
	 - iso8208V3(5), ISO/IEC 8208 Edition 3
	 - iso8208V4(6), ISO/IEC 8208 Edition 4
	
	 Note that ISO/IEC 8208 editions are backward 
	 compatible with previous editions and are also 
	 backwared compatible with preceding X.25 versions.  
	 That is ISO/IEC 8208 4th Edition is backward compatible 
	 with all the protocol versions listed above."
    REFERENCE
	"ITU-T Rec. X.283 | ISO/IEC 10733 : x25PLE 
	     protocolVersionsSupported."
    ::= { x25PLEEntry 4 }

x25PLELocalDTEAddress OBJECT-TYPE
    SYNTAX	DTEAddress
    MAX-ACCESS	read-write
    STATUS	current
    DESCRIPTION
	"The Full DTE address of this PLE expressed as an X.121, 
	 E.164 or TOA/NPI address using the DTEAddress textual  
	 convention.  This object has not default value and must 
	 be specified on creation.  The DTEAddress textual 
	 convention supports X.121 and E.164 DTE addresses as 
	 well as TOA/NPI addresses.  For an X.25 DCE, this is 
	 the address of the DTE at the far end of the data link."
    REFERENCE
	"ITU-T Rec. X.283 | ISO/IEC 10733 : x25PLE 
	     localDTEAddress.
	 ITU-T Rec. X.25 Clause 5.2."
    ::= { x25PLEEntry 5 }

x25PLEInterfaceMode OBJECT-TYPE
    SYNTAX	InterfaceMode
    MAX-ACCESS	read-only
    STATUS	current
    DESCRIPTION
	"Indicates the interface mode of the X.25 PLE using the 
	 InterfaceMode textual convention.  This will be one of 
	 the following:
	
	 - dTE(0), the entry was created by creating an entry in 
	   the x25PLEDTETable, and corresponds to an X.25 or ISO 
	   8208 DTE.  There exists a corresponding entry with 
	   the same x25PLEId in the x25PLEDTETable.
	
	 - dCE(1), the entry was created by creating an entry in 
	   the x25PLEDCETable, and corresponds to an X.25 DCE.  
	   There exists a corresponding entry with the same 
	   x25PLEId in the x25PLEDCETable.
	
	 - dTEasDCE(2), the entry was created by creating an 
	   entry in the x25PLEDXETable, and corresponds to an 
	   ISO 8208 DXE. There exists a corresponding entry with 
	   the same x25PLEId in the x25PLEDXETable.
	
	 Note that the dTEasDCE(2) value is only applicable to 
	 ISO 8208 protocol versions.  The other values are 
	 applicable to ITU-T Rec. X.25 operation."
    REFERENCE
	"ITU-T Rec. X.283 | ISO/IEC 10733 : x25PLE x25PLEMode 
	     (X.283) or interfaceMode (10733)."
    ::= { x25PLEEntry 6 }

x25PLEFacilityNonNegotiable OBJECT-TYPE
    SYNTAX	FacilityNonNegotiable
    MAX-ACCESS	read-write
    STATUS	current
    DESCRIPTION
	"Specified or indicates the subscription of 
	 non-negotiable facilities, using the 
	 FacilityNonNegotiable textual convention.
	
	 For a DTE subscribed to the On-line Facility 
	 Registration facility, this set value represents the 
	 subscribed non-negotiable facilities reported by the 
	 DCE or DXE in a registration confirmation packet.  In 
	 this case, the object is treated as read-only to 
	 management stations.
	
	 For a DTE not subscribed to the On-line Facility 
	 Registration facility, this set value represents the 
	 subscribed facilities, agreed to for a time between 
	 the DTE and the DCE or DXE, and is writable by a 
	 management station.
	
	 For a DCE, this set value represents the non-negotiable 
	 facilities that are agree to for a time between the DCE 
	 and the DTE and will be reported to the DTE in a 
	 registration confirmation packet, and is writable by a 
	 management station.
	
	 The facilities that may be contained in the set are:
	
	 - lCP(0), Local Charging Prevention is an optional user 
	   facility that requires subcription only.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ISO/IEC 8208 : 2000, 16.2.2.1 Non-negotiable facilities 
	     values."
    ::= { x25PLEEntry 7 }

x25PLEFacilityAvailability OBJECT-TYPE
    SYNTAX	FacilityAvailability
    MAX-ACCESS	read-write
    STATUS	current
    DESCRIPTION
	"Specifies or indicates the availability for 
	 registration of optional user facilities using the 
	 FacilityAvailability textual convention.
	
	 For a DTE subscribed to the On-line Facility 
	 Registration facility, this set value represents the 
	 availability for registration of facilities reported by 
	 the DCE or DXE in a registration confirmation packet.  
	 In this case, the object is treated as read-only to 
	 management stations.
	
	 For a DTE not subscribed to the On-line Facility 
	 Registration facility, this set value represents the 
	 subscription of facilities not requiring further 
	 negotiation, agreed to for a time between the DTE and 
	 DCE, and is writable by a management station.  No 
	 facilities are available for registration.
	
	 For a DCE, this set value represents the facilities 
	 available for registration or subscribed that are 
	 agreed to for a time between the DCE and DTE and will 
	 be reported to the DTE in a registration confirmation 
	 packet, and is writable by a management station.
	
	 The facilities that may be contained in the set 
	 indicating availabiliy, are as follows:
	
	 - ePSN(0), Extended Packet Sequence Numbering;
	
	 - pR(1), Packet Retransmission;
	
	 - dM(2), D-bit Modification;
	
	 - cIPI(4) Charging Information (Per Interface);
	
	 - rCA(6), Reverse Charging Acceptance;
	
	 - dTCA(8), Default Throughput Classes Assignment;
	
	 - nDWSB(9), Non-standard Default Window Sizes for 
	   Normal and Extended Packet Sequence Numbering;
	
	 - nDPS(10), Non-standard Default Packet Sizes;
	
	 - lCTR(11), Logical Channel Type Ranges;
	
	 - sPSN(14), Super Extended Packet Sequence Numbering;
	
	 - nDWSSE(15), Non-standard Default Window Sizes Super 
	   Extended Packet Sequence Numbering.
	
	 The facilities that may be contained in the set 
	 indicating subscription are:
	
	 - cLAMN(3), Called Line Address Modification;
	
	 - cIPVC(5), Charging Information (Per Virtual Call);
	
	 - rC(7), Reverse Charging;
	
	 - rOAS(12), ROA Selection.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ISO/IEC 8208 : 2000, 16.2.2.2 Availability of 
	     facilities."
    ::= { x25PLEEntry 8 }

x25PLEFacilityNegotiation OBJECT-TYPE
    SYNTAX	FacilityNegotiation
    MAX-ACCESS	read-write
    STATUS	current
    DESCRIPTION
	"Specifies or indicates the current subscription of 
	 facilities that may be negotiated at any time using the 
	 On-line Facility Registration facility, using the 
	 FacilityNegotiation textual convention.
	
	 For a DTE subscribed to the On-line Facility 
	 Registration facility, this set value represents the 
	 subscription of facilities reported by the DCE or DXE 
	 in a registration confirmation packet, and is writable 
	 by a management station subject to negotiation with the 
	 DCE.
	
	 For a DTE not subscribed to the On-line Facility 
	 Registration facility, this set value represents the 
	 subscription of facilities, agreed to for a time 
	 between the DTE and DCE, and is writable by a 
	 management station without negotiation with the DCE.
	
	 For a DCE, this set value represents the subscribed 
	 facilities, agreed to for a time between the DCE and 
	 the DTE and will be reported to the DTE in a 
	 registration confirmation packet, and is writable by a 
	 management station.
	
	 The facilities that may be contained in the set, 
	 indicating subscription, are as follows:
	
	 - iCB(0), Incoming Calls Barred;
	
	 - oCB(1), Outgoing Calls Barred;
	
	 - fSA(2), Fast Select Acceptance;
	
	 - rCA(3), Reverse Charging Acceptance;
	
	 - fCPN(4), Flow Control Parameter Negotiation is an 
	   essential facility requiring subscription followed by 
	   dynamic invocation [X.7 6.1.2.3].  When subscribed 
	   and the flow control parameters requested for a 
	   virtual call are different from the default 
	   parameters, they will be negotiated using the 
	   associated facilities in the call request and call 
	   accepted packets.
	
	 - bTCN(5), Basic Throughput Class Negotiation is an 
	   optional facility requiring subscription followed by 
	   dynamic invocation [X.7 6.1.1.2].  When subscribed 
	   and the throughput class parameters requested fro a 
	   virtual call are different from the default 
	   parameters, they will be negotiated using the 
	   associated facilities in the call request and call 
	   call accepted packets.
	
	 - cIPI(6), Charging Information (Per-Interface);
	
	 - eTCN(15), Extended Throughput Class Negotiation;
	
	 Only one of bTCN(5) and eTCN(15) can be present in the 
	 set at one time.
	 
	 Adding or removing values to the set has no effect on 
	 calls in progress and are only applicable to new 
	 virtual calls.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE, 
	     flowControlParameterNegotiation, 
	     throughputClassNegotiation.
	 ISO/IEC 8208 : 2000, 16.2.2.3 Facilities that may be 
	     negotiated at any time.
	 ITU-T Rec. X.7 6.1.1.2, 6.1.2.3."
    ::= { x25PLEEntry 9 }

x25PLEFacilityWhileIdle OBJECT-TYPE
    SYNTAX	FacilityWhileIdle
    MAX-ACCESS	read-write
    STATUS	current
    DESCRIPTION
	"Specifies or indicates the current subscription of 
	 faciltiies that may only be negotiated when no virtual 
	 calls are in progress on the interface, with the 
	 On-line Facility Registration facility, using the 
	 FacilityWhileIdle textual convention.
	
	 For a DTE subscribed to ths On-line Facility 
	 Registration facility, this set value represents the 
	 subscription of facilities reported by the DCE or DXE 
	 in a registration confirmation packet, and is writable 
	 by a management station when the administrative state 
	 is 'locked' and subject to negotiation with the DCE.
	
	 For a DTE not subscribed to the On-line Facility 
	 Registration facility, this set value represents the 
	 subscription of facilities, agreed to for a time 
	 between the DTE and DCE, and is writable by a 
	 management station when the administrative stat is 
	 'locked' but without negotiation with the DCE.
	
	 For a DCE, this set value represents the subscribed 
	 facilities, agreed to for a time between the DCE and 
	 the DTE and will be reported to the DTE in a 
	 registration confirmation packet, and is writable by a 
	 management station.
	
	 The facilities that may be contained in the set, 
	 indicating subscription, are as follows:
	
	 - ePSN(0),  Extended Packet Sequence Numbering; this 
	   value should only be set by the agent when the 
	   correspoding bit in the X25PLEFacilityAvailability 
	   column is also set.
	
	 - pR(1), Packet Retransmission; this value should only 
	   be set by the agent when the corresponding bit in the 
	   x25PLEFacilityAvailability column is also set.
	
	 - dM(2), D-bit Modification; this value should only be 
	   set by the agent when the corresponding bit in the 
	   x25PLEFacilityAvailability column is also set.
	
	 - sPSN(3), Super Extended Packet Sequence Numbering; 
	   this value should only be set by the agent when the 
	   corresponding bit in the x25PLEFacilityAvailability 
	   column is also set.  Super Extended Packet Sequence 
	   Numbering is not supported in protocol versions 
	   earlier than ITU-T Rec. X.25 (1996).
	
	 - tNAS(4), TOA/NPI Address Subscription.
	
	 Note that for DTE subscribed to the On-line Facility 
	 Registration facility, writing to this column while the 
	 X.25 PLE is operational and locked will result in a 
	 registration request packet being issued to the DCE or 
	 DXE.  Reading the value will return the facilities 
	 reported as subscribed the the DCE in a registration 
	 confirmation packet.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ISO/IEC 8208 : 2000, 16.2.2.4 Facilities that may be 
	     negotiated only when all logical channels used for 
	     Virtual Calls are in state p1."
    ::= { x25PLEEntry 10 }

x25PLEPacketSequenceNumbering OBJECT-TYPE
    SYNTAX	Modulo
    MAX-ACCESS	read-write
    STATUS	current
    DESCRIPTION
	"The modulo of the packet sequence number space using 
	 the Modulo textual convention.  Expressed as a general 
	 format indicator.  ITU-T Rec.  X.25 | ISO/IEC 8208 only 
	 requires support for the values modulo8(1), 
	 modulo128(2) and modulo32768(3), but it is possible 
	 that some future version may extend the range.  A 
	 system is only required to support the settings of 
	 values that are also required by the protocol standard.  
	 A system shall return and error when an attempt is made 
	 to set the value to a value that is not supported by 
	 that system.
	
	 Extended Packet Sequence Numbering and Super Extended 
	 Packet Sequence Numbering are optional user facilities 
	 that require subscription followed by dynamic 
	 invocation on packet switched networks.
	
	 ITU-T Rec. X.25 only permits this value to be set for 
	 an entire DTE.  That is, where the setting applies to 
	 all switched virtual calls and permanent virtual 
	 circuits (logical channels) proviided by the DTE X.25 
	 Packet Layer Entity.  It also permits the packet 
	 sequence numbering scheme to be applied individually to 
	 each logical channel for the DTE X.25 PLE.  When the 
	 network supports the user of multiple modulos at the 
	 same interface, for virtual calls the selection is made 
	 by signalling of the GFI, for permanent virtual 
	 circuits, the modulo is established by subscription."
    REFERENCE
	""
    ::= { x25PLEEntry 11 }

--  x25PLEDefaultPacketSizes
x25PLEDefaultPacketSizeIncoming OBJECT-TYPE
    SYNTAX	PacketSize
    MAX-ACCESS	read-write
    STATUS	current
    DESCRIPTION
	"Specifies the incoming default packet size for virtual 
	 calls and permanent virtual circuits from the X.25 PLE 
	 using the PacketSize textual convention.  When set to 
	 default(0), it indicates that the X.25 or ISO 8208 
	 default packet size of 128 applies.  Any other value 
	 indicates the value agreed by the Non-standard Default 
	 Packet Sizes facility.
	
	 For a DTE subscribed to the On-line Facility 
	 Registration facility, this value can only be written 
	 with a value other than the default value when the 
	 Non-standard Default Packet Sizes facility is indicated 
	 as available in the x25PLEFacilityAvailability column.  
	 In this case, writing a value will invoke the 
	 registration of the non-standard default packet size 
	 with the DCE.  When non-subscribed to the On-line 
	 Facility Registration facility, this value, when other 
	 than the default, refelects the current value, agreet o 
	 for a time between the DTE and the DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE, 
	     defaultPacketSizes.
	 ISO/IEC 8208 : 2000, 16.2.2.5 Non-standard default 
	     packet sizes."
    ::= { x25PLEEntry 12 }

x25PLEDefaultPacketSizeOutgoing OBJECT-TYPE
    SYNTAX	PacketSize
    MAX-ACCESS	read-write
    STATUS	current
    DESCRIPTION
	"Specifies the outgoing default packet size for virtual 
	 calls and permanent virtual circuits from the X.25 PLE 
	 using the PacketSize textual convention.  When set to 
	 default(0), it indicates that the X.25 or ISO 8208 
	 default packet size of 128 applies.  Any other value 
	 indicates the value agreed by the Non-standard Default 
	 Packet Sizes facility.
	
	 For a DTE subscribed to the On-line Facility 
	 Registration facility, this value can only be written 
	 with a value other than the default value when the 
	 Non-standard Default Packet Sizes facility is indicated 
	 as available in the x25PLEFacilityAvailability column.  
	 In this case, writing a value will invoke the 
	 registration of the non-standard default packet size 
	 with the DCE.
	
	 When the DTE is not subscribed to the On-line Facility 
	 Registration facility, this value, when other than the 
	 default, reflects the current value, agreed to for a 
	 time between the DTE and the DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE, 
	     defaultPacketSizes.
	 ISO/IEC 8208 : 2000, 16.2.2.5 Non-standard default 
	     packet sizes."
    ::= { x25PLEEntry 13 }

--  x25PLEDefaultWindowSizes
x25PLEDefaultWindowSizeIncoming OBJECT-TYPE
    SYNTAX	WindowSize
    MAX-ACCESS	read-write
    STATUS	current
    DESCRIPTION
	"Specifies the incoming default window size for virtual 
	 calls and permanent virtual circuits from the X.25 PLE 
	 using the WindowSize textual convention.  When set to 
	 default(0), it indicates that the X.25 or ISO 8208 
	 default window size of 2 (for basic and extended 
	 sequence numbering) or 128 (for super extended sequence 
	 numbering) applies.  Any other value indicates the 
	 value agreed to by the Non-standard Default Window 
	 Sizes facility.
	
	 For a DTE subscribed to the On-line Facility 
	 Registration facility, this value can only be written 
	 with a value other than the default value within the 
	 basic range when the Non-standard Default Window 
	 Sizes for Normal and Extended Packet Sequence Numbering 
	 Registration facility is indicated as available in the 
	 x25PLEFacilityAvailability column, or in the extended 
	 range when the Non-standard Default Window Sizes for 
	 Super Exended Packet Sequence Numbering Registration 
	 facility is indicated as available in the 
	 x25PLEFacilityAvailaiblity column.
	
	 When the DTE is not subscribed to the On-line Facility 
	 Registration facility, this value, when other than the 
	 default value, reflects the current value, agreed to 
	 for a time between the DTE and the DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE, 
	     defaultWindowSizes."
    ::= { x25PLEEntry 14 }

x25PLEDefaultWindowSizeOutgoing OBJECT-TYPE
    SYNTAX	WindowSize
    MAX-ACCESS	read-write
    STATUS	current
    DESCRIPTION
	"Specifies the outgoing default window size for virtual 
	 calls and permanent virtual circuits from the X.25 PLE 
	 using the WindowSize textual convention.  When set to 
	 default(0), it indicates that the X.25 or ISO 8208 
	 default window size of 2 (for basic and extended 
	 sequence numbering) or 128 (for super extended sequence 
	 numbering) applies.  Any other value indicates the 
	 value agreed to by the Non-standard Default Window 
	 Sizes facility.
	
	 For a DTE subscribed to the On-line Facility 
	 Registration facility, this value can only be written 
	 with a value other than the default value within the 
	 basic range when the Non-standard Default Window 
	 Sizes for Normal and Extended Packet Sequence Numbering 
	 Registration facility is indicated as available in the 
	 x25PLEFacilityAvailability column, or in the extended 
	 range when the Non-standard Default Window Sizes for 
	 Super Exended Packet Sequence Numbering Registration 
	 facility is indicated as available in the 
	 x25PLEFacilityAvailabilty column.
	
	 When the DTE is not subscribed to the On-line Facility 
	 Registration facility, this value, when other than the 
	 default value, reflects the current value, agreed to 
	 for a time between the DTE and the DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE, 
	     defaultWindowSizes."
    ::= { x25PLEEntry 15 }

--  x25PLEDefaultThroughputClasses
x25PLEDefaultThroughputClassIncoming OBJECT-TYPE
    SYNTAX	ThroughputClass
    MAX-ACCESS	read-write
    STATUS	current
    DESCRIPTION
	"Provides the default incoming throughput class using 
	 the ThroughputClass textual convention.  When this 
	 value is set to default(0), it specifies that the 
	 throughput class is the normal default throughput 
	 class.  The normal default throughput is just less than 
	 or just greater than the bit rate of a full duplex DCE/DTE 
	 interface, or half the rate of a half-duplex interface.  
	 When set to a different value, it provides the default 
	 value specified by the Default Throughput Classes 
	 Assignment facility.  When virtual calls are 
	 established and the proposed throughtput class does not 
	 match this, the default throughput class, negotiation 
	 using the Basic or Extended Throughpug Class 
	 Negotiation facility will be necessary when available.
	
	 For a DTE subscribed to the On-line Faciltiy 
	 Registration facility, this value can only be written 
	 with a value other than the default value within the 
	 basic or extended range when the Default Throughput 
	 Classes Assignment facility is indicated as available 
	 in the x25PLEFacilityAvailability column.
	
	 When the DTE is not subscribed to the On-line Facility 
	 Registration facility, this value, when other than the 
	 default value, reflects the current value, agreed to 
	 for a time between the DTE and the DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE, 
	     defaultThroughputClasses."
    DEFVAL	{ 0 } -- default(0)
    ::= { x25PLEEntry 16 }

x25PLEDefaultThroughputClassOutgoing OBJECT-TYPE
    SYNTAX	ThroughputClass
    MAX-ACCESS	read-write
    STATUS	current
    DESCRIPTION
	"Provides the default outgoing throughput class using 
	 the ThroughputClass textual convention.  When this 
	 value is set to default(0), it specifies that the 
	 throughput class is the normal default throughput 
	 class.  The normal default throughput is just less than 
	 or just greater than the bit reate of a full duplex 
	 DCE/DTE interface, or half the rate of a half-duplex 
	 interface.  When set to a different value, it provides 
	 the default value specified by the Default Throughput 
	 Classes Assignment facility.  When virtual calls are 
	 established and the proposed throughtput class does not 
	 match this, the default throughput class, negotiation 
	 using the Flow Control Parameter Negotiation facility 
	 will be necessary when available.
	
	 For a DTE subscribed to the On-line Faciltiy 
	 Registration facility, this value can only be written 
	 with a value other than the default value within the 
	 basic or extended range when the Default Throughput 
	 Classes Assignment facility is indicated as available 
	 in the x25PLEFacilityAvailability column.
	
	 When the DTE is not subscribed to the On-line Facility 
	 Registration facility, this value, when other than the 
	 default value, reflects the current value, agreed to 
	 for a time between the DTE and the DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE.
	     defaultThroughputClasses."
    DEFVAL	{ 0 } -- default(0)
    ::= { x25PLEEntry 17 }

x25PLESNServiceProvider OBJECT-TYPE
    SYNTAX	RowPointer
    MAX-ACCESS	read-write
    STATUS	current
    DESCRIPTION
	""
    REFERENCE
	"ITU-T Rec. X.283 | ISO/IEC 10733 : x25PLE."
    ::= { x25PLEEntry 18 }

x25PLESNSAP OBJECT-TYPE
    SYNTAX	RowPointer
    MAX-ACCESS	read-write
    STATUS	current
    DESCRIPTION
	""
    REFERENCE
	"ITU-T Rec. X.283 | ISO/IEC 10733 : x25PLE."
    ::= { x25PLEEntry 19 }

--  x25PLELogicalChannelAssignments
x25PLELogicalChannelAssignmentHIC OBJECT-TYPE
    SYNTAX	LogicalChannelNumber
    MAX-ACCESS	read-write
    STATUS	current
    DESCRIPTION
	"Specifies the highest logical channel number used for 
	 incoming virtual calls, using the LogicalChannelNumber 
	 textual convention.  This is used in conjunction with 
	 the corresponding LIC value, 
	 x25PLELogicalChannelAssignmentLIC, to define a range of 
	 logical channels.  When set to zero(0), No logical 
	 channels are assigned to incoming virtual calls.  This 
	 is also the default.
	
	 The value must be zero(0) when the corresponding LIC is 
	 set to zero(0), or, otherwise, at least one greater 
	 than the value of the corresponding LIC and at least 
	 one less than the value of the corresponding LTC.  The 
	 range defined by the corresponding LIC and HIC values 
	 must not overlap with the other ranges specified for 
	 logical channel assignment.
	
	 Note that this value may be overridden by the 
	 corresponding value in the x25PLEIVMOTable.
	
	 For a DTE subscribed to the On-line Facility 
	 Registration facility, and where the Logical Channel 
	 Assignment facility is indicated as available in the 
	 x25PLEFacilityAvailability column, writing to this 
	 column may invoke the registration procedure.
	
	 When the DTE is not subscribed to the On-line Facility 
	 Registration facility, this value reflects the current 
	 value, agreed to for a time between the DTE and the 
	 DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE."
    DEFVAL	{ 0 }
    ::= { x25PLEEntry 20 }

x25PLELogicalChannelAssignmentLIC OBJECT-TYPE
    SYNTAX	LogicalChannelNumber
    MAX-ACCESS	read-write
    STATUS	current
    DESCRIPTION
	"Specifies the lowest logical channel number used for 
	 incoming virtual calls, using the LogicalChannelNumber 
	 textual convention.  This is used in conjunction with 
	 the corresponding HIC value, 
	 x25PLELogicalChannelAssignmentHIC, to define a range of 
	 logical channels.  When set to zero(0), no logical 
	 channels are assigned to incoming virtual calls.  This 
	 is also the default.
	
	 The value must be zero(0) when the corresponding HIC is 
	 set to zero(0), or, otherwise, at least one less than 
	 the value of the corresponding HIC.  The range defined 
	 by the corresponding LIC and HIC values must not 
	 overlap with the other ranges specified for logical 
	 channel assignment.
	
	 Note that this value may be overridden by the 
	 corresponding value in the x25PLEIVMOTable.
	
	 For a DTE subscribed to the On-line Facility 
	 Registration facility, and where the Logical Channel 
	 Assignment facility is indicated as available in the 
	 x25PLEFacilityAvailability column, writing to this 
	 column may invoke the registration procedure.
	
	 When the DTE is not subscribed to the On-line Facility 
	 Registration facility, this value reflects the current 
	 value, agreed to for a time between the DTE and the 
	 DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE."
    DEFVAL	{ 0 }
    ::= { x25PLEEntry 21 }

x25PLELogicalChannelAssignmentHTC OBJECT-TYPE
    SYNTAX	LogicalChannelNumber
    MAX-ACCESS	read-write
    STATUS	current
    DESCRIPTION
	"Specifies the highest logical channel number used for 
	 two-way virtual calls, using the LogicalChannelNumber textual 
	 convention.  This is used in conjunction with the 
	 corresponding LTC value, 
	 x25PLELogicalChannelAssignmentLTC, to define a range of 
	 logical channels.  When set to zero(0), no logical 
	 channels are assigned to two-way virtual calls.  This 
	 is also the default.
	
	 The value must be zero(0) when the corresponding LTC is 
	 set to zero(0), or, otherwise, at least one greater 
	 than the value of the corresponding LTC and at least 
	 one less than the value of the corresponding LOC.  The 
	 range defined by the corresponding LTC and HTC values 
	 must not overlap with the other ranges specified for 
	 logical channel assignment.
	
	 Note that this value may be overridden by the 
	 corresponding value in the x25PLEIVMOTable.
	
	 For a DTE subscribed to the On-line Facility 
	 Registration facility, and where the Logical Channel 
	 Assignment facility is indicated as available in the 
	 x25PLEFacilityAvailability column, writing to this 
	 column may invoke the registration procedure.
	
	 When the DTE is not subscribed to the On-line Facility 
	 Registration facility, this value reflects the current 
	 value, agreed to for a time between the DTE and the 
	 DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE."
    DEFVAL	{ 0 }
    ::= { x25PLEEntry 22 }

x25PLELogicalChannelAssignmentLTC OBJECT-TYPE
    SYNTAX	LogicalChannelNumber
    MAX-ACCESS	read-write
    STATUS	current
    DESCRIPTION
	"Specifies the lowest logical channel number used for 
	 two-way virtual calls, using the LogicalChannelNumber textual 
	 convention.  This is used in conjunction with the 
	 corresponding HTC value, 
	 x25PLELogicalChannelAssignmentHTC, to define a range of 
	 logical channels.  When set to zero(0), no logical 
	 channels are assigned to two-way virtual calls.  This 
	 is also the default.
	
	 The value must be zero(0) when the corresponding HTC is 
	 set to zero(0), or, otherwise, at least one less that 
	 the value of the corresponding HTC.  The range defined 
	 by the corresponding LTC and HTC values must not 
	 overlap with the other ranges specified for logical 
	 channel assignment.
	
	 Note that this value may be overridden by the 
	 corresponding value in the x25PLEIVMOTable.
	
	 For a DTE subscribed to the On-line Facility 
	 Registration facility, and where the Logical Channel 
	 Assignment facility is indicated as available in the 
	 x25PLEFacilityAvailability column, writing to this 
	 column may invoke the registration procedure.
	
	 When the DTE is not subscribed to the On-line Facility 
	 Registration facility, this value reflects the current 
	 value, agreed to for a time between the DTE and the 
	 DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE."
    DEFVAL	{ 0 }
    ::= { x25PLEEntry 23 }

x25PLELogicalChannelAssignmentHOC OBJECT-TYPE
    SYNTAX	LogicalChannelNumber
    MAX-ACCESS	read-write
    STATUS	current
    DESCRIPTION
	"Specifies the highest logical channel number used for 
	 outgoing virtual calls, using the LogicalChannelNumber 
	 textual convention.  This is used in conjunction with 
	 the corresponding LOC value, 
	 x25PLELogicalChannelAssignmentLOC, to define a range of 
	 logical channels.  When set to zero(0), no logical 
	 channels are assigned to one-way outgoing virtual 
	 calls.  This is also the default.
	
	 The value must be zero(0) when the corresponding LOC is 
	 set to zero(0), or, otherwise, at least one greater 
	 than the value of the corresponding LOC.  The range 
	 defined by the corresponding LOC and HOC values must 
	 not overlap with the other ranges specified for logical 
	 channel assignment.
	
	 Note that this value may be overridden by the 
	 corresponding value in the x25PLEIVMOTable.
	
	 For a DTE subscribed to the On-line Facility 
	 Registration facility, and where the Logical Channel 
	 Assignment facility is indicated as available in the 
	 x25PLEFacilityAvailability column, writing to this 
	 column may invoke the registration procedure.
	
	 When the DTE is not subscribed to the On-line Facility 
	 Registration facility, this value reflects the current 
	 value, agreed to for a time between the DTE and the 
	 DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE."
    DEFVAL	{ 0 }
    ::= { x25PLEEntry 24 }

x25PLELogicalChannelAssignmentLOC OBJECT-TYPE
    SYNTAX	LogicalChannelNumber
    MAX-ACCESS	read-write
    STATUS	current
    DESCRIPTION
	"Specifies the lowest logical channel number used for 
	 outgoing virtual calls, using the LogicalChannelNumber 
	 textual convention.  This is used in conjunction with 
	 the corresponding HOC value, 
	 x25PLELogicalChannelAssignmentHOC, to define a range of 
	 logical channels.  When set to zero(0), no logical 
	 channels are assigned to one-way outgoing virtual 
	 calls.  This is also the default.
	
	 The value must be zero(0) when the corresponding HOC is 
	 set to zero(0), or, otherwise, at least one less than 
	 the value of the corresponding HOC.  The range defined 
	 by the corresponding LOC and HOC values must not 
	 overlap with the other ranges specified for logical 
	 channel assignment.
	
	 Note that this value may be overridden by the 
	 corresponding value in the x25PLEIVMOTable.
	
	 For a DTE subscribed to the On-line Facility 
	 Registration facility, and where the Logical Channel 
	 Assignment facility is indicated as available in the 
	 x25PLEFacilityAvailability column, writing to this 
	 column may invoke the registration procedure.
	
	 When the DTE is not subscribed to the On-line Facility 
	 Registration facility, this value reflects the current 
	 value, agreed to for a time between the DTE and the 
	 DCE.
	
	 When the DTE is subscribed to the On-line Facility 
	 Registration facility, writing this value at for a DTE 
	 can result in the generation of a REGISTRATION REQUEST 
	 packet toward the DXE; writing this value at a DXE can 
	 result in the generation of a RESTART INDICATION or 
	 RESET INDICATION packet."
    REFERENCE
	"ITU-T Rec. X.283 | ISO/IEC 10733 : x25PLE."
    DEFVAL	{ 0 }
    ::= { x25PLEEntry 25 }


x25PLEIVMO OBJECT IDENTIFIER
    ::= { x25PLPTables 2 }

x25PLEIVMOTable OBJECT-TYPE
    SYNTAX	SEQUENCE OF X25PLEIVMOEntry
    MAX-ACCESS	not-accessible
    STATUS	current
    DESCRIPTION
	"Entries in this table generate objectCreation and 
	 objectDeletion notifications."
    REFERENCE
	"ITU-T Rec. X.283 | ISO/IEC 10733 : x25PLEIVMO MOC."
    ::= { x25PLEIVMO 1 }

x25PLEIVMOEntry OBJECT-TYPE
    SYNTAX	X25PLEIVMOEntry
    MAX-ACCESS	not-accessible
    STATUS	current
    DESCRIPTION
	"This MO class is never instanitated.  It serves as a 
	 generic x25PLE IVMO from which both the x25PLEIVMO-DTE 
	 and x25PLEIVMO-DCE MO classes are derived.  Note that 
	 the values of the x25PLEIVMOId naming attribute are 
	 required to be unique across all instances of MOs 
	 derived from this, which have a common superior.
	
	 Whenever a derived MO is created an instance of this 
	 MOC is also created.  That is, creating a rown in the 
	 x25PLEIVMODTE, x25PLEIVMODCE or x25PLEIVMODXE tables 
	 results in the creation of a row in this table with the 
	 same index."
    REFERENCE
	"ITU-T Rec. X.283 | ISO/IEC 10733 : x25PLEIVMO MO."
    INDEX	{
		    x25PLEId,	    -- shared index (CONTAINED BY)
		    x25PLEIVMOId    -- (BASE CLASS INSTANCE)
		 }
    ::= { x25PLEIVMOTable 1 }

X25PLEIVMOEntry ::= SEQUENCE {
    x25PLEIVMOId				SimpleNameType,
    x25PLEIVMOInterfaceMode			InterfaceMode,
    x25PLEIVMODefaultPacketSizeIncoming		PacketSize,
    x25PLEIVMODefaultPacketSizeOutgoing		PacketSize,
    x25PLEIVMODefaultThroughputClassIncoming	ThroughputClass,
    x25PLEIVMODefaultThroughputClassOutgoing	ThroughputClass,
    x25PLEIVMODefaultWindowSizeIncoming		WindowSize,
    x25PLEIVMODefaultWindowSizeOutgoing		WindowSize,
    x25PLEIVMOFlowControlParameterNegotiation	Subscription,
    x25PLEIVMOLocalDTEAddress			DTEAddress,
    x25PLEIVMOLogicalChannelAssignmentHPC	LogicalChannelNumber,
    x25PLEIVMOLogicalChannelAssignmentLPC	LogicalChannelNumber,
    x25PLEIVMOLogicalChannelAssignmentHIC	LogicalChannelNumber,
    x25PLEIVMOLogicalChannelAssignmentLIC	LogicalChannelNumber,
    x25PLEIVMOLogicalChannelAssignmentHTC	LogicalChannelNumber,
    x25PLEIVMOLogicalChannelAssignmentLTC	LogicalChannelNumber,
    x25PLEIVMOLogicalChannelAssignmentHOC	LogicalChannelNumber,
    x25PLEIVMOLogicalChannelAssignmentLOC	LogicalChannelNumber,
    x25PLEIVMOSNServiceProvider			RowPointer,
    x25PLEIVMOThroughputClassNegotiation	Subscription,
}

x25PLEIVMOId OBJECT-TYPE
    SYNTAX	SimpleNameType
    MAX-ACCESS	not-accessible
    STATUS	current
    DESCRIPTION
	""
    REFERENCE
	"ITU-T Rec. X.283 | ISO/IEC 10733 : x25PLEIVMO."
    ::= { x25PLEIVMOEntry 1 }

x25PLEIVMOInterfaceMode OBJECT-TYPE
    SYNTAX	InterfaceMode
    MAX-ACCESS	read-only
    STATUS	current
    DESCRIPTION
	"Indicates the interface mode for the X.25 Packet Layer 
	 Entity according to the InterfaceMode textual 
	 convention.  This can have values:
	
	 - dTE(0), the entry was created by creating an entry in 
	   the x25PLEIVMODTETable, and corresponds to an X.25 or 
	   ISP 8208 DTE.  There exists a corresponding entry 
	   with the same x25PLEId and x25PLEIVMOId in the 
	   x25PLEIVMODTETable.
	
	 - dCE(1), the entry was created by creating an entry in 
	   the x25PLEIVMODCETable, and corresponds to an X.25 
	   DCE.  There exists a corresponding entry with the 
	   same x25PLEId and X25PLEIVMOId in the 
	   x25PLEIVMODCETable.
	
	 - dTEasDCE(2), the entry was created by creating an 
	   entry in the x25PLEIVMODXETable, and corresponds to 
	   an ISO 8208 DXE.  There exists a corresponding entry 
	   with the same x25PLEId and x25PLEIVMOId in the 
	   x25PLEIVMODXETable.
	
	 The dTEasDCE(2) value is only applicable to ISO/IEC 
	 8208 protocol versions.  The other values are 
	 applicable to ITU-T Rec. X.25 operation."
    REFERENCE
	"ITU-T Rec. X.283 | ISO/IEC 10733 : x25PLEIVMO."
    ::= { x25PLEIVMOEntry 2 }

--  x25PLEIVMODefaultPacketSizes
x25PLEIVMODefaultPacketSizeIncoming OBJECT-TYPE
    SYNTAX	PacketSize
    UNITS	"octets"
    MAX-ACCESS	read-write
    STATUS	current
    DESCRIPTION
	"Specifies the incoming packet size using the PacketSize 
	 textual convention.  This is the porposed value of the 
	 incoming packet size in octets to be used when 
	 establishing a virtual call from the X.25 PLE.  A value 
	 of zero(0) indicates that the default incoming packet 
	 size attribute of the containing X.25 PLE MO, 
	 x25PLEDefaultPacketSizeIncoming, is to be used.  This 
	 is also the default."
    REFERENCE
	"ITU-T Rec. X.283 | ISO/IEC 10733 : x25PLEIVMO."
    DEFVAL	{ 0 }
    ::= { x25PLEIVMOEntry 3 }

x25PLEIVMODefaultPacketSizeOutgoing OBJECT-TYPE
    SYNTAX	PacketSize
    MAX-ACCESS	read-write
    STATUS	current
    DESCRIPTION
	"Specifies the outgoing packet size using the PacketSize 
	 textual convention.  This is the porposed value of the 
	 outgoing packet size in octets to be used when 
	 establishing a virtual call from the X.25 PLE.  A value 
	 of zero(0) indicates that the default outgoing packet 
	 size attribute of the containing X.25 PLE MO, 
	 x25PLEDefaultPacketSizeOutgoing, is to be used.  This 
	 is also the default."
    REFERENCE
	"ITU-T Rec. X.283 | ISO/IEC 10733 : x25PLEIVMO."
    DEFVAL	{ 0 }
    ::= { x25PLEIVMOEntry 4 }

--  x25PLEIVMODefaultThroughputClasses
x25PLEIVMODefaultThroughputClassIncoming OBJECT-TYPE
    SYNTAX	ThroughputClass
    MAX-ACCESS	read-write
    STATUS	current
    DESCRIPTION
	"Specifies the incoming throughput class using the 
	 ThroughputClass textual convention.  This is the 
	 proposed value of the incoming throughput class to be 
	 used when establishing a virtual call from the X.25 
	 PLE.  A value of none(0) indicates that the default 
	 incoming throughput class attribute of the containing 
	 X.25 PLE MO, x25PLEDefaultThroughputClassIncoming, is 
	 to be used.  This is also the default."
    REFERENCE
	"ITU-T Rec. X.283 | ISO/IEC 10733 : x25PLEIVMO."
    DEFVAL	{ none(0) }
    ::= { x25PLEIVMOEntry 5 }

x25PLEIVMODefaultThroughputClassOutgoing OBJECT-TYPE
    SYNTAX	ThroughputClass
    MAX-ACCESS	read-write
    STATUS	current
    DESCRIPTION
	"Specifies the outgoing throughput class using the 
	 ThroughputClass textual convention.  This is the 
	 proposed value of the outgoing throughput class to be 
	 used when establishing a virtual call from the X.25 
	 PLE.  A value of none(0) indicates that the default 
	 incoming throughput class attribute of the containing 
	 X.25 PLE MO, x25PLEDefaultThroughputClassOutgoing, is 
	 to be used.  This is also the default."
    REFERENCE
	"ITU-T Rec. X.283 | ISO/IEC 10733 : x25PLEIVMO."
    DEFVAL	{ none(0) }
    ::= { x25PLEIVMOEntry 6 }

--  x25PLEIVMODefaultWindowSizes
x25PLEIVMODefaultWindowSizeIncoming OBJECT-TYPE
    SYNTAX	WindowSize
    MAX-ACCESS	read-write
    STATUS	current
    DESCRIPTION
	"Specifies the incoming window size using the WindowSize 
	 textual convention.  This is the proposed value of the 
	 incoming window size to be used when establishing a 
	 virtual call crom the X.25 PLE.  A value of zero(0) 
	 indicates that the default incoming window size 
	 attribute of the containing X.25 PLE MO, 
	 x25PLEDefaultWindowSizeIncoming, is to be used.  This 
	 is also the default."
    REFERENCE
	"ITU-T Rec. X.283 | ISO/IEC 10733 : x25PLEIVMO."
    DEFVAL	{ 0 }
    ::= { x25PLEIVMOEntry 7 }

x25PLEIVMODefaultWindowSizeOutgoing OBJECT-TYPE
    SYNTAX	WindowSize
    MAX-ACCESS	read-write
    STATUS	current
    DESCRIPTION
	"Specifies the outgoing window size using the WindowSize 
	 textual convention.  This is the proposed value of the 
	 outgoing window size to be used when establishing a 
	 virtual call crom the X.25 PLE.  A value of zero(0) 
	 indicates that the default outgoing window size 
	 attribute of the containing X.25 PLE MO, 
	 x25PLEDefaultWindowSizeOutgoing, is to be used.  This 
	 is also the default."
    REFERENCE
	"ITU-T Rec. X.283 | ISO/IEC 10733 : x25PLEIVMO."
    DEFVAL	{ 0 }
    ::= { x25PLEIVMOEntry 8 }

x25PLEIVMOFlowControlParameterNegotiation OBJECT-TYPE
    SYNTAX	Subscription
    MAX-ACCESS	read-write
    STATUS	current
    DESCRIPTION
	"Specifies the subscription of the Flow Control 
	 Parameter Negotiation facility as described in ITU-T 
	 Rec. X.2, ITU-T Rec. X.7, ITU-T Rec. X.25, ISO/IEC 
	 8208.
	
	 - unknown(0), the value of the corresponding X.25 PLE 
	   object, x25PLEFlowControlParameterNegotiation, 
	   applies.
	
	 - basic(1), the use of Flow Control Parameter 
	   Negotiation (by specifying values for the basic 
	   window and packet size in call request and accept 
	   packets) is permitted.
	
	 - notsubscribed(2), no such values shall be specified 
	   in call request and accept packets and any values 
	   specified in an IVMO or via an internal inteface 
	   shall be ignored.
	
	 - extended(3), the use of Flow Control Parameter 
	   Negotiation (by specifying values for the extended 
	   window and packet size in call request and accept 
	   packets) is permitted.
	
	 Flow Control Parameter Negotiation is a facility 
	 requiring subscription and dynamic invocation on packet 
	 switched networks only."
    REFERENCE
	"ITU-T Rec. X.283 | ISO/IEC 10733 : x25PLEIVMO, 
	     flowControlParameterNegotiation.
	 ITU-T Rec. X.7, Clause 6.1.2.3."
    ::= { x25PLEIVMOEntry 9 }

x25PLEIVMOLocalDTEAddress OBJECT-TYPE
    SYNTAX	DTEAddress
    MAX-ACCESS	read-write
    STATUS	current
    DESCRIPTION
	"Specifies the full DTE address of this PLE expressed as 
	 an X.121, E.164 or TOA/NPI address, using the DTEAddress 
	 textual convention.  This object has no default value 
	 and must be specified on creation.  The DTEAddress 
	 textual convention supports X.121 and E.164 DTE 
	 addresses as well as TOA/NPI addresses."
    REFERENCE
	"ITU-T Rec. X.283 | ISO/IEC 10733 : x25PLEIVMO 
	     localDTEAddress.
	 ITU-T Rec. X.25 Clause 5.2."
    ::= { x25PLEIVMOEntry 10 }

--  x25PLEIVMOLogicalChannelAssignments
x25PLEIVMOLogicalChannelAssignmentHPC OBJECT-TYPE
    SYNTAX	LogicalChannelNumber
    MAX-ACCESS	read-write
    STATUS	current
    DESCRIPTION
	"Specifies the highest logical channel number used for 
	 permanent virtual circuits (PVC), using the 
	 LogicalChannelNumber textual convention.  This is used in 
	 conjunction with the corresponding LPC value, 
	 x25PLEIVMOLogicalChannelAssignmentLPC, to define a 
	 range of logical channels.  When set to zero(0), the 
	 value of the corresponding HPC attribute of the 
	 containing X.25 PLE shall be used.  This is also the 
	 default.
	
	 The value must be zero(0) when the corresponding LPC is 
	 set to zero(0), or, otherwise, at least one greater 
	 than the value of the corresponding LPC and at least 
	 one less than the value of the corresponding LIC.  The 
	 range defined by the corresponding LPC and HPC values 
	 must not overlap with the other ranges specified for 
	 logical channel assignment."
    REFERENCE
	"ITU-T Rec. X.283 | ISO/IEC 10733 : x25PLEIVMO."
    DEFVAL	{ 0 }
    ::= { x25PLEIVMOEntry 11 }

x25PLEIVMOLogicalChannelAssignmentLPC OBJECT-TYPE
    SYNTAX	LogicalChannelNumber
    MAX-ACCESS	read-write
    STATUS	current
    DESCRIPTION
	"Specifies the lowest logical channel number used for 
	 permanent virtual circuits (PVC), using the 
	 LogicalChannelNumber textual convention.  This is used in 
	 conjunction with the corresponding HPC value, 
	 x25PLEIVMOLogicalChannelAssignmentHPC, to define a 
	 range of logical channels.  When set to zero(0), the 
	 value of the corresponding LPC attribute of the 
	 containing X.25 PLE shall be used.  This is also the 
	 default.
	
	 The value must be zero(0) when the corresponding HPC is 
	 set to zero(0), or, otherwise, at least one less than 
	 the value of the corresponding HPC.  The range defined 
	 by the corresponding LPC and HPC values must not 
	 overlap with the other ranges specified for logical 
	 channel assignment."
    REFERENCE
	"ITU-T Rec. X.283 | ISO/IEC 10733 : x25PLEIVMO."
    DEFVAL	{ 0 }
    ::= { x25PLEIVMOEntry 12 }

x25PLEIVMOLogicalChannelAssignmentHIC OBJECT-TYPE
    SYNTAX	LogicalChannelNumber
    MAX-ACCESS	read-write
    STATUS	current
    DESCRIPTION
	"Specifies the highest logical channel number used for 
	 incoming virtual calls, using the LogicalChannelNumber 
	 textual convention.  This is used in conjunction with 
	 the corresponding LIC value, 
	 x25PLEIVMOLogicalChannelAssignmentLIC, to define a 
	 range of logical channels.  When set to zero(0), the 
	 value of the corresponding HIC attribute of the 
	 containing X.25 PLE shall be used.  This is also the 
	 default.
	
	 The value must be zero(0) when the corresponding LIC is 
	 set to zero(0), or, otherwise, at least one greater 
	 than the value of the corresponding LIC and at least 
	 one less than the value of the corresponding LTC.  The 
	 range defined by the corresponding LIC and HIC values 
	 must not overlap with the other ranges specified for 
	 logical channel assignment."
    REFERENCE
	"ITU-T Rec. X.283 | ISO/IEC 10733 : x25PLEIVMO."
    DEFVAL	{ 0 }
    ::= { x25PLEIVMOEntry 13 }

x25PLEIVMOLogicalChannelAssignmentLIC OBJECT-TYPE
    SYNTAX	LogicalChannelNumber
    MAX-ACCESS	read-write
    STATUS	current
    DESCRIPTION
	"Specifies the lowest logical channel number used for 
	 incoming virtual calls, using the LogicalChannelNumber 
	 textual convention.  This is used in conjunction with 
	 the corresponding HIC value, 
	 x25PLEIVMOLogicalChannelAssignmentHIC, to define a 
	 range of logical channels.  When set to zero(0), the 
	 value of the corresponding LIC attribute of the 
	 containing X.25 PLE shall be used.  This is also the 
	 default.
	
	 The value must be zero(0) when the corresponding HIC is 
	 set to zero(0), or, otherwise, at least one less than 
	 the value of the corresponding HIC.  The range defined 
	 by the corresponding LIC and HIC values must not 
	 overlap with the other ranges specified for logical 
	 channel assignment."
    REFERENCE
	"ITU-T Rec. X.283 | ISO/IEC 10733 : x25PLEIVMO."
    DEFVAL	{ 0 }
    ::= { x25PLEIVMOEntry 14 }

x25PLEIVMOLogicalChannelAssignmentHTC OBJECT-TYPE
    SYNTAX	LogicalChannelNumber
    MAX-ACCESS	read-write
    STATUS	current
    DESCRIPTION
	"Specifies the highest logical channel number used for 
	 two-way virtual calls, using the LogicalChannelNumber 
	 textual convention.  This is used in conjunction with 
	 the corresponding LTC value, 
	 x25PLEIVMOLogicalChannelAssignmentLTC, to define a 
	 range of logical channels.  When set to zero(0), the 
	 value of the corresponding HTC attribute of the 
	 containing X.25 PLE shall be used.  This is also the 
	 default.
	
	 The value must be zero(0) when the corresponding LTC is 
	 set to zero(0), or, otherwise, at least one greater 
	 than the value of the corresponding LTC and at least 
	 one less than the value of the corresponding LOC.  The 
	 range defined by the corresponding LTC and HTC values 
	 must not overlap with the other ranges specified for 
	 logical channel assignment."
    REFERENCE
	"ITU-T Rec. X.283 | ISO/IEC 10733 : x25PLEIVMO."
    DEFVAL	{ 0 }
    ::= { x25PLEIVMOEntry 15 }

x25PLEIVMOLogicalChannelAssignmentLTC OBJECT-TYPE
    SYNTAX	LogicalChannelNumber
    MAX-ACCESS	read-write
    STATUS	current
    DESCRIPTION
	"Specifies the lowest logical channel number used for 
	 two-way virtual calls, using the LogicalChannelNumber 
	 textual convention.  This is used in conjunction with 
	 the corresponding HTC value, 
	 x25PLEIVMOLogicalChannelAssignmentHTC, to define a 
	 range of logical channels.  When set to zero(0), the 
	 value of the corresponding LTC attribute of the 
	 containing X.25 PLE shall be used.  This is also the 
	 default.
	
	 The value must be zero(0) when the corresponding HTC is 
	 set to zero(0), or, otherwise, at least one less that 
	 the value of the corresponding HTC.  The range defined 
	 by the corresponding LTC and HTC values must not 
	 overlap with the other ranges specified for logical 
	 channel assignment."
    REFERENCE
	"ITU-T Rec. X.283 | ISO/IEC 10733 : x25PLEIVMO."
    DEFVAL	{ 0 }
    ::= { x25PLEIVMOEntry 16 }

x25PLEIVMOLogicalChannelAssignmentHOC OBJECT-TYPE
    SYNTAX	LogicalChannelNumber
    MAX-ACCESS	read-write
    STATUS	current
    DESCRIPTION
	"Specifies the highest logical channel number used for 
	 outgoing virtual calls, using the LogicalChannelNumber 
	 textual convention.  This is used in conjunction with 
	 the corresponding LOC value, 
	 x25PLEIVMOLogicalChannelAssignmentLOC, to define a 
	 range of logical channels.  When set to zero(0), the 
	 value of the corresponding HOC attribute of the 
	 containing X.25 PLE shall be used.  This is also the 
	 default.
	
	 The value must be zero(0) when the corresponding LOC is 
	 set to zero(0), or, otherwise, at least one greater 
	 than the value of the corresponding LOC.  The range 
	 defined by the corresponding LOC and HOC values must 
	 not overlap with the other ranges specified for logical 
	 channel assignment."
    REFERENCE
	"ITU-T Rec. X.283 | ISO/IEC 10733 : x25PLEIVMO."
    DEFVAL	{ 0 }
    ::= { x25PLEIVMOEntry 17 }

x25PLEIVMOLogicalChannelAssignmentLOC OBJECT-TYPE
    SYNTAX	LogicalChannelNumber
    MAX-ACCESS	read-write
    STATUS	current
    DESCRIPTION
	"Specifies the lowest logical channel number used for 
	 outgoing virtual calls, using the LogicalChannelNumber 
	 textual convention.  This is used in conjunction with 
	 the corresponding HOC value, 
	 x25PLEIVMOLogicalChannelAssignmentHOC, to define a 
	 range of logical channels.  When set to zero(0), the 
	 value of the corresponding LOC attribute of the 
	 containing X.25 PLE shall be used.  This is also the 
	 default.
	
	 The value must be zero(0) when the corresponding HOC is 
	 set to zero(0), or, otherwise, at least one less than 
	 the value of the corresponding HOC.  The range defined 
	 by the corresponding LOC and HOC values must not 
	 overlap with the other ranges specified for logical 
	 channel assignment."
    REFERENCE
	"ITU-T Rec. X.283 | ISO/IEC 10733 : x25PLEIVMO."
    DEFVAL	{ 0 }
    ::= { x25PLEIVMOEntry 18 }

x25PLEIVMOSNServiceProvider OBJECT-TYPE
    SYNTAX	RowPointer
    MAX-ACCESS	read-write
    STATUS	current
    DESCRIPTION
	""
    REFERENCE
	"ITU-T Rec. X.283 | ISO/IEC 10733 : x25PLEIVMO."
    ::= { x25PLEIVMOEntry 19 }

x25PLEIVMOThroughputClassNegotiation OBJECT-TYPE
    SYNTAX	Subscription
    MAX-ACCESS	read-write
    STATUS	current
    DESCRIPTION
	"Specifies the subscription of the throughput class 
	 negotiation facility as described in ITU-T Rec. X.25 | 
	 ISO/IEC 8208.  Expressed as a boolean where a value of 
	 basic(1) or extended(3) indicates subscription and a 
	 value of notsubscribed(2) indicates non-subscription.  
	 The default value is notsubscribed(2).  When basic(1), 
	 the basic throughput class negotiation facility will be 
	 used; when extended(3), the extended throughput class 
	 negotiation facility will be used."
    REFERENCE
	"ITU-T Rec. X.283 | ISO/IEC 10733 : x25PLEIVMO."
    DEFVAL	{ notsubscribed(2) }
    ::= { x25PLEIVMOEntry 20 }


x25PLEDTE OBJECT IDENTIFIER
    ::= { x25PLPTables 3 }

x25PLEDTETable OBJECT-TYPE
    SYNTAX	SEQUENCE OF X25PLEDTEEntry
    MAX-ACCESS	not-accessible
    STATUS	current
    DESCRIPTION
	"Objects in this table generate communicationsAlarm 
	 notifications.
	
	 The x25PLE-P package imports the communicationsAlarm 
	 notification from Rec.  X.721 (1992) | ISO/IEC 10165-2.  
	 It is used to report the following x25PLE managed 
	 object events.
	
	 providerInitiatedDisconnect:
	    Issued upon receipt of a clear packet with a cause 
	    code other than 'DTE originated'.
	
	 remotelyInitiatedReset:
	    Issued upon occurrence of a remotely initiated 
	    reset.  This event is issued in lieu of a 
	    'providerInitiatedReset' when operating in a DTE-DXE 
	    environment. 
	
	 remotelyInitiatedRestart:
	    Issued upon receipt of a remotely (including 
	    provider) initiated restart.
	
	 restartCountExceeded:
	    Issued on restart failure due to restart count (R20) 
	    exceeded.
	
	 protocolErrorDetectedLocally:
	    Issued upon receipt of a packet which causes the 
	    'A=Error' action in the ISO/IEC 8208 or ITU-T Rec.  
	    X.25 state tables to be taken.
	
	 accusedOfProtocolError:
	    Issued upon receipt of a diagnostic packet or a 
	    clear, reset or restart packet with a cause code 
	    equal to one of the following: Remote Procedure 
	    Error, Incompatible Destination, Invalid Facility 
	    Request, Local Procedure Error. No other x25PLE 
	    communication alarm shall be generated as a result 
	    of this particular instance of packet.
	
	 callEstablishmentRetryCountExceeded:
	    Issued on retry failure during call establishment 
	    due to retry limit exceeded.
	
	 clearCountExceeded:
	    Issued on retry failure due to clear limit (R23) 
	    exceeded.  The information relating to the call 
	    shall be reported as a parameter in the 
	    additionalInformation field of the 
	    communicationsAlarm, using the notificationData 
	    PARAMETER"
    REFERENCE
	"ITU-T X.283 | ISO/IEC 10733 : x25PLE-DCE MOC."
    ::= { x25PLEDTE 1 }

x25PLEDTEEntry OBJECT-TYPE
    SYNTAX	X25PLEDTEEntry
    MAX-ACCESS	not-accessible
    STATUS	current
    DESCRIPTION
	"There may be multiple isntances of these MOs within a 
	 system, corresponding to multiple X.25 PLE.  The 
	 defintion of this MO permits it to be created and 
	 deleted explictly by mangement operation or to be 
	 created and deleted automatically as part of system 
	 operation.  When an instance of this MO is created 
	 automatically, an instance of the x25PLEIVMO-DTE may be 
	 used as the source of the initial values for attributes 
	 of this MO.  When the x25 PLE is operable, the 
	 operationalState hsall have the value 'enabled'; 
	 otherwise it shall have the value 'disabled'.  
	 Transitions of operationalState shall be reported using 
	 the stateChange notification."
    REFERENCE
	"ITU-T X.283 | ISO/IEC 10733 : x25PLE-DCE MO."
    INDEX	{
		    x25PLEId	-- shared index (DERIVED FROM)
		}
    ::= { x25PLEDTETable 1 }

X25PLEDTEEntry ::= SEQUENCE {
    x25PLEDTEPacketSequencing		    Modulo,
    x25PLEDTEMaxActiveCircuits		    MaxActiveCircuits,
    x25PLEDTECallDeflectionSubscription	    TruthValue,
    x25PLEDTERestartTime		    TimeInterval,
    x25PLEDTERestartCount		    INTEGER,
    x25PLEDTEMinimumRecallTimer		    TimeInterval,
    -- PACKAGE onlineRegistration-P
    x25PLEDTERegistrationTime		    TimeInterval,
    x25PLEDTERegistrationCount		    INTEGER,
    x25PLEDTERegistrationPermitted	    TruthValue,
    -- Added
    x25PLEDTEFacilityAvailability	    FacilityAvailability,
    x25PLEDTEFacilityNegotiation	    FacilityNegotiation,
    x25PLEDTEFacilityWhileIdle		    FacilityWhileIdle,
    x25PLEDTENonStandardDefaultPacketSizes  TruthValue,
    x25PLEDTENonStandardDefaultWindowSizes  Subscription,
    x25PLEDTEDefaultThroughputClassesAssignment Subscription,
    -- Miscellaneous conversion
    x25PLEDTEProfile						RowPointer,
    x25PLEDTERowStatus						RowStatus,

    --
    -- Per Interface
    --
    -- Extended Frame Sequence Numbering
    -- Super-extended Frame Sequence Numbering
    -- Multilink Procedure
    -- (x.25 reg) Extended Packet Sequence Numbering
    -- (x.25 reg) Super-extended Packet Sequence Numbering
    -- (X.25 reg) D-bit Modification
    -- (X.25 reg) Packet Retransmission
    -- (x.25 reg) Incoming Calls Barred
    -- (x.25 reg) Outgoing Calls Barred
    -- (x.25 reg) One-way Logical Channel Outgoing
    -- (x.25 reg) One-way Logical Channel Incoming
    -- (x.25 reg) Non-standard Default Packet Sizes
    -- (x.25 reg) Non-standard Default Window Sizes
    -- (x.25 reg) Default Throughput Classes Assignment
    -- (x.25 reg) Flow Control Parameter Negotiation
    -- (x.25 reg) Basic Throughput Class Negotiation
    -- (x.25 reg) Exended Throughput Class Negotiation
    -- Closed User Group
    -- Closed User Group with Outgoing Access
    -- Closed User Group with Incoming Access
    -- Incoming Calls Barred within a Closed User Group
    -- Outgoing Calls Barred within a Closed User Group
    -- Bilateral Closed User Group
    -- Bilateral Closed User Group with Ougoing Access
    -- NUI Subscription
    -- NUI Override
    -- ROA Subscription
    -- Hunt Group
    -- Call Redirection
    -- Call Defelection Subscription
    -- Direct Call
    -- Internetwork Call Redirection or Deflection Prevention SUbscription
    -- Global Alternative Address Registration
    -- Interface Specific Alternative Address Registration
    -- Alternative Address Usage Subscription
    --
    -- (X.25 reg) Logical Channel Types Ranges
    --
    -- Per Virtual Call
    --
    -- (X.25 fac) (x.25 reg) Flow Control Parameter Negotiation
    -- (X.25 fac) (x.25 reg) Basic Throughput Class Negotiation
    -- (X.25 fac) (x.25 reg) Extended Throughput Class Negotiation
    -- (X.25 fac) Closed User Group Selection
    -- (X.25 fac) Closed User Group with Outgoing Access Selection
    -- (X.25 fac) Bilateral Closed User Group Selection
    -- (X.25 fac) (x.25 reg) Reverse Charging
    -- (X.25 fac) Fast Select
    -- (X.25 fac) NUI Selection
    -- (X.25 fac) (X.25 reg) Charging Information
    -- (X.25 fac) (x.25 reg) ROA Selection
    -- (X.25 fac) Call Deflection Selection
    -- (X.25 fac) Call Redirection or Call Deflection Notification
    -- (X.25 fac) (X.25 reg) Called Line Address Modified Notification
    -- (X.25 fac) Transit Delay Selection and Indication
    -- (X.25 fac) Internetwork Call Redirection/Deflection Status Selection
    -- Abbreviated Address Calling
    -- Alternative Address Selection
}

x25PLEDTEPacketSequencing OBJECT-TYPE
    SYNTAX	Modulo
    MAX-ACCESS	read-create
    STATUS	current
    DESCRIPTION
	"The modulo of the packet sequence number space using 
	 the Modulo textual convention.  Expressed as a general 
	 format indicator.  ITU-T Rec.  X.25 | ISO/IEC 8208 only 
	 requires support for the values modulo8(1), 
	 modulo128(2) and modulo32768(3), but it is possible 
	 that some future version may extend the range.  A 
	 system is only required to support the settings of 
	 values that are also required by the protocol standard.  
	 A system shall return and error when an attempt is made 
	 to set the value to a value that is not supported by 
	 that system.
	
	 Extended Packet Sequence Numbering and Super Extended 
	 Packet Sequence Numbering are optional user facilities 
	 that require subscription followed by dynamic 
	 invocation on packet switched networks.
	
	 ITU-T Rec. X.25 only permits this value to be set for 
	 an entire DTE.  That is, where the setting applies to 
	 all switched virtual calls and permanent virtual 
	 circuits (logical channels) proviided by the DTE X.25 
	 Packet Layer Entity.  It also permits the packet 
	 sequence numbering scheme to be applied individually to 
	 each logical channel for the DTE X.25 PLE.  When the 
	 network supports the user of multiple modulos at the 
	 same interface, for virtual calls the selection is made 
	 by signalling of the GFI, for permanent virtual 
	 circuits, the modulo is established by subscription."
    REFERENCE
	"ITU-T Rec. X.283 | ISO/IEC 10733 : x25PLE-DTE 
	     extendedPacketSequenceNumbering.
	 ITU-T Rec. X.7, Clause 6.1.3.1, 6.1.3.2."
    DEFVAL	{ 1 } -- modulo8(1)
    ::= { x25PLEDTEEntry 1 }

x25PLEDTEMaxActiveCircuits OBJECT-TYPE
    SYNTAX	MaxActiveCircuits
    MAX-ACCESS	read-create
    STATUS	current
    DESCRIPTION
	"The maximum number of active circuits permitted on this 
	 X.25 PLE.  When the value zero(0) is specified, the 
	 maximum number of active circuits shall be limited only 
	 by the resources available to the entity."
    REFERENCE
	"ITU-T Rec. X.283 | ISO/IEC 10733 : x25PLE-DTE 
	     maxActiveCircuits."
    DEFVAL	{ 0 }
    ::= { x25PLEDTEEntry 2 }

x25PLEDTECallDeflectionSubscription OBJECT-TYPE
    SYNTAX	TruthValue
    MAX-ACCESS	read-create
    STATUS	current
    DESCRIPTION
	"The subscription of the call deflection facility as 
	 described in ITU-T Rec. X.25 | ISO/IEC 8208.  Expressed 
	 as a boolean where a value of true(1) indicates 
	 subscription and a value of false(2) indicates 
	 non-subscription.
	
	 Call Deflection Subscription is an optional user 
	 facility that requires subscription followed by dynamic 
	 invocation on packet switched networks.
	 "
    REFERENCE
	"ITU-T Rec. X.283 | ISO/IEC 10733 : x25PLE-DTE 
	     callDeflectionSubscription.
	 ITU-T Rec. X.7, Clause 6.4.2.1."
    ::= { x25PLEDTEEntry 3 }

x25PLEDTERestartTime OBJECT-TYPE
    SYNTAX	TimeInterval
    UNITS	"seconds"
    MAX-ACCESS	read-create
    STATUS	current
    DESCRIPTION
	"Specifies the value for Timer T20 (Restart Request 
	 Response Timer) in centiseconds (displayed in seconds).  
	 The default value is 18000 (180 seconds)."
    REFERENCE
	"ITU-T Rec. X.283 | ISO/IEC 10733 : x25PLE-DTE 
	     restartRequestResponseTimer.
	 ITU-T Rec. X.25 | ISO/IEC 8208 : Timer T20."
    DEFVAL	{ 18000 } -- 180 seconds
    ::= { x25PLEDTEEntry 4 }

x25PLEDTERestartCount OBJECT-TYPE
    SYNTAX	INTEGER
    UNITS	"retransmissions"
    MAX-ACCESS	read-create
    STATUS	current
    DESCRIPTION
	"Specifies the value for Count R20 (Restart Request 
	 Retranmission Count) in retransmissions.  The default 
	 value is one (1) retransmission."
    REFERENCE
	"ITU-T Rec. X.283 | ISO/IEC 10733 : x25PLE-DTE, 
	     restartRequestRetransmissionCount.
	 ITU-T Rec. X.25 | ISO/IEC 8208 : Count R20."
    DEFVAL	{ 1 }
    ::= { x25PLEDTEEntry 5 }

x25PLEDTEMinimumRecallTimer OBJECT-TYPE
    SYNTAX	TimeInterval
    UNITS	"seconds"
    MAX-ACCESS	read-create
    STATUS	current
    DESCRIPTION
	"Specifies the minimum time, in centiseconds (displayed 
	 in seconds), before recall is permitted.  This timer 
	 determines the minimum time interval which shall elapse 
	 following an unsuccessful first call attempt before a 
	 subsequent call attempt is permitted.  There is not 
	 default value and a value must be specified at 
	 creation."
    REFERENCE
	"ITU-T Rec. X.283 | ISO/IEC 10733 : x25PLE-DTE 
	     minimumRecallTimer."
    ::= { x25PLEDTEEntry 6 }

-- PACKAGE onlineRegistration-P
x25PLEDTERegistrationTime OBJECT-TYPE
    SYNTAX	TimeInterval
    UNITS	"seconds"
    MAX-ACCESS	read-create
    STATUS	current
    DESCRIPTION
	"Specifies the value for Timer T28 (Registration Request 
	 Response Timer) in centiseconds (displayed in seconds).  
	 The default value is 30000 (300 seconds)."
    REFERENCE
	"ITU-T Rec. X.283 | ISO/IEC 10733 : x25PLE-DTE 
	     registrationRequestResponseTimer."
    DEFVAL	{ 30000 } -- 300 seconds
    ::= { x25PLEDTEEntry 7 }

x25PLEDTERegistrationCount OBJECT-TYPE
    SYNTAX	INTEGER
    MAX-ACCESS	read-create
    STATUS	current
    DESCRIPTION
	"Specifies the value for Count R28 (Registration Request 
	 Retransmission Count) in retransmissions.  The default 
	 value is one (1) retranmission."
    REFERENCE
	"ITU-T Rec. X.283 | ISO/IEC 10733 : x25PLE-DTE 
	     registrationRequestRetransmissionCount."
    DEFVAL	{ 1 }
    ::= { x25PLEDTEEntry 8 }

x25PLEDTERegistrationPermitted OBJECT-TYPE
    SYNTAX	TruthValue
    MAX-ACCESS	read-create
    STATUS	current
    DESCRIPTION
	"Specifies the use of the online facility registration.  
	 When true(1), online facility registration is 
	 permitted; when false(2), not permitted.  The default 
	 is false(2)."
    REFERENCE
	"ITU-T Rec. X.283 | ISO/IEC 10733 : x25PLE-DTE 
	     registrationPermitted."
    DEFVAL	{ 2 } -- false(2)
    ::= { x25PLEDTEEntry 9 }

-- Miscellaneous conversion
x25PLEDTEProfile OBJECT-TYPE
    SYNTAX	RowPointer
    MAX-ACCESS	read-create
    STATUS	current
    DESCRIPTION
	""
    REFERENCE
	"ITU-T Rec. X.283 | ISO/IEC 10733 : x25PLE-DTE."
    ::= { x25PLEDTEEntry 10 }

x25PLEDTERowStatus OBJECT-TYPE
    SYNTAX	RowStatus
    MAX-ACCESS	read-create
    STATUS	current
    DESCRIPTION
	""
    REFERENCE
	"ITU-T Rec. X.283 | ISO/IEC 10733 : x25PLE-DTE."
    ::= { x25PLEDTEEntry 11 }


x25PLEDCE OBJECT IDENTIFIER
    ::= { x25PLPTables 4 }

x25PLEDCETable OBJECT-TYPE
    SYNTAX	SEQUENCE OF X25PLEDCEEntry
    MAX-ACCESS	not-accessible
    STATUS	current
    DESCRIPTION
	"There may be multiple instances of these MOs within a 
	 system, corresponding to multiple X.25 PLE.  The 
	 definition of this MO permits it to be created 
	 explicitly by management operation or to be created and 
	 deleted automatically as part of system operation.  
	 When an instance of this MO is created automatically, 
	 an instance of the x25PLEIVMO-DCE may be used as the 
	 source of the initial values for attributes of this MO.  
	 When the x25 PLE is operable, the operationalState 
	 shall have the value 'enabled'; otherwise it shall hvae 
	 the value disabled.  Transitions of operationalState 
	 shall be reported using the stateChange notification.
	
	 Objects in this table do not generate notifications."
    REFERENCE
	"ITU-T Rec. X.283 | ISO/IEC 10733 : x25PLE-DCE MOC."
    ::= { x25PLEDCE 1 }

x25PLEDCEEntry OBJECT-TYPE
    SYNTAX	X25PLEDCEEntry
    MAX-ACCESS	not-accessible
    STATUS	current
    DESCRIPTION
	"
	 Entries in this table represent an X.25 DCE PLE.  
	 Associated with the X.25 DCE PLE are all of the 
	 user facilities that are either subscription only or 
	 are subscription-or-dynamic, or are 
	 subscription-followed-by-dynamic-invocation in the 
	 ITU-T Recommendation X.7 tables."
    REFERENCE
	"ITU-T Rec. X.283 | ISO/IEC 10733 : x25PLE-DCE MO.
	 ITU-T Rec. X.2, ITU-T Rec. X.7."
    INDEX	{
		    x25PLEId	-- shared index (DERIVED FROM)
		}
    ::= { x25PLEDCETable 1 }

X25PLEDCEEntry ::= SEQUENCE {
    x25PLEDCEPacketSequencing			Modulo,

    x25PLEDCEIncomingCallsBarred		TruthValue,
    x25PLEDCEOutgoingCallsBarred		TruthValue,
    x25PLEDCEFastSelectAcceptance		TruthValue,
    x25PLEDCEReverseChargingAcceptance		TruthValue,
    x25PLEDCEChargingInformation		TruthValue,

    x25PLEDCECallDeflectionSubscription		TruthValue,
    x25PLEDCERestartTime			TimeInterval,
    x25PLEDCERestartCount			INTEGER<
    x25PLEDCECUG				Subscription,
    x25PLEDCEOneWayLogicalChannelOutgoing	TruthValue,
    x25PLEDCEBilateralCUG			Subscription,
    x25PLEDCEBilateralCUGWithOutgoingAccess	Subscription,
    x25PLEDCECallRedirection			TruthValue,
    x25PLEDCECUGWithIncomingAccess		Subscription,
    x25PLEDCECUGWithOutgoingAccess		Subscription,
    x25PLEDCEDBitModification			TruthValue,
--  x25PLEDCEDefaultThroughputClassesAssignment
    x25PLEDCEDefaultThroughputClassSubscription	TruthValue,
    x25PLEDCEDefaultThroughputClassSupported	ThroughputClassSupport,
    x25PLEDCEDefaultThroughputClassIncoming	ThroughputClass,
    x25PLEDCEDefaultThroughputClassOutgoing	ThroughputClass,
    x25PLEDCEHuntGroup				TruthValue,
    x25PLEDCEIncomingCallBarredWithinCUG	TruthValue,
    x25PLEDCELocalChargingPrevention		TruthValue,
    x25PLEDCENonStandardDefaultPacketSizeSubscription	TruthValue,
    x25PLEDCENonStandardDefaultPacketSizeMaximum	PacketSize,
    x25PLEDCENonStandardDefaultPacketSizeIncoming	PacketSize,
    x25PLEDCENonStandardDefaultPacketSizeOutgoing	PacketSize,
    x25PLEDCENonStandardDefaultWindowSizeSubscription	TruthValue,
    x25PLEDCENonStandardDefaultWindowSizeMaximum	INTEGER,
    x25PLEDCENonStandardDefaultWindowSizeIncoming	WindowSize,
    x25PLEDCENonStandardDefaultWindowSizeOutgoing	WindowSize,
    x25PLEDCENUIOverride			TruthValue,
    x25PLEDCENUISubscription			TruthValue,
    x25PLEDCEOneWayLogicalChannelIncoming	TruthValue,
    x25PLEDCEOnlineFacilityRegistration		TruthValue,
    x25PLEDCEOutgoingCallBarredWithinCUG	TruthValue,
    x25PLEDCEPacketRetransmission		TruthValue,
    x25PLEDCEROASubscription			Subscription,

    x25PLEDCERestartIndication			TimeInterval,
    x25PLEDCERestartCount			INTEGER,
    x25PLEDCEIncomingCall			TimeInterval,
    x25PLEDCECallCount				INTEGER,
    x25PLEDCEResetIndication			TimeInterval,
    x25PLEDCEResetCount				INTEGER,
    x25PLEDCEClearIndication			TimeInterval,
    x25PLEDCEProfile				RowPointer,
    x25PLEDCERowStatus				RowStatus,
    -- Global Alternative Address Selection ? X.7 6.3.5.1
    -- Interface Specific Alternative Address Selection ? X.7 6.3.5.1
    -- Alternative Address Usage Subscription ? X.7 6.3.5.2
    -- Direct Call ? X.7 6.3.6
    -- TOA/NPI Address Subscription ? X.7 6.3.10
    -- Inter-network Call Redirection and Deflection Prevention Subscription ? X.7 6.4.3.1
    -- Reverse Charging Prevention ? X.7 - doesn't exist
    -- Secure Dial-back ? X.7 6.6.8
}

x25PLEDCEPacketSequencing OBJECT-TYPE
    SYNTAX	Modulo
    MAX-ACCESS	read-create
    STATUS	current
    DESCRIPTION
	"The modulo of the packet sequence number space using 
	 the Modulo textual convention.  Expressed as a general 
	 format indicator.  ITU-T Rec.  X.25 | ISO/IEC 8208 only 
	 requires support for the values modulo8(1), 
	 modulo128(2) and modulo32768(3), but it is possible 
	 that some future version may extend the range.  A 
	 system is only required to support the settings of 
	 values that are also required by the protocol standard.  
	 A system shall return and error when an attempt is made 
	 to set the value to a value that is not supported by 
	 that system.
	
	 Extended Packet Sequence Numbering and Super Extended 
	 Packet Sequence Numbering are optional user facilities 
	 that require subscription followed by dynamic 
	 invocation on packet switched networks.
	
	 ITU-T Rec. X.25 only permits this value to be set for 
	 an entire DCE.  That is, where the setting applies to 
	 all switched virtual calls and permanent virtual 
	 circuits (logical channels) proviided by the DCE X.25 
	 Packet Layer Entity.  It also permits the packet 
	 sequence numbering scheme to be applied individually to 
	 each logical channel for the DCE X.25 PLE.  When the 
	 network supports the user of multiple modulos at the 
	 same interface, for virtual calls the selection is made 
	 by signalling of the GFI, for permanent virtual 
	 circuits, the modulo is established by subscription."
    REFERENCE
	"ITU-T Rec. X.283 | ISO/IEC 10733 : x25PLE-DCE 
	     extendedPacketSequenceNumbering.
	 ITU-T Rec. X.7, Clause 6.1.3.1, 6.1.3.2."
    ::= { x25PLEDCEEntry 1 }

x25PLEDCECallDeflectionSubscription OBJECT-TYPE
    SYNTAX	TruthValue
    MAX-ACCESS	read-create
    STATUS	current
    DESCRIPTION
	"
	 Call Deflection Subscription is an optional user 
	 facility that requires subscription followed by dynamic 
	 invocation on packet switched networks.
	 "
    REFERENCE
	"ITU-T Rec. X.283 | ISO/IEC 10733 : x25PLE-DCE, 
	     callDeflectionSubscription.
	 ITU-T Rec. X.7, Clause 6.4.2.1."
    ::= { x25PLEDCEEntry 2 }

x25PLEDCECUG OBJECT-TYPE
    SYNTAX	Subscription
    MAX-ACCESS	read-create
    STATUS	current
    DESCRIPTION
	"
	 Closed User Group is an optional user facility 
	 requiring subscription followed by dynamic invocation 
	 on a circuit switched or packet switched network.
	 "
    REFERENCE
	"ITU-T Rec. X.283 | ISO/IEC 10733 : x25PLE-DCE."
    ::= { x25PLEDCEEntry 3 }

x25PLEDCEFastSelectAcceptance OBJECT-TYPE
    SYNTAX	TruthValue
    MAX-ACCESS	read-create
    STATUS	current
    DESCRIPTION
	"
	 Fast Select Acceptance is an optional user facility 
	 that requires subscription only on a packet switched 
	 network.
	 "
    REFERENCE
	"ITU-T Rec. X.283 | ISO/IEC 10733 : x25PLE-DCE 
	     fastSelectAcceptance.
	 ITU-T Rec. X.7, Clause 6.2.1.2."
    ::= { x25PLEDCEEntry 4 }

x25PLEDCEIncomingCallsBarred OBJECT-TYPE
    SYNTAX	TruthValue
    MAX-ACCESS	read-create
    STATUS	current
    DESCRIPTION
	"
	 Incoming Calls Barred is an optional user facility 
	 requiring subscription only in a circuit switched or 
	 packet switched network.
	 "
    REFERENCE
	"ITU-T Rec. X.283 | ISO/IEC 10733 : x25PLE-DCE, 
	     incomingCallsBarred.
	 ITU-T Rec. X.7, Clause 6.6.1."
    ::= { x25PLEDCEEntry 5 }

x25PLEDCEOneWayLogicalChannelOutgoing OBJECT-TYPE
    SYNTAX	TruthValue
    MAX-ACCESS	read-create
    STATUS	current
    DESCRIPTION
	"
	 One-way Logical Channel Outgoing is an optional user 
	 facility requiring subcription only in a packet 
	 switched network.
	"
    REFERENCE
	"ITU-T Rec. X.283 | ISO/IEC 10733 : x25PLE-DCE, 
	     oneWayLogicalChannelOutgoing.
	 ITU-T Rec. X.7, Clause 6.6.4."
    ::= { x25PLEDCEEntry 6 }

x25PLEDCEOutgoingCallsBarred OBJECT-TYPE
    SYNTAX	TruthValue
    MAX-ACCESS	read-create
    STATUS	current
    DESCRIPTION
	"
	 Outgoing Calls Barred is an optional user facility 
	 requiring subscription only in a circuit switched or 
	 packet switched network.
	 "
    REFERENCE
	"ITU-T Rec. X.283 | ISO/IEC 10733 : x25PLE-DCE, 
	     outgoingCallsBarred.
	 ITU-T Rec. X.7, Clause 6.6.2."
    ::= { x25PLEDCEEntry 7 }

-- dCEX25PLEFacilities-P
x25PLEDCEBilateralCUG OBJECT-TYPE
    SYNTAX	Subscription
    MAX-ACCESS	read-create
    STATUS	current
    DESCRIPTION
	"
	 Bilateral Closed user Group is an optional user 
	 facility requiring subscription followed by dynamic 
	 invocation on a circuit switched or packet switched 
	 network.
	 "
    REFERENCE
	"ITU-T Rec. X.283 | ISO/IEC 10733 : x25PLE-DCE."
    ::= { x25PLEDCEEntry 8 }

x25PLEDCEBilateralCUGWithOutgoingAccess OBJECT-TYPE
    SYNTAX	Subscription
    MAX-ACCESS	read-create
    STATUS	current
    DESCRIPTION
	"
	 Bilateral Closed User Group With Outgoing Access is an 
	 optional user facility requiring subscription followed 
	 by dynamic invocation on a circuit switched or packet 
	 switched network.
	 "
    REFERENCE
	"ITU-T Rec. X.283 | ISO/IEC 10733 : x25PLE-DCE."
    ::= { x25PLEDCEEntry 9 }

x25PLEDCECallRedirection OBJECT-TYPE
    SYNTAX	TruthValue
    MAX-ACCESS	read-create
    STATUS	current
    DESCRIPTION
	"
	 Call Redirection is an optional user facility that 
	 requirest subscription only on circuit switched or 
	 packet switched networks.
	 "
    REFERENCE
	"ITU-T Rec. X.283 | ISO/IEC 10733 : x25PLE-DCE 
	     callRedirection.
	 ITU-T Rec. X.7, Clause 6.4.1."
    ::= { x25PLEDCEEntry 10 }

x25PLEDCEChargingInformation OBJECT-TYPE
    SYNTAX	TruthValue
    MAX-ACCESS	read-create
    STATUS	current
    DESCRIPTION
	"
	 Charging Information is an optional user facility that 
	 requires subscription only or dynamic invocation only 
	 on a circuit switched or packet switched network.
	
	 Note that the Charging Information facility is not 
	 supported by the 1980 version of X.25, x2580(8).
	 "
    REFERENCE
	"ITU-T Rec. X.283 | ISO/IEC 10733 : x25PLE-DCE, 
	     chargingInformation.
	 ITU-T Rec. X.7, Clause 6.5.4."
    ::= { x25PLEDCEEntry 11 }

x25PLEDCECUGWithIncomingAccess OBJECT-TYPE
    SYNTAX	Subscription
    MAX-ACCESS	read-create
    STATUS	current
    DESCRIPTION
	"
	 Closed User Group With Incoming Access is an optional 
	 user facility requiring subscription followed by 
	 dynamic invocation on a circuit switched or packet 
	 switched network.
	 "
    REFERENCE
	"ITU-T Rec. X.283 | ISO/IEC 10733 : x25PLE-DCE."
    ::= { x25PLEDCEEntry 12 }

x25PLEDCECUGWithOutgoingAccess OBJECT-TYPE
    SYNTAX	Subscription
    MAX-ACCESS	read-create
    STATUS	current
    DESCRIPTION
	"
	 Closed User Group With Outgoing Access is an optional 
	 user facility requiring subscription followed by 
	 dynamic invocation on a circuit switched or packet 
	 switched network.
	"
    REFERENCE
	"ITU-T Rec. X.283 | ISO/IEC 10733 : x25PLE-DCE."
    ::= { x25PLEDCEEntry 13 }

x25PLEDCEDBitModification OBJECT-TYPE
    SYNTAX	TruthValue
    MAX-ACCESS	read-create
    STATUS	current
    DESCRIPTION
	"
	 D-bit Modification is an optional user facility that 
	 requires subscription only on packet switched networks.

	 The D-bit Modification facility may be negotatited 
	 (this value altered) when there are no active virtual 
	 calls.
	 "
    REFERENCE
	"ITU-T Rec. X.283 | ISO/IEC 10733 : x25PLE-DCE, 
	     dBitModification.
	 ITU-T Rec. X.7, Clause 6.1.5."
    ::= { x25PLEDCEEntry 14 }


--  x25PLEDCEDefaultThroughputClassesAssignment
x25PLEDCEDefaultThroughputClassSubscription OBJECT-TYPE
    SYNTAX	TruthValue
    MAX-ACCESS	read-create
    STATUS	current
    DESCRIPTION
	"Specifies subscription of the DTE to the Default 
	 Throughput Classes Assignment facility of ITU-T Rec. 
	 X.2 using the TruthValue textual convention.  When 
	 true(1), it specifies that the DTE is subscribed to the 
	 Default Throughput Classes Assignement facility; when 
	 false(2), not subscribed.
	
	 Default Throughput Classes Assignment is available by 
	 subscription only on packet switched networks.
	
	 Default Throughput Classes Assignment is an optional 
	 user faciltiy agreed for a period of time.  This 
	 facility, if subscribed to, provides for the selection 
	 of default throughput classes from the list of 
	 throghput classes supported by the Administraiton.  
	 Some networks may contstrain the default throughput 
	 classes to be the same for each direction of data 
	 transmission.  In the absense of this facility, the 
	 default throughput classes correspond to the data rate 
	 of the DTE/DCE interface (see X.25/7.3.2) but do not 
	 exceed the maximum throughput class supported by the 
	 network.
	
	 NOTE 1 -  When no throughput class corresponds to the 
	 data rate of the DTE/DCE interface, the default 
	 throughput classes should be the ones just lower than 
	 the data rate.  However, some networks may choose the 
	 ones just higher than the data rate.
	
	 The default throughput classes are the maximum 
	 throughput classes which may be associated with any 
	 virtual call at the DTE/DCE interface.  Values other 
	 than the default throughpug clases may be negotiated 
	 for a virtual call by means of one of the throughput 
	 class negotiation facilities (see X.25/6.13).  Values 
	 other than the default throughput clases may be agreed 
	 for a period of time for each permanent virtual 
	 circuit.
	
	 NOTE 2 - Throughput characteristics and throughtput 
	 classes are described in X.25/4.4.2."
    REFERENCE
	"ITU-T Rec. X.283 | ISO/IEC 10733 : x25PLE-DCE 
	     defaultThroughputClassesAssignment.
	 ITU-T Rec. X.25 | ISO/IEC 8208 : Clause 6.11, Default 
	     Throughput Classes Assignment facility.
	 ITU-T Rec. X.7, Clause 6.1.1.1."
    ::= { x25PLEDCEEntry 15 }

x25PLEDCEDefaultThroughputClassSupported OBJECT-TYPE
    SYNTAX	ThroughputClassSupport
    MAX-ACCESS	read-create
    STATUS	current
    DESCRIPTION
	"Specifies the throughput classes that are supported in 
	 accordance with the Default Throughput Classes 
	 Assignment facility of ITU-T Rec. X.2 using the 
	 ThroughputClassSupport textual convention.  This is a 
	 set-valued object that must contain one or more of the 
	 throughput classes described for the 
	 ThroughputClassSupport textual convention.
	
	 Default Throughput Classes Assignment is available by 
	 subscription only on packet switched networks.
	
	 When the Default Throughput Classes Assignment facility 
	 is not subscribed by the DTE (i.e. when 
	 x25PLEDCEDefaultThroughputClassSubscription is 
	 false(2)), then the value of this object is ignored."
    REFERENCE
	"ITU-T Rec. X.283 | ISO/IEC 10733 : x25PLE-DCE 
	     defaultThroughputClassesAssignment.
	 ITU-T Rec. X.25 | ISO/IEC 8208 : Clause 6.11, Default 
	     Throughput Classes Assignment facility.
	 ITU-T Rec. X.7, Clause 6.1.1.1."
    ::= { x25PLEDCEEntry 16 }

x25PLEDCEDefaultThroughputClassIncoming OBJECT-TYPE
    SYNTAX	ThroughputClass
    MAX-ACCESS	read-create
    STATUS	current
    DESCRIPTION
	"Specifies the default incoming throughput class in 
	 accordance with the Default Throughput Classes 
	 Assignment facility of ITU-T Rec. X.2 using the 
	 ThroughputClass textual convention.  This is the 
	 default throughput class assigned to the incoming 
	 traffic direction.
	
	 Default Throughput Classes Assignment is available by 
	 subscription only on packet switched networks.
	
	 When the Default Throughput Classes Assignment facility 
	 is not subscribed by the DTE (i.e. when 
	 x25PLEDCEDefaultThroughputClassSubscription is 
	 false(2)), then the value of this object is ignored.
	
	 When this object is given the value default(0), the 
	 default throughput class will be used.  The default 
	 throughput class is the throughput class that is just 
	 less than or just greater than the rate of the DTE/DCE 
	 interface for full duplex links, or half the rate of 
	 the DTE/DCE interface for half-duplex links."
    REFERENCE
	"ITU-T Rec. X.283 | ISO/IEC 10733 : x25PLE-DCE 
	     defaultThroughputClassesAssignment.
	 ITU-T Rec. X.25 | ISO/IEC 8208 : Clause 6.11, Default 
	     Throughput Classes Assignment facility.
	 ITU-T Rec. X.7, Clause 6.1.1.1."
    ::= { x25PLEDCEEntry 17 }

x25PLEDCEDefaultThroughputClassOutgoing OBJECT-TYPE
    SYNTAX	ThroughputClass
    MAX-ACCESS	read-create
    STATUS	current
    DESCRIPTION
	"Specifies the default ougoing throughput class in 
	 accodance wih the Default Throughput Classes Assignment 
	 facility of ITU-T Rec. X.2 using the ThroughputClass 
	 texutal convention.  This is the default throughput 
	 class assigned to the outgoing traffic direction.
	
	 Default Throughput Classes Assignment is available by 
	 subscription only on packet switched networks.
	
	 When the Default Throughput Classes Assignment facility 
	 is not subscribed by the DTE (i.e. when 
	 x25PLEDCEDefaultThroughputClassSubscription is 
	 false(2)), then the value of this object is ignored.
	
	 When this object is given the value default(0), the 
	 default throughput class will be used.  The default 
	 throughput class is the throughput class that is just 
	 less than or just greater than the rate of the DTE/DCE 
	 interface for full duplex links, or half the rate of 
	 the DTE/DCE interface for half-duplex links."
    REFERENCE
	"ITU-T Rec. X.283 | ISO/IEC 10733 : x25PLE-DCE 
	     defaultThroughputClassesAssignment.
	 ITU-T Rec. X.25 | ISO/IEC 8208 : Clause 6.11, Default 
	     Throughput Classes Assignment facility.
	 ITU-T Rec. X.7, Clause 6.1.1.1."
    ::= { x25PLEDCEEntry 18 }

x25PLEDCEHuntGroup OBJECT-TYPE
    SYNTAX	TruthValue
    MAX-ACCESS	read-create
    STATUS	current
    DESCRIPTION
	"The subscription of the DTE to the Hunt Group facility 
	 as described in ITU-T Recommendation X.2. Expressed as 
	 a TruthValue where a value of 'true(1)' indicates 
	 subscription and a value of false(2) indicates 
	 non-subscription.
	
	 The Hunt Group facility is an optional user faciltiy 
	 that requires subscription only on a circuit switched 
	 or packet switched network.
	
	 Note that neither the Hunt Group facility nor the 
	 Called Line Address Modificiation Notificaiton facility 
	 is not supported by the 1980 version of X.25, x2580(8).
	
	 Hunt Group is an optional user facility agreed for a 
	 period of time.  This user facility, if subscribed to, 
	 distributes incoming calls having an address associated 
	 with the hunt group across a designated grouping of 
	 DTE/DCE interfaces.
	
	 Selection is performed forn an incoming virtual call if 
	 there is at least one logical channel in the ready 
	 state (see X.25/4.1.1), excluding one-way outgoing 
	 logical channels, available for virtual calls on any of 
	 the DTE/DCE interfaces in the group.  Once a virtual 
	 call is assigned to a DTE/DCE interface, it is treated 
	 as a regular call.
	
	 When virtual calls are placed to a hunt group address 
	 in the case that specific addresses have also been 
	 assigned to the individual DTE/DCE interfaces, the 
	 clear indication packet (when no call accepted packet 
	 has been transmitted) or the call connected packet 
	 transferred to the calling DTE may contain the called 
	 DTE address of the selected DTE/DCE interface and the 
	 Called Line Address Modified Notification facility (see 
	 X.25/6.26) indicating the reason why the called DTE 
	 address is different from the one originally requested.
	
	 Virtual calls may be originated by the DTEs on DTE/DCE 
	 interfaces belonging to the hunt group; these are 
	 handled in the normal manner.  In particular, the 
	 calling DTE address transferred to the remote DTE in 
	 the incoming call packet is the hunt group address 
	 unless the DTE/DCE interface has a specific address 
	 assigned.  Permanent virtual circuits may be assigned 
	 to DTE/DCE interfaces belongin to the hunt group.  
	 These permanent vritual circuits are independent of the 
	 operation of the hunt group.  Some networks may apply 
	 virtual call subscription time user facilities in 
	 common to all DTE/DCE interfaces in the hunt group, 
	 place a limit on the number of DTE/DCE interfaces in 
	 the hunt group, and/or constrain the size of the 
	 geographic region that can be served by a single hunt 
	 group."
    REFERENCE
	"ITU-T Rec. X.283 | ISO/IEC 10733 : x25PLE-DCE, 
	     huntGroup.
	 ITU-T Rec. X.25, Clause 6.24 Hunt group.
	 ITU-T Rec. X.7, Clause 6.3.8."
    ::= { x25PLEDCEEntry 19 }

x25PLEDCEIncomingCallBarredWithinCUG OBJECT-TYPE
    SYNTAX	TruthValue
    MAX-ACCESS	read-create
    STATUS	current
    DESCRIPTION
	"The subscription of the DTE to the Incoming Call Barred 
	 within a CUG facility as described in ITU-T 
	 Recommendation X.2.  Expressed as a TruthValue where a 
	 value of 'true(1)' indicates subscription and a value 
	 of 'false(2)' indicates non-subscription.  Incoming 
	 calls barred within a closed user group is an optional 
	 user facility agreed for a period of time.  This user 
	 facility, if subscribed to for a given closed user 
	 group, permits the DTE to originate virtual calls to 
	 DTEs in this closed user group, but precludes the 
	 reception of incoming calls from DTEs in this closed 
	 user group.
	
	 Incoming Calls Barred WIthin a Closed User Group is an 
	 optional user facility that requires subscription only 
	 in a circuit switched or packet switched network.
	"
    REFERENCE
	"ITU-T Rec. X.283 | ISO/IEC 10733 : x25PLE-DCE, 
	     incomingCallBarredWithinCUG.
	 ITU-T Rec. X.25, Section 6.14.4 Incoming calls barred 
	     within a closed user group."
    ::= { x25PLEDCEEntry 20 }

x25PLEDCELocalChargingPrevention OBJECT-TYPE
    SYNTAX	TruthValue
    MAX-ACCESS	read-create
    STATUS	current
    DESCRIPTION
	"The subscription of the DTE to the Local Charging 
	 Prevention facility as described in ITU-T 
	 Recommendation X.2.  Expressed as a TruthValue where a 
	 value of 'true(1)' indicates subscription and a value 
	 of 'false(2)' indicates non-subscription.
	
	 Local Charging Prevention is an optional user facility 
	 that requires subscription only on a packet switched 
	 network.
	
	 Note that the Local Charging Prevention facility is not 
	 supported by the 1980 version of ITU-T Rec. X.25, 
	 x2580(8).
	
	 Local Charging Prevention is an optional user facility 
	 agreed for a period of time for virtual calls.  This 
	 user facility, when subscribed to, authorizes the DCE 
	 to prevent the establishment of virtual calls which the 
	 subscription must pay for by:
	
	 a) not transmitting to the DTE incoming calls which 
	    request the Reverse Charging facility; and

	 b) ensuring that the charges are made to another part 
	    whenever a call is requested by the DTE.  This other 
	    party can be deteremined by using any of a number of 
	    actions, both procedural and administrative.  The 
	    procedural methods include:
	
	    - the use of Reverse Charging;
	
	    - identification of a third part using NUI 
	      Subscription facility (see X.25/6.21.1) and NUI 
	      Selection facility (see X.25/6.21.3).
	
	 When the party to be charged has not been established 
	 for a call request, the DCE that receives the call 
	 request packet will apply Reverse Charging to this 
	 call.
	
	 NOTE - For an interim period of time, some networks may 
	 choose to enforce Local Charging Prevention by clearing 
	 the call when the party to be charged has not been 
	 established."
    REFERENCE
	"ITU-T Rec. X.283 | ISO/IEC 10733 : x25PLE-DCE, 
	     localChargingPrevention.
	 ITU-T Rec. X.25, Clause 6.20 Local charging prevention.
	 ITU-T Rec. X.7, Clause 6.5.2."
    ::= { x25PLEDCEEntry 21 }

--  x25PLEDCENonStandardDefaultPacketSizes

x25PLEDCENonStandardDefaultPacketSizeSubscription OBJECT-TYPE
    SYNTAX	TruthValue
    MAX-ACCESS	read-create
    STATUS	current
    DESCRIPTION
	"The subscription of the DTE to the Non-standard Default 
	 Packet Sizes facility as described in ITU-T 
	 Recommendation X.2, section 6.9.  Expressed as a 
	 TruthValue where a value of 'true(1)' indicates 
	 subscription and a value of 'false(2)' indicates 
	 non-subscription.
	
	 Non-standard Default Packet Sizes is a subscription 
	 only facility available only on packet switched 
	 networks.
	
	 Non-standard Default Packet Sizes is an optional user 
	 facility agreed to for a period of time.  This 
	 facility, if subscribed to, provides for the selection 
	 of defualt packet sizes from the list of packet sizes 
	 supported by the Administration.  Some networks may 
	 constraint the packet sizes to be the same for each 
	 direction of data transmission across the DTE/DCE 
	 interface.  In the absense of this facility, the 
	 default packet sizes are 128 octets.
	
	 Values other than the default packet sizes may be 
	 negotiated for a virtual call by means of the Flow 
	 Control Parameter Negotiation facility.  Values other 
	 than the default packet sizes may be agreed for a 
	 period of time for each permanent virtual circuit."
    REFERENCE
	"ITU-T Rec. X.283 | ISO/IEC 10733 : x25PLE-DCE, 
	     nonStandardDefaultPacketSizes.
	 ITU-T Rec. X.25 | ISO/IEC 8208 : Clause 6.9, 
	     Non-standard default packet sizes.
	 ITU-T Rec. X.7, Clause 6.1.2.1."
    ::= { x25PLEDCEEntry 22 }

x25PLEDCENonStandardDefaultPacketSizeMaximum OBJECT-TYPE
    SYNTAX	PacketSize
    MAX-ACCESS	read-create
    STATUS	current
    DESCRIPTION
	"When the Non-standard Default Packet Sizes facility is 
	 subscribed, this columnar object specifies the maximum 
	 negotiable packet size.
	
	 Non-standard Default Packet Sizes is a subscription 
	 only facility available only on packet switched 
	 networks."
    REFERENCE
	"ITU-T Rec. X.283 | ISO/IEC 10733 : x25PLE-DCE, 
	     nonStandardDefaultPacketSizes.
	 ITU-T Rec. X.25 | ISO/IEC 8208 : Clause 6.9, 
	     Non-standard default packet sizes.
	 ITU-T Rec. X.7, Clause 6.1.2.1."
    ::= { x25PLEDCEEntry 23 }

x25PLEDCENonStandardDefaultPacketSizeIncoming OBJECT-TYPE
    SYNTAX	PacketSize
    MAX-ACCESS	read-create
    STATUS	current
    DESCRIPTION
	"When the Non-standard Default Packet Sizes facility is 
	 subscribed, this columnar object specifies the 
	 non-standard default incoming packet size.
	
	 Non-standard Default Packet Sizes is a subscription 
	 only facility available only on packet switched 
	 networks."
    REFERENCE
	"ITU-T Rec. X.283 | ISO/IEC 10733 : x25PLE-DCE, 
	     nonStandardDefaultPacketSizes.
	 ITU-T Rec. X.25 | ISO/IEC 8208 : Clause 6.9, 
	     Non-standard default packet sizes.
	 ITU-T Rec. X.7, Clause 6.1.2.1."
    ::= { x25PLEDCEEntry 24 }

x25PLEDCENonStandardDefaultPacketSizeOutgoing OBJECT-TYPE
    SYNTAX	PacketSize
    MAX-ACCESS	read-create
    STATUS	current
    DESCRIPTION
	"When the Non-standard Default Packet Sizes facility is 
	 subscribed, this columnar object specifies the 
	 non-standard default outgoing packet size.
	
	 Non-standard Default Packet Sizes is a subscription 
	 only facility available only on packet switched 
	 networks."
    REFERENCE
	"ITU-T Rec. X.283 | ISO/IEC 10733 : x25PLE-DCE, 
	     nonStandardDefaultPacketSizes.
	 ITU-T Rec. X.25 | ISO/IEC 8208 : Clause 6.9, 
	     Non-standard default packet sizes.
	 ITU-T Rec. X.7, Clause 6.1.2.1."
    ::= { x25PLEDCEEntry 25 }

--  x25PLEDCENonStandardDefaultWindowSizes
x25PLEDCENonStandardDefaultWindowSizeSubscription OBJECT-TYPE
    SYNTAX	TruthValue
    MAX-ACCESS	read-create
    STATUS	current
    DESCRIPTION
	"The subscription of the DTE to the Non-standard Default 
	 Window Sizes facility as described in ITU-T 
	 Recommendation X.2, section 6.10.  Expressed as a 
	 TruthValue where a value 'true(1)' indicates 
	 subscription and a value of 'false(2)' indicates 
	 non-subscription.
	
	 Non-standard Default Window Sizes is a subscription 
	 only facility available only on packet switched 
	 networks.
	
	 Non-standard Default Window Sizes is an optional user 
	 facility agreed for a period of time.  This facility, 
	 if subscribed to, provides for the selection of default 
	 window sizes from a list of window sizes supported by 
	 the Administration.  Some networks may constrain the 
	 default window sizes to be the same for each direction 
	 of data transmission across the DTE/DCE interface.  In 
	 the absense of this facility, the default window sizes 
	 for normal and extended sequence numbering are 2, and 
	 the default window sizes fro super extended sequence 
	 numbers are 128.
	
	 Values other than the default window sizes may be 
	 negotiated for a virtual call by means of the Flow 
	 Control Parameter Negotiation facility (see X.25/6.12). 
	 Values other than the default window sizes may be 
	 agreed for a period of time for each permanent virtual 
	 circuit."
    REFERENCE
	"ITU-T Rec. X.283 | ISO/IEC 10733 : x25PLE-DCE, 
	     nonStandardDefaultWindowSizes.
	 ITU-T Rec. X.25, Clause 6.10 Non-standard default 
	     window sizes.
	 ITU-T Rec. X.7, Clause 6.1.2.2."
    ::= { x25PLEDCEEntry 26 }

x25PLEDCENonStandardDefaultWindowSizeMaximum OBJECT-TYPE
    SYNTAX	INTEGER
    MAX-ACCESS	read-create
    STATUS	current
    DESCRIPTION
	"When the Non-standard Default Window Sizes facility is 
	 subscribed, this columnar object specifies the maximum 
	 negotiable window size.
	
	 Non-standard Default Window Sizes is a subscription 
	 only facility available only on packet switched 
	 networks."
    REFERENCE
	"ITU-T Rec. X.283 | ISO/IEC 10733 : x25PLE-DCE, 
	     nonStandardDefaultWindowSizes.
	 ITU-T Rec. X.25, Clause 6.10 Non-standard default 
	     window sizes.
	 ITU-T Rec. X.7, Clause 6.1.2.2."
    ::= { x25PLEDCEEntry 27 }

x25PLEDCENonStandardDefaultWindowSizeIncoming OBJECT-TYPE
    SYNTAX	WindowSize
    MAX-ACCESS	read-create
    STATUS	current
    DESCRIPTION
	"When the Non-standard Default Window Sizes facility is 
	 subscribed, this columnar object specifies the 
	 non-standard default incoming window size.
	
	 Non-standard Default Window Sizes is a subscription 
	 only facility available only on packet switched 
	 networks."
    REFERENCE
	"ITU-T Rec. X.283 | ISO/IEC 10733 : x25PLE-DCE, 
	     nonStandardDefaultWindowSizes.
	 ITU-T Rec. X.25, Clause 6.10 Non-standard default 
	     window sizes.
	 ITU-T Rec. X.7, Clause 6.1.2.2."
    ::= { x25PLEDCEEntry 28 }

x25PLEDCENonStandardDefaultWindowSizeOutgoing OBJECT-TYPE
    SYNTAX	WindowSize
    MAX-ACCESS	read-create
    STATUS	current
    DESCRIPTION
	"When the Non-standard Default Window Sizes facility is 
	 subscribed, this columnar object specifies the 
	 non-standard default outgoing window size.
	
	 Non-standard Default Window Sizes is a subscription 
	 only facility available only on packet switched 
	 networks."
    REFERENCE
	"ITU-T Rec. X.283 | ISO/IEC 10733 : x25PLE-DCE, 
	     nonStandardDefaultWindowSizes.
	 ITU-T Rec. X.25, Clause 6.10 Non-standard default 
	     window sizes.
	 ITU-T Rec. X.7, Clause 6.1.2.2."
    ::= { x25PLEDCEEntry 29 }

x25PLEDCENUIOverride OBJECT-TYPE
    SYNTAX	TruthValue
    MAX-ACCESS	read-create
    STATUS	current
    DESCRIPTION
	"
	
	 NUI Override is an optional user facility that requires 
	 subscription followed by dynamic invocation on packet 
	 switched networks.
	
	 Note that Network User Identification facilities are 
	 not supported by the 1980 version of X.25, x2580(9).
	 "
    REFERENCE
	"ITU-T Rec. X.283 | ISO/IEC 10733 : x25PLE-DCE, 
	     nUIOverride.
	 ITU-T Rec. X.7, Clause 6.5.3.2."
    ::= { x25PLEDCEEntry 30 }

x25PLEDCENUISubscription OBJECT-TYPE
    SYNTAX	TruthValue
    MAX-ACCESS	read-create
    STATUS	current
    DESCRIPTION
	"
	 NUI Subscription is an optional user facility requiring 
	 subscription followed by dynamic invocation on a packet 
	 switched network.
	
	 Note that Network User Identification facilities are 
	 not supported by the 1980 version of X.25, x2580(8).
	"
    REFERENCE
	"ITU-T Rec. X.283 | ISO/IEC 10733 : x25PLE-DCE, 
	     nUISubscription.
	 ITU-T Rec. X.7, Clause 6.5.3.1."
    ::= { x25PLEDCEEntry 31 }

x25PLEDCEOneWayLogicalChannelIncoming OBJECT-TYPE
    SYNTAX	TruthValue
    MAX-ACCESS	read-create
    STATUS	current
    DESCRIPTION
	"
	 One-way Logical Channel Incoming is an optional user 
	 facility requiring subcription only in a packet 
	 switched network.
	 "
    REFERENCE
	"ITU-T Rec. X.283 | ISO/IEC 10733 : x25PLE-DCE, 
	     oneWayLogicalChannelIncoming.
	 ITU-T Rec. X.7, Clause 6.6.3."
    ::= { x25PLEDCEEntry 32 }

x25PLEDCEOnlineFacilityRegistration OBJECT-TYPE
    SYNTAX	TruthValue
    MAX-ACCESS	read-create
    STATUS	current
    DESCRIPTION
	"The subscription of the On-line Facility Registration 
	 facility as described in ITU-T Recommendation X.2.  
	 Expressed as a TruthValue where a value of 'true(1)' 
	 indicates subscription and a value of 'false(2)' 
	 indicates non subscription.
	
	 On-line Facility Registration is an optional user 
	 facility requiring subscription followed by dynamic 
	 invocation on a circuit switched or packet switched 
	 network.
	
	 On-line Facility Registration is an optional user 
	 facility agreed to for a period of time.  This user 
	 facility, if subscribed to, permits a DTE at any time 
	 to request registration of optional user facilities 
	 and/or to obtain the current values of such facilities 
	 as understood by the interfacing DCE.  The DTE is 
	 always the initiator of the registration procedure 
	 while the DCE is always the responder.
	
	 Note that the ITU-T Rec. X.25 (1996) and (1980) 
	 protocol versions, x2596(6) and x2580(8), do not 
	 support the on-line regsitration facility and this 
	 value will always be 'false(2)' for those protocol 
	 versions."
    REFERENCE
	"ITU-T Rec. X.283 | ISO/IEC 10733 : x25PLE-DCE 
	     onlineFacilityRegistration."
    ::= { x25PLEDCEEntry 33 }

x25PLEDCEOutgoingCallBarredWithinCUG OBJECT-TYPE
    SYNTAX	TruthValue
    MAX-ACCESS	read-create
    STATUS	current
    DESCRIPTION
	"The subscription of the Outgoing Call Barred Within a 
	 CUG facility as described in ITU-T Recommendation X.2, 
	 clause 6.14.5.  Expressed as a TruthValue where a value 
	 of 'true(1)' indicates subscription and a value of 
	 'false(2)' indicates non-subscription.
	
	 Outgoing Calls Barred within a Closed User Group is an 
	 optional user facility agreed for a period of time.  
	 This user facility, if subscribed for a given closed 
	 user group, permits the DTE to receive vitual calls 
	 from DTEs in this closed user group, but prevents the 
	 DTE from originating virtual calls to DTEs in this 
	 closed user group.
	
	 Outgoing Calls Barred WIthin a Closed User Group is an 
	 optional user facility that requires subscription only 
	 in a circuit switched or packet switched network.
	 "
    REFERENCE
	"ITU-T Rec. X.283 | ISO/IEC 10733 : x25PLE-DCE 
	     outgoingCallBarredWithinCUG.
	 ITU-T Rec. X.25, Clause 6.14.5, Outgoing calls barred 
	     within a closed user group."
    ::= { x25PLEDCEEntry 34 }

x25PLEDCEPacketRetransmission OBJECT-TYPE
    SYNTAX	TruthValue
    MAX-ACCESS	read-create
    STATUS	current
    DESCRIPTION
	"The subscription of the Packet Retransmissions facility 
	 as described in ITU-T Recommendation X.2. Expressed as 
	 a TruthValue where a value of 'true(1)' indicates 
	 subscription and a value of 'false(2)' indicates 
	 non-subscription. If non-subscription, then the 
	 attributes for rejectTimer and rejectCount will have 
	 NULL values.
	
	 Packet Retranmission is an optional user facility 
	 agreed for a period of time.  It is common to all 
	 logical channels at the DTE/DCE interface.  The 
	 facility requires subscription followed by dynamic 
	 invocation on packet switched networks.
	
	 This user facility, if subscribed to, allows a DTE to 
	 requires retransmission of one or several consecutive 
	 DCE data packets from the DCE by transferring across 
	 the DTE/DCE interface a DTE reject packet specifying 
	 the logical channel number and a sequence number P(R).  
	 The value of this P(R) should be within the range from 
	 the last P(R) received by the DCE up to, but not 
	 including, the P(S) of the next DCE data packet to be 
	 transmitted by the DCE.  If the P(R) is outside this 
	 range, the DCE will initated the reset procedure with 
	 the cause 'Local procedure error' and diagnostic #2.
	
	 When received a DTE reject packet, the DCE initiates on 
	 the sepcified logical channel retransmission of the DCE 
	 dat packets, the packet send sequence numbers of which 
	 are starting from P(R), where P(R) is indicated in the 
	 DTE reject packet.  Until the DCE transfers across the 
	 DTE/DCE interface a DCE data packet with a packe send 
	 sequence number equal to the P(R) indicated in the DTE 
	 reject packet, the DCE will consider the receipt of 
	 another DTE reject packet as a procedure error and 
	 reset the logical channel.
	
	 Additional DCE data packets pending inital transmission 
	 may follow the retransmitted packet(s).
	
	 A DTE receive not ready situation indicated by the 
	 transmission of an RNR packet is cleared by the 
	 transmission of a DTE reject packet.
	
	 The conditions under which the DCE ignores a DTE reject 
	 packet, or considers it as a procedure error, are those 
	 described for flow control packets (see Annex C)."
    REFERENCE
	"ITU-T Rec. X.283 | ISO/IEC 10733 : x25PLE-DCE 
	     packetRetransmission."
    ::= { x25PLEDCEEntry 35 }

x25PLEDCEReverseChargingAcceptance OBJECT-TYPE
    SYNTAX	TruthValue
    MAX-ACCESS	read-create
    STATUS	current
    DESCRIPTION
	"The subscription of the Reverse Charging Acceptance 
	 facility as described in ITU-T Recommendation X.2, 
	 clause 6.19.  Expressed as a TruthValue where a value 
	 of 'true(1)' indicates subscription and a value of 
	 'false(2)' indicates non-subscription.
	
	 Reverse Charging Acceptable is an optional user 
	 facility that requires subscription only on a circuit 
	 switched or packet switched network.
	
	 Reverse Charging Acceptance is an optional user 
	 faciltiy agreed for a period of time for virtual calls.  
	 This user facility, if subscribed to, authorizes the 
	 DCE to transmit to the DTE incoming calls which request 
	 Reverse Charging facility.  In the absence of this 
	 facility, the DCE will not transmit to the DTE incoming 
	 calls which request the Reverse Charging facility."
    REFERENCE
	"ITU-T Rec. X.283 | ISO/IEC 10733 : x25PLE-DCE 
	     reverseChargingAcceptance.
	 ITU-T Rec. X.25, Clause 6.19: Reverse charging 
	     acceptance.
	 ITU-T Rec. X.7, Clause 6.5.1.2."
    ::= { x25PLEDCEEntry 36 }

x25PLEDCEROASubscription OBJECT-TYPE
    SYNTAX	Subscription
    MAX-ACCESS	read-create
    STATUS	current
    DESCRIPTION
	"The subscription of the ROA Subscription facility as 
	 described in ITU-T Recommendation X.2, clause 6.23.1. 
	 Expressed as a TruthValue where a value of 'true(1)' 
	 indicates subscription and a value of 'false(2)' 
	 indicates non-subscription.
	
	 ROA Subscription is an optional user facility that 
	 requires subscription only on a packet switched 
	 network.
	
	 ROA Subscription is an optional user facility agreed 
	 for a period of time for virtual calls.  This user 
	 faciltiy,if subscribed to, applies (unless overridden 
	 for a single virtual call by the ROA Selection 
	 facility) to all virtual calls where more than one ROA 
	 transit network exist at a sequence of one or more 
	 gateways.  The ROA Subscription facility provides a 
	 sequence of ROA transit networks through which the 
	 calls are to be routed.  In the absence of both the ROA 
	 Subscription facility and the ROA Selection facility 
	 (see X.25/6.23.2), no user designation of ROA transit 
	 networks is in effect."
    REFERENCE
	"ITU-T Rec. X.283 | ISO/IEC 10733 : x25PLE-DCE, 
	     rOASubscription.
	 ITU-T Rec. X.25, Clause 6.23.1: ROA subscription.
	 ITU-T Rec. X.7, Clause 6.4.6.1."
    ::= { x25PLEDCEEntry 37 }

-- dCEX25PLETimers-P
x25PLEDCERestartIndication OBJECT-TYPE
    SYNTAX	TimeInterval
    UNITS	"seconds"
    MAX-ACCESS	read-create
    STATUS	current
    DESCRIPTION
	"Specifies the value for Timer T10 (Restart Indication 
	 Response Timer) in centiseconds (displayed in seconds).  
	 The default value is 6000 (60 seconds).  Specifies the 
	 time interval from the point of issuing a restart 
	 indication that the DCE will wait to receive a restart 
	 confirmation or restart request from the DTE."
    REFERENCE
	"ITU-T Rec. X.283 | ISO/IEC 10733 : x25PLE-DCE,
	     restartIndication.
	 ITU-T Rec. X.25 | ISO/IEC 8208 : Timer T10."
    DEFVAL	{ 6000 } -- 60 seconds
    ::= { x25PLEDCEEntry 38 }

x25PLEDCERestartCount OBJECT-TYPE
    SYNTAX	INTEGER
    UNITS	"retransmissions"
    MAX-ACCESS	read-create
    STATUS	current
    DESCRIPTION
	"Specifies the value for Count R10 (Restart Indication 
	 Retransmission Count) in retransmissions.  The default 
	 value is one (1 retransmission).  Specifies the number 
	 of times that a restart indication will be 
	 retransmitted as a result of the expiry of Timer T10."
    REFERENCE
	"ITU-T Rec. X.25, Annex D, Table D.1/X.25."
    DEFVAL	{ 1 } -- one retransmission
    ::= { x25PLEDCEEntry 39 }

x25PLEDCEIncomingCall OBJECT-TYPE
    SYNTAX	TimeInterval
    UNITS	"seconds"
    MAX-ACCESS	read-create
    STATUS	current
    DESCRIPTION
	"Specifies the value of Timer T11 (Incoming Call 
	 Response Timer) in centiseconds (displayed in seconds).  
	 The default value is 18000 (180 seconds).  Specifies 
	 the time interval from the point of issuing an incoming 
	 call that the DCE will wait to receive a call accepted, 
	 clear request or call request from the DTE."
    REFERENCE
	"ITU-T Rec. X.283 | ISO/IEC 10733 : x25PLE-DCE, 
	     incomingCall.
	 ITU-T Rec. X.25 | ISO/IEC 8208 : Timer T11."
    DEFVAL	{ 18000 } -- 180 seconds
    ::= { x25PLEDCEEntry 40 }

x25PLEDCECallCount OBJECT-TYPE
    SYNTAX	INTEGER
    UNITS	"retransmissions"
    MAX-ACCESS	read-create
    STATUS	current
    DESCRIPTION
	"Specifies the value for count R11 (Incoming Call 
	 Retransmission Count) in retransmissions.  The default 
	 value is zero (0 retransmissions).  Specifies the 
	 number of times that a incoming call will be 
	 retransmitted as a result of the expiry of Timer T11."
    REFERENCE
	"ITU-T Rec. X.25, Annex D, Table D.1/X.25."
    DEFVAL	{ 0 } -- zero retransmission
    ::= { x25PLEDCEEntry 41 }

x25PLEDCEResetIndication OBJECT-TYPE
    SYNTAX	TimeInterval
    UNITS	"seconds"
    MAX-ACCESS	read-create
    STATUS	current
    DESCRIPTION
	"Specifies the value for Timer T12 (Reset Indication 
	 Response Timer) in centiseconds (displayed in seconds). 
	 The default value is 6000 (60 seconds).  Specifies the 
	 time interval from the point of issuing an reset 
	 indication that the DCE will wait to receive a reset 
	 confirmation or reset request from the DTE."
    REFERENCE
	"ITU-T Rec. X.283 | ISO/IEC 10733 : x25PLE-DCE,
	     resetIndication.
	 ITU-T Rec. X.25 | ISO/IEC 8208 : Timer T12."
    ::= { x25PLEDCEEntry 42 }

x25PLEDCEResetCount OBJECT-TYPE
    SYNTAX	INTEGER
    UNITS	"retransmissions"
    MAX-ACCESS	read-create
    STATUS	current
    DESCRIPTION
	"specifies the value for Count R12 (Reset Indication 
	 Retransmission Count) in retransmissions.  The default 
	 value is one (1 retransmission).  Specifies the number 
	 of times that a reset indication will be retransmitted 
	 as a result of the expiry of Timer T12."
    REFERENCE
	"ITU-T Rec. X.25, Annex D, Table D.1/X.25."
    DEFVAL	{ 1 } -- one retranmission
    ::= { x25PLEDCEEntry 43 }

x25PLEDCEClearIndication OBJECT-TYPE
    SYNTAX	TimeInterval
    UNITS	"seconds"
    MAX-ACCESS	read-create
    STATUS	current
    DESCRIPTION
	"Specifies the value of Timer T13 (Clear Indication 
	 Response Timer) in centiseconds (displayed in seconds).  
	 The default value is 6000 (60 seconds).  Specifies the 
	 time interval from the point of issuing a clear 
	 indication that the DCE will wait to receive a clear 
	 confirmation or clear request from the DTE."
    REFERENCE
	"ITU-T Rec. X.283 | ISO/IEC 10733 : x25PLE-DCE, 
	     clearIndication.
	 ITU-T Rec. X.25 | ISO/IEC 8208 : Timer T13."
    DEFVAL	{ 6000 } -- 60 seconds
    ::= { x25PLEDCEEntry 44 }

x25PLEDCEClearCount OBJECT-TYPE
    SYNTAX	INTEGER
    UNITS	"retransmissions"
    MAX-ACCESS	read-create
    STATUS	current
    DESCRIPTION
	"specifies the value for Count R13 (Clear Indication 
	 Retransmission Count) in retransmissions.  The default 
	 value is one (1 retransmission).  Specifies the number 
	 of times that a clear indication will be retransmitted 
	 as a result of the expiry of Timer T13."
    REFERENCE
	"ITU-T Rec. X.25, Annex D, Table D.1/X.25."
    DEFVAL	{ 1 } -- one retranmission
    ::= { x25PLEDCEEntry 45 }

-- Miscellaneous conversion
x25PLEDCEProfile OBJECT-TYPE
    SYNTAX	RowPointer
    MAX-ACCESS	read-create
    STATUS	current
    DESCRIPTION
	""
    REFERENCE
	"ITU-T Rec. X.283 | ISO/IEC 10733 : x25PLE-DCE."
    ::= { x25PLEDCEEntry 46 }

x25PLEDCERowStatus OBJECT-TYPE
    SYNTAX	RowStatus
    MAX-ACCESS	read-create
    STATUS	current
    DESCRIPTION
	""
    REFERENCE
	"ITU-T Rec. X.283 | ISO/IEC 10733 : x25PLE-DCE."
    ::= { x25PLEDCEEntry 47 }


x25PLEDXE OBJECT IDENTIFIER
    ::= { x25PLPTables 5 }

x25PLEDXETable OBJECT-TYPE
    SYNTAX	SEQUENCE OF X25PLEDXEEntry
    MAX-ACCESS	not-accessible
    STATUS	current
    DESCRIPTION
	"This managed object class is made to appear like that 
	 of the x25PLE MOC defined in ISO/IEC 10733, which is 
	 really for a DXE.
	
	 Objects in this table generate communicationsAlarm 
	 notifications.
	
	 The x25PLE-P package imports the communicationsAlarm 
	 notification from Rec.  X.721 (1992) | ISO/IEC 10165-2. 
	 It is used to report the following x25PLE managed 
	 object events.
	
	 providerInitiatedDisconnect:
	    Issued upon receipt of a clear packet with a cause 
	    code other than 'DTE originated'.
	
	 remotelyInitiatedReset:
	    Issued upon occurrence of a remotely initiated 
	    reset.  This event is issued in lieu of a 
	    'providerInitiatedReset' when operating in a DTE-DXE 
	    environment. 
	
	 providerInitiatedReset:
	    Issued upon occurance of a provider initiated reset.  
	    This event is issued when operating in a DTE-DCE 
	    environment. The information relating to the packet 
	    shall be reported as a parameter in the 
	    additionalInformation field of the 
	    communicationsAlarm, using the notificationData 
	    PARAMETER
	
	 remotelyInitiatedRestart:
	    Issued upon receipt of a remotely (including 
	    provider) initiated restart.
	
	 restartCountExceeded:
	    Issued on restart failure due to restart count (R20) 
	    exceeded.
	
	 protocolErrorDetectedLocally:
	    Issued upon receipt of a packet which causes the 
	    'A=Error' action in the ISO/IEC 8208 or ITU-T Rec. 
	     X.25 state tables to be taken.
	
	 accusedOfProtocolError:
	    Issued upon receipt of a diagnostic packet or a 
	    clear, reset or restart packet with a cause code 
	    equal to one of the following: Remote Procedure 
	    Error, Incompatible Destination, Invalid Facility 
	    Request, Local Procedure Error. No other x25PLE 
	    communication alarm shall be generated as a result 
	    of this particular instance of packet.
	
	 callEstablishmentRetryCountExceeded:
	    Issued on retry failure during call establishment 
	    due to retry limit exceeded.
	
	 clearCountExceeded:
	    Issued on retry failure due to clear limit (R23) 
	    exceeded.  The information relating to the call 
	    shall be reported as a parameter in the 
	    additionalInformation field of the 
	    communicationsAlarm, using the notificationData 
	    PARAMETER"
    REFERENCE
	"ISO/IEC 10733 : x25PLE MOC."
    ::= { x25PLEDXE 1 }

x25PLEDXEEntry OBJECT-TYPE
    SYNTAX	X25PLEDXEEntry
    MAX-ACCESS	not-accessible
    STATUS	current
    DESCRIPTION
	"There may be multiple instances of these MOs within a 
	 system, corresponding to multiple X.25 PLEs.  Its 
	 definition perimits it to be created and deleted 
	 explicitly by management operation or to be created and 
	 deleted automatically as a part of system operations.  
	 For an automatically created X.25 PLE managed object, 
	 an x25PLEIVMO may be used as the source of intiial 
	 values of attributes of the x25PLE managed object.  
	 When the PLE is operable, the operationalState shall 
	 have the valud 'enabled'; otherwise it shall have the 
	 value 'disabled'.  Transitions of operationalState 
	 shall be reported using the stateChange notification."
    REFERENCE
	"ISO/IEC 10733 : x25PLE MO."
    INDEX	{
		    x25PLEId	-- shared index (DERIVED FROM)
		}
    ::= { x25PLEDXETable 1 }

X25PLEDXEEntry ::= SEQUENCE {
    x25PLEDXEPacketSequencing		INTEGER,
    x25PLEDXEMaxActiveCircuits		MaxActiveCircuits,
    x25PLEDXECallDeflectionSubscription	TruthValue,
    x25PLEDXERestartTime		TimeInterval,
    x25PLEDXERestartCount		INTEGER,
    x25PLEDXEMinimumRecallTimer		TimeInterval,
    -- PACKAGE onlineRegistration-P
    x25PLEDXERegistrationTime		TimeInterval,
    x25PLEDXERegistrationCount		INTEGER,
    x25PLEDXERegistrationPermitted	TruthValue,
    -- Miscellaneous conversion
    x25PLEDXEPLEClientMOName		RowPointer,
    -- Miscellaneous conversion
    x25PLEDXEProfile			RowPointer,
    x25PLEDXERowStatus			RowStatus,
}

x25PLEDXEPacketSequencing OBJECT-TYPE
    SYNTAX	INTEGER
    MAX-ACCESS	read-create
    STATUS	current
    DESCRIPTION
	"The modulo of the packet sequence number space using 
	 the Modulo textual convention.  Expressed as a general 
	 format indicator.  ITU-T Rec.  X.25 | ISO/IEC 8208 only 
	 requires support for the values modulo8(1), 
	 modulo128(2) and modulo32768(3), but it is possible 
	 that some future version may extend the range.  A 
	 system is only required to support the settings of 
	 values that are also required by the protocol standard.  
	 A system shall return and error when an attempt is made 
	 to set the value to a value that is not supported by 
	 that system.
	
	 Extended Packet Sequence Numbering and Super Extended 
	 Packet Sequence Numbering are optional user facilities 
	 that require subscription followed by dynamic 
	 invocation on packet switched networks.
	
	 ITU-T Rec. X.25 only permits this value to be set for 
	 an entire DXE.  That is, where the setting applies to 
	 all switched virtual calls and permanent virtual 
	 circuits (logical channels) proviided by the DXE X.25 
	 Packet Layer Entity.  It also permits the packet 
	 sequence numbering scheme to be applied individually to 
	 each logical channel for the DXE X.25 PLE.  When the 
	 network supports the user of multiple modulos at the 
	 same interface, for virtual calls the selection is made 
	 by signalling of the GFI, for permanent virtual 
	 circuits, the modulo is established by subscription."
    REFERENCE
	"ITU-T Rec. X.283 | ISO/IEC 10733 : x25PLE, 
	     packetSequencing.
	 ITU-T Rec. X.7, Clause 6.1.3.1, 6.1.3.2."
    ::= { x25PLEDXEEntry 1 }

x25PLEDXEMaxActiveCircuits OBJECT-TYPE
    SYNTAX	MaxActiveCircuits
    MAX-ACCESS	read-create
    STATUS	current
    DESCRIPTION
	"The maximum number of active circuits permitted on this 
	 X.25 PLE.  When the value zero(0) is specified, the 
	 maximum number of active circuits shall be limited only 
	 by the resources available to the entity."
    REFERENCE
	"ITU-T Rec. X.283 | ISO/IEC 10733 : x25PLE 
	     maxActiveCircuits."
    DEFVAL	{ 0 }
    ::= { x25PLEDXEEntry 2 }

x25PLEDXECallDeflectionSubscription OBJECT-TYPE
    SYNTAX	TruthValue
    MAX-ACCESS	read-create
    STATUS	current
    DESCRIPTION
	"The subscription of the call deflection facility as 
	 described in ITU-T Rec. X.25 | ISO/IEC 8208.  Expressed 
	 as a boolean where a value of true(1) indicates 
	 subscription and a value of false(2) indicates 
	 non-subscription.
	
	 Call Deflection Subscription is an optional user 
	 facility that requires subscription followed by dynamic 
	 invocation on packet switched networks.
	 "
    REFERENCE
	"ITU-T Rec. X.283 | ISO/IEC 10733 : x25PLE 
	     callDeflectionSubscription.
	 ITU-T Rec. X.7, Clause 6.4.2.1."
    ::= { x25PLEDXEEntry 3 }

x25PLEDXERestartTime OBJECT-TYPE
    SYNTAX	TimeInterval
    MAX-ACCESS	read-create
    STATUS	current
    DESCRIPTION
	"Specifies the value for Timer T20 (Restart Request 
	 Response Timer) in centiseconds (displayed in seconds).  
	 The default value is 18000 (180 seconds)."
    REFERENCE
	"ITU-T Rec. X.283 | ISO/IEC 10733 : x25PLE restartTime.
	 ITU-T Rec. X.25 | ISO/IEC 8208 : Timer T20."
    DEFVAL	{ 18000 } -- 180 seconds
    ::= { x25PLEDXEEntry 4 }

x25PLEDXERestartCount OBJECT-TYPE
    SYNTAX	INTEGER
    MAX-ACCESS	read-create
    STATUS	current
    DESCRIPTION
	"Specifies the value for Count R20 (Restart Request 
	 Retranmission Count) in retransmissions.  The default 
	 value is one (1) retransmission."
    REFERENCE
	"ITU-T Rec. X.283 | ISO/IEC 10733 : x25PLE restartCount.
	 ITU-T Rec. X.25 | ISO/IEC 8208 : Count R20."
    ::= { x25PLEDXEEntry 5 }

x25PLEDXEMinimumRecallTimer OBJECT-TYPE
    SYNTAX	TimeInterval
    UNITS	"seconds"
    MAX-ACCESS	read-create
    STATUS	current
    DESCRIPTION
	"Specifies the minimum time, in centiseconds (displayed 
	 in seconds), before recall is permitted.  This timer 
	 determines the minimum time interval which shall elapse 
	 following an unsuccessful first call attempt before a 
	 subsequent call attempt is permitted.  There is not 
	 default value and a value must be specified at 
	 creation."
    REFERENCE
	"ITU-T Rec. X.283 | ISO/IEC 10733 : x25PLE 
	     minimumRecallTimer."
    ::= { x25PLEDXEEntry 6 }

-- PACKAGE onlineRegistration-P
x25PLEDXERegistrationTime OBJECT-TYPE
    SYNTAX	TimeInterval
    UNITS	"seconds"
    MAX-ACCESS	read-create
    STATUS	current
    DESCRIPTION
	"Specifies the value for Timer T28 (Registration Request 
	 Response Timer) in centiseconds (displayed in seconds).  
	 The default value is 30000 (300 seconds)."
    REFERENCE
	"ITU-T Rec. X.283 | ISO/IEC 10733 : x25PLE 
	     registrationRequestTime."
    DEFVAL	{ 30000 } -- 300 seconds
    ::= { x25PLEDXEEntry 7 }

x25PLEDXERegistrationCount OBJECT-TYPE
    SYNTAX	INTEGER
    UNITS	"retransmissions"
    MAX-ACCESS	read-create
    STATUS	current
    DESCRIPTION
	"Specifies the value for Count R28 (Registration Request 
	 Retransmission Count) in retransmissions.  The default 
	 value is one (1) retranmission."
    REFERENCE
	"ITU-T Rec. X.283 | ISO/IEC 10733 : x25PLE 
	     registrationRequestCount."
    DEFVAL	{ 1 }
    ::= { x25PLEDXEEntry 8 }

x25PLEDXERegistrationPermitted OBJECT-TYPE
    SYNTAX	TruthValue
    MAX-ACCESS	read-create
    STATUS	current
    DESCRIPTION
	"Specifies the use of the online facility registration.  
	 When true(1), online facility registration is 
	 permitted; when false(2), not permitted.  The default 
	 is false(2)."
    REFERENCE
	"ITU-T Rec. X.283 | ISO/IEC 10733 : x25PLE 
	     registrationPermitted."
    DEFVAL	{ 2 } -- false(2)
    ::= { x25PLEDXEEntry 9 }

x25PLEDXEPLEClientMOName OBJECT-TYPE
    SYNTAX	RowPointer
    MAX-ACCESS	read-create
    STATUS	current
    DESCRIPTION
	"Specifies the name of the local disinguished name, 
	 using the RowPointer textual convention, of the client 
	 managed object.  For OSI stacks, this should normally 
	 be either a transport layer MO or a CLNS MO.  This is 
	 useful for the NULL subset only (e.g., where all SVC 
	 default to the same default user, i.e., the transport 
	 layer user.)  Except for the NULL subset it should be 
	 left as NULL, the default."
    REFERENCE
	"ISO/IEC 10733 : x25PLE pLEClientMOName."
    ::= { x25PLEDXEEntry 10 }

-- Miscellaneous
x25PLEDXEProfile OBJECT-TYPE
    SYNTAX	RowPointer
    MAX-ACCESS	read-create
    STATUS	current
    DESCRIPTION
	""
    REFERENCE
	"ITU-T Rec. X.283 | ISO/IEC 10733 : x25PLE."
    ::= { x25PLEDXEEntry 11 }

x25PLEDXERowStatus OBJECT-TYPE
    SYNTAX	RowStatus
    MAX-ACCESS	read-create
    STATUS	current
    DESCRIPTION
	""
    REFERENCE
	"ITU-T Rec. X.283 | ISO/IEC 10733 : x25PLE."
    ::= { x25PLEDXEEntry 12 }


x25PLEIVMODTE OBJECT IDENTIFIER
    ::= { x25PLPTables 6 }

x25PLEIVMODTETable OBJECT-TYPE
    SYNTAX	SEQUENCE OF X25PLEIVMODTEEntry
    MAX-ACCESS	not-accessible
    STATUS	current
    DESCRIPTION
	""
    REFERENCE
	"ITU-T Rec. X.283 | ISO/IEC 10733 : x25PLEIVMO-DTE MOC."
    ::= { x25PLEIVMODTE 1 }

x25PLEIVMODTEEntry OBJECT-TYPE
    SYNTAX	X25PLEIVMODTEEntry
    MAX-ACCESS	not-accessible
    STATUS	current
    DESCRIPTION
	"There may be multiple instances of the x25PLEIVMO-DTE 
	 in a system.  An x25PLEIVMO-DTE may be used to supply 
	 initial values for the attributes of the x25PLE-DTE MO.  
	 Different instances of x25PLEIVMO-DTE may contain 
	 different intial values.  Its defintion permits it to 
	 be created and deleted explicitly by management 
	 operation."
    REFERENCE
	"ITU-T Rec. X.283 | ISO/IEC 10733 : x25PLEIVMO-DTE MO."
    INDEX	{
		    x25PLEId,	    -- shared index (CONTAINED BY)
		    x25PLEIVMOId    -- shared index (DERIVED FROM)
		}
    ::= { x25PLEIVMODTETable 1 }

X25PLEIVMODTEEntry ::= SEQUENCE {
    x25PLEIVMODTECallDeflectionSubscription	TruthValue,		-- SVC ONLY
    x25PLEIVMODTECallTime			TimeInterval,		-- SVC ONLY
    x25PLEIVMODTEClearTime			TimeInterval,		-- SVC ONLY
    x25PLEIVMODTEClearCount			INTEGER,		-- SVC ONLY
    x25PLEIVMODTEPacketSequencing		Modulo,
    x25PLEIVMODTEInterruptTime			TimeInterval,
    x25PLEIVMODTEMaxActiveCircuits		MaxActiveCircuits,
    x25PLEIVMODTEMinimumRecallTimer		TimeInterval,
    x25PLEIVMODTEResetTime			TimeInterval,		-- SVC ONLY
    x25PLEIVMODTEResetCount			INTEGER,		-- SVC ONLY
    x25PLEIVMODTERestartTime			TimeInterval,
    x25PLEIVMODTERestartCount			INTEGER,
    -- PACKAGE receivingWindowRotationRecoveryProcedures-P
    x25PLEIVMODTEWindowTime			TimeInterval,
    -- PACKAGE transmittingWindowRotationRecoveryProcedures-P
    x25PLEIVMODTEDataTime			TimeInterval,
    -- PACKAGE packetRetransmissionProcedures-P
    x25PLEIVMODTEDataCount			INTEGER,
    x25PLEIVMODTERejectTime			TimeInterval,
    x25PLEIVMODTERejectCount			INTEGER,
    -- PACKAGE onlineRegistration-P
    x25PLEIVMODTERegistrationTime		TimeInterval,
    x25PLEIVMODTERegistrationCount		INTEGER,
    x25PLEIVMODTERegistrationPermitted		TruthValue,
    -- Miscellaneous conversion
    x25PLEIVMODTERowStatus			RowStatus,
}

x25PLEIVMODTECallDeflectionSubscription OBJECT-TYPE
    SYNTAX	TruthValue
    MAX-ACCESS	read-create
    STATUS	current
    DESCRIPTION
	"
	 Call Deflection Subscription is an optional user 
	 facility that requires subscription followed by dynamic 
	 invocation on packet switched networks.
	 "
    REFERENCE
	"ITU-T Rec. X.283 | ISO/IEC 10733 : x25PLEIVMO-DTE, 
	     callDeflectionSubscription.
	 ITU-T Rec. X.7, Clause 6.4.2.1."
    ::= { x25PLEIVMODTEEntry 1 }

x25PLEIVMODTECallTime OBJECT-TYPE
    SYNTAX	TimeInterval
    MAX-ACCESS	read-create
    STATUS	current
    DESCRIPTION
	""
    REFERENCE
	"ITU-T Rec. X.283 | ISO/IEC 10733 : x25PLEIVMO-DTE 
	     callRequestResponseTimer."
    ::= { x25PLEIVMODTEEntry 2 }

x25PLEIVMODTEClearTime OBJECT-TYPE
    SYNTAX	TimeInterval
    MAX-ACCESS	read-create
    STATUS	current
    DESCRIPTION
	""
    REFERENCE
	"ITU-T Rec. X.283 | ISO/IEC 10733 : x25PLEIVMO-DTE
	     clearRequestResponseTimer.
	 ITU-T Rec. X.25 | ISO/IEC 8208 : Timer T23."
    ::= { x25PLEIVMODTEEntry 3 }

x25PLEIVMODTEClearCount OBJECT-TYPE
    SYNTAX	INTEGER
    MAX-ACCESS	read-create
    STATUS	current
    DESCRIPTION
	""
    REFERENCE
	"ITU-T Rec. X.283 | ISO/IEC 10733 : x25PLEIVMO-DTE
	     clearRequestRetransmissionCount.
	 ITU-T Rec. X.25 | ISO/IEC 8208 : Count R23."
    ::= { x25PLEIVMODTEEntry 4 }

x25PLEIVMODTEPacketSequencing OBJECT-TYPE
    SYNTAX	Modulo
    MAX-ACCESS	read-create
    STATUS	current
    DESCRIPTION
	"
	 Extended Packet Sequence Numbering and Super Extended 
	 Packet Sequence Numbering are optional user facilities 
	 that require subscription followed by dynamic 
	 invocation on packet switched networks.
	"
    REFERENCE
	"ITU-T Rec. X.283 | ISO/IEC 10733 : x25PLEIVMO-DTE 
	     extendedPacketSequenceNumbering.
	 ITU-T Rec. X.7, Clause 6.1.3.1, 6.1.3.2."
    ::= { x25PLEIVMODTEEntry 5 }

x25PLEIVMODTEInterruptTime OBJECT-TYPE
    SYNTAX	TimeInterval
    MAX-ACCESS	read-create
    STATUS	current
    DESCRIPTION
	""
    REFERENCE
	"ITU-T Rec. X.283 | ISO/IEC 10733 : x25PLEIVMO-DTE
	     interruptResponseTimer.
	 ITU-T Rec. X.25 | ISO/IEC 8208 : Timer T26."
    ::= { x25PLEIVMODTEEntry 6 }

x25PLEIVMODTEMaxActiveCircuits OBJECT-TYPE
    SYNTAX	MaxActiveCircuits
    MAX-ACCESS	read-create
    STATUS	current
    DESCRIPTION
	""
    REFERENCE
	"ITU-T Rec. X.283 | ISO/IEC 10733 : x25PLEIVMO-DTE."
    ::= { x25PLEIVMODTEEntry 7 }

x25PLEIVMODTEMinimumRecallTimer OBJECT-TYPE
    SYNTAX	TimeInterval
    MAX-ACCESS	read-create
    STATUS	current
    DESCRIPTION
	""
    REFERENCE
	"ITU-T Rec. X.283 | ISO/IEC 10733 : x25PLEIVMO-DTE."
    ::= { x25PLEIVMODTEEntry 8 }

x25PLEIVMODTEResetTime OBJECT-TYPE
    SYNTAX	TimeInterval
    MAX-ACCESS	read-create
    STATUS	current
    DESCRIPTION
	""
    REFERENCE
	"ITU-T Rec. X.283 | ISO/IEC 10733 : x25PLEIVMO-DTE
	     resetRequestResponseTimer.
	 ITU-T Rec. X.25 | ISO/IEC 8208 : Timer T22"
    ::= { x25PLEIVMODTEEntry 9 }

x25PLEIVMODTEResetCount OBJECT-TYPE
    SYNTAX	INTEGER
    MAX-ACCESS	read-create
    STATUS	current
    DESCRIPTION
	""
    REFERENCE
	"ITU-T Rec. X.283 | ISO/IEC 10733 : x25PLEIVMO-DTE
	     resetRequestRetransmissionCount.
	 ITU-T Rec. X.25 | ISO/IEC 8208 : Count R22."
    ::= { x25PLEIVMODTEEntry 10 }

x25PLEIVMODTERestartTime OBJECT-TYPE
    SYNTAX	TimeInterval
    MAX-ACCESS	read-create
    STATUS	current
    DESCRIPTION
	""
    REFERENCE
	"ITU-T Rec. X.283 | ISO/IEC 10733 : x25PLEIVMO-DTE
	     restartRequestResponseTimer.
	 ITU-T Rec. X.25 | ISO/IEC 8208 : Timer T20."
    ::= { x25PLEIVMODTEEntry 11 }

x25PLEIVMODTERestartCount OBJECT-TYPE
    SYNTAX	INTEGER
    MAX-ACCESS	read-create
    STATUS	current
    DESCRIPTION
	""
    REFERENCE
	"ITU-T Rec. X.283 | ISO/IEC 10733 : x25PLEIVMO-DTE 
	     restartRequestRetranmissionCount."
    ::= { x25PLEIVMODTEEntry 12 }

-- PACKAGE receivingWindowRotationRecoveryProcedures-P
x25PLEIVMODTEWindowTime OBJECT-TYPE
    SYNTAX	TimeInterval
    MAX-ACCESS	read-create
    STATUS	current
    DESCRIPTION
	""
    REFERENCE
	"ITU-T Rec. X.283 | ISO/IEC 10733 : x25PLEIVMO-DTE 
	     windowStatusTransmissionTimer."
    ::= { x25PLEIVMODTEEntry 13 }

-- PACKAGE transmittingWindowRotationRecoveryProcedures-P
x25PLEIVMODTEDataTime OBJECT-TYPE
    SYNTAX	TimeInterval
    MAX-ACCESS	read-create
    STATUS	current
    DESCRIPTION
	""
    REFERENCE
	"ITU-T Rec. X.283 | ISO/IEC 10733 : x25PLEIVMO-DTE 
	     windowRotationTimer."
    ::= { x25PLEIVMODTEEntry 14 }

x25PLEIVMODTEDataCount OBJECT-TYPE
    SYNTAX	INTEGER
    MAX-ACCESS	read-create
    STATUS	current
    DESCRIPTION
	""
    REFERENCE
	"ITU-T Rec. X.283 | ISO/IEC 10733 : x25PLEIVMO-DTE 
	     dataPacketRetransmissionCount."
    ::= { x25PLEIVMODTEEntry 15 }

-- PACKAGE packetRetransmissionProcedures-P
x25PLEIVMODTERejectTime OBJECT-TYPE
    SYNTAX	TimeInterval
    MAX-ACCESS	read-create
    STATUS	current
    DESCRIPTION
	""
    REFERENCE
	"ITU-T Rec. X.283 | ISO/IEC 10733 : x25PLEIVMO-DTE 
	     rejectResponseTimer."
    ::= { x25PLEIVMODTEEntry 16 }

x25PLEIVMODTERejectCount OBJECT-TYPE
    SYNTAX	INTEGER
    MAX-ACCESS	read-create
    STATUS	current
    DESCRIPTION
	""
    REFERENCE
	"ITU-T Rec. X.283 | ISO/IEC 10733 : x25PLEIVMO-DTE 
	     rejectRetransmissionCount."
    ::= { x25PLEIVMODTEEntry 17 }

-- PACKAGE onlineRegistration-P
x25PLEIVMODTERegistrationTime OBJECT-TYPE
    SYNTAX	TimeInterval
    MAX-ACCESS	read-create
    STATUS	current
    DESCRIPTION
	""
    REFERENCE
	"ITU-T Rec. X.283 | ISO/IEC 10733 : x25PLEIVMO-DTE 
	     registrationRequestResponseTimer."
    ::= { x25PLEIVMODTEEntry 18 }

x25PLEIVMODTERegistrationCount OBJECT-TYPE
    SYNTAX	INTEGER
    MAX-ACCESS	read-create
    STATUS	current
    DESCRIPTION
	""
    REFERENCE
	"ITU-T Rec. X.283 | ISO/IEC 10733 : x25PLEIVMO-DTE 
	     registrationRequestRetransmissionCount."
    ::= { x25PLEIVMODTEEntry 19 }

x25PLEIVMODTERegistrationPermitted OBJECT-TYPE
    SYNTAX	TruthValue
    MAX-ACCESS	read-create
    STATUS	current
    DESCRIPTION
	""
    REFERENCE
	"ITU-T Rec. X.283 | ISO/IEC 10733 : x25PLEIVMO-DTE."
    ::= { x25PLEIVMODTEEntry 20 }

-- Miscellaneous
x25PLEIVMODTERowStatus OBJECT-TYPE
    SYNTAX	RowStatus
    MAX-ACCESS	read-create
    STATUS	current
    DESCRIPTION
	""
    REFERENCE
	"ITU-T Rec. X.283 | ISO/IEC 10733 : x25PLEIVMO-DTE."
    ::= { x25PLEIVMODTEEntry 21 }


x25PLEIVMODCE OBJECT IDENTIFIER
    ::= { x25PLPTables 7 }

x25PLEIVMODCETable OBJECT-TYPE
    SYNTAX	SEQUENCE OF X25PLEIVMODCEEntry
    MAX-ACCESS	not-accessible
    STATUS	current
    DESCRIPTION
	""
    REFERENCE
	"ITU-T Rec. X.283 | ISO/IEC 10733 : x25PLEIVMO-DCE MOC."
    ::= { x25PLEIVMODCE 1 }

x25PLEIVMODCEEntry OBJECT-TYPE
    SYNTAX	X25PLEIVMODCEEntry
    MAX-ACCESS	not-accessible
    STATUS	current
    DESCRIPTION
	"There may be multiple instances of the x25PLEIVMO-DCE 
	 in a system.  An x25PLEIVMO-DCE may be used to supply 
	 initial values for the attributes of the x25PLE-DCE MO.  
	 Different instances of x25PLEIVMO-DCE may contain 
	 different intial values.  Its defintion permits it to 
	 be created and deleted explicitly by management 
	 operation."
    REFERENCE
	"ITU-T Rec. X.283 | ISO/IEC 10733 : x25PLEIVMO-DCE MO."
    INDEX	{
		    x25PLEId,	    -- shared index (CONTAINED BY)
		    x25PLEIVMOId    -- shared index (DERIVED FROM)
		}
    ::= { x25PLEIVMODCETable 1 }

X25PLEIVMODCEEntry ::= SEQUENCE {
    x25PLEIVMODCERowStatus	RowStatus,
}

x25PLEIVMODCERowStatus OBJECT-TYPE
    SYNTAX	RowStatus
    MAX-ACCESS	read-create
    STATUS	current
    DESCRIPTION
	""
    REFERENCE
	"ITU-T Rec. X.283 | ISO/IEC 10733 : x25PLEIVMO-DCE."
    ::= { x25PLEIVMODCEEntry 1 }

x25PLEIVMODXE OBJECT IDENTIFIER
    ::= { x25PLPTables 8 }

x25PLEIVMODXETable OBJECT-TYPE
    SYNTAX	SEQUENCE OF X25PLEIVMODXEEntry
    MAX-ACCESS	not-accessible
    STATUS	current
    DESCRIPTION
	""
    REFERENCE
	"ISO/IEC 10733 : x25PLEIVMO MOC."
    ::= { x25PLEIVMODXE 1 }

x25PLEIVMODXEEntry OBJECT-TYPE
    SYNTAX	X25PLEIVMODXEEntry
    MAX-ACCESS	not-accessible
    STATUS	current
    DESCRIPTION
	""
    REFERENCE
	"ISO/IEC 10733 : x25PLEIVMO MO."
    INDEX	{
		    x25PLEId,	    -- shared index (CONTAINED BY)
		    x25PLEIVMOId    -- shared index (DERIVED FROM)
		}
    ::= { x25PLEIVMODXETable 1 }

X25PLEIVMODXEEntry ::= SEQUENCE {
    x25PLEIVMODTECallDeflectionSubscription  TruthValue,
    x25PLEIVMODTEMaxActiveCircuits	     MaxActiveCircuits,
    x25PLEIVMODTERestartTime		     TimeInterval,
    x25PLEIVMODTEMinimumRecallTimer	     TimeInterval,
    x25PLEIVMODTERestartCount		     INTEGER,
    x25PLEIVMODTEPacketSequencing	     INTEGER,
    x25PLEIVMODTERegistrationTime	     TimeInterval,
    x25PLEIVMODTERegistrationCount	     INTEGER,
    x25PLEIVMODTERegistrationPermitted	     TruthValue,
}

x25PLEIVMODTECallDeflectionSubscription OBJECT-TYPE
    SYNTAX	TruthValue
    MAX-ACCESS	read-create
    STATUS	current
    DESCRIPTION
	"
	 Call Deflection Subscription is an optional user 
	 facility that requires subscription followed by dynamic 
	 invocation on packet switched networks.
	 "
    REFERENCE
	"ITU-T Rec. X.283 | ISO/IEC 10733 : x25PLEIVMO-DTE, 
	     callDeflectionSubscription.
	 ITU-T Rec. X.7, Clause 6.4.2.1."
    ::= { x25PLEIVMODXEEntry 1 }

x25PLEIVMODTEMaxActiveCircuits OBJECT-TYPE
    SYNTAX	MaxActiveCircuits
    MAX-ACCESS	read-create
    STATUS	current
    DESCRIPTION
	""
    REFERENCE
	"ITU-T Rec. X.283 | ISO/IEC 10733 : x25PLEIVMO-DTE."
    ::= { x25PLEIVMODXEEntry 2 }

x25PLEIVMODTERestartTime OBJECT-TYPE
    SYNTAX	TimeInterval
    MAX-ACCESS	read-create
    STATUS	current
    DESCRIPTION
	""
    REFERENCE
	"ITU-T Rec. X.283 | ISO/IEC 10733 : x25PLEIVMO-DTE."
    ::= { x25PLEIVMODXEEntry 3 }

x25PLEIVMODTEMinimumRecallTimer OBJECT-TYPE
    SYNTAX	TimeInterval
    MAX-ACCESS	read-create
    STATUS	current
    DESCRIPTION
	""
    REFERENCE
	"ITU-T Rec. X.283 | ISO/IEC 10733 : x25PLEIVMO-DTE."
    ::= { x25PLEIVMODXEEntry 4 }

x25PLEIVMODTERestartCount OBJECT-TYPE
    SYNTAX	INTEGER
    MAX-ACCESS	read-create
    STATUS	current
    DESCRIPTION
	""
    REFERENCE
	"ITU-T Rec. X.283 | ISO/IEC 10733 : x25PLEIVMO-DTE
	     restartRequestRetransmissionCount.
	 ITU-T Rec. X.25 | ISO/IEC 8208 : Count R20."
    ::= { x25PLEIVMODXEEntry 5 }

x25PLEIVMODTEPacketSequencing OBJECT-TYPE
    SYNTAX	INTEGER
    MAX-ACCESS	read-create
    STATUS	current
    DESCRIPTION
	"
	 Extended Packet Sequence Numbering and Super Extended 
	 Packet Sequence Numbering are optional user facilities 
	 that require subscription followed by dynamic 
	 invocation on packet switched networks.
	"
    REFERENCE
	"ITU-T Rec. X.283 | ISO/IEC 10733 : x25PLEIVMO-DTE, 
	     packetSequencing.
	 ITU-T Rec. X.7, Clause 6.1.3.1, 6.1.3.2."
    ::= { x25PLEIVMODXEEntry 6 }

-- PACKAGE onlineRegistration-P
x25PLEIVMODTERegistrationTime OBJECT-TYPE
    SYNTAX	TimeInterval
    MAX-ACCESS	read-create
    STATUS	current
    DESCRIPTION
	""
    REFERENCE
	"ITU-T Rec. X.283 | ISO/IEC 10733 : x25PLEIVMO-DTE 
	     registrationRequestTime."
    ::= { x25PLEIVMODXEEntry 7 }

x25PLEIVMODTERegistrationCount OBJECT-TYPE
    SYNTAX	INTEGER
    MAX-ACCESS	read-create
    STATUS	current
    DESCRIPTION
	""
    REFERENCE
	"ITU-T Rec. X.283 | ISO/IEC 10733 : x25PLEIVMO-DTE."
    ::= { x25PLEIVMODXEEntry 8 }

x25PLEIVMODTERegistrationPermitted OBJECT-TYPE
    SYNTAX	TruthValue
    MAX-ACCESS	read-create
    STATUS	current
    DESCRIPTION
	""
    REFERENCE
	"ITU-T Rec. X.283 | ISO/IEC 10733 : x25PLEIVMO-DTE."
    ::= { x25PLEIVMODXEEntry 9 }


x25VC OBJECT IDENTIFIER
    ::= { x25PLPTables 9 }

x25VCTable OBJECT-TYPE
    SYNTAX	SEQUENCE OF X25VCEntry
    MAX-ACCESS	not-accessible
    STATUS	current
    DESCRIPTION
	"This MO Class is never instantiated.  It services as a 
	 generic Virtual Circuit MO from which both the Virtual 
	 Circuit DTE and Virtual Circuit DCE MOs are derived.  
	 Note that the values of the virtualCircuitId naming 
	 attribute are required to be unique across all 
	 instances of MOs derived from thi which have a common 
	 superior.
	
	 Objects in this table generate objectCreation and 
	 objectDeletion notifications."
    REFERENCE
	"ITU-T Rec. X.283 | ISO/IEC 10733 : virtualCircuit MOC."
    ::= { x25VC 1 }

x25VCEntry OBJECT-TYPE
    SYNTAX	X25VCEntry
    MAX-ACCESS	not-accessible
    STATUS	current
    DESCRIPTION
	"Entries in this table are not created explicitly by 
	 management stations.  When a entry is created in the 
	 x25VCDTETable, x25VCDCETable or x25VCDXETable, a entry 
	 appears in this table with the same indices.  When a 
	 entry is removed from one of those tables, it is also 
	 removed from this table.
	
	 Each entry in this table provides basic information 
	 necessary for operation of the X.25 PLP on any virtual 
	 circuit, regardless of interface mode and regardless of 
	 switched virtual calls or permanent virtual circuits.
	
	 Note that this table is not indexed on logical channel, 
	 but on x25VCId.  For SVC this is because a switched 
	 virtual call exists before and after it has been 
	 assigned to a logical channel."
    REFERENCE
	"ITU-T Rec. X.283 | ISO/IEC 10733 : virtualCircuit MO."
    INDEX	{
		    x25PLEId,	-- shared index (CONTAINED BY)
		    x25VCId	-- (BASE CLASS INSTANCE)
		}
    ::= { x25VCTable 1 }

X25VCEntry ::= SEQUENCE {
    x25VCId				SimpleNameType,
    x25VCLogicalChannel			LogicalChannelNumber,
    x25VCPacketSequencing		Modulo,
    x25VCPacketSizeIncoming		PacketSize,
    x25VCPacketSizeOutgoing		PacketSize,
    x25VCWindowSizeIncoming		WindowSize,
    x25VCWindowSizeOutgoing		WindowSize,
    x25VCThroughputClassIncoming	ThroughputClass,
    x25VCThroughputClassOutgoing	ThroughputClass,
}

x25VCId OBJECT-TYPE
    SYNTAX	SimpleNameType
    MAX-ACCESS	not-accessible
    STATUS	current
    DESCRIPTION
	""
    REFERENCE
	"ITU-T Rec. X.283 | ISO/IEC 10733 : virtualCall."
    ::= { x25VCEntry 1 }

x25VCLogicalChannel OBJECT-TYPE
    SYNTAX	LogicalChannelNumber
    MAX-ACCESS	read-only
    STATUS	current
    DESCRIPTION
	"Indicates the logical channel number currently assigned 
	 to a switched virtual call or permanent virtual 
	 circuit."
    REFERENCE
	"ITU-T Rec. X.283 | ISO/IEC 10733 : virtualCall 
	     logicalChannel."
    DEFVAL	{ 0 }
    ::= { x25VCEntry 2 }

x25VCPacketSequencing OBJECT-TYPE
    SYNTAX	Modulo
    MAX-ACCESS	read-write
    STATUS	current
    DESCRIPTION
	"The packet sequenceing modulo used by the switched 
	 virtual call (SVC) or permanent virtual circuit (PVC) 
	 using the Modulo textual convention.  When set to 
	 default(0), it specifies that the packe sequencing 
	 modulo applied to the X.25 Packet Layer Entity (PLE) 
	 from the x25PLETable is to be used.  Otherwise, it is 
	 pecified as modulo 8, modulo 128 or modulo 32768 
	 operation.  Setting this value to other than default(0) 
	 has the effect of specifying the packet sequencing 
	 modulo on a call or circuit basis.  This object is only 
	 writable for a PVC, and then only when the PVC is not 
	 in an 'enabled' operational state.
	
	 Extended Packet Sequence Numbering and Super Extended 
	 Packet Sequence Numbering are optional user facilities 
	 that require subscription followed by dynamic 
	 invocation on packet switched networks."
    REFERENCE
	"ITU-T Rec. X.25 Clause 4.4.1.1.
	 ITU-T Rec. X.7, Clause 6.1.3.1, 6.1.3.2."
    DEFVAL	{ 0 }
    ::= { x25VCEntry 3 }

--  x25VCPacketSizes
x25VCPacketSizeIncoming OBJECT-TYPE
    SYNTAX	PacketSize
    MAX-ACCESS	read-write
    STATUS	current
    DESCRIPTION
	"The incoming packet size used on the switched virtual 
	 call (SVC) or permanent virtual circuit (PVC) using the 
	 PacketSize textual convention.  When set to default(0), 
	 the incoming packet size associated with the X.25 
	 Packet Layer Entity (PLE) from the x25PLETable is to be 
	 used.  Otherwise, it is specified as a power of two 
	 between 16 and 4096 inclusive.  Setting this value to 
	 other than the default has the effect of specifying the 
	 incoming packet size on a call or circuit basis.  This 
	 object is only writable for a PVC, and then only when 
	 the PVC is not in an 'enabled' operational state."
    REFERENCE
	"ITU-T Rec. X.283 | ISO/IEC 10733 : virtualCall 
	     packetSizes."
    ::= { x25VCEntry 4 }

x25VCPacketSizeOutgoing OBJECT-TYPE
    SYNTAX	PacketSize
    MAX-ACCESS	read-write
    STATUS	current
    DESCRIPTION
	"The outgoing packet size used on the switched virtual 
	 call (SVC) or permanent virtual circuit (PVC) using the 
	 PacketSize textual convention.  When set to default(0), 
	 the outgoing packet size associated with the X.25 
	 Packet Layer Entity (PLE) from the x25PLETable is to be 
	 used.  Otherwise, it is specified as a power of two 
	 between 16 and 4096 inclusive.  Setting this value to 
	 other than the default has the effect of specifying the 
	 outgoing packet size on a call or circuit basis.  This 
	 object is only writable for a PVC, and then only when 
	 the PVC is not in an 'enabled' operational state."
    REFERENCE
	"ITU-T Rec. X.283 | ISO/IEC 10733 : virtualCall 
	     packetSizes."
    ::= { x25VCEntry 5 }

--  x25VCWindowSizes
x25VCWindowSizeIncoming OBJECT-TYPE
    SYNTAX	WindowSize
    MAX-ACCESS	read-write
    STATUS	current
    DESCRIPTION
	"The incoming window size used on the switched virtual 
	 call (SVC) or permanent virtual circuit (PVC) using the 
	 WindowSize textual convention.  When set to default(0), 
	 the incoming window size associated with the X.25 
	 Packet Layer Entity (PLE) from the x25PLETable is to be 
	 used.  Otherwise, it is specified as a value between 1 
	 and the modulo minus one.  Setting this value to other 
	 than the default has the effect of specifying the 
	 incoming window size on a call or circuit basis.  This 
	 object is only writable for a PVC, and then only when 
	 the PVC is not in an 'enabled' operational state."
    REFERENCE
	"ITU-T Rec. X.283 | ISO/IEC 10733 : virtualCall 
	     windowSizes."
    ::= { x25VCEntry 6 }

x25VCWindowSizeOutgoing OBJECT-TYPE
    SYNTAX	WindowSize
    MAX-ACCESS	read-write
    STATUS	current
    DESCRIPTION
	"The outgoing window size used on the switched virtual 
	 call (SVC) or permanent virtual circuit (PVC) using the 
	 WindowSize textual convention.  When set to default(0), 
	 the outgoing window size associated with the X.25 
	 Packet Layer Entity (PLE) from the x25PLETable is to be 
	 used.  Otherwise, it is specified as a value between 1 
	 and the modulo minus one.  Setting this value to other 
	 than the default has the effect of specifying the 
	 outgoing window size on a call or circuit basis.  This 
	 object is only writable for a PVC, and then only when 
	 the PVC is not in an 'enabled' operational state."
    REFERENCE
	"ITU-T Rec. X.283 | ISO/IEC 10733 : virtualCall 
	     windowSizes."
    ::= { x25VCEntry 7 }

--  x25VCThroughputClasses
x25VCThroughputClassIncoming OBJECT-TYPE
    SYNTAX	ThroughputClass
    MAX-ACCESS	read-write
    STATUS	current
    DESCRIPTION
	"The incoming throughput class on the switched virtual 
	 call (SVC) or permanent virtual circuit (PVC) using the 
	 ThroughputClass textual convention.  When set to 
	 default(0), the incoming throughput class associated 
	 with the X.25 Packet Layer Entity (PLE) from the 
	 x25PLETable is to be used.  Otherwise, it is specified 
	 as a value between 3 and 15 for basic throughput classes 
	 and 16 and 44 for extended throughput clases.  Setting 
	 this value to other than the default has the effect of 
	 specifying the incoming throughput class on a call or 
	 circuit basis.  This object is only writable for a PVC, 
	 and then only when the PVC is not in an 'enabled' 
	 operational state."
    REFERENCE
	"ITU-T Rec. X.283 | ISO/IEC 10733 : virtualCall 
	     throughputClasses."
    ::= { x25VCEntry 8 }

x25VCThroughputClassOutgoing OBJECT-TYPE
    SYNTAX	ThroughputClass
    MAX-ACCESS	read-write
    STATUS	current
    DESCRIPTION
	"The outgoing throughput class on the switched virtual 
	 call (SVC) or permanent virtual circuit (PVC) using the 
	 ThroughputClass textual convention.  When set to 
	 default(0), the outgoing throughput class associated 
	 with the X.25 Packet Layer Entity (PLE) from the 
	 x25PLETable is to be used.  Otherwise, it is specified 
	 as a value between 3 and 15 for basic throughput classes 
	 and 16 and 44 for extended throughput clases.  Setting 
	 this value to other than the default has the effect of 
	 specifying the outgoing throughput class on a call or 
	 circuit basis.  This object is only writable for a PVC, 
	 and then only when the PVC is not in an 'enabled' 
	 operational state."
    REFERENCE
	"ITU-T Rec. X.283 | ISO/IEC 10733 : virtualCall 
	     throughputClasses."
    ::= { x25VCEntry 9 }


x25VCDTE OBJECT IDENTIFIER
    ::= { x25PLPTables 10 }

x25VCDTETable OBJECT-TYPE
    SYNTAX	SEQUENCE OF X25VCDTEEntry
    MAX-ACCESS	not-accessible
    STATUS	current
    DESCRIPTION
	"This MO Classs in never instantiated.  It serves as a 
	 generic Virtual Circuit DTE MO from which both the 
	 Virtual Call DTE and Permanent Virtual Circuit DTE MOs 
	 are derived.  Note that the values of the 
	 virtualCircuitId naming attribute are required to be 
	 unique across all instances of MOs derived from this 
	 which have a common superior."
    REFERENCE
	"ITU-T Rec. X.283 | ISO/IEC 10733 : virtualCircuit-DTE MOC."
    ::= { x25VCDTE 1 }

x25VCDTEEntry OBJECT-TYPE
    SYNTAX	X25VCDTEEntry
    MAX-ACCESS	not-accessible
    STATUS	current
    DESCRIPTION
	"Entries in this table are not explicitly created by 
	 management stations.  They are created automatically by 
	 the agent whenever an entry in the x25SVCDTETable or 
	 x25PVCDTETable are created; and destroyed whenever the  
	 corresponding entry is destroyed."
    REFERENCE
	"ITU-T Rec. X.283 | ISO/IEC 10733 : virtualCircuit-DTE MO."
    INDEX	{
		    x25PLEId,	-- shared index (CONTAINED BY)
		    x25VCId	-- shared index (DERIVED FROM)
		}
    ::= { x25VCDTETable 1 }

X25VCDTEEntry ::= SEQUENCE {
    x25VCDTEOctetsReceived		Counter64,
    x25VCDTEOctetsSent			Counter64,
    x25VCDTEDataPacketsReceived		Counter64,
    x25VCDTEDataPacketsSent		Counter64,
    x25VCDTEDataTimeouts		Counter64,
    x25VCDTEInterruptPacketsReceived	Counter64,
    x25VCDTEInterruptPacketsSent	Counter64,
    x25VCDTEInterruptTimeouts		Counter64,
    x25VCDTEProviderResets		Counter64,
    x25VCDTERemoteResets		Counter64,
    x25VCDTEResetTimeouts		Counter64,
}

x25VCDTEOctetsReceived OBJECT-TYPE
    SYNTAX	Counter64
    MAX-ACCESS	read-only
    STATUS	current
    DESCRIPTION
	"This is the value of the count of the number of user 
	 data octets succesfully received for this switched 
	 virtual call or permanent virtual circuit.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : virtualCall-DTE 
	     octetsRecevedCounter
	 ITU-T Rec. X.721 | ISO/IEC 10165-2 : 
	     octetsReceivedCounter."
    ::= { x25VCDTEEntry 1 }

x25VCDTEOctetsSent OBJECT-TYPE
    SYNTAX	Counter64
    MAX-ACCESS	read-only
    STATUS	current
    DESCRIPTION
	"This is the value of the count of the number of user 
	 data octets successfully sent for this switched virtual 
	 call or permanent virtual circuit.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : virtualCall-DTE 
	     octetsSentCounter
	 ITU-T Rec. X.721 | ISO/IEC 10165-2 : 
	     octetsSentCoutner."
    ::= { x25VCDTEEntry 2 }

x25VCDTEDataPacketsReceived OBJECT-TYPE
    SYNTAX	Counter64
    MAX-ACCESS	read-only
    STATUS	current
    DESCRIPTION
	"The value of the count of the number of data packets 
	 received for this switched virtual call or permanent 
	 virtual circuit."
    REFERENCE
	"ITU-T Rec. X.283 | ISO/IEC 10733 : virtualCall-DTE 
	     dataPacketsReceived."
    ::= { x25VCDTEEntry 3 }

x25VCDTEDataPacketsSent OBJECT-TYPE
    SYNTAX	Counter64
    MAX-ACCESS	read-only
    STATUS	current
    DESCRIPTION
	"The value of the count of the number of data packets 
	 sent for this switched virtual call or permanent 
	 virtual circuit."
    REFERENCE
	"ITU-T Rec. X.283 | ISO/IEC 10733 : virtualCall-DTE 
	     dataPacketsSent."
    ::= { x25VCDTEEntry 4 }

x25VCDTEDataTimeouts OBJECT-TYPE
    SYNTAX	Counter64
    MAX-ACCESS	read-only
    STATUS	current
    DESCRIPTION
	"The value of the count of the number of times that 
	 Timer 25 expired, for this switched virtual call or 
	 permanent virtual circuit.  When the option is not 
	 implemented, this object always returns zero (0)."
    REFERENCE
	"ITU-T Rec. X.283 | ISO/IEC 10733 : virtualCall-DTE 
	     dataRetransmissionTimerExpiries.
	 ITU-T Rec. X.25 | ISO/IEC 8208 : Timer T25."
    ::= { x25VCDTEEntry 5 }

x25VCDTEInterruptPacketsReceived OBJECT-TYPE
    SYNTAX	Counter64
    MAX-ACCESS	read-only
    STATUS	current
    DESCRIPTION
	"The value of the count of the number of interrupt 
	 packets received for this switched virtual call or 
	 permanent virtual circuit."
    REFERENCE
	"ITU-T Rec. X.283 | ISO/IEC 10733 : virtualCall-DTE 
	     interruptPacketsReceived."
    ::= { x25VCDTEEntry 6 }

x25VCDTEInterruptPacketsSent OBJECT-TYPE
    SYNTAX	Counter64
    MAX-ACCESS	read-only
    STATUS	current
    DESCRIPTION
	"The value of the count of the number of interrupt 
	 packets sent for this switched virtual call or 
	 permanent virtual circuit."
    REFERENCE
	"ITU-T Rec. X.283 | ISO/IEC 10733 : virtualCall-DTE 
	     interruptPacketsSent."
    ::= { x25VCDTEEntry 7 }

x25VCDTEInterruptTimeouts OBJECT-TYPE
    SYNTAX	Counter64
    MAX-ACCESS	read-only
    STATUS	current
    DESCRIPTION
	"The value of the count of the number of times that 
	 Timer T26 expired, for this switched virtual call or 
	 permanent virtual circuit."
    REFERENCE
	"ITU-T Rec. X.283 | ISO/IEC 10733 : virtualCall-DTE 
	     interruptTimerExpiries.
	 ITU-T Rec. X.25 | ISO/IEC 8208 : Timer T26."
    ::= { x25VCDTEEntry 8 }

x25VCDTEProviderResets OBJECT-TYPE
    SYNTAX	Counter64
    MAX-ACCESS	read-only
    STATUS	current
    DESCRIPTION
	"The value of the count of the number of provider 
	 initiated resets that constituted a 
	 providerInitiatedReset event that generated a 
	 communications alarm notification.  This count is the 
	 associated with this switched virtual call or permanent 
	 virtual circuit."
    REFERENCE
	"ITU-T Rec. X.283 | ISO/IEC 10733 : virtualCall-DTE 
	     providerInitiatedResets."
    ::= { x25VCDTEEntry 9 }

x25VCDTERemoteResets OBJECT-TYPE
    SYNTAX	Counter64
    MAX-ACCESS	read-only
    STATUS	current
    DESCRIPTION
	"The value of the count of the number of remotely 
	 initated resets that constituted a 
	 remotelyInitiatedReset even that generated a 
	 communicaitons alarm notification.  This count is 
	 associated with this switched virtual call or permanent 
	 virtual circuit."
    REFERENCE
	"ITU-T Rec. X.283 | ISO/IEC 10733 : virtualCall-DTE 
	     remotelyInitiatedResets."
    ::= { x25VCDTEEntry 10 }

x25VCDTEResetTimeouts OBJECT-TYPE
    SYNTAX	Counter64
    MAX-ACCESS	read-only
    STATUS	current
    DESCRIPTION
	"The value of the count of the number of times that 
	 Timer T22 expired, for this switched virtual call or 
	 permanent virtual circuit."
    REFERENCE
	"ITU-T Rec. X.283 | ISO/IEC 10733 : virtualCall-DTE, 
	     resetTimeouts.
	 ITU-T Rec. X.25 | ISO/IEC 8208 : Timer T22."
    ::= { x25VCDTEEntry 11 }


x25VCDCE OBJECT IDENTIFIER
    ::= { x25PLPTables 11 }

x25VCDCETable OBJECT-TYPE
    SYNTAX	SEQUENCE OF X25VCDCEEntry
    MAX-ACCESS	not-accessible
    STATUS	current
    DESCRIPTION
	"This MO Classs in never instantiated.  It serves as a 
	 generic Virtual Circuit DCE MO from which both the 
	 Virtual Call DCE and Permanent Virtual Circuit DCE MOs 
	 are derived.  Note that the values of the 
	 virtualCircuitId naming attribute are required to be 
	 unique across all instances of MOs derived from this 
	 which have a common superior."
    REFERENCE
	"ITU-T Rec. X.283 | ISO/IEC 10733 : virtualCircuit-DCE 
	     MOC."
    ::= { x25VCDCE 1 }

x25VCDCEEntry OBJECT-TYPE
    SYNTAX	X25VCDCEEntry
    MAX-ACCESS	not-accessible
    STATUS	current
    DESCRIPTION
	"Entries in this table are not explicitly created by 
	 management stations.  They are created automatically by 
	 the agent whenver an entry in the x25SVCDCETable or 
	 x25PVCDCETable are created; and destroyed whenever the 
	 corresponding entry is destroyed."
    REFERENCE
	"ITU-T Rec. X.283 | ISO/IEC 10733 : virtualCircuit-DCE 
	     MO."
    INDEX	{
		    x25PLEId,	-- shared index (CONTAINED BY)
		    x25VCId	-- shared index (DERIVED FROM)
		}
    ::= { x25VCDCETable 1 }

X25VCDCEEntry ::= SEQUENCE {
    x25VCDCEOctetsReceived		Counter64,
    x25VCDCEOctetsSent			Counter64,
    x25VCDCEDataPacketsReceived		Counter64,
    x25VCDCEDataPacketsSent		Counter64,
    x25VCDCEInterruptPacketsReceived	Counter64,
    x25VCDCEInterruptPacketsSent	Counter64,
    x25VCDCEProviderResets		Counter64,
    x25VCDCERemoteResets		Counter64,
    x25VCDCEResetTimeouts		Counter64,
    x25VCDCERemoteRestarts		Counter64,
    x25VCDCEProviderDisconnects		Counter64,
    x25VCDCEX25SegmentsReceived		Counter64,
    x25VCDCEX25SegmentsSent		Counter64,
}

x25VCDCEOctetsReceived OBJECT-TYPE
    SYNTAX	Counter64
    MAX-ACCESS	read-only
    STATUS	current
    DESCRIPTION
	"This is the value of the count of the number of user 
	 data octets succesfully received for this switched 
	 virtual call or permanent virtual circuit.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : virtualCall-DCE 
	     octetsReceivedCounter
	 ITU-T Rec. X.721 | ISO/IEC 10165-2 : 
	     octetsReceivedCounter."
    ::= { x25VCDCEEntry 1 }

x25VCDCEOctetsSent OBJECT-TYPE
    SYNTAX	Counter64
    MAX-ACCESS	read-only
    STATUS	current
    DESCRIPTION
	"This is the value of the count of the number of user 
	 data octets successfully sent for this switched virtual 
	 call or permanent virtual circuit.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : virtualCall-DCE 
	     octetsSentCounter
	 ITU-T Rec. X.721 | ISO/IEC 10165-2 : 
	     octetsSentCoutner."
    ::= { x25VCDCEEntry 2 }

x25VCDCEDataPacketsReceived OBJECT-TYPE
    SYNTAX	Counter64
    MAX-ACCESS	read-only
    STATUS	current
    DESCRIPTION
	"The value of the count of the number of data packets 
	 received for this switched virtual call or permanent 
	 virtual circuit."
    REFERENCE
	"ITU-T Rec. X.283 | ISO/IEC 10733 : virtualCall-DCE 
	     dataPacketsReceived."
    ::= { x25VCDCEEntry 3 }

x25VCDCEDataPacketsSent OBJECT-TYPE
    SYNTAX	Counter64
    MAX-ACCESS	read-only
    STATUS	current
    DESCRIPTION
	"The value of the count of the number of data packets 
	 sent for this switched virtual call or permanent 
	 virtual circuit."
    REFERENCE
	"ITU-T Rec. X.283 | ISO/IEC 10733 : virtualCall-DCE 
	     dataPacketsSent."
    ::= { x25VCDCEEntry 4 }

x25VCDCEInterruptPacketsReceived OBJECT-TYPE
    SYNTAX	Counter64
    MAX-ACCESS	read-only
    STATUS	current
    DESCRIPTION
	"The value of the count of the number of interrupt 
	 packets received for this switched virtual call or 
	 permanent virtual circuit."
    REFERENCE
	"ITU-T Rec. X.283 | ISO/IEC 10733 : virtualCall-DCE 
	     interruptPacketsReceived."
    ::= { x25VCDCEEntry 5 }

x25VCDCEInterruptPacketsSent OBJECT-TYPE
    SYNTAX	Counter64
    MAX-ACCESS	read-only
    STATUS	current
    DESCRIPTION
	"The value of the count of the number of interrupt 
	 packets sent for this switched virtual call or 
	 permanent virtual circuit."
    REFERENCE
	"ITU-T Rec. X.283 | ISO/IEC 10733 : virtualCall-DCE 
	     interruptPacketsSent."
    ::= { x25VCDCEEntry 6 }

x25VCDCEProviderResets OBJECT-TYPE
    SYNTAX	Counter64
    MAX-ACCESS	read-only
    STATUS	current
    DESCRIPTION
	"The value of the count of the number of provider 
	 initiated resets that constituted a 
	 providerInitiatedReset event that generated a 
	 communications alarm notification.  This count is 
	 associated with this switched virtual call or permanent 
	 virtual circuit."
    REFERENCE
	"ITU-T Rec. X.283 | ISO/IEC 10733 : virtualCall-DCE 
	     providerInitiatedResets."
    ::= { x25VCDCEEntry 7 }

x25VCDCERemoteResets OBJECT-TYPE
    SYNTAX	Counter64
    MAX-ACCESS	read-only
    STATUS	current
    DESCRIPTION
	"The value of the count of the number of remotely 
	 initated resets that constituted a 
	 remotelyInitiatedReset even that generated a 
	 communicaitons alarm notification.  This count is 
	 associated with this switched virtual call or permanent 
	 virtual circuit."
    REFERENCE
	"ITU-T Rec. X.283 | ISO/IEC 10733 : virtualCall-DCE 
	     remotelyInitiatedResets."
    ::= { x25VCDCEEntry 8 }

x25VCDCEResetTimeouts OBJECT-TYPE
    SYNTAX	Counter64
    MAX-ACCESS	read-only
    STATUS	current
    DESCRIPTION
	"The value of the count of the number of times that 
	 Timer T22 expired, for this switched virtual call or 
	 permanent virtual circuit."
    REFERENCE
	"ITU-T Rec. X.283 | ISO/IEC 10733 : virtualCall-DCE, 
	     resetTimeouts.
	 ITU-T Rec. X.25 | ISO/IEC 8208 : Timer T22."
    ::= { x25VCDCEEntry 9 }

x25VCDCERemoteRestarts OBJECT-TYPE
    SYNTAX	Counter64
    MAX-ACCESS	read-only
    STATUS	current
    DESCRIPTION
	"The value of the count of the number of remotely 
	 initated restarts.  This is the number of remotely 
	 initated (including provider initiated) restarts 
	 experienced by the switched virtual call or permanent 
	 virtual circuit."
    REFERENCE
	"ITU-T Rec. X.283 | ISO/IEC 10733 : virtualCall-DCE 
	     remotelyInitiatedRestarts."
    ::= { x25VCDCEEntry 10 }

x25VCDCEProviderDisconnects OBJECT-TYPE
    SYNTAX	Counter64
    MAX-ACCESS	read-only
    STATUS	current
    DESCRIPTION
	"The value of the count of the number or provider 
	 initiated disconnects that constitued a 
	 providerInitiatedDisconnect event that generated a 
	 communications alarm notification.  Tihs count is the 
	 associated with this switched virtual call or permanent 
	 virtual circuit."
    REFERENCE
	"ITU-T Rec. X.283 | ISO/IEC 10733 : virtualCall-DCE 
	     providerInitiatedDisconnects."
    ::= { x25VCDCEEntry 11 }

x25VCDCEX25SegmentsReceived OBJECT-TYPE
    SYNTAX	Counter64
    MAX-ACCESS	read-only
    STATUS	current
    DESCRIPTION
	"The value of the count of the X.25 segments received.  
	 The segments received is the number of data PDUs 
	 received prior to reassembly, including those whch may 
	 subsequently be discarded.  Note: not to be confused 
	 with the D-Series counts of the same name."
    REFERENCE
	"ITU-T Rec. X.283 | ISO/IEC 10733 : virtualCall-DCE 
	     X25SegmentsReceived."
    ::= { x25VCDCEEntry 12 }

x25VCDCEX25SegmentsSent OBJECT-TYPE
    SYNTAX	Counter64
    MAX-ACCESS	read-only
    STATUS	current
    DESCRIPTION
	"The value of the count of the X.25 segments sent.  This 
	 is the number of data PDUs sent after segmentation 
	 processing occurs.  Note: not to be confused with the 
	 D-Series counts of the same name."
    REFERENCE
	"ITU-T Rec. X.283 | ISO/IEC 10733 : virtualCall-DCE 
	     X25SegmentsSent."
    ::= { x25VCDCEEntry 13 }


x25VCDXE OBJECT IDENTIFIER
    ::= { x25PLPTables 12 }

x25VCDXETable OBJECT-TYPE
    SYNTAX	SEQUENCE OF X25VCDXEEntry
    MAX-ACCESS	not-accessible
    STATUS	current
    DESCRIPTION
	"This MO Classs in never instantiated.  It serves as a 
	 generic Virtual Circuit DXE MO from which both the 
	 Virtual Call DXE and Permanent Virtual Circuit DXE MOs 
	 are derived.  Note that the values of the 
	 virtualCircuitId naming attribute are required to be 
	 unique across all instances of MOs derived from this 
	 which have a common superior."
    REFERENCE
	"ISO/IEC 10733 : virtualCall MOC."
    ::= { x25VCDXE 1 }

x25VCDXEEntry OBJECT-TYPE
    SYNTAX	X25VCDXEEntry
    MAX-ACCESS	not-accessible
    STATUS	current
    DESCRIPTION
	"Entries in this table are not explicitly created by 
	 management stations.  They are created automatically by 
	 the agent whenver an entry in the x25SVCDXETable or 
	 x25PVCDXETable are created; and destroyed whenever the 
	 corresponding entry is destroyed."
    REFERENCE
	"ISO/IEC 10733 : virtualCall MO."
    INDEX	{
		    x25PLEId,	-- shared index (CONTAINED BY)
		    x25VCId	-- shared index (DERIVED FROM)
		}
    ::= { x25VCDXETable 1 }

X25VCDXEEntry ::= SEQUENCE {
    x25VCDXEOctetsReceived		Counter64,
    x25VCDXEOctetsSent			Counter64,
    x25VCDXEDataPacketsReceived		Counter64,
    x25VCDXEDataPacketsSent		Counter64,
    x25VCDXEDataTimeouts		Counter64,
    x25VCDXEInterruptPacketsReceived	Counter64,
    x25VCDXEInterruptPacketsSent	Counter64,
    x25VCDXEInterruptTimeouts		Counter64,
    x25VCDXEProviderResets		Counter64,
    x25VCDXERemoteResets		Counter64,
    x25VCDXEResetTimeouts		Counter64,
}

-- PACKAGE dTEVirtualCircuitCounters-P
x25VCDXEOctetsReceived OBJECT-TYPE
    SYNTAX	Counter64
    MAX-ACCESS	read-only
    STATUS	current
    DESCRIPTION
	"This is the value of the count of the number of user 
	 data octets succesfully received for this switched 
	 virtual call or permanent virtual circuit.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : virtualCall 
	     octetsReceivedCounter
	 ITU-T Rec. X.721 | ISO/IEC 10165-2 : 
	     octetsReceivedCounter."
    ::= { x25VCDXEEntry 1 }

x25VCDXEOctetsSent OBJECT-TYPE
    SYNTAX	Counter64
    MAX-ACCESS	read-only
    STATUS	current
    DESCRIPTION
	"This is the value of the count of the number of user 
	 data octets successfully sent for this switched virtual 
	 call or permanent virtual circuit.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : virtualCall 
	     octetsSentCounter
	 ITU-T Rec. X.721 | ISO/IEC 10165-2 : 
	     octetsSentCoutner."
    ::= { x25VCDXEEntry 2 }

x25VCDXEDataPacketsReceived OBJECT-TYPE
    SYNTAX	Counter64
    MAX-ACCESS	read-only
    STATUS	current
    DESCRIPTION
	"The value of the count of the number of data packets 
	 received for this switched virtual call or permanent 
	 virtual circuit."
    REFERENCE
	"ITU-T Rec. X.283 | ISO/IEC 10733 : virtualCall 
	     dataPacketsReceived."
    ::= { x25VCDXEEntry 3 }

x25VCDXEDataPacketsSent OBJECT-TYPE
    SYNTAX	Counter64
    MAX-ACCESS	read-only
    STATUS	current
    DESCRIPTION
	"The value of the count of the number of data packets 
	 sent for this switched virtual call or permanent 
	 virtual circuit."
    REFERENCE
	"ITU-T Rec. X.283 | ISO/IEC 10733 : virtualCall 
	     dataPacketsSent."
    ::= { x25VCDXEEntry 4 }

x25VCDXEDataTimeouts OBJECT-TYPE
    SYNTAX	Counter64
    MAX-ACCESS	read-only
    STATUS	current
    DESCRIPTION
	"The value of the count of the number of times that 
	 Timer 25 expired.  for this switched virtual call or 
	 permanent virtual circuit.  When the option is not 
	 implemented, this object always returns zero (0)."
    REFERENCE
	"ITU-T Rec. X.283 | ISO/IEC 10733 : virtualCall 
	     dataRetransmissionTimerExpiries.
	 ITU-T Rec. X.25 | ISO/IEC 8208 : Timer T25."
    ::= { x25VCDXEEntry 5 }

x25VCDXEInterruptPacketsReceived OBJECT-TYPE
    SYNTAX	Counter64
    MAX-ACCESS	read-only
    STATUS	current
    DESCRIPTION
	"The value of the count of the number of interrupt 
	 packets received for this switched virtual call or 
	 permanent virtual circuit."
    REFERENCE
	"ITU-T Rec. X.283 | ISO/IEC 10733 : virtualCall 
	     interruptPacketsReceived."
    ::= { x25VCDXEEntry 6 }

x25VCDXEInterruptPacketsSent OBJECT-TYPE
    SYNTAX	Counter64
    MAX-ACCESS	read-only
    STATUS	current
    DESCRIPTION
	"The value of the count of the number of interrupt 
	 packets sent for this switched virtual call or 
	 permanent virtual circuit."
    REFERENCE
	"ITU-T Rec. X.283 | ISO/IEC 10733 : virtualCall 
	     interruptPacketsSent."
    ::= { x25VCDXEEntry 7 }

x25VCDXEInterruptTimeouts OBJECT-TYPE
    SYNTAX	Counter64
    MAX-ACCESS	read-only
    STATUS	current
    DESCRIPTION
	"The value of the count of the number of times that 
	 Timer T26 expired, for this switched virtual call or 
	 permanent virtual circuit."
    REFERENCE
	"ITU-T Rec. X.283 | ISO/IEC 10733 : virtualCall 
	     interruptTimerExpiries.
	 ITU-T Rec. X.25 | ISO/IEC 8208 : Timer T26."
    ::= { x25VCDXEEntry 8 }

x25VCDXEProviderResets OBJECT-TYPE
    SYNTAX	Counter64
    MAX-ACCESS	read-only
    STATUS	current
    DESCRIPTION
	"The value of the count of the number of provider 
	 initiated resets that constituted a 
	 providerInitiatedReset event that generated a 
	 communications alarm notification.  This count is 
	 associated with this switched virtual call or permanent 
	 virtual circuit."
    REFERENCE
	"ITU-T Rec. X.283 | ISO/IEC 10733 : virtualCall 
	     providerInitiatedResets."
    ::= { x25VCDXEEntry 9 }

x25VCDXERemoteResets OBJECT-TYPE
    SYNTAX	Counter64
    MAX-ACCESS	read-only
    STATUS	current
    DESCRIPTION
	"The value of the count of the number of remotely 
	 initated resets that constituted a 
	 remotelyInitiatedReset even that generated a 
	 communicaitons alarm notification.  This count is 
	 associated with this switched virtual call or permanent 
	 virtual circuit."
    REFERENCE
	"ITU-T Rec. X.283 | ISO/IEC 10733 : virtualCall 
	     remotelyInitiatedResets."
    ::= { x25VCDXEEntry 10 }

x25VCDXEResetTimeouts OBJECT-TYPE
    SYNTAX	Counter64
    MAX-ACCESS	read-only
    STATUS	current
    DESCRIPTION
	"The value of the count of the number of times that 
	 Timer T22 expired, for this switched virtual call or 
	 permanent virtual circuit."
    REFERENCE
	"ITU-T Rec. X.283 | ISO/IEC 10733 : virtualCall, 
	     resetTimeouts.
	 ITU-T Rec. X.25 | ISO/IEC 8208 : Timer T22."
    ::= { x25VCDXEEntry 11 }


x25PVCDTE OBJECT IDENTIFIER
    ::= { x25PLPTables 13 }

x25PVCDTETable OBJECT-TYPE
    SYNTAX	SEQUENCE OF X25PVCDTEEntry
    MAX-ACCESS	not-accessible
    STATUS	current
    DESCRIPTION
	""
    REFERENCE
	"ITU-T Rec. X.283 | ISO/IEC 10733 : 
	     permanentVirtualCircuit-DTE MOC."
    ::= { x25PVCDTE 1 }

x25PVCDTEEntry OBJECT-TYPE
    SYNTAX	X25PVCDTEEntry
    MAX-ACCESS	not-accessible
    STATUS	current
    DESCRIPTION
	"An instance of this MO exists for each Permanent 
	 Virtual Circuit.  It may be both created and deleted by 
	 management.
	
	 When the MO is created, the protocol machine shall be 
	 reinitialized and as reset PDU with a cause code of DTE 
	 originated (encoded as 000000000) and a diagnostic code 
	 of DTE operational (161) shall be transmitted.  When 
	 the MO is deleted, the protocol machine shall be 
	 reinitialized and a reset PDU with a cause code of DTE 
	 originated (encoded as 
	 00000000) and a diagnostic code of not operational 
	 (162) shall be transmitted."
    REFERENCE
	"ITU-T Rec. X.283 | ISO/IEC 10733 : 
	     permanentVirtualCircuit-DTE MO."
    INDEX	{
		    x25PLEId,	-- shared index (CONTAINED BY)
		    x25VCId	-- shared index (DERIVED FROM)
		}
    ::= { x25PVCDTETable 1 }

X25PVCDTEEntry ::= SEQUENCE {
    x25PVCDTELogicalChannel		LogicalChannelNumber,
    x25PVCDTERowStatus			RowStatus,
}

x25PVCDTELogicalChannel OBJECT-TYPE
    SYNTAX	LogicalChannelNumber
    MAX-ACCESS	read-create
    STATUS	current
    DESCRIPTION
	"Specifies the logical channel number assigned to this 
	 permanent virtual circuit.  When set to zero(0), the 
	 PVC is non-operational (the default)."
    REFERENCE
	"ITU-T Rec. X.283 | ISO/IEC 10733 : 
	     permanentVirtualCircuit-DTE."
    DEFVAL	{ 0 } -- non-operational
    ::= { x25PVCDTEEntry 1 }

-- Miscellaneous
x25PVCDTERowStatus OBJECT-TYPE
    SYNTAX	RowStatus
    MAX-ACCESS	read-create
    STATUS	current
    DESCRIPTION
	"Provides a mechanism whereby management stations may 
	 create and delete entries in this table.  Each entry 
	 created in this table represents a permanent virtual 
	 circuit allocated to the X.25 PLE."
    REFERENCE
	"ITU-T Rec. X.283 | ISO/IEC 10733 : 
	     permanentVirtualCircuit-DTE."
    ::= { x25PVCDTEEntry 2 }


x25PVCDCE OBJECT IDENTIFIER
    ::= { x25PLPTables 14 }

x25PVCDCETable OBJECT-TYPE
    SYNTAX	SEQUENCE OF X25PVCDCEEntry
    MAX-ACCESS	not-accessible
    STATUS	current
    DESCRIPTION
	"Objects in this table generate stateChange 
	 notifications."
    REFERENCE
	"ITU-T Rec. X.283 | ISO/IEC 10733 : 
	     permanentVirtualCircuit-DCE MOC."
    ::= { x25PVCDCE 1 }

x25PVCDCEEntry OBJECT-TYPE
    SYNTAX	X25PVCDCEEntry
    MAX-ACCESS	not-accessible
    STATUS	current
    DESCRIPTION
	"An instance of this MO exists for each Permanent 
	 Virtual Circuit.  It may be both created and deleted by 
	 management.
	
	 When the MO is created, the protocol machine shall be 
	 re-initialized and a reset PDU shall be transmitted.  A 
	 cause caode of remote DTE Operational (encoded as X000 
	 1001) or Network Operational (encoded as X000 1111) 
	 may, for example, be included.  When the MO is deleted 
	 the protocol machine shall be reinitialized and a reset 
	 PDU shall be transmitted.  A cause code of Out of Order 
	 (encoded as X000 0001) or Network Out of Order (encoded 
	 as X001 1101) may, for example, be included."
    REFERENCE
	"ITU-T Rec. X.283 | ISO/IEC 10733 : 
	     permanentVirtualCircuit-DCE MO."
    INDEX	{
		    x25PLEId,	-- shared index (CONTAINED BY)
		    x25VCId	-- shared index (DERIVED FROM)
		}
    ::= { x25PVCDCETable 1 }

X25PVCDCEEntry ::= SEQUENCE {
    x25PVCDCELogicalChannel		LogicalChannelNumber,
    x25PVCDCEChargingDirection		TruthValue,
    x25PVCDCERemoteDTEAddress		DTEAddress,
    x25PVCDCERemoteLogicalChannel	LogicalChannelNumber,
    x25PVCDCEOperationalState		OperationalState,
    x25PVCDCERowStatus			RowStatus,
}

x25PVCDCELogicalChannel OBJECT-TYPE
    SYNTAX	LogicalChannelNumber
    MAX-ACCESS	read-create
    STATUS	current
    DESCRIPTION
	"Specifies the logical channel number assigned to this 
	 permanent virtual circuit.  When set to zero(0), the 
	 PVC is non-operational (the default)."
    REFERENCE
	"ITU-T Rec. X.283 | ISO/IEC 10733 : 
	     permanentVirtualCircuit-DCE."
    DEFVAL	{ 0 } -- non-operational
    ::= { x25PVCDCEEntry 1 }

x25PVCDCEChargingDirection OBJECT-TYPE
    SYNTAX	TruthValue
    MAX-ACCESS	read-create
    STATUS	current
    DESCRIPTION
	""
    REFERENCE
	"ITU-T Rec. X.283 | ISO/IEC 10733 : 
	     permanentVirtualCircuit-DCE."
    ::= { x25PVCDCEEntry 2 }

x25PVCDCEOperationalState OBJECT-TYPE
    SYNTAX	OperationalState
    MAX-ACCESS	read-only
    STATUS	current
    DESCRIPTION
	"
	 - diabled(0),
	 - enabled(1),
	 "
    REFERENCE
	"ITU-T Rec. X.283 | ISO/IEC 10733 : 
	     permanentVirtualCircuit-DCE."
    ::= { x25PVCDCEEntry 3 }

x25PVCDCERemoteDTEAddress OBJECT-TYPE
    SYNTAX	DTEAddress
    MAX-ACCESS	read-create
    STATUS	current
    DESCRIPTION
	"The DTE Address of the remote DTE, using the DTEAddress 
	 textual convention.  In the case of an outgoing call 
	 this is the remote DTE address form the called address 
	 of the transmitted call request packet.  In the case of 
	 an incoming call, it is the calling address from the 
	 received call request packet.  For a PVC, it is the 
	 admintratively assigned address of the DTE at the 
	 remote end of the PVC. The DTEAddress textual 
	 convention supports X.121 and E.164 DTE addresses as 
	 well as TOA/NPI addresses."
    REFERENCE
	"ITU-T Rec. X.283 | ISO/IEC 10733 : 
	     permanentVirtualCircuit-DCE remoteDTEAddress."
    ::= { x25PVCDCEEntry 4 }

x25PVCDCERemoteLogicalChannel OBJECT-TYPE
    SYNTAX	LogicalChannelNumber
    MAX-ACCESS	read-create
    STATUS	current
    DESCRIPTION
	""
    REFERENCE
	"ITU-T Rec. X.283 | ISO/IEC 10733 : 
	     permanentVirtualCircuit-DCE."
    ::= { x25PVCDCEEntry 5 }

-- Miscellaneous
x25PVCDCERowStatus OBJECT-TYPE
    SYNTAX	RowStatus
    MAX-ACCESS	read-create
    STATUS	current
    DESCRIPTION
	"Provides a mechanism whereby management stations may 
	 create and delete entries in this table.  Each entry 
	 created in this table represents a permanent virtual 
	 circuit allocated to the X.25 PLE."
    REFERENCE
	"ITU-T Rec. X.283 | ISO/IEC 10733 : 
	     permanentVirtualCircuit-DCE."
    ::= { x25PVCDCEEntry 6 }


x25PVCDXE OBJECT IDENTIFIER
    ::= { x25PLPTables 15 }

x25PVCDXETable OBJECT-TYPE
    SYNTAX	SEQUENCE OF X25PVCDXEEntry
    MAX-ACCESS	not-accessible
    STATUS	current
    DESCRIPTION
	""
    REFERENCE
	"ISO/IEC 10733 : permanentVirtualCircuit MOC."
    ::= { x25PVCDXE 1 }

x25PVCDXEEntry OBJECT-TYPE
    SYNTAX	X25PVCDXEEntry
    MAX-ACCESS	not-accessible
    STATUS	current
    DESCRIPTION
	""
    REFERENCE
	"ISO/IEC 10733 : permanentVirtualCircuit MO."
    INDEX	{
		    x25PLEId,	-- shared index (CONTAINED BY)
		    x25VCId	-- shared index (DERIVED FROM)
		}
    ::= { x25PVCDXETable 1 }

X25PVCDXEEntry ::= SEQUENCE {
    x25PVCDXELogicalChannel		LogicalChannelNumber,
    x25PVCDXERowStatus			RowStatus,
}

x25PVCDXELogicalChannel OBJECT-TYPE
    SYNTAX	LogicalChannelNumber
    MAX-ACCESS	read-create
    STATUS	current
    DESCRIPTION
	"Specifies the logical channel number assigned to this 
	 permanent virtual circuit.  When set to zero(0), the 
	 PVC is non-operational (the default)."
    REFERENCE
	"ITU-T Rec. X.283 | ISO/IEC 10733 : 
	     permanentVirualCircuit."
    DEFVAL	{ 0 } -- non-operational
    ::= { x25PVCDXEEntry 1 }

-- Miscellanous
x25PVCDXERowStatus OBJECT-TYPE
    SYNTAX	RowStatus
    MAX-ACCESS	read-create
    STATUS	current
    DESCRIPTION
	"Provides a mechanism whereby management stations may 
	 create and delete entries in this table.  Each entry 
	 created in this table represents a permanent virtual 
	 circuit allocated to the X.25 PLE."
    REFERENCE
	"ITU-T Rec. X.283 | ISO/IEC 10733 : 
	     permanentVirualCircuit."
    ::= { x25PVCDXEEntry 2 }


x25SVCIVMO OBJECT IDENTIFIER
    ::= { x25PLPTables 16 }

x25SVCIVMOTable OBJECT-TYPE
    SYNTAX	SEQUENCE OF X25SVCIVMOEntry
    MAX-ACCESS	not-accessible
    STATUS	current
    DESCRIPTION
	"Objects in this table generate objectCreation and 
	 objectDeletion notifications."
    REFERENCE
	"ITU-T Rec. X.283 | ISO/IEC 10733 : virtualCallIVMO 
	     MOC."
    ::= { x25SVCIVMO 1 }

x25SVCIVMOEntry OBJECT-TYPE
    SYNTAX	X25SVCIVMOEntry
    MAX-ACCESS	not-accessible
    STATUS	current
    DESCRIPTION
	"There may be multiple instances of the virtualCallIVMO 
	 in a system.  A virtualCallIVMO may be used to supply 
	 initial values for the attributes of the 
	 virtualCall-DTE or virtualCall-DCE MO.  Different 
	 instances of virtualCallIVMO may contain different 
	 intial values.  Its defintion permits it to be created 
	 and deleted explicitly by management operation.
	
	 Under ITU-T Rec. X.238, the virtualCallIVMO MO is 
	 contained by an instance of an x25PLE-DTE or x25PLE-DCE 
	 MO which are in turn contained by a networkSubsystem 
	 MO.  This SNMP implementation represents a single 
	 networkSubsystem, and the naming of x25SVCIVMO rows 
	 must be unique across all instances of X.25 PLE."
    REFERENCE
	"ITU-T Rec. X.283 | ISO/IEC 10733 : virtualCallIVMO MO."
    INDEX	{
		    x25PLEId,	    -- shared index (CONTAINED BY)
		    x25SVCIVMOId    -- (BASE CLASS INSTANCE)
		}
    ::= { x25SVCIVMOTable 1 }

X25SVCIVMOEntry ::= SEQUENCE {
    x25SVCIVMOId			SimpleNameType,
    x25SVCIVMOFastSelect		FastSelect,
    x25SVCIVMOPacketSizeIncoming	PacketSize,
    x25SVCIVMOPacketSizeOutgoing	PacketSize,
    x25SVCIVMOReverseCharging		TruthValue,
    x25SVCIVMOThroughputClassIncoming	ThroughputClass,
    x25SVCIVMOThroughputClassOutgoing	ThroughputClass,
    x25SVCIVMOWindowSizeIncoming	WindowSize,
    x25SVCIVMOWindowSizeOutgoing	WindowSize,
    x25SVCIVMORowStatus			RowStatus,
}

x25SVCIVMOId OBJECT-TYPE
    SYNTAX	SimpleNameType
    MAX-ACCESS	read-create
    STATUS	current
    DESCRIPTION
	""
    REFERENCE
	"ITU-T Rec. X.283 | ISO/IEC 10733 : virtualCallIVMO."
    ::= { x25SVCIVMOEntry 1 }

x25SVCIVMOFastSelect OBJECT-TYPE
    SYNTAX	FastSelect
    MAX-ACCESS	read-create
    STATUS	current
    DESCRIPTION
	"
	 Fast Select is an optional user faciltiy that requires 
	 dynamic invocation on packet switched networks.
	 "
    REFERENCE
	"ITU-T Rec. X.283 | ISO/IEC 10733 : virtualCallIVMO, 
	     fastSelect.
	 ITU-T Rec. X.7, Clause 6.2.1.1."
    ::= { x25SVCIVMOEntry 2 }

--  x25SVCIVMOPacketSizes
x25SVCIVMOPacketSizeIncoming OBJECT-TYPE
    SYNTAX	PacketSize
    MAX-ACCESS	read-create
    STATUS	current
    DESCRIPTION
	""
    REFERENCE
	"ITU-T Rec. X.283 | ISO/IEC 10733 : virtualCallIVMO."
    ::= { x25SVCIVMOEntry 3 }

x25SVCIVMOPacketSizeOutgoing OBJECT-TYPE
    SYNTAX	PacketSize
    MAX-ACCESS	read-create
    STATUS	current
    DESCRIPTION
	""
    REFERENCE
	"ITU-T Rec. X.283 | ISO/IEC 10733 : virtualCallIVMO."
    ::= { x25SVCIVMOEntry 4 }

x25SVCIVMOReverseCharging OBJECT-TYPE
    SYNTAX	TruthValue
    MAX-ACCESS	read-create
    STATUS	current
    DESCRIPTION
	"
	 Reverse Charging is an optional user facility that 
	 requires dynamic invocation on a circuit switched or 
	 packet switched network.
	 "
    REFERENCE
	"ITU-T Rec. X.283 | ISO/IEC 10733 : virtualCallIVMO, 
	     reverseCharging.
	 ITU-T Rec. X.7, Clause 6.5.1.1."
    ::= { x25SVCIVMOEntry 5 }

--  x25SVCIVMOThroughputClasses
x25SVCIVMOThroughputClassIncoming OBJECT-TYPE
    SYNTAX	ThroughputClass
    MAX-ACCESS	read-create
    STATUS	current
    DESCRIPTION
	""
    REFERENCE
	"ITU-T Rec. X.283 | ISO/IEC 10733 : virtualCallIVMO."
    ::= { x25SVCIVMOEntry 6 }

x25SVCIVMOThroughputClassOutgoing OBJECT-TYPE
    SYNTAX	ThroughputClass
    MAX-ACCESS	read-create
    STATUS	current
    DESCRIPTION
	""
    REFERENCE
	"ITU-T Rec. X.283 | ISO/IEC 10733 : virtualCallIVMO."
    ::= { x25SVCIVMOEntry 7 }

--  x25SVCIVMOWindowSizes
x25SVCIVMOWindowSizeIncoming OBJECT-TYPE
    SYNTAX	WindowSize
    MAX-ACCESS	read-create
    STATUS	current
    DESCRIPTION
	""
    REFERENCE
	"ITU-T Rec. X.283 | ISO/IEC 10733 : virtualCallIVMO."
    ::= { x25SVCIVMOEntry 8 }

x25SVCIVMOWindowSizeOutgoing OBJECT-TYPE
    SYNTAX	WindowSize
    MAX-ACCESS	read-create
    STATUS	current
    DESCRIPTION
	""
    REFERENCE
	"ITU-T Rec. X.283 | ISO/IEC 10733 : virtualCallIVMO."
    ::= { x25SVCIVMOEntry 9 }

-- Miscellaneous
x25SVCIVMORowStatus OBJECT-TYPE
    SYNTAX	RowStatus
    MAX-ACCESS	read-create
    STATUS	current
    DESCRIPTION
	""
    REFERENCE
	"ITU-T Rec. X.283 | ISO/IEC 10733 : virtualCallIVMO."
    ::= { x25SVCIVMOEntry 10 }


x25SVCIVMODTE OBJECT IDENTIFIER
    ::= { x25PLPTables 17 }

x25SVCIVMODTETable OBJECT-TYPE
    SYNTAX	SEQUENCE OF X25SVCIVMODTEEntry
    MAX-ACCESS	not-accessible
    STATUS	current
    DESCRIPTION
	""
    REFERENCE
	""
    ::= { x25SVCIVMODTE 1 }

x25SVCIVMODTEEntry OBJECT-TYPE
    SYNTAX	X25SVCIVMODTEEntry
    MAX-ACCESS	not-accessible
    STATUS	current
    DESCRIPTION
	""
    REFERENCE
	""
    INDEX	{
		    x25PLEId,	    -- shared index (CONTAINED BY)
		    x25SVCIVMOId    -- shared index (DERIVED FROM)
		}
    ::= { x25SVCIVMODTETable 1 }

X25SVCIVMODTEEntry ::= SEQUENCE {
    x25SVCIVMODTECallTime		TimeInterval,
    x25SVCIVMODTEResetTime		TimeInterval,
    x25SVCIVMODTEResetCount		INTEGER,
    x25SVCIVMODTEInterruptTime		TimeInterval,
    x25SVCIVMODTEClearTime		TimeInterval,
    x25SVCIVMODTEClearCount		INTEGER,
    -- PACKAGE receivingWindowRotationRecoveryProcedures-P
    x25SVCIVMODTEWindowTime		TimeInterval,
    -- PACKAGE transmittingWindowRotationRecoveryProcedures-P
    x25SVCIVMODTEDataTime		TimeInterval,
    x25SVCIVMODTEDataCount		INTEGER,
    -- PACKAGE packetRetransmissionProcedures-P
    x25SVCIVMODTERejectTime		TimeInterval,
    x25SVCIVMODTERejectCount		INTEGER,
    x25SVCIVMODTERowStatus		RowStatus,
}

x25SVCIVMODTECallTime OBJECT-TYPE
    SYNTAX	TimeInterval
    UNITS	"seconds"
    MAX-ACCESS	read-create
    STATUS	current
    DESCRIPTION
	"The value for Timer T21 (Call Request Response Timer) 
	 in centiseconds (displayed in seconds).  The default 
	 value is 200 seconds."
    REFERENCE
	"ITU-T Rec. X.283 | ISO/IEC 10733 : x25PLE-DTE 
	     callRequestResponseTimer.
	 ITU-T Rec. X.25 | ISO/IEC 8208 : Timer T21."
    DEFVAL	{ 20000 } -- 200 seconds
    ::= { x25SVCIVMODTEEntry 1 }

x25SVCIVMODTEResetTime OBJECT-TYPE
    SYNTAX	TimeInterval
    UNITS	"seconds"
    MAX-ACCESS	read-create
    STATUS	current
    DESCRIPTION
	"Specifies the value for Timer T22 (Reset Request 
	 Response Timer) in centiseconds (displayed in seconds).  
	 The default value is 18000 (180 seconds)."
    REFERENCE
	"ITU-T Rec. X.283 | ISO/IEC 10733 : x25PLE-DTE 
	     resetRequestResponseTimer.
	 ITU-T Rec. X.25 | ISO/IEC 8208 : Timer T22"
    DEFVAL	{ 18000 } -- 180 seconds
    ::= { x25SVCIVMODTEEntry 2 }

x25SVCIVMODTEResetCount OBJECT-TYPE
    SYNTAX	INTEGER
    UNITS	"retransmissions"
    MAX-ACCESS	read-create
    STATUS	current
    DESCRIPTION
	"Specifies the value for Count R22 (Reset Request 
	 Retranmission Count) in retransmissions.  The default 
	 value is one (1) retransmission."
    REFERENCE
	"ITU-T Rec. X.283 | ISO/IEC 10733 : x25PLE-DTE 
	     resetRequestRetransmissionCount.
	 ITU-T Rec. X.25 | ISO/IEC 8208 : Count R22."
    DEFVAL	{ 1 }
    ::= { x25SVCIVMODTEEntry 3 }

x25SVCIVMODTEInterruptTime OBJECT-TYPE
    SYNTAX	TimeInterval
    UNITS	"seconds"
    MAX-ACCESS	read-create
    STATUS	current
    DESCRIPTION
	"Specifies the value for Timer T26 (Interrupt Response 
	 Timer) in centiseconds (displayed in seconds).  The 
	 default value is 18000 (180 seconds)."
    REFERENCE
	"ITU-T Rec. X.283 | ISO/IEC 10733 : x25PLE-DTE 
	     interruptResponseTimer.
	 ITU-T Rec. X.25 | ISO/IEC 8208 : Timer T26."
    DEFVAL	{ 18000 } -- 180 seconds
    ::= { x25SVCIVMODTEEntry 4 }

x25SVCIVMODTEClearTime OBJECT-TYPE
    SYNTAX	TimeInterval
    UNITS	"seconds"
    MAX-ACCESS	read-create
    STATUS	current
    DESCRIPTION
	"Specifies the value for Timer T23 (Clear Request 
	 Response Timer) in centiseconds (displayed in seconds).  
	 The default value is 18000 (180 seconds)."
    REFERENCE
	"ITU-T Rec. X.283 | ISO/IEC 10733 : x25PLE-DTE 
	     clearRequestResponseTimer.
	 ITU-T Rec. X.25 | ISO/IEC 8208 : Timer T23."
    DEFVAL	{ 18000 } -- 180 seconds
    ::= { x25SVCIVMODTEEntry 5 }

x25SVCIVMODTEClearCount OBJECT-TYPE
    SYNTAX	INTEGER
    UNITS	"restransmissions"
    MAX-ACCESS	read-create
    STATUS	current
    DESCRIPTION
	"Specifies the value for Count R23 (Clear Request 
	 Retransmission Count) in retransmissions.  The default 
	 value is one (1) retransmission."
    REFERENCE
	"ITU-T Rec. X.283 | ISO/IEC 10733 : x25PLE-DTE 
	     clearRequestRetransmissionCount.
	 ITU-T Rec. X.25 | ISO/IEC 8208 : Count R23."
    ::= { x25SVCIVMODTEEntry 6 }

-- PACKAGE receivingWindowRotationRecoveryProcedures-P
x25SVCIVMODTEWindowTime OBJECT-TYPE
    SYNTAX	TimeInterval
    MAX-ACCESS	read-create
    STATUS	current
    DESCRIPTION
	""
    REFERENCE
	"ITU-T Rec. X.283 | ISO/IEC 10733 : x25PLE-DTE 
	     windowStatusTransmissionTimer."
    ::= { x25SVCIVMODTEEntry 7 }

-- PACKAGE transmittingWindowRotationRecoveryProcedures-P
x25SVCIVMODTEDataTime OBJECT-TYPE
    SYNTAX	TimeInterval
    MAX-ACCESS	read-create
    STATUS	current
    DESCRIPTION
	""
    REFERENCE
	"ITU-T Rec. X.283 | ISO/IEC 10733 : x25PLE-DTE 
	     windowRotationTimer."
    ::= { x25SVCIVMODTEEntry 8 }

x25SVCIVMODTEDataCount OBJECT-TYPE
    SYNTAX	INTEGER
    MAX-ACCESS	read-create
    STATUS	current
    DESCRIPTION
	""
    REFERENCE
	"ITU-T Rec. X.283 | ISO/IEC 10733 : x25PLE-DTE 
	     dataPacketRetransmissionCount."
    ::= { x25SVCIVMODTEEntry 9 }

-- PACKAGE packetRetransmissionProcedures-P
x25SVCIVMODTERejectTime OBJECT-TYPE
    SYNTAX	TimeInterval
    MAX-ACCESS	read-create
    STATUS	current
    DESCRIPTION
	""
    REFERENCE
	"ITU-T Rec. X.283 | ISO/IEC 10733 : x25PLE-DTE 
	     rejectResponseTimer."
    ::= { x25SVCIVMODTEEntry 10 }

x25SVCIVMODTERejectCount OBJECT-TYPE
    SYNTAX	INTEGER
    MAX-ACCESS	read-create
    STATUS	current
    DESCRIPTION
	""
    REFERENCE
	"ITU-T Rec. X.283 | ISO/IEC 10733 : x25PLE-DTE 
	     rejectRetransmissionCount."
    ::= { x25SVCIVMODTEEntry 11 }

x25SVCIVMODTERowStatus OBJECT-TYPE
    SYNTAX	RowStatus
    MAX-ACCESS	read-create
    STATUS	current
    DESCRIPTION
	""
    REFERENCE
	""
    ::= { x25SVCIVMODTEEntry 12 }

x25SVCIVMODXE OBJECT IDENTIFIER
    ::= { x25PLPTables 18 }

x25SVCIVMODXETable OBJECT-TYPE
    SYNTAX	SEQUENCE OF X25SVCIVMODXEEntry
    MAX-ACCESS	not-accessible
    STATUS	current
    DESCRIPTION
	""
    REFERENCE
	"ITU-T Rec. X.283 | ISO/IEC 10733 : virtualCallIVMO."
    ::= { x25SVCIVMODXE 1 }

x25SVCIVMODXEEntry OBJECT-TYPE
    SYNTAX	X25SVCIVMODXEEntry
    MAX-ACCESS	not-accessible
    STATUS	current
    DESCRIPTION
	""
    REFERENCE
	"ITU-T Rec. X.283 | ISO/IEC 10733 : virtualCallIVMO."
    INDEX	{
		    x25PLEId,	    -- shared index (CONTAINED BY)
		    x25SVCIVMOId    -- shared index (DERIVED FROM)
		}
    ::= { x25SVCIVMODXETable 1 }

X25SVCIVMODXEEntry ::= SEQUENCE {
    x25SVCIVMODXECallTime		TimeInterval,
    x25SVCIVMODXEResetTime		TimeInterval,
    x25SVCIVMODXEResetCount		INTEGER,
    x25SVCIVMODXEInterruptTime		TimeInterval,
    x25SVCIVMODXEClearTime		TimeInterval,
    x25SVCIVMODXEClearCount		INTEGER,
    -- PACKAGE receivingWindowRotationRecoveryProcedures-P
    x25SVCIVMODXEWindowTime		TimeInterval,
    -- PACKAGE transmittingWindowRotationRecoveryProcedures-P
    x25SVCIVMODXEDataTime		TimeInterval,
    x25SVCIVMODXEDataCount		INTEGER,
    -- PACKAGE packetRetransmissionProcedures-P
    x25SVCIVMODXERejectTime		TimeInterval,
    x25SVCIVMODXERejectCount		INTEGER,
    x25SVCIVMODXERowStatus		RowStatus,
}

x25SVCIVMODXECallTime OBJECT-TYPE
    SYNTAX	TimeInterval
    MAX-ACCESS	read-create
    STATUS	current
    DESCRIPTION
	""
    REFERENCE
	"ISO/IEC 10733: virtualCallIVMO."
    ::= { x25SVCIVMODXEEntry 1 }

x25SVCIVMODXEResetTime OBJECT-TYPE
    SYNTAX	TimeInterval
    MAX-ACCESS	read-create
    STATUS	current
    DESCRIPTION
	""
    REFERENCE
	"ISO/IEC 10733: virtualCallIVMO."
    ::= { x25SVCIVMODXEEntry 2 }

x25SVCIVMODXEResetCount OBJECT-TYPE
    SYNTAX	INTEGER
    MAX-ACCESS	read-create
    STATUS	current
    DESCRIPTION
	""
    REFERENCE
	"ISO/IEC 10733: virtualCallIVMO."
    ::= { x25SVCIVMODXEEntry 5 }

x25SVCIVMODXEInterruptTime OBJECT-TYPE
    SYNTAX	TimeInterval
    MAX-ACCESS	read-create
    STATUS	current
    DESCRIPTION
	""
    REFERENCE
	"ISO/IEC 10733: virtualCallIVMO."
    ::= { x25SVCIVMODXEEntry 4 }

x25SVCIVMODXEClearTime OBJECT-TYPE
    SYNTAX	TimeInterval
    MAX-ACCESS	read-create
    STATUS	current
    DESCRIPTION
	""
    REFERENCE
	"ISO/IEC 10733: virtualCallIVMO."
    ::= { x25SVCIVMODXEEntry 3 }

x25SVCIVMODXEClearCount OBJECT-TYPE
    SYNTAX	INTEGER
    MAX-ACCESS	read-create
    STATUS	current
    DESCRIPTION
	""
    REFERENCE
	"ISO/IEC 10733: virtualCallIVMO."
    ::= { x25SVCIVMODXEEntry 6 }

-- PACKAGE receivingWindowRotationRecoveryProcedures-P
x25SVCIVMODXEWindowTime OBJECT-TYPE
    SYNTAX	TimeInterval
    MAX-ACCESS	read-create
    STATUS	current
    DESCRIPTION
	""
    REFERENCE
	"ISO/IEC 10733: virtualCallIVMO windowTime."
    ::= { x25SVCIVMODXEEntry 8 }

-- PACKAGE transmittingWindowRotationRecoveryProcedures-P
x25SVCIVMODXEDataTime OBJECT-TYPE
    SYNTAX	TimeInterval
    MAX-ACCESS	read-create
    STATUS	current
    DESCRIPTION
	""
    REFERENCE
	"ISO/IEC 10733: virtualCallIVMO dataRetransmissionTime."
    ::= { x25SVCIVMODXEEntry 9 }

x25SVCIVMODXEDataCount OBJECT-TYPE
    SYNTAX	INTEGER
    MAX-ACCESS	read-create
    STATUS	current
    DESCRIPTION
	""
    REFERENCE
	"ISO/IEC 10733: virtualCallIVMO dataRetransmissionCount."
    ::= { x25SVCIVMODXEEntry 10 }

-- PACKAGE packetRetransmissionProcedures-P
x25SVCIVMODXERejectTime OBJECT-TYPE
    SYNTAX	TimeInterval
    MAX-ACCESS	read-create
    STATUS	current
    DESCRIPTION
	""
    REFERENCE
	"ISO/IEC 10733: virtualCallIVMO rejectTime."
    ::= { x25SVCIVMODXEEntry 12 }

x25SVCIVMODXERejectCount OBJECT-TYPE
    SYNTAX	INTEGER
    MAX-ACCESS	read-create
    STATUS	current
    DESCRIPTION
	""
    REFERENCE
	"ISO/IEC 10733: virtualCallIVMO rejectCount."
    ::= { x25SVCIVMODXEEntry 13 }

x25SVCIVMODXERowStatus OBJECT-TYPE
    SYNTAX	RowStatus
    MAX-ACCESS	read-create
    STATUS	current
    DESCRIPTION
	""
    REFERENCE
	"ISO/IEC 10733: virtualCallIVMO."
    ::= { x25SVCIVMODXEEntry 7 }


x25SVCDTE OBJECT IDENTIFIER
    ::= { x25PLPTables 19 }

x25SVCDTETable OBJECT-TYPE
    SYNTAX	SEQUENCE OF X25SVCDTEEntry
    MAX-ACCESS	not-accessible
    STATUS	current
    DESCRIPTION
	"Objects in this table generate 
	 communicationsInformation notifications.
	
	 This package imports the communicationsInformation 
	 notification from GMI.  It is used to report the 
	 following events:
	
	 successfulConnectionEstablishment: Generate when a 
	 connection is sucessfully established.  However, the 
	 precise synchronization between the notification and 
	 the corresponding protocol and service interface 
	 interactions is not defined by this Specification.  The 
	 value NLM.successfulConnectionEstablishment shall be 
	 reported in the informationType field.
	
	 Objects in this table support the 'deactivate' action.
	
	 The Deactivate action causes the connection to be 
	 terminated.  The termination should occur as rapidly as 
	 practical, but no particular time constraints are 
	 implied. Typically, this action simulates a disconnect 
	 request received across the service interface. If a 
	 more rapid means for terminating the connection exists, 
	 then this should be used. The termination shall occur 
	 in conformance to the protocol standard. The Managed 
	 Object remains in existence after completion of the 
	 Deactivate action.  It is subsequently deleted when the 
	 connection is terminated, in the same way as if the 
	 connection has been terminated by other means. A 
	 deactivate action may fail (with the ProcessingError 
	 response) if it is temporarily not possible to 
	 terminate the connection."
    REFERENCE
	"ITU-T Rec. X.283 | ISO/IEC 10733 : virtualCall-DTE 
	     MOC."
    ::= { x25SVCDTE 1 }

x25SVCDTEEntry OBJECT-TYPE
    SYNTAX	X25SVCDTEEntry
    MAX-ACCESS	not-accessible
    STATUS	current
    DESCRIPTION
	"An instance of this MO exists for each Virtual Call.  
	 It is not created by management but by the operation of 
	 the protocol state machine.  An existing instance may, 
	 however, be deactivated by mangement action, which will 
	 cause the associated VC to be cleared.
	
	 An instance of this MO is created and exists as long as 
	 real resources are consumed by the existence of the 
	 virtual call.  It is an implementation matter to 
	 determine the point during call establishment when real 
	 resources are consumed, and conversely, when during 
	 call clearing, when they are released."
    REFERENCE
	"ITU-T Rec. X.283 | ISO/IEC 10733 : virtualCall-DTE MO."
    INDEX	{
		    x25PLEId,	-- shared index (CONTAINED BY)
		    x25VCId	-- shared index (DERIVED FROM)
		}
    ::= { x25SVCDTETable 1 }

X25SVCDTEEntry ::= SEQUENCE {
    x25SVCDTEDirection			Direction,
    x25SVCDTERemoteDTEAddress		DTEAddress,
    x25SVCDTEFastSelect			FastSelect,
    x25SVCDTEReverseCharging		TruthValue,
    x25SVCDTERedirectReason		RedirectReason,
    x25SVCDTEOriginallyCalledAddress	DTEAddress,
    x25SVCDTECallingAddressExtension	NetworkAddress,
    x25SVCDTECalledAddressExtension	NetworkAddress,
    -- Minimum Throughput Class Negotiation ? X.7, 6.1.1.3 ITU-DTE
    -- Transit Delay Selection and Indication ? X.7, 6.1.4.1 ITU-DTE
    -- End-to-end Transit Delay Negotiation ? X.7, 6.1.4.2 ITU-DTE
    -- Expedited Data ? X.7, 6.1.7. ITU-DTE
    -- Priority ? X.7, 6.1.8. ITU-DTE
    -- Alternative Address Selection ? X.7 6.3.5.3
    -- Direct Call ? X.7 6.3.6
    -- Called Line Address Modification Notification ? X.7 6.3.9
    -- Call Deflection Selection ? X.7 6.4.2.1
    -- IRCD Status Selection ? X.7 6.4.3.2
    -- ROA Selection ? X.7 6.4.6.2
    -- NUI Subscription ? X.7 6.5.3.1.
    -- NUI Override ? X.7 6.5.3.2
    -- NUI Selection ? X.7 6.5.3.3.
    -- Closed User Group Selection ?
    -- Closed User Group With Outgoing Access Selection ?
    -- Bilateral Closed User Group Selection ?
    -- Protection ? X.7 6.6.7 ITU-DTE
}

x25SVCDTEDirection OBJECT-TYPE
    SYNTAX	Direction
    MAX-ACCESS	read-only
    STATUS	current
    DESCRIPTION
	"The direction of the call using the Direction textual 
	 convention.  This value can either be incoming(0) or 
	 outgoing(1)."
    REFERENCE
	"ITU-T Rec. X.283 | ISO/IEC 10733 : virtualCall-DTE."
    ::= { x25SVCDTEEntry 3 }

x25SVCDTERemoteDTEAddress OBJECT-TYPE
    SYNTAX	DTEAddress
    MAX-ACCESS	read-only
    STATUS	current
    DESCRIPTION
	"The DTE Address of the remote DTE, using the DTEAddress 
	 textual convention.  In the case of an outgoing call 
	 this is the remote DTE address form the called address 
	 of the transmitted call request packet.  In the case of 
	 an incoming call, it is the calling address from the 
	 received call request packet.  For a PVC, it is the 
	 admintratively assigned address of the DTE at the 
	 remote end of the PVC.  The DTEAddress textual 
	 convention supports X.121 and E.164 DTE adresses as 
	 well as TOA/NPI addresses."
    REFERENCE
	"ITU-T Rec. X.283 | ISO/IEC 10733 : virtualCall-DTE 
	     remoteDTEAddress.
	 ITU-T Rec. X.25 Clause 5.2."
    ::= { x25SVCDTEEntry 7 }

x25SVCDTEFastSelect OBJECT-TYPE
    SYNTAX	FastSelect
    MAX-ACCESS	read-only
    STATUS	current
    DESCRIPTION
	"The type of fast select used on the call using the 
	 FastSelect textual convention.  This can have values as 
	 follows:
	
	 - notSpecified(0), the agent does not track fast select 
	   setting for switched virtual calls.
	   
	 - fastSelect(1), fast select with unrestricted response 
	   was selected for the call.
	   
	 - fastSelectWithRestrictedResponse(2), fast select with 
	   restricted response was selected for the call.
	   
	 - noFastSelect(3), fast select was not selected for the 
	   call.
	
	 Fast Select is an optional user facility that requires 
	 dynamic invocation on packet switched networks."
    REFERENCE
	"ITU-T Rec. X.283 | ISO/IEC 10733 : virtualCall-DTE 
	     fastSelect.
	 ITU-T Rec. X.7, Clause 6.2.1.1."
    ::= { x25SVCDTEEntry 4 }

x25SVCDTEReverseCharging OBJECT-TYPE
    SYNTAX	TruthValue
    MAX-ACCESS	read-only
    STATUS	current
    DESCRIPTION
	"Whether the call was initiated requesting reverse 
	 charging.  When true(1), the call was initiated 
	 requesting reverse charging.  When false(2), reverse 
	 charging was not requested.  This is only applicable to 
	 DTE operating in the X.25 mode.
	
	 Reverse Charging is an optional user facility that 
	 requires dynamic invocation on a circuit switched or 
	 packet switched network."
    REFERENCE
	"ITU-T Rec. X.283 | ISO/IEC 10733 : virtualCall-DTE 
	     reverseCharging.
	 ITU-T Rec. X.7, Clause 6.5.1.1."
    ::= { x25SVCDTEEntry 8 }

x25SVCDTERedirectReason OBJECT-TYPE
    SYNTAX	RedirectReason
    MAX-ACCESS	read-only
    STATUS	current
    DESCRIPTION
	"The reason why the call has been redirected. This is 
	 the reason why the call has been offered or has been 
	 connected to an address different from the originally 
	 called address. That is, the value of the first octet 
	 of the Facility Parameter Field of the Call Redirection 
	 or Call Deflection Notification (CRCDN) or Called Line 
	 Address Modified Notification (CLAMN) facility, 
	 indicating the reason for call redirection or call 
	 deflection. The zero value indicates that the call was 
	 not redirected.
	
	 Call Redirection or Call Deflection Notification is an 
	 optional user facility that requires dynamic invocation 
	 on an packet switched network.
	
	 Note that Call Redireaction and Call Deflection 
	 Notification (CRCDN) and Called Line Address Modified 
	 Notification (CLAMN) facilities are not supported by 
	 the 1980 version of X.25, x2580(8)."
    REFERENCE
	"ITU-T Rec. X.283 | ISO/IEC 10733 : virtualCall-DTE 
	     redirectReason.
	 ITU-T Rec. X.7, Clause 6.3.9., 6.4.4."
    ::= { x25SVCDTEEntry 6 }

x25SVCDTEOriginallyCalledAddress OBJECT-TYPE
    SYNTAX	DTEAddress
    MAX-ACCESS	read-only
    STATUS	current
    DESCRIPTION
	"Indicates the originalling called DTE address using the 
	 DTEAddress textual convention.  This differs from the 
	 remote DTE address (for outgoing calls) or from the 
	 local DTE address (for incoming calls) when the call 
	 has been deflected or redirected.  The DTEAddress 
	 textual convention supports X.121 and E.164 DTE 
	 addresses as well as TOA/NPI addresses."
    REFERENCE
	"ITU-T Rec. X.283 | ISO/IEC 10733 : virtualCall-DTE 
	     originallyCalledAddress.
	 ITU-T Rec. X.25 Clause 5.2."
    ::= { x25SVCDTEEntry 5 }

x25SVCDTECallingAddressExtension OBJECT-TYPE
    SYNTAX	NetworkAddress
    MAX-ACCESS	read-only
    STATUS	current
    DESCRIPTION
	"Indicates the calling address extension facility 
	 associated with the virtual call, using the 
	 NetworkAddress textual convention.  This is the 
	 contents of the Calling Address Extension Facility 
	 associated with the call per ITU-T Rec. X.25 Clause 7.2 
	 and Annex G.3.1.  When the address is a null octet 
	 string, it indicates that there was no Calling address 
	 extension facility in the call setup packets.
	
	 Address Extension is an optional ITU-T Specified DTE 
	 user facility that requires dynamic invocation on a 
	 packet switched network.
	
	 Calling and Called Address Extension facilities are 
	 optional ITU-T Specified DTE user facilities which may 
	 be used for a given virtual call.  They provide for 
	 transparent conveyance in call request and incoming 
	 call packets of additional calling and called 
	 addressing information (e.g. OSI Network Service Access 
	 Point (NSAP) addresses)."
    REFERENCE
	"ITU-T Rec. X.283 | ISO/IEC 10733 : virtualCall-DTE.
	 ITU-T Rec. X.25 7.2, Annex G.3.1.
	 ITU-T Rec. X.7, Clause 6.3.1."
    ::= { x25SVCDTEEntry 1 }

x25SVCDTECalledAddressExtension OBJECT-TYPE
    SYNTAX	NetworkAddress
    MAX-ACCESS	read-only
    STATUS	current
    DESCRIPTION
	"Indicates the Called address extension facilyt 
	 associated with the virtual call, using the 
	 NetworkAddress textual convention.  This is the 
	 contents of the Called Address Extension Facility 
	 associated with the call per ITU-T Rec. X.25 Clause 7.2 
	 and Annex G.3.2.  When the address is a null octet 
	 string, it indicates that there was no Called address 
	 extension facility in the call setup packets.
	
	 Address Extension is an optional ITU-T Specified DTE 
	 user facility that requires dynamic invocation on a 
	 packet switched network.
	
	 Calling and Called Address Extension facilities are 
	 optional ITU-T Specified DTE user facilities which may 
	 be used for a given virtual call.  They provide for 
	 transparent conveyance in call request and incoming 
	 call packets of additional calling and called 
	 addressing information (e.g. OSI Network Service Access 
	 Point (NSAP) addresses).
	
	 The Called Address Extention facility also provides for 
	 transparent conveyance of additional responding 
	 addressing information in call accepted/call connected 
	 packets and in clear request/clear indication packets."
    REFERENCE
	"ITU-T Rec. X.283 | ISO/IEC 10733 : virtualCall-DTE.
	 ITU-T Rec. X.25 7.2, Annex G.3.2.
	 ITU-T Rec. X.7, Clause 6.3.1."
    ::= { x25SVCDTEEntry 2 }


x25SVCDCE OBJECT IDENTIFIER
    ::= { x25PLPTables 20 }

x25SVCDCETable OBJECT-TYPE
    SYNTAX	SEQUENCE OF X25SVCDCEEntry
    MAX-ACCESS	not-accessible
    STATUS	current
    DESCRIPTION
	"Objects in this table generate 
	 communicationsInformation notifications.
	
	 This package imports the communicationsInformation 
	 notification from GMI.  It is used to report the 
	 following events:
	
	 successfulConnectionEstablishment: Generate when a 
	 connection is sucessfully established.  However, the 
	 precise synchronization between the notification and 
	 the corresponding protocol and service interface 
	 interactions is not defined by this Specification.  The 
	 value NLM.successfulConnectionEstablishment shall be 
	 reported in the informationType field.
	
	 Objects in this table support the 'deactivate' action.
	
	 The Deactivate action causes the connection to be 
	 terminated.  The termination should occur as rapidly as 
	 practical, but no particular time constraints are 
	 implied. Typically, this action simulates a disconnect 
	 request received across the service interface. If a 
	 more rapid means for terminating the connection exists, 
	 then this should be used. The termination shall occur 
	 in conformance to the protocol standard. The Managed 
	 Object remains in existence after completion of the 
	 Deactivate action.  It is subsequently deleted when the 
	 connection is terminated, in the same way as if the 
	 connection has been terminated by other means. A 
	 deactivate action may fail (with the ProcessingError 
	 response) if it is temporarily not possible to 
	 terminate the connection."
    REFERENCE
	"ITU-T Rec. X.283 | ISO/IEC 10733 : virtualCall-DCE 
	     MOC."
    ::= { x25SVCDCE 1 }

x25SVCDCEEntry OBJECT-TYPE
    SYNTAX	X25SVCDCEEntry
    MAX-ACCESS	not-accessible
    STATUS	current
    DESCRIPTION
	"An instance of this MO is created and exists as long a 
	 real resources are consumed by the existence of the 
	 Virtual Call.  It is an implementation matter to 
	 determine the point during a call establishment when 
	 real resources are consumed, and conversely, when 
	 during call clearing, when they are released."
    REFERENCE
	"ITU-T Rec. X.283 | ISO/IEC 10733 : virtualCall-DCE MO."
    INDEX	{
		    x25PLEId,	-- shared index (CONTAINED BY)
		    x25VCId	-- shared index (DERIVED FROM)
		}
    ::= { x25SVCDCETable 1 }

X25SVCDCEEntry ::= SEQUENCE {
    x25SVCDCEDirection				Direction,
    x25SVCDCERemoteDTEAddress			DTEAddress,
    x25SVCDCEFastSelect				FastSelect,
    x25SVCDCEChargingDirection			TruthValue,
    x25SVCDCECUGSelection			Subscription,
    x25SVCDCETransitDelaySelectionAndIndication	TruthValue,
    -- Minimum Throughput Class Negotiation ? X.7, 6.1.1.3 ITU-DTE
    -- End-to-end Transit Delay Negotiation ? X.7, 6.1.4.2 ITU-DTE
    -- Expedited Data ? X.7, 6.1.7. ITU-DTE
    -- Priority ? X.7, 6.1.8. ITU-DTE
    -- Alternative Address Selection ? X.7 6.3.5.3
    -- Direct Call ? X.7 6.3.6
    -- Called Line Address Modification Notification ? X.7 6.3.9
    -- Call Deflection Selection ? X.7 6.4.2.1
    -- IRCD Status Selection ? X.7 6.4.3.2
    -- ROA Selection ? X.7 6.4.6.2
    -- NUI Subscription ? X.7 6.5.3.1.
    -- NUI Override ? X.7 6.5.3.2
    -- NUI Selection ? X.7 6.5.3.3.
    -- Closed User Group Selection ?
    -- Closed User Group With Outgoing Access Selection ?
    -- Bilateral Closed User Group Selection ?
    -- Protection ? X.7 6.6.7 ITU-DTE
}

x25SVCDCEDirection OBJECT-TYPE
    SYNTAX	Direction
    MAX-ACCESS	read-only
    STATUS	current
    DESCRIPTION
	"The direction of the call using the Direction textual 
	 convention.  This value can either be incoming(0) or 
	 outgoing(1)."
    REFERENCE
	"ITU-T Rec. X.283 | ISO/IEC 10733 : virtualCall-DCE."
    ::= { x25SVCDCEEntry 3 }

x25SVCDCERemoteDTEAddress OBJECT-TYPE
    SYNTAX	DTEAddress
    MAX-ACCESS	read-only
    STATUS	current
    DESCRIPTION
	"The DTE Address of the remote DTE, using the DTEAddress 
	 textual convention.  In the case of an outgoing call 
	 this is the remote DTE address form the called address 
	 of the transmitted call request packet.  In the case of 
	 an incoming call, it is the calling address from the 
	 received call request packet.  For a PVC, it is the 
	 admintratively assigned address of the DTE at the 
	 remote end of the PVC.  The DTEAddress textual 
	 convention supports X.121 and E.164 DTE adresses as 
	 well as TOA/NPI addresses."
    REFERENCE
	"ITU-T Rec. X.283 | ISO/IEC 10733 : virtualCall-DCE 
	     remoteDTEAddress.
	 ITU-T Rec. X.25 Clause 5.2."
    ::= { x25SVCDCEEntry 5 }

x25SVCDCEFastSelect OBJECT-TYPE
    SYNTAX	FastSelect
    MAX-ACCESS	read-only
    STATUS	current
    DESCRIPTION
	"The type of fast select used on the call using the 
	 FastSelect textual convention.  This can have values as 
	 follows:
	
	 - notSpecified(0), the agent does not track fast select 
	   setting for switched virtual calls.
	   
	 - fastSelect(1), fast select with unrestricted response 
	   was selected for the call.
	   
	 - fastSelectWithRestrictedResponse(2), fast select with 
	   restricted response was selected for the call.
	   
	 - noFastSelect(3), fast select was not selected for the 
	   call.

	 Fast Select is an optional user facility that requires 
	 dynamic invocation on a packet-switched network."
    REFERENCE
	"ITU-T Rec. X.283 | ISO/IEC 10733 : virtualCall-DCE 
	     fastSelect.
	 ITU-T Rec. X.7, Clause 6.2.1.1."
    ::= { x25SVCDCEEntry 4 }

x25SVCDCEChargingDirection OBJECT-TYPE
    SYNTAX	TruthValue
    MAX-ACCESS	read-only
    STATUS	current
    DESCRIPTION
	""
    REFERENCE
	"ITU-T Rec. X.283 | ISO/IEC 10733 : virtualCall-DCE 
	     chargingDirection."
    ::= { x25SVCDCEEntry 1 }

x25SVCDCECUGSelection OBJECT-TYPE
    SYNTAX	Subscription
    MAX-ACCESS	read-only
    STATUS	current
    DESCRIPTION
	"Whether the Closed User Group (CUG) facility was 
	 selected for the call using the TruthValue textual 
	 convention.  When true(1), it indicates that the CUG 
	 facility was selected; when false(2), CUG was not 
	 selected.
	
	 Closed User Group Selection is an optional user 
	 facility that requires dynamic invocation on circuit 
	 switched and packet switched networks.
	 "
    REFERENCE
	"ITU-T Rec. X.283 | ISO/IEC 10733 : virtualCall-DCE 
	     cUGSelection."
    ::= { x25SVCDCEEntry 2 }

x25SVCDCETransitDelaySelectionAndIndication OBJECT-TYPE
    SYNTAX	TruthValue
    MAX-ACCESS	read-only
    STATUS	current
    DESCRIPTION
	"Whether the Transit Delay Selection and Indication 
	 (TDSI) facility was selected for the call using the 
	 TruthValue textual convention.  When true(1), TDSI was 
	 requested for the call; when false(2), TSDI was not 
	 selected.
	
	 Transit Delay Selection and Indication is an optional 
	 ITU-T Specified DTE user facility that requires dynamic 
	 invocation on packet switched networks.
	
	 Note that the Transit Delay Selection and Indication 
	 (TSDI) faciltiy is not supported by the 1980 version of 
	 X.25, x2580(8)."
    REFERENCE
	"ITU-T Rec. X.283 | ISO/IEC 10733 : virtualCall-DCE 
	     transitDelaySelectionAndIndication.
	 ITU-T Rec. X.7, Clause 6.1.4.1."
    ::= { x25SVCDCEEntry 6 }


x25SVCDXE OBJECT IDENTIFIER
    ::= { x25PLPTables 21 }

x25SVCDXETable OBJECT-TYPE
    SYNTAX	SEQUENCE OF X25SVCDXEEntry
    MAX-ACCESS	not-accessible
    STATUS	current
    DESCRIPTION
	"Objects in this table generate 
	 communicationsInformation notifications.
	
	 This package imports the communicationsInformation 
	 notification from GMI.  It is used to report the 
	 following events:
	
	 successfulConnectionEstablishment: Generate when a 
	 connection is sucessfully established.  However, the 
	 precise synchronization between the notification and 
	 the corresponding protocol and service interface 
	 interactions is not defined by this Specification.  The 
	 value NLM.successfulConnectionEstablishment shall be 
	 reported in the informationType field.
	
	 Objects in this table support the 'deactivate' action.
	
	 The Deactivate action causes the connection to be 
	 terminated.  The termination should occur as rapidly as 
	 practical, but no particular time constraints are 
	 implied. Typically, this action simulates a disconnect 
	 request received across the service interface. If a 
	 more rapid means for terminating the connection exists, 
	 then this should be used. The termination shall occur 
	 in conformance to the protocol standard. The Managed 
	 Object remains in existence after completion of the 
	 Deactivate action.  It is subsequently deleted when the 
	 connection is terminated, in the same way as if the 
	 connection has been terminated by other means. A 
	 deactivate action may fail (with the ProcessingError 
	 response) if it is temporarily not possible to 
	 terminate the connection."
    REFERENCE
	"ISO/IEC 10733 : switchedVirtualCall MOC."
    ::= { x25SVCDXE 1 }

x25SVCDXEEntry OBJECT-TYPE
    SYNTAX	X25SVCDXEEntry
    MAX-ACCESS	not-accessible
    STATUS	current
    DESCRIPTION
	"An instance of this MO exists for each Virtual Call.  
	 It is not created by management, but by the operation 
	 of the protocol state machine.  An existing instance 
	 may, however, be deleted by management action, which 
	 will cause the associated VC to be cleared.  An 
	 instance of this MO is created and exists as long as 
	 real resources are consumed by the existence of the 
	 virtual call.  It is an implementation matter to 
	 determine th point during call establishment when real 
	 resources are consumed, and conversely, when during 
	 call clearing, when they are released."
    REFERENCE
	"ISO/IEC 10733 : switchedVirtualCall MO."
    INDEX	{
		    x25PLEId,	-- shared index (CONTAINED BY)
		    x25VCId	-- shared index (DERIVED FROM)
		}
    ::= { x25SVCDXETable 1 }

X25SVCDXEEntry ::= SEQUENCE {
    x25SVCDXEDirection			Direction,
    x25SVCDXERemoteDTEAddress		DTEAddress,
    x25SVCDXEFastSelect			FastSelect,
    x25SVCDXERedirectReason		RedirectReason,
    x25SVCDXEOriginallyCalledAddress	DTEAddress,
    x25SVCDXECallingAddressExtension	NetworkAddress,
    x25SVCDXECalledAddressExtension	NetworkAddress,
    -- Minimum Throughput Class Negotiation ? X.7, 6.1.1.3 ITU-DTE
    -- Transit Delay Selection and Indication ? X.7, 6.1.4.1 ITU-DTE
    -- End-to-end Transit Delay Negotiation ? X.7, 6.1.4.2 ITU-DTE
    -- Expedited Data ? ITU-DTE
    -- Priority ? X.7, 6.1.8. ITU-DTE
    -- Alternative Address Selection ? X.7 6.3.5.3
    -- Direct Call ? X.7 6.3.6
    -- Called Line Address Modification Notification ?
    -- Call Deflection Selection ? X.7 6.4.2.1
    -- IRCD Status Selection ? X.7 6.4.3.2
    -- ROA Selection ? X.7 6.4.6.2
    -- NUI Subscription ? X.7 6.5.3.1.
    -- NUI Override ? X.7 6.5.3.2
    -- NUI Selection ? X.7 6.5.3.3.
    -- Closed User Group Selection ?
    -- Closed User Group With Outgoing Access Selection ?
    -- Bilateral Closed User Group Selection ?
    -- Protection ? X.7 6.6.7 ITU-DTE
}

x25SVCDXEDirection OBJECT-TYPE
    SYNTAX	Direction
    MAX-ACCESS	read-only
    STATUS	current
    DESCRIPTION
	"The direction of the call using the Direction textual 
	 convention.  This value can either be incoming(0) or 
	 outgoing(1)."
    REFERENCE
	"ITU-T Rec. X.283 | ISO/IEC 10733 : switchedVirtualCall."
    ::= { x25SVCDXEEntry 1 }

x25SVCDXERemoteDTEAddress OBJECT-TYPE
    SYNTAX	DTEAddress
    MAX-ACCESS	read-only
    STATUS	current
    DESCRIPTION
	"The DTE Address of the remote DTE, using the DTEAddress 
	 textual convention.  In the case of an outgoing call 
	 this is the remote DTE address form the called address 
	 of the transmitted call request packet.  In the case of 
	 an incoming call, it is the calling address from the 
	 received call request packet.  For a PVC, it is the 
	 admintratively assigned address of the DTE at the 
	 remote end of the PVC.  The DTEAddress textual 
	 convention supports X.121 and E.164 DTE adresses as 
	 well as TOA/NPI addresses."
    REFERENCE
	"ITU-T Rec. X.283 | ISO/IEC 10733 : switchedVirtualCall 
	     remoteDTEAddress.
	 ITU-T Rec. X.25 Clause 5.2."
    ::= { x25SVCDXEEntry 2 }

x25SVCDXEFastSelect OBJECT-TYPE
    SYNTAX	FastSelect
    MAX-ACCESS	read-only
    STATUS	current
    DESCRIPTION
	"The type of fast select used on the call using the 
	 FastSelect textual convention.  This can have values as 
	 follows:
	
	 - notSpecified(0), the agent does not track fast select 
	   setting for switched virtual calls.
	   
	 - fastSelect(1), fast select with unrestricted response 
	   was selected for the call.
	   
	 - fastSelectWithRestrictedResponse(2), fast select with 
	   restricted response was selected for the call.
	   
	 - noFastSelect(3), fast select was not selected for the 
	   call.
	
	 Fast Select is an optional user facility that requires 
	 dynamic invocation on a packet-switched network."
    REFERENCE
	"ITU-T Rec. X.283 | ISO/IEC 10733 : virtualCall-DTE 
	     fastSelect.
	 ITU-T Rec. X.7, Clause 6.2.1.1."
    ::= { x25SVCDXEEntry 4 }

--  x25SVCDXEThroughputClass
x25SVCDXERedirectReason OBJECT-TYPE
    SYNTAX	RedirectReason
    MAX-ACCESS	read-only
    STATUS	current
    DESCRIPTION
	"The reason why the call has been redirected. This is 
	 the reason why the call has been offered or has been 
	 connected to an address different from the originally 
	 called address. That is, the value of the first octet 
	 of the Facility Parameter Field of the Call Redirection 
	 or Call Deflection Notification (CRCDN) or Called Line 
	 Address Modified Notification (CLAMN) facility, 
	 indicating the reason for call redirection or call 
	 deflection. The zero value indicates that the call was 
	 not redirected.
	
	 Call Redirection or Call Deflection Notification is an 
	 optional user facility that requires dynamic invocation 
	 on an packet switched network.
	
	 Note that Call Redireaction and Call Deflection 
	 Notification (CRCDN) and Called Line Address Modified 
	 Notification (CLAMN) facilities are not supported by 
	 the 1980 version of X.25, x2580(8)."
    REFERENCE
	"ITU-T Rec. X.283 | ISO/IEC 10733 : switchedVirtualCall 
	     redirectReason.
	 ITU-T Rec. X.7, Clause 6.3.9., 6.4.4."
    ::= { x25SVCDXEEntry 5 }

x25SVCDXEOriginallyCalledAddress OBJECT-TYPE
    SYNTAX	DTEAddress
    MAX-ACCESS	read-only
    STATUS	current
    DESCRIPTION
	"Indicates the originalling called DTE address using the 
	 DTEAddress textual convention.  This differs from the 
	 remote DTE address (for outgoing calls) or from the 
	 local DTE address (for incoming calls) when the call 
	 has been deflected or redirected.  The DTEAddress 
	 textual convention supports X.121 and E.164 DTE 
	 addresses as well as TOA/NPI addresses."
    REFERENCE
	"ITU-T Rec. X.283 | ISO/IEC 10733 : switchedVirtualCall 
	     originallyCalledAddress.
	 ITU-T Rec. X.25 Clause 5.2."
    ::= { x25SVCDXEEntry 6 }

x25SVCDXECallingAddressExtension OBJECT-TYPE
    SYNTAX	NetworkAddress
    MAX-ACCESS	read-only
    STATUS	current
    DESCRIPTION
	"Indicates the calling address extension facility 
	 associated with the virtual call, using the 
	 NetworkAddress textual convention.  This is the 
	 contents of the Calling Address Extension Facility 
	 associated with the call per ITU-T Rec. X.25 Clause 7.2 
	 and Annex G.3.1.  When the address is a null octet 
	 string, it indicates that there was no Calling address 
	 extension facility in the call setup packets.
	
	 Address Extension is an optional ITU-T Specified DTE 
	 user facility that requires dynamic invocation on a 
	 packet switched network.
	
	 Calling and Called Address Extension facilities are 
	 optional ITU-T Specified DTE user facilities which may 
	 be used for a given virtual call.  They provide for 
	 transparent conveyance in call request and incoming 
	 call packets of additional calling and called 
	 addressing information (e.g. OSI Network Service Access 
	 Point (NSAP) addresses)."
    REFERENCE
	"ITU-T Rec. X.283 | ISO/IEC 10733 : switchedVirtualCall.
	 ITU-T Rec. X.25 7.2, Annex G.3.1.
	 ITU-T Rec. X.7, Clause 6.3.1."
    ::= { x25SVCDXEEntry 7 }

x25SVCDXECalledAddressExtension OBJECT-TYPE
    SYNTAX	NetworkAddress
    MAX-ACCESS	read-only
    STATUS	current
    DESCRIPTION
	"Indicates the Called address extension facilyt 
	 associated with the virtual call, using the 
	 NetworkAddress textual convention.  This is the 
	 contents of the Called Address Extension Facility 
	 associated with the call per ITU-T Rec. X.25 Clause 7.2 
	 and Annex G.3.2.  When the address is a null octet 
	 string, it indicates that there was no Called address 
	 extension facility in the call setup packets.
	
	 Address Extension is an optional ITU-T Specified DTE 
	 user facility that requires dynamic invocation on a 
	 packet switched network.
	
	 Calling and Called Address Extension facilities are 
	 optional ITU-T Specified DTE user facilities which may 
	 be used for a given virtual call.  They provide for 
	 transparent conveyance in call request and incoming 
	 call packets of additional calling and called 
	 addressing information (e.g. OSI Network Service Access 
	 Point (NSAP) addresses).
	
	 The Called Address Extention facility also provides for 
	 transparent conveyance of additional responding 
	 addressing information in call accepted/call connected 
	 packets and in clear request/clear indication packets."
    REFERENCE
	"ITU-T Rec. X.283 | ISO/IEC 10733 : switchedVirtualCall.
	 ITU-T Rec. X.25 7.2, Annex G.3.2.
	 ITU-T Rec. X.7, Clause 6.3.1."
    ::= { x25SVCDXEEntry 8 }


x25DSC OBJECT IDENTIFIER
    ::= { x25PLPTables 22 }

x25DSCTable OBJECT-TYPE
    SYNTAX	SEQUENCE OF X25DSCEntry
    MAX-ACCESS	not-accessible
    STATUS	current
    DESCRIPTION
	"Objects in this table generated objectCreation and 
	 objectDeletion notifications.
	
	 ITU-T Rec. D.11: The charges relating to the network 
	 utilization component should be proportional to the 
	 volume of information transmitted and to the duration 
	 of communication and should be calculated in accordance 
	 with the methods prescribed below:
	
	 The volume of information transmitted should be 
	 measured and expressed in conformity with ITU-T Rec.  
	 D.12.  Any chargeable packet other than the data packet 
	 should be considered as a packet for which a charge 
	 corresponding to a segment is levied.
	
	 The following packets are chargeable:
	
	 - data packet;
	
	 - interrupt packet;
	
	 - call request/call incoming packet;
	
	 - reset request/reset indication packet, provided the 
	   cause of the call reset is either 'DTE originated,' 
	   'local procedure error' or 'remote procedure error';
	
	 - clear request (when the fast select facility is 
	   signalled in the call request packet without 
	   restrictions).
	
	 The chargeable duration of a communication should be 
	 calculated on the basis of the information below.  The 
	 duration of communications should be measured and 
	 expressed in terms of a unit being equal to one minute.  
	 The duration of the communication should be the 
	 interval between:
	
	 - the moment when the call-connected packet or the 
	   call-accepted packet is sent or received by the 
	   chanrging DSE where the recording of the duration 
	   takes place; and
	
	 - the moment when the clear request packet or the clear 
	   indication packet is received or sent by the charging 
	   DSE.
	
	 If the duration of communications thus obtained 
	 contains a fractin of a minute, it should be rounded up 
	 to the next whole minute.  For a chargeable call as 
	 provided above, Administrations may apply a duration 
	 charge equal to one unit in addition to the charge for 
	 packets."
    REFERENCE
	"ITU-T Rec. X.283 | ISO/IEC 10733 : dSeriesCounts MOC."
    ::= { x25DSC 1 }

x25DSCEntry OBJECT-TYPE
    SYNTAX	X25DSCEntry
    MAX-ACCESS	not-accessible
    STATUS	current
    DESCRIPTION
	"There is one instance of this MO created by management 
	 action or automatically for each instance of a virtual 
	 call where the Tarriff Princiiples applying to Data 
	 Communications Services over dedicated Public Data 
	 networks are applicable.  The provisions of the tariff 
	 principles are defined in Recommendations D.10, D.11 
	 and D.12.
	
	 Provides the set of packet and segment counts required 
	 to collect the charges contained in ITU-T 
	 Recommendation D.10, D.11 and D.12 for international 
	 packet switched public data communications services.  
	 The values collected are reported at object deletion."
    REFERENCE
	"ITU-T Rec. X.283 | ISO/IEC 10733 : dSeriesCounts MO."
    INDEX	{
		    x25PLEId,	-- shared index (CONTAINED BY)
		    x25VCId,	-- shared index (CONTAINED BY)
		    x25DSCId	-- (BASE CLASS INSTANCE)
		}
    ::= { x25DSCTable 1 }

X25DSCEntry ::= SEQUENCE {
    x25DSCId					SimpleNameType,
    x25DSCResetRequestIndicationPackets		Counter64,
    x25DSCSegmentsSent				Counter64,
    x25DSCSegmentsReceived			Counter64,
}

x25DSCId OBJECT-TYPE
    SYNTAX	SimpleNameType
    MAX-ACCESS	read-only
    STATUS	current
    DESCRIPTION
	""
    REFERENCE
	"ITU-T Rec. X.283 | ISO/IEC 10733 : dSeriesCounts."
    ::= { x25DSCEntry 1 }

x25DSCResetRequestIndicationPackets OBJECT-TYPE
    SYNTAX	Counter64
    MAX-ACCESS	read-only
    STATUS	current
    DESCRIPTION
	"The value of the count of the Reset Request or Reset 
	 Indication packets with retrictions defined in 
	 ITU-T Recommendation D.11."
    REFERENCE
	"ITU-T Rec. X.283 | ISO/IEC 10733 : dSeriesCounts."
    ::= { x25DSCEntry 2 }

x25DSCSegmentsSent OBJECT-TYPE
    SYNTAX	Counter64
    MAX-ACCESS	read-only
    STATUS	current
    DESCRIPTION
	"The value of the count of segments sent, in 64 octets, 
	 as per ITU-T Rec. D.12.
	
	 ITU-T Rec. D.12: Definition of segment: the measurement 
	 unit use for charging for the volume of information 
	 transmitted in a packet-switched service is independent 
	 of the maximum packet length.  It is called a segment 
	 and its length is 64 octets (this number is subject to 
	 further study).  Operating rule: the quantity of 
	 chargeable data contained in each message is expressed 
	 as a number of segments and is rounded off to the next 
	 higher unit.
	 "
    REFERENCE
	"ITU-T Rec. X.283 | ISO/IEC 10733 : dSeriesCounts."
    ::= { x25DSCEntry 3 }

x25DSCSegmentsReceived OBJECT-TYPE
    SYNTAX	Counter64
    MAX-ACCESS	read-only
    STATUS	current
    DESCRIPTION
	"The value of the count of segments received, in 64 
	 octets, as per ITU-T Rec. D.12.
	
	 ITU-T Rec. D.12: Definition of segment: the measurement 
	 unit use for charging for the volume of information 
	 transmitted in a packet-switched service is independent 
	 of the maximum packet length.  It is called a segment 
	 and its length is 64 octets (this number is subject to 
	 further study).  Operating rule: the quantity of 
	 chargeable data contained in each message is expressed 
	 as a number of segments and is rounded off to the next 
	 higher unit.
	 "
    REFERENCE
	"ITU-T Rec. X.283 | ISO/IEC 10733 : dSeriesCounts."
    ::= { x25DSCEntry 4 }


x25PLEDTEStats OBJECT IDENTIFIER
    ::= { x25PLPTables 23 }

x25PLEDTEStatsTable OBJECT-TYPE
    SYNTAX	SEQUENCE OF X25PLEDTEStatsEntry
    MAX-ACCESS	not-accessible
    STATUS	current
    DESCRIPTION
	""
    REFERENCE
	"ITU-T Rec. X.283 | ISO/IEC 10733."
    ::= { x25PLEDTEStats 1 }

x25PLEDTEStatsEntry OBJECT-TYPE
    SYNTAX	X25PLEDTEStatsEntry
    MAX-ACCESS	not-accessible
    STATUS	current
    DESCRIPTION
	""
    REFERENCE
	"ITU-T Rec. X.283 | ISO/IEC 10733."
    INDEX	{
		    x25PLEId	-- shared index (AUGMENTS)
		}
    ::= { x25PLEDTEStatsTable 1 }

X25PLEDTEStatsEntry ::= SEQUENCE {
    x25PLEDTEStatsCallAttempts			Counter64,
    x25PLEDTEStatsProtocolErrorsDetectedLocally	Counter64,
    x25PLEDTEStatsProtocolErrorsAccusedOf	Counter64,
    x25PLEDTEStatsCallCountsExceeded		Counter64,
    -- PACKAGE dTEX25PLECounters-P
    x25PLEDTEStatsOctetsReceived		Counter64,
    x25PLEDTEStatsOctetsSent			Counter64,
    x25PLEDTEStatsCallTimeouts			Counter64,
    x25PLEDTEStatsCallsConnected		Counter64,
    x25PLEDTEStatsDataPacketsReceived		Counter64,
    x25PLEDTEStatsDataPacketsSent		Counter64,
    x25PLEDTEStatsDataTimeouts			Counter64,
    x25PLEDTEStatsProviderResets		Counter64,
    x25PLEDTEStatsProviderDisconnects		Counter64,
    x25PLEDTEStatsRemoteResets			Counter64,
    x25PLEDTEStatsRemoteRestarts		Counter64,
    x25PLEDTEStatsResetTimeouts			Counter64,
    x25PLEDTEStatsRestartCountsExceeded		Counter64,
    x25PLEDTEStatsClearTimeouts			Counter64,
    x25PLEDTEStatsClearCountsExceeded		Counter64,
}

x25PLEDTEStatsCallAttempts OBJECT-TYPE
    SYNTAX	Counter64
    MAX-ACCESS	read-only
    STATUS	current
    DESCRIPTION
	"Provides a count of the total number of call attempts 
	 for this X.25 PLE DTE."
    REFERENCE
	"ITU-T Rec. X.283 | ISO/IEC 10733 : x25PLE-DTE 
	     callAttempts."
    ::= { x25PLEDTEStatsEntry 1 }

x25PLEDTEStatsProtocolErrorsDetectedLocally OBJECT-TYPE
    SYNTAX	Counter64
    MAX-ACCESS	read-only
    STATUS	current
    DESCRIPTION
	"Provides a count of the total number of protocol errors 
	 detected locally events, protocolErrorDetectedLocally, 
	 which also generate a communications alarm 
	 notification."
    REFERENCE
	"ITU-T Rec. X.283 | ISO/IEC 10733 : x25PLE-DTE 
	     protocolErrorsDetectedLocally."
    ::= { x25PLEDTEStatsEntry 2 }

x25PLEDTEStatsProtocolErrorsAccusedOf OBJECT-TYPE
    SYNTAX	Counter64
    MAX-ACCESS	read-only
    STATUS	current
    DESCRIPTION
	"Provides a count of the total number of protocol errors 
	 accused of events, accusedoOfProtocolError, which also 
	 generate a communications alarm notification."
    REFERENCE
	"ITU-T Rec. X.283 | ISO/IEC 10733 : x25PLE-DTE 
	     protocolErrorsAccusedOf."
    ::= { x25PLEDTEStatsEntry 3 }

x25PLEDTEStatsCallCountsExceeded OBJECT-TYPE
    SYNTAX	Counter64
    MAX-ACCESS	read-only
    STATUS	current
    DESCRIPTION
	"Provides a count of the total number of call 
	 establishment failures, 
	 callEstablishmentRetryCountExceeded events, which also 
	 generate a communications alarm notification.
	
	 Because both ITU-T Rec. X.25 and ISO/IEC 8208 have no 
	 Count R21 that corresponds to Timer 21, it is almost as 
	 though there exists an R21 with a value of zero (0), 
	 and it can be considered that the count is exceeded 
	 whenever Timer T21 expires."
    REFERENCE
	"ITU-T Rec. X.283 | ISO/IEC 10733 : x25PLE-DTE 
	     callEstablishmentRetryCountsExceeded."
    ::= { x25PLEDTEStatsEntry 4 }

-- PACKAGE dTEX25PLECounters-P
x25PLEDTEStatsOctetsReceived OBJECT-TYPE
    SYNTAX	Counter64
    MAX-ACCESS	read-only
    STATUS	current
    DESCRIPTION
	"This is the value of the count of the number of user 
	 data octets successfully received accumulated across 
	 all switched virtual calls and permanent virtual 
	 circuits for the X.25 Packet Layer Entity.
	
	 The octetsReceivedCounter and octetsSentCounter shall 
	 count only user data octets in valid data packets.  The 
	 shall not count user data octets in data packets that 
	 are rejected for any reason, not user data octets in 
	 non-data packets."
    REFERENCE
	"ITU-T Rec. X.283 | ISO/IEC 10733 : x25PLE-DTE 
	     dTEX25PLECounters-P octetsReceivedCounter.
	 ITU-T Rec. X.721 | ISO/IEC 10165-2 : 
	     octetsReceivedCounter."
    ::= { x25PLEDTEStatsEntry 5 }

x25PLEDTEStatsOctetsSent OBJECT-TYPE
    SYNTAX	Counter64
    MAX-ACCESS	read-only
    STATUS	current
    DESCRIPTION
	"This is the value of the count of the number of user 
	 data octets successfully sent accumulated across all 
	 switched virtual calls and permanent virtual circuits 
	 for the X.25 Packet Layer Entity.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : x25PLE-DTE 
	     dTEX25PLECounters-P octetsSentCounter
	 ITU-T Rec. X.721 | ISO/IEC 10165-2 : 
	     octetsSentCoutner."
    ::= { x25PLEDTEStatsEntry 6 }

x25PLEDTEStatsCallTimeouts OBJECT-TYPE
    SYNTAX	Counter64
    MAX-ACCESS	read-only
    STATUS	current
    DESCRIPTION
	"Provides a count of the total number of times that 
	 Timer T21 expires for the X.25 PLE DTE."
    REFERENCE
	"ITU-T Rec. X.283 | ISO/IEC 10733 : x25PLE-DTE 
	     dTEX25PLECounters-P callTimeouts."
    ::= { x25PLEDTEStatsEntry 7 }

x25PLEDTEStatsCallsConnected OBJECT-TYPE
    SYNTAX	Counter64
    MAX-ACCESS	read-only
    STATUS	current
    DESCRIPTION
	"Provides a count of the total number of calls that have 
	 reached the open state."
    REFERENCE
	"ITU-T Rec. X.283 | ISO/IEC 10733 : x25PLE-DTE 
	     dTEX25PLECounters-P callsConnected."
    ::= { x25PLEDTEStatsEntry 8 }

x25PLEDTEStatsDataPacketsReceived OBJECT-TYPE
    SYNTAX	Counter64
    MAX-ACCESS	read-only
    STATUS	current
    DESCRIPTION
	"The value of the count of the number of data packets 
	 received across all switched virtual calls and permanent 
	 virtual circuits for the DTE X.25 Packet Layer Entity."
    REFERENCE
	"ITU-T Rec. X.283 | ISO/IEC 10733 : x25PLE-DTE 
	     dataPacketsReceived."
    ::= { x25PLEDTEStatsEntry 9 }

x25PLEDTEStatsDataPacketsSent OBJECT-TYPE
    SYNTAX	Counter64
    MAX-ACCESS	read-only
    STATUS	current
    DESCRIPTION
	"The value of the count of the number of data packets 
	 sent across all switched virtual calls and permanent 
	 virtual circuits for the DTE X.25 Packet Layer Entity."
    REFERENCE
	"ITU-T Rec. X.283 | ISO/IEC 10733 : x25PLE-DTE 
	     dataPacketsSent."
    ::= { x25PLEDTEStatsEntry 10 }

x25PLEDTEStatsDataTimeouts OBJECT-TYPE
    SYNTAX	Counter64
    MAX-ACCESS	read-only
    STATUS	current
    DESCRIPTION
	"The value of the count of the number of times that 
	 Timer 25 expired, accumulated across all switched 
	 virtual calls and permanent virtual circuits for this 
	 DTE X.25 Packet Layer Entity.  When the option is not 
	 implemented, this object always returns zero (0)."
    REFERENCE
	"ITU-T Rec. X.283 | ISO/IEC 10733 : x25PLE-DTE 
	     dataRetransmissionTimerExpiries.
	 ITU-T Rec. X.25 | ISO/IEC 8208 : Timer T25."
    ::= { x25PLEDTEStatsEntry 11 }

x25PLEDTEStatsProviderResets OBJECT-TYPE
    SYNTAX	Counter64
    MAX-ACCESS	read-only
    STATUS	current
    DESCRIPTION
	"The value of the count of the number of provider 
	 initiated resets that constituted a 
	 providerInitiatedReset event that generated a 
	 communications alarm notification.  This count is the 
	 accumulated counts associated with all switched virtual 
	 calls and permanent virtual circuits for this DTE X.25 
	 Packet Layer Entity."
    REFERENCE
	"ITU-T Rec. X.283 | ISO/IEC 10733 : x25PLE-DTE 
	     providerInitiatedResets."
    ::= { x25PLEDTEStatsEntry 12 }

x25PLEDTEStatsProviderDisconnects OBJECT-TYPE
    SYNTAX	Counter64
    MAX-ACCESS	read-only
    STATUS	current
    DESCRIPTION
	"The value of the count of the number or provider 
	 initiated disconnects that constitued a 
	 providerInitiatedDisconnect event that generated a 
	 communications alarm notification.  Tihs count is the 
	 accumulated counts associated with all switched virtual 
	 calls and permanent virtual circuits for this DTE X.25 
	 Packet Layer Entity."
    REFERENCE
	"ITU-T Rec. X.283 | ISO/IEC 10733 : x25PLE-DTE 
	     providerInitiatedDisconnects."
    ::= { x25PLEDTEStatsEntry 13 }

x25PLEDTEStatsRemoteResets OBJECT-TYPE
    SYNTAX	Counter64
    MAX-ACCESS	read-only
    STATUS	current
    DESCRIPTION
	""
    REFERENCE
	"ITU-T Rec. X.283 | ISO/IEC 10733 : x25PLE-DTE 
	     remotelyInitiatedResets."
    ::= { x25PLEDTEStatsEntry 14 }

x25PLEDTEStatsRemoteRestarts OBJECT-TYPE
    SYNTAX	Counter64
    MAX-ACCESS	read-only
    STATUS	current
    DESCRIPTION
	""
    REFERENCE
	"ITU-T Rec. X.283 | ISO/IEC 10733 : x25PLE-DTE 
	     remotelyInitiatedRestarts."
    ::= { x25PLEDTEStatsEntry 15 }

x25PLEDTEStatsResetTimeouts OBJECT-TYPE
    SYNTAX	Counter64
    MAX-ACCESS	read-only
    STATUS	current
    DESCRIPTION
	"ITU-T Rec. X.283 | ISO/IEC 10733 : x25PLE-DTE 
	     resetTimeouts."
    REFERENCE
	""
    ::= { x25PLEDTEStatsEntry 16 }

x25PLEDTEStatsRestartCountsExceeded OBJECT-TYPE
    SYNTAX	Counter64
    MAX-ACCESS	read-only
    STATUS	current
    DESCRIPTION
	""
    REFERENCE
	"ITU-T Rec. X.283 | ISO/IEC 10733 : x25PLE-DTE 
	     restartCountsExceeded."
    ::= { x25PLEDTEStatsEntry 17 }

x25PLEDTEStatsClearTimeouts OBJECT-TYPE
    SYNTAX	Counter64
    MAX-ACCESS	read-only
    STATUS	current
    DESCRIPTION
	""
    REFERENCE
	"ITU-T Rec. X.283 | ISO/IEC 10733 : x25PLE-DTE 
	     clearTimeouts."
    ::= { x25PLEDTEStatsEntry 18 }

x25PLEDTEStatsClearCountsExceeded OBJECT-TYPE
    SYNTAX	Counter64
    MAX-ACCESS	read-only
    STATUS	current
    DESCRIPTION
	"Provides a count of the total number of clear count 
	 exceeded events, clearCountExceeded, that also generate 
	 a communication alarm notification."
    REFERENCE
	"ITU-T Rec. X.283 | ISO/IEC 10733 : x25PLE-DTE 
	     dTEX25PLECounters-P clearCountsExceeded."
    ::= { x25PLEDTEStatsEntry 19 }



x25PLEDCEStats OBJECT IDENTIFIER
    ::= { x25PLPTables 24 }

x25PLEDCEStatsTable OBJECT-TYPE
    SYNTAX	SEQUENCE OF X25PLEDCEStatsEntry
    MAX-ACCESS	not-accessible
    STATUS	current
    DESCRIPTION
	""
    REFERENCE
	"ITU-T Rec. X.283 | ISO/IEC 10733."
    ::= { x25PLEDCEStats 1 }

x25PLEDCEStatsEntry OBJECT-TYPE
    SYNTAX	X25PLEDCEStatsEntry
    MAX-ACCESS	not-accessible
    STATUS	current
    DESCRIPTION
	""
    REFERENCE
	"ITU-T Rec. X.283 | ISO/IEC 10733."
    INDEX	{
		    x25PLEId	-- shared index (AUGMENTS)
		}
    ::= { x25PLEDCEStatsTable 1 }

X25PLEDCEStatsEntry ::= SEQUENCE {
    x25PLEDCEStatsCallAttempts			Counter64,
    x25PLEDCEStatsCallsConnected		Counter64,
    -- PACKAGE dCECommonVirtualCircuitCounters-P PACKAGE
    x25PLEDCEStatsOctetsReceived		Counter64,
    x25PLEDCEStatsOctetsSent			Counter64,
    x25PLEDCEStatsDataPacketsReceived		Counter64,
    x25PLEDCEStatsDataPacketsSent		Counter64,
    x25PLEDCEStatsInterruptPacketsReceived	Counter64,
    x25PLEDCEStatsInterruptPacketsSent		Counter64,
    x25PLEDCEStatsProviderResets		Counter64,
    x25PLEDCEStatsProviderDisconnects		Counter64,
    x25PLEDCEStatsRemoteResets			Counter64,
    x25PLEDCEStatsRemoteRestarts		Counter64,
    x25PLEDCEStatsResetTimeouts			Counter64,
    x25PLEDCEStatsX25SegmentsReceived		Counter64,
    x25PLEDCEStatsX25SegmentsSent		Counter64,
}

x25PLEDCEStatsCallAttempts OBJECT-TYPE
    SYNTAX	Counter64
    MAX-ACCESS	read-only
    STATUS	current
    DESCRIPTION
	""
    REFERENCE
	"ITU-T Rec. X.283 | ISO/IEC 10733 : x25PLE-DCE 
	     callAttempts."
    ::= { x25PLEDCEStatsEntry 1 }

x25PLEDCEStatsCallsConnected OBJECT-TYPE
    SYNTAX	Counter64
    MAX-ACCESS	read-only
    STATUS	current
    DESCRIPTION
	""
    REFERENCE
	"ITU-T Rec. X.283 | ISO/IEC 10733 : x25PLE-DCE 
	     callsConnected."
    ::= { x25PLEDCEStatsEntry 2 }

-- PACKAGE dCECommonVirtualCircuitCounters-P PACKAGE
x25PLEDCEStatsOctetsReceived OBJECT-TYPE
    SYNTAX	Counter64
    MAX-ACCESS	read-only
    STATUS	current
    DESCRIPTION
	"This is the value of the count of the number of user 
	 data octets successfully received accumulated across 
	 all switched virtual calls and permanent virtual 
	 circuits for the X.25 Packet Layer Entity.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : x25PLE-DCE 
	     octetsReceivedCounter
	 ITU-T Rec. X.721 | ISO/IEC 10165-2 : 
	     octetsReceivedCounter."
    ::= { x25PLEDCEStatsEntry 3 }

x25PLEDCEStatsOctetsSent OBJECT-TYPE
    SYNTAX	Counter64
    MAX-ACCESS	read-only
    STATUS	current
    DESCRIPTION
	"This is the value of the count of the number of user 
	 data octets successfully sent accumulated across all 
	 switched virtual calls and permanent virtual circuits 
	 for the X.25 Packet Layer Entity.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : x25PLE-DCE 
	     octetsSentCounter
	 ITU-T Rec. X.721 | ISO/IEC 10165-2 : 
	     octetsSentCoutner."
    ::= { x25PLEDCEStatsEntry 4 }

x25PLEDCEStatsDataPacketsReceived OBJECT-TYPE
    SYNTAX	Counter64
    MAX-ACCESS	read-only
    STATUS	current
    DESCRIPTION
	"The value of the count of the number of data packets 
	 received across all switched virtual calls and permanent 
	 virtual circuits for the DCE X.25 Packet Layer Entity."
    REFERENCE
	"ITU-T Rec. X.283 | ISO/IEC 10733 : x25PLE-DCE 
	     dataPacketsReceived."
    ::= { x25PLEDCEStatsEntry 5 }

x25PLEDCEStatsDataPacketsSent OBJECT-TYPE
    SYNTAX	Counter64
    MAX-ACCESS	read-only
    STATUS	current
    DESCRIPTION
	"The value of the count of the number of data packets 
	 sent across all switched virtual calls and permanent 
	 virtual circuits for the DCE X.25 Packet Layer Entity."
    REFERENCE
	"ITU-T Rec. X.283 | ISO/IEC 10733 : x25PLE-DCE 
	     dataPacketsSent."
    ::= { x25PLEDCEStatsEntry 6 }

x25PLEDCEStatsInterruptPacketsReceived OBJECT-TYPE
    SYNTAX	Counter64
    MAX-ACCESS	read-only
    STATUS	current
    DESCRIPTION
	""
    REFERENCE
	"ITU-T Rec. X.283 | ISO/IEC 10733 : x25PLE-DCE 
	     interruptPacketsReceived."
    ::= { x25PLEDCEStatsEntry 7 }

x25PLEDCEStatsInterruptPacketsSent OBJECT-TYPE
    SYNTAX	Counter64
    MAX-ACCESS	read-only
    STATUS	current
    DESCRIPTION
	""
    REFERENCE
	"ITU-T Rec. X.283 | ISO/IEC 10733 : x25PLE-DCE 
	     interruptPacketsSent."
    ::= { x25PLEDCEStatsEntry 8 }

x25PLEDCEStatsProviderResets OBJECT-TYPE
    SYNTAX	Counter64
    MAX-ACCESS	read-only
    STATUS	current
    DESCRIPTION
	"The value of the count of the number of provider 
	 initiated resets that constituted a 
	 providerInitiatedReset event that generated a 
	 communications alarm notification.  This count is the 
	 accumulated counts associated with all switched virtual 
	 calls and permanent virtual circuits for this DCE X.25 
	 Packet Layer Entity."
    REFERENCE
	"ITU-T Rec. X.283 | ISO/IEC 10733 : x25PLE-DCE 
	     providerInitiatedResets."
    ::= { x25PLEDCEStatsEntry 9 }

x25PLEDCEStatsProviderDisconnects OBJECT-TYPE
    SYNTAX	Counter64
    MAX-ACCESS	read-only
    STATUS	current
    DESCRIPTION
	"The value of the count of the number or provider 
	 initiated disconnects that constitued a 
	 providerInitiatedDisconnect event that generated a 
	 communications alarm notification.  Tihs count is the 
	 accumulated counts associated with all switched virtual 
	 calls and permanent virtual circuits for this DCE X.25 
	 Packet Layer Entity."
    REFERENCE
	"ITU-T Rec. X.283 | ISO/IEC 10733 : x25PLE-DCE 
	     providerInitiatedDisconnects."
    ::= { x25PLEDCEStatsEntry 10 }

x25PLEDCEStatsRemoteResets OBJECT-TYPE
    SYNTAX	Counter64
    MAX-ACCESS	read-only
    STATUS	current
    DESCRIPTION
	""
    REFERENCE
	"ITU-T Rec. X.283 | ISO/IEC 10733 : x25PLE-DCE 
	     remotelyInitiatedResets."
    ::= { x25PLEDCEStatsEntry 11 }

x25PLEDCEStatsRemoteRestarts OBJECT-TYPE
    SYNTAX	Counter64
    MAX-ACCESS	read-only
    STATUS	current
    DESCRIPTION
	""
    REFERENCE
	"ITU-T Rec. X.283 | ISO/IEC 10733 : x25PLE-DCE 
	     remotelyInitiatedRestarts."
    ::= { x25PLEDCEStatsEntry 12 }

x25PLEDCEStatsResetTimeouts OBJECT-TYPE
    SYNTAX	Counter64
    MAX-ACCESS	read-only
    STATUS	current
    DESCRIPTION
	""
    REFERENCE
	"ITU-T Rec. X.283 | ISO/IEC 10733 : x25PLE-DCE 
	     resetTimeouts."
    ::= { x25PLEDCEStatsEntry 13 }

x25PLEDCEStatsX25SegmentsReceived OBJECT-TYPE
    SYNTAX	Counter64
    MAX-ACCESS	read-only
    STATUS	current
    DESCRIPTION
	""
    REFERENCE
	"ITU-T Rec. X.283 | ISO/IEC 10733 : x25PLE-DCE 
	     x25SegmentsReceived."
    ::= { x25PLEDCEStatsEntry 14 }

x25PLEDCEStatsX25SegmentsSent OBJECT-TYPE
    SYNTAX	Counter64
    MAX-ACCESS	read-only
    STATUS	current
    DESCRIPTION
	""
    REFERENCE
	"ITU-T Rec. X.283 | ISO/IEC 10733 : x25PLE-DCE 
	     x25SegmentsSent."
    ::= { x25PLEDCEStatsEntry 15 }



x25PLEDXEStats OBJECT IDENTIFIER
    ::= { x25PLPTables 25 }

x25PLEDXEStatsTable OBJECT-TYPE
    SYNTAX	SEQUENCE OF X25PLEDXEStatsEntry
    MAX-ACCESS	not-accessible
    STATUS	current
    DESCRIPTION
	""
    REFERENCE
	"ITU-T Rec. X.283 | ISO/IEC 10733."
    ::= { x25PLEDXEStats 1 }

x25PLEDXEStatsEntry OBJECT-TYPE
    SYNTAX	X25PLEDXEStatsEntry
    MAX-ACCESS	not-accessible
    STATUS	current
    DESCRIPTION
	""
    REFERENCE
	"ITU-T Rec. X.283 | ISO/IEC 10733."
    INDEX	{
		    x25PLEId	-- shared index (AUGMENTS)
		}
    ::= { x25PLEDXEStatsTable 1 }

X25PLEDXEStatsEntry ::= SEQUENCE {
    x25PLEDXEStatsCallAttempts			Counter64,
    x25PLEDXEStatsProtocolErrorsDetectedLocally	Counter64,
    x25PLEDXEStatsProtocolErrorsAccusedOf	Counter64,
    x25PLEDXEStatsCallCountsExceeded		Counter64,

    x25PLEDXEStatsOctetsReceived		Counter64,
    x25PLEDXEStatsOctetsSent			Counter64,
    x25PLEDXEStatsCallTimeouts			Counter64,
    x25PLEDXEStatsCallsConnected		Counter64,
    x25PLEDXEStatsClearTimeouts			Counter64,
    x25PLEDXEStatsDataPacketsReceived		Counter64,
    x25PLEDXEStatsDataPacketsSent		Counter64,
    x25PLEDXEStatsDataTimeouts			Counter64,
    x25PLEDXEStatsProviderResets		Counter64,
    x25PLEDXEStatsProviderDisconnects		Counter64,
    x25PLEDXEStatsRemoteResets			Counter64,
    x25PLEDXEStatsRemoteRestarts		Counter64,
    x25PLEDXEStatsResetTimeouts			Counter64,
    x25PLEDXEStatsRestartCountsExceeded		Counter64,
    x25PLEDXEStatsClearCountsExceeded		Counter64,
}

x25PLEDXEStatsCallAttempts OBJECT-TYPE
    SYNTAX	Counter64
    MAX-ACCESS	read-only
    STATUS	current
    DESCRIPTION
	""
    REFERENCE
	"ITU-T Rec. X.283 | ISO/IEC 10733 : x25PLE callAttempts."
    ::= { x25PLEDXEStatsEntry 1 }

x25PLEDXEStatsProtocolErrorsDetectedLocally OBJECT-TYPE
    SYNTAX	Counter64
    MAX-ACCESS	read-only
    STATUS	current
    DESCRIPTION
	""
    REFERENCE
	"ITU-T Rec. X.283 | ISO/IEC 10733 : x25PLE 
	     protocolErrorsDetectedLocally."
    ::= { x25PLEDXEStatsEntry 2 }

x25PLEDXEStatsProtocolErrorsAccusedOf OBJECT-TYPE
    SYNTAX	Counter64
    MAX-ACCESS	read-only
    STATUS	current
    DESCRIPTION
	""
    REFERENCE
	"ITU-T Rec. X.283 | ISO/IEC 10733 : x25PLE 
	     protocolErrorsAccusedOf."
    ::= { x25PLEDXEStatsEntry 3 }

x25PLEDXEStatsCallCountsExceeded OBJECT-TYPE
    SYNTAX	Counter64
    MAX-ACCESS	read-only
    STATUS	current
    DESCRIPTION
	"Provides a count of the total number of call 
	 establishment failures, 
	 callEstablishmentRetryCountExceeded events, which also 
	 generate a communications alarm notification."
    REFERENCE
	"ITU-T Rec. X.283 | ISO/IEC 10733 : x25PLE
	     callEstablishmentRetryCountsExceeded."
    ::= { x25PLEDXEStatsEntry 4 }

x25PLEDXEStatsOctetsReceived OBJECT-TYPE
    SYNTAX	Counter64
    MAX-ACCESS	read-only
    STATUS	current
    DESCRIPTION
	"This is the value of the count of the number of user 
	 data octets successfully received accumulated across 
	 all switched virtual calls and permanent virtual 
	 circuits for the X.25 Packet Layer Entity.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : x25PLE 
	     octetsReceivedCounter
	 ITU-T Rec. X.721 | ISO/IEC 10165-2 : 
	     octetsReceivedCounter."
    ::= { x25PLEDXEStatsEntry 5 }

x25PLEDXEStatsOctetsSent OBJECT-TYPE
    SYNTAX	Counter64
    MAX-ACCESS	read-only
    STATUS	current
    DESCRIPTION
	"This is the value of the count of the number of user 
	 data octets successfully sent accumulated across all 
	 switched virtual calls and permanent virtual circuits 
	 for the X.25 Packet Layer Entity.
	
	 The octetsReceivedCounter and octetsSentCounter shall 
	 count only user data octets in valid data packets.  
	 The shall not count user data octets in data packets 
	 that are rejected for any reason, not user data octets 
	 in non-data packets."
    REFERENCE
	"ITU-T Rec. X.283 | ISO/IEC 10733 : x25PLE 
	     octetsSentCounter
	 ITU-T Rec. X.721 | ISO/IEC 10165-2 : 
	     octetsSentCoutner."
    ::= { x25PLEDXEStatsEntry 6 }

x25PLEDXEStatsCallTimeouts OBJECT-TYPE
    SYNTAX	Counter64
    MAX-ACCESS	read-only
    STATUS	current
    DESCRIPTION
	""
    REFERENCE
	"ITU-T Rec. X.283 | ISO/IEC 10733 : x25PLE callTimeouts."
    ::= { x25PLEDXEStatsEntry 7 }

x25PLEDXEStatsCallsConnected OBJECT-TYPE
    SYNTAX	Counter64
    MAX-ACCESS	read-only
    STATUS	current
    DESCRIPTION
	""
    REFERENCE
	"ITU-T Rec. X.283 | ISO/IEC 10733 : x25PLE 
	     callsConnected."
    ::= { x25PLEDXEStatsEntry 8 }

x25PLEDXEStatsClearTimeouts OBJECT-TYPE
    SYNTAX	Counter64
    MAX-ACCESS	read-only
    STATUS	current
    DESCRIPTION
	""
    REFERENCE
	"ITU-T Rec. X.283 | ISO/IEC 10733 : x25PLE clearTimeouts."
    ::= { x25PLEDXEStatsEntry 9 }

x25PLEDXEStatsDataPacketsReceived OBJECT-TYPE
    SYNTAX	Counter64
    MAX-ACCESS	read-only
    STATUS	current
    DESCRIPTION
	"The value of the count of the number of data packets 
	 received across all switched virtual calls and permanent 
	 virtual circuits for the DXE X.25 Packet Layer Entity."
    REFERENCE
	"ITU-T Rec. X.283 | ISO/IEC 10733 : x25PLE 
	     dataPacketsReceived."
    ::= { x25PLEDXEStatsEntry 10 }

x25PLEDXEStatsDataPacketsSent OBJECT-TYPE
    SYNTAX	Counter64
    MAX-ACCESS	read-only
    STATUS	current
    DESCRIPTION
	"The value of the count of the number of data packets 
	 sent across all switched virtual calls and permanent 
	 virtual circuits for the DXE X.25 Packet Layer Entity."
    REFERENCE
	"ITU-T Rec. X.283 | ISO/IEC 10733 : x25PLE 
	     dataPacketsSent."
    ::= { x25PLEDXEStatsEntry 11 }

x25PLEDXEStatsDataTimeouts OBJECT-TYPE
    SYNTAX	Counter64
    MAX-ACCESS	read-only
    STATUS	current
    DESCRIPTION
	"The value of the count of the number of times that 
	 Timer 25 expired, accumulated across all switched 
	 virtual calls and permanent virtual circuits for this 
	 DXE X.25 Packet Layer Entity.  When the option is not 
	 implemented, this object always returns zero (0)."
    REFERENCE
	"ITU-T Rec. X.283 | ISO/IEC 10733 : x25PLE 
	     dataRetransmissionTimerExpiries.
	 ITU-T Rec. X.25 | ISO/IEC 8208 : Timer T25."
    ::= { x25PLEDXEStatsEntry 12 }

x25PLEDXEStatsProviderResets OBJECT-TYPE
    SYNTAX	Counter64
    MAX-ACCESS	read-only
    STATUS	current
    DESCRIPTION
	"The value of the count of the number of provider 
	 initiated resets that constituted a 
	 providerInitiatedReset event that generated a 
	 communications alarm notification.  This count is the 
	 accumulated counts associated with all switched virtual 
	 calls and permanent virtual circuits for this DXE X.25 
	 Packet Layer Entity."
    REFERENCE
	"ITU-T Rec. X.283 | ISO/IEC 10733 : x25PLE 
	     providerInitiatedResets."
    ::= { x25PLEDXEStatsEntry 13 }

x25PLEDXEStatsProviderDisconnects OBJECT-TYPE
    SYNTAX	Counter64
    MAX-ACCESS	read-only
    STATUS	current
    DESCRIPTION
	"The value of the count of the number or provider 
	 initiated disconnects that constitued a 
	 providerInitiatedDisconnect event that generated a 
	 communications alarm notification.  Tihs count is the 
	 accumulated counts associated with all switched virtual 
	 calls and permanent virtual circuits for this DXE X.25 
	 Packet Layer Entity."
    REFERENCE
	"ITU-T Rec. X.283 | ISO/IEC 10733 : x25PLE 
	     providerInitiatedDisconnects."
    ::= { x25PLEDXEStatsEntry 14 }

x25PLEDXEStatsRemoteResets OBJECT-TYPE
    SYNTAX	Counter64
    MAX-ACCESS	read-only
    STATUS	current
    DESCRIPTION
	""
    REFERENCE
	"ITU-T Rec. X.283 | ISO/IEC 10733 : x25PLE 
	     remotelyInitiatedResets."
    ::= { x25PLEDXEStatsEntry 15 }

x25PLEDXEStatsRemoteRestarts OBJECT-TYPE
    SYNTAX	Counter64
    MAX-ACCESS	read-only
    STATUS	current
    DESCRIPTION
	""
    REFERENCE
	"ITU-T Rec. X.283 | ISO/IEC 10733 : x25PLE 
	     remotelyInitiatedRestarts."
    ::= { x25PLEDXEStatsEntry 16 }

x25PLEDXEStatsResetTimeouts OBJECT-TYPE
    SYNTAX	Counter64
    MAX-ACCESS	read-only
    STATUS	current
    DESCRIPTION
	""
    REFERENCE
	"ITU-T Rec. X.283 | ISO/IEC 10733 : x25PLE."
    ::= { x25PLEDXEStatsEntry 17 }

x25PLEDXEStatsRestartCountsExceeded OBJECT-TYPE
    SYNTAX	Counter64
    MAX-ACCESS	read-only
    STATUS	current
    DESCRIPTION
	""
    REFERENCE
	"ITU-T Rec. X.283 | ISO/IEC 10733 : x25PLE."
    ::= { x25PLEDXEStatsEntry 18 }

x25PLEDXEStatsClearCountsExceeded OBJECT-TYPE
    SYNTAX	Counter64
    MAX-ACCESS	read-only
    STATUS	current
    DESCRIPTION
	""
    REFERENCE
	"ITU-T Rec. X.283 | ISO/IEC 10733 : x25PLE."
    ::= { x25PLEDXEStatsEntry 19 }




x25PLPScalars OBJECT IDENTIFIER
    ::= { x25PLPObjects 2 }

x25PLPNotifs OBJECT IDENTIFIER
    ::= { x25PLPObjects 3 }

x25PLPOids OBJECT IDENTIFIER
    ::= { x25PLPObjects 4 }

x25PLPParameters OBJECT IDENTIFIER
    ::= { x25PLPMIB1 2 }

notificationDataChannel OBJECT-TYPE
    SYNTAX	LogicalChannelNumber
    MAX-ACCESS	accessible-for-notify
    STATUS	current
    DESCRIPTION
	"Information relating to the call which resulted in the 
	 notificaiton."
    REFERENCE
	"ITU-T Rec. X.283 | ISO/IEC 10733 : notificationData 
	     PARAMETER."
    ::= { x25PLPParameters 1 }

notificationDataPacketHeader OBJECT-TYPE
    SYNTAX	OCTET STRING
    MAX-ACCESS	accessible-for-notify
    STATUS	current
    DESCRIPTION
	"Information relating to the call which resulted in the 
	 notificaiton."
    REFERENCE
	"ITU-T Rec. X.283 | ISO/IEC 10733 : notificationData 
	     PARAMETER."
    ::= { x25PLPParameters 2 }

notificationDataDiagnosticCode OBJECT-TYPE
    SYNTAX	OCTET STRING
    MAX-ACCESS	accessible-for-notify
    STATUS	current
    DESCRIPTION
	"Information relating to the call which resulted in the 
	 notificaiton."
    REFERENCE
	"ITU-T Rec. X.283 | ISO/IEC 10733 : notificationData 
	     PARAMETER."
    ::= { x25PLPParameters 3 }

notificationDataCauseCode OBJECT-TYPE
    SYNTAX	OCTET STRING
    MAX-ACCESS	accessible-for-notify
    STATUS	current
    DESCRIPTION
	"Information relating to the call which resulted in the 
	 notification."
    REFERENCE
	"ITU-T Rec. X.283 | ISO/IEC 10733 : notificationData 
	     PARAMETER."
    ::= { x25PLPParameters 4 }


x25PLPSpecificExtensions OBJECT IDENTIFIER
    ::= { x25PLPMIB1 3 }

-- The x25PLE-P package imports the communicationsAlarm notification from Rec.  
-- X.721 (1992) | ISO/IEC 10165-2. It is used to report the following x25PLE 
-- managed object events.

x25PLPSpecificProblems OBJECT IDENTIFIER
    ::= { x25PLPSpecificExtensions 1 }


-- providerInitiatedDisconnect:
--     Issued upon receipt of a clear packet with a cause code other than 'DTE 
--     originated'.
-- 
--     The information relating to the packet shall be reported as a parameter 
--     in the additionalInformation field of the communicationsAlarm, using the 
--     notificationData PARAMETER.
-- 
--     The significance sub-parameter of each item of additionalInformation 
--     shall be set to the value 'False' (i.e. not significant) so that a 
--     managing system receiving the event report will be less likely to reject 
--     it. The value NLM.providerInitiatedDisconnect shall be reported in the 
--     specificProblems parameter. The probableCause shall be set to 
--     NLM.communicationsProtocolError.
-- 
--     The perceivedSeverity shall be set to 'Minor'. A subsequent 
--     communicationsAlarm with a perceivedSeverity value of 'Cleared' shall 
--     not be generated. No other fields or parameters shall be used, with the 
--     exception of further parameters in the additionalInformation field.
-- 
providerInitiatedDisconnect OBJECT-IDENTITY
    STATUS current
    DESCRIPTION
	"SpecificProblem.  This object identity is used with 
	 SpecificProblems in a communicationsAlarm notification 
	 when the ProbableCause is communicationsProtocolError.  
	 It identifies the specific cause of the protocol error 
	 which was a provider initiated disconnect.
	
	 When the managed element issues a communications alarm 
	 notification with a probable cause of communications 
	 protocol error, and the specific problem was a provider 
	 initiated disconnect, this object identity will be 
	 placed in the specificProblems field in the 
	 notificaiton.
	
	 It is issued upon receipt by an X.25 PLE of a clear 
	 packet with a cause code of other than 'DTE 
	 originated'.
	
	 The perceivedSeverity shall be set to 'Minor'.  A 
	 subsequent communicationsAlarm with a perceivedSeverity 
	 value of 'Cleared' shall not be generated."
    REFERENCE
	"ITU-T Rec. X.283 | ISO/IEC 10733 : 
	     x25PLEPImportedNotifications-B BEHAVIOUR."
    ::= { x25PLPSpecificProblems 1 }

-- remotelyInitiatedReset:
--     Issued upon occurrence of a remotely initiated reset.  This event is 
--     issued in lieu of a 'providerInitiatedReset' when operating in a DTE-DXE 
--     environment. 
--
--     The information relating to the packet shall be reported as a parameter 
--     in the additionalInformation field of the communicationsAlarm, using the 
--     notificationData PARAMETER
-- 
--     The significance sub-parameter of each item of additionalInformation 
--     shall be set to the value 'False' (i.e. not significant) so that a 
--     managing system receiving the event report will be less likely to reject 
--     it. The value NLM.remotelyInitiatedDisconnect shall be reported in the 
--     specificProblems parameter. The probableCause shall be set to 
--     NLM.communicationsProtocolError.
-- 
--     The perceivedSeverity shall be set to 'Minor'. A subsequent 
--     communicationsAlarm with a perceivedSeverity value of 'Cleared' shall 
--     not be generated. No other fields or parameters shall be used, with the 
--     exception of further parameters in the additionalInformation field.
-- 
remotelyInitiatedReset OBJECT-IDENTITY
    STATUS current
    DESCRIPTION
	"SpecificProblem.  This object identity is used with 
	 SpecificProblems in a communicationsAlarm when the 
	 ProbableCause is communicationsProtooclError.  It 
	 identifies the specific cause of the protocol error 
	 which was a remotely initated reset.
	
	 When the managed element issues a communications alarm 
	 notification with a probable cause of communications 
	 protocol error, and the specific problem was a remotely 
	 initiated reset, this object identity will be placed in 
	 the specificProblems field in the notification.
	
	 It is issued upon occurence of a remotely initiated 
	 reset.  This event is issued in lieu of a 
	 providerInitiatedReset when operating in the DTE-DXE 
	 environment.
	
	 The perceivedSeverity shall be set to 'Minor'.  A 
	 subsequent communicationsAlarm with a perceivedSeverity 
	 value of 'Cleared' shall not be generated."
    REFERENCE
	"ITU-T Rec. X.283 | ISO/IEC 10733 : 
	     x25PLEPImportedNotifications-B BEHAVIOUR."
    ::= { x25PLPSpecificProblems 2 }

-- providerInitiatedReset:
--     Issued upon occurrence of a provider initiated reset.  This event is 
--     issued when operating in a DTE-DCE environment. The information relating 
--     to the packet shall be reported as a parameter in the 
--     additionalInformation field of the communicationsAlarm, using the 
--     notificationData PARAMETER
-- 
--     The significance sub-parameter of each item of additionalInformation 
--     shall be set to the value 'False' (i.e. not significant) so that a 
--     managing system receiving the event report will be less likely to reject 
--     it. The value NLM.providerInitiatedReset shall be reported in the 
--     specificProblems parameter.  The probableCause shall be set to 
--     NLM.communicationsProtocolError.
-- 
--     The perceivedSeverity shall be set to 'Minor'. A subsequent 
--     communicationsAlarm with a perceivedSeverity value of 'Cleared' shall not 
--     be generated. No other fields or parameters shall be used, with the 
--     exception of further parameters in the additionalInformation field.
providerInitiatedReset OBJECT-IDENTITY
    STATUS current
    DESCRIPTION
	"SpecificProblem.  This object identity is used with 
	 specificProblems in a communicationsAlarm when the 
	 ProbableCause is communicationsProtocolError.  It 
	 identifies the specific cause of the protocol error 
	 which was a provider initiated reset.

	 When the managed element issues a communications alarm 
	 notification with a probable cause of communications 
	 protocol error, and the specific problem was a provider 
	 initiated reset, this object identity will be palced in 
	 the specificProblems field in the notification.

	 It is issued upon occurence of a provider initiated 
	 reset.  This event is issued when operating in the 
	 DTE-DCE environment.

	 The perceivedSeverity shall be set to 'Minor'. A 
	 subsequent communicationsAlarm with a perceivedSeverity 
	 value of 'Cleared' shall not be generated."
    REFERENCE
	"ITU-T Rec. X.283 | ISO/IEC 10733 : 
	     x25PLEPImportedNotifications-B BEHAVIOUR."
    ::= { x25PLPSpecificProblems 3 }

-- remotelyInitiatedRestart:
--     Issued upon receipt of a remotely (including provider) initiated 
--     restart.
--
--     The information relating to the packet shall be reported as a parameter 
--     in the additionalInformation field of the communicationsAlarm, using the 
--     notificationData PARAMETER
-- 
--     The significance sub-parameter of each item of additionalInformation 
--     shall be set to the value 'False' (i.e. not significant) so that a 
--     managing system receiving the event report will be less likely to reject 
--     it. The value NLM.remotelyInitiatedRestart shall be reported in the 
--     specificProblems parameter. The probableCause shall be set to 
--     NLM.communicationsProtocolError.
-- 
--     The perceivedSeverity shall be set to 'Minor'. A subsequent 
--     communicationsAlarm with a perceivedSeverity value of 'Cleared' shall 
--     not be generated. No other fields or parameters shall be used, with the 
--     exception of further parameters in the additionalInformation field.
-- 
remotelyInitiatedRestart OBJECT-IDENTITY
    STATUS current
    DESCRIPTION
	"SpecificProblem.  This object identity is used with 
	 SpecificProblems in a communicationsAlarm notification 
	 when the ProbableCause is communicationsProtocolError.  
	 It identifies the specific cause of the protocol error 
	 which was a remotely initiated restart.
	
	 When the managed element issues a communications alarm 
	 notification with a probable cause of communications 
	 protocol error, and the specific problem was a remotely 
	 initated restart, this object identity will be placed 
	 in the specificProblems field in the notification.
	
	 It is issued upon receipt of a remotely (including 
	 provider) initiated restart.
	
	 The perceivedSeverity shall be set to 'Minor'.  A 
	 subsequent communicationsAlarm with a perceivedSeverity 
	 value of 'Cleared' shall not be generated."
    REFERENCE
	"ITU-T Rec. X.283 | ISO/IEC 10733 : 
	     x25PLEPImportedNotifications-B BEHAVIOUR."
    ::= { x25PLPSpecificProblems 4 }

-- restartCountExceeded:
--     Issued on restart failure due to restart count (R20) exceeded.
--
--     The information relating to the packet shall be reported as a parameter 
--     in the additionalInformation field of the communicationsAlarm, using the 
--     notificationData PARAMETER
-- 
--     The significance sub-parameter of each item of additionalInformation 
--     shall be set to the value 'False' (i.e. not significant) so that a 
--     managing system receiving the event report will be less likely to reject 
--     it.
-- 
--     The value NLM.restartCountExceeded shall be reported in the 
--     specificProblems parameter. The probableCause shall be set to 
--     NLM.communicationsProtocolError.
-- 
--     The perceivedSeverity shall be set to 'Minor'. A subsequent 
--     communicationsAlarm with a perceivedSeverity value of 'Cleared' shall 
--     not be generated. No other fields or parameters shall be used, with the 
--     exception of further parameters in the additionalInformation field.
-- 
restartCountExceeded OBJECT-IDENTITY
    STATUS current
    DESCRIPTION
	"SpecificProblem.  This object identity is used with 
	 SpecificProblems in a communicationsAlarm notification 
	 when the ProbableCause is communicationsProtocolError.  
	 It identifies the specific cause of the protocol error 
	 which was an exceeded restart count.
	
	 When the managed element issues a communications alarm 
	 notification with a probable cause of communications 
	 protocol error, and the specific problem was an 
	 exceeded restart count, this object identity will be 
	 placed in the specificProblems field in the 
	 notification.
	
	 It is issued on restart failure due to restart count 
	 (R20) exceeded.
	
	 The perceivedSeverity shall be set to 'Minor'.  A 
	 subsequent communicationsAlarm with a perceivedSeverity 
	 value of 'Cleared' shall not be generated."
    REFERENCE
	"ITU-T Rec. X.283 | ISO/IEC 10733 : 
	     x25PLEPImportedNotifications-B BEHAVIOUR."
    ::= { x25PLPSpecificProblems 5 }

-- protocolErrorDetectedLocally:
--     Issued upon receipt of a packet which causes the "A=Error" action in the 
--     ISO/IEC 8208 or ITU-T Rec. X.25 state tables to be taken.
-- 
--     The information relating to the packet shall be reported as a parameter 
--     in the additionalInformation field of the communicationsAlarm, using the 
--     notificationData PARAMETER.
-- 
--     The values of cause and diagnostic codes shall be those which would have 
--     been placed in a diagnostic packet had one been generated by the DTE 
--     (i.e. as if it were a DTE). The actual generation of such a packet is 
--     not required.
-- 
--     The significance sub-parameter of each item of additionalInformation 
--     shall be set to the value 'False' (i.e. not significant) so that a 
--     managing system receiving the event report will be less likely to reject 
--     it. The value NLM.communicationsProtocolErrorDetectedLocally shall be 
--     reported in the specificProblems parameter.
-- 
--     The probableCause shall be set to NLM.communicationsProtocolError.
-- 
--     The perceivedSeverity shall be set to 'Minor'. A subsequent 
--     communicationsAlarm with a perceivedSeverity value of 'Cleared' shall 
--     not be generated. No other fields or parameters shall be used, with the 
--     exception of further parameters in the additionalInformation field.
-- 
protocolErrorDetectedLocally OBJECT-IDENTITY
    STATUS current
    DESCRIPTION
	"SpecificProblem.  This object identity is used with 
	 SpecificProblems in a communicationsAlarm notification 
	 when the ProbableCause is communicationsProtocolError.  
	 It identifies the specific cause of the protocol error 
	 which was a locally detected protocol error.
	
	 When the managed element issues a communications alarm 
	 notification with a probable cuase of communications 
	 protocol error, and the specific problem was a locally 
	 detected protocol error, this object identity will be 
	 placed in the specificProblems field in the 
	 notification.
	
	 It is issued upon receipt of a packet which causes the 
	 'A=error' action in the ISO/IEC 8208 or ITU-T Rec. X.25 
	 state tables to be taken.
	
	 The perceivedSeverity shall be set to 'Minor'.  A 
	 subsequent communicationsAlarm with a perceivedSeverity 
	 value of 'Cleared' shall not be generated."
    REFERENCE
	"ITU-T Rec. X.283 | ISO/IEC 10733 : 
	     x25PLEPImportedNotifications-B BEHAVIOUR."
    ::= { x25PLPSpecificProblems 6 }

-- accusedOfProtocolError:
--     Issued upon receipt of a diagnostic packet or a clear, reset or restart 
--     packet with a cause code equal to one of the following: Remote Procedure 
--     Error, Incompatible Destination, Invalid Facility Request, Local 
--     Procedure Error. No other x25PLE communication alarm shall be generated 
--     as a result of this particular instance of packet.
-- 
--     The information relating to the packet shall be reported as a parameter 
--     in the additionalInformation field of the communicationsAlarm, using the 
--     notificationData PARAMETER
-- 
--     The significance sub-parameter of each item of additionalInformation 
--     shall be set to the value 'False' (i.e. not significant) so that a 
--     managing system receiving the event report will be less likely to reject 
--     it. The value NLM.accusedOfProtocolError shall be reported in the 
--     specificProblems parameter.
-- 
--     The probableCause shall be set to NLM.communicationsProtocolError.
-- 
--     The perceivedSeverity shall be set to 'Minor'. A subsequent 
--     communicationsAlarm with a perceivedSeverity value of 'Cleared' shall 
--     not be generated. No other fields or parameters shall be used, with the 
--     exception of further parameters in the additionalInformation field.
-- 
accusedOfProtocolError OBJECT-IDENTITY
    STATUS current
    DESCRIPTION
	"SpecificProblem.  This object identity is used with 
	 SpecificProblems in a communicationsAlarm notification 
	 when the ProbableCause is communicationsProtocolError.  
	 It identifies the specific cause of the protocol error 
	 which was a remotely reported protocol error.
	
	 When the managed element issues a communications alarm 
	 notification with a probable cause of communications 
	 protocol error, and the specific problem was a remotely 
	 detected protocol error, this object identity will be 
	 placed in the specificProblems field in the 
	 notification.
	
	 It is issued upon receipt of a diagnostic packet or a 
	 clear, reset or restart packet with a cause code equal 
	 to one of the following: Remote Procedure Error, 
	 Incompatible Destination, Invalid Facility Request, 
	 Local Procedure Error.  No other x25PLE communication 
	 alarm shall be generated as a result of this particular 
	 instance of packet.
	
	 The perceivedSeverity shall be set to 'Minor'.  A 
	 subsequent communicationsAlarm with a perceivedSeverity 
	 value of 'Cleared' shall not be generated."
    REFERENCE
	"ITU-T Rec. X.283 | ISO/IEC 10733 : 
	     x25PLEPImportedNotifications-B BEHAVIOUR."
    ::= { x25PLPSpecificProblems 7 }

-- callEstablishmentRetryCountExceeded:
--     Issued on retry failure during call establishment due to retry limit 
--     exceeded.
-- 
--     The information relating to the call shall be reported as a parameter in 
--     the additionalInformation field of the communicationsAlarm, using the 
--     notificationData PARAMETER
-- 
--     The significance sub-parameter of each item of additionalInformation 
--     shall be set to the value 'False' (i.e. not significant) so that a 
--     managing system receiving the event report will be less likely to reject 
--     it. The value NLM.callEstablishmentRetryCountExceeded shall be reported 
--     in the specificProblems parameter.
-- 
--     The probableCause shall be set to NLM.communicationsProtocolError.
-- 
--     The perceivedSeverity shall be set to 'Minor'. A subsequent 
--     communicationsAlarm with a perceivedSeverity value of 'Cleared' shall 
--     not be generated. No other fields or parameters shall be used, with the 
--     exception of further parameters in the additionalInformation field.
-- 
callEstablishmentRetryCountExceeded OBJECT-IDENTITY
    STATUS current
    DESCRIPTION
	"SpecificProblem.  This object identity is used with 
	 SpecificProblems in a communicationsAlarm notification 
	 when the ProbableCause is communicationsProtocolError.  
	 It identifies the specific cause of the protocol error 
	 which was an exceeded call establishment retry count.
	
	 When the managed element issues a communications alarm 
	 notification with a probable cause of communications 
	 protocol error, and the specific problem was an 
	 exceeded call establishment retry count, this object 
	 identity will be placed in the specificProblems field 
	 in the notification.
	
	 It is issued on retry failure during call establishment 
	 due to retry limit exceeded.
	
	 The perceivedSeverity shall be set to 'Minor'.  A 
	 subsequent communicationsAlarm with a perceivedSeverity 
	 value of 'Cleared' shall not be generated."
    REFERENCE
	"ITU-T Rec. X.283 | ISO/IEC 10733 : 
	     x25PLEPImportedNotifications-B BEHAVIOUR."
    ::= { x25PLPSpecificProblems 8 }

-- clearCountExceeded:
--     Issued on retry failure due to clear limit (R23) exceeded.  The 
--     information relating to the call shall be reported as a parameter in the 
--     additionalInformation field of the communicationsAlarm, using the 
--     notificationData PARAMETER
-- 
--     The significance sub-parameter of each item of additionalInformation 
--     shall be set to the value 'False' (i.e. not significant) so that a 
--     managing system receiving the event report will be less likely to reject 
--     it.
-- 
--     The value NLM.clearCountExceeded shall be reported in the 
--     specificProblems parameter. The probableCause shall be set to 
--     NLM.communicationsProtocolError.
-- 
--     The perceivedSeverity shall be set to 'Minor'. A subsequent 
--     communicationsAlarm with a perceivedSeverity value of 'Cleared' shall 
--     not be generated. No other fields or parameters shall be used, with the 
--     exception of further parameters in the additionalInformation field.
--
clearCountExceeded OBJECT-IDENTITY
    STATUS current
    DESCRIPTION
	"SpecificProblem.  This object identity is used with 
	 SpecificProblems in a communicationsAlarm notification 
	 when the ProbableCuase is communicationsProtocolError.  
	 It identifies the specific cause of the protocol error 
	 which was an exceeded clear count.
	
	 When the managed element issues a communications alarm 
	 notification with a probable cause of communications 
	 protocol error, and the specific problem was an 
	 exceeded clear count, this object identity will be 
	 placed in the specificProblems field in the 
	 notification.
	
	 It is issued on retry failure due to clear limit (R23) 
	 exceeded.  The information relating to the call shall 
	 be reported as a parameter in the additionalInformation 
	 field of the communications alarm, using the 
	 notification data parameter.
	
	 The perceivedSeverity shall be set to 'Minor'.  A 
	 subsequent communicationsAlarm with a perceivedSeverity 
	 value of 'Cleared' shall not be generated."
    REFERENCE
	"ITU-T Rec. X.283 | ISO/IEC 10733 : 
	     x25PLEPImportedNotifications-B BEHAVIOUR."
    ::= { x25PLPSpecificProblems 9 }

x25PLPInformationType OBJECT IDENTIFIER
    ::= { x25PLPSpecificExtensions 2 }

-- This Package imports the communicationsInformation notification from "GMI". 
-- It is used to report the following events. 
--
-- successfulConnectionEstablishment:
--     Generated when a connection is successfully established. However, the 
--     precise synchronization between the notification and the corresponding 
--     protocol and service interface interactions is not defined by this 
--     Specification. The value NLM.successfulConnectionEstablishment shall be 
--     reported in the informationType field.

successfulConnectionEstablishment OBJECT-IDENTITY
    STATUS current
    DESCRIPTION
	"InformationType.  This object identity is used with 
	 InformationType in a communicationsInformation 
	 notification.  It identifies that the type of the 
	 information is a successful connection establishment."
    REFERENCE
	"ITU-T Rec. X.282 | ISO/IEC 10733 : 
	     successfulConnectionEstablishment-B BEHAVIOR."
    ::= { x25PLPInformationType 1 }


x25PLPConform OBJECT IDENTIFIER
    ::= { x25PLPMIB1 4 }

x25PLPCompliances OBJECT IDENTIFIER
    ::= { x25PLPConform 1 }

x25PLPGroups OBJECT IDENTIFIER
    ::= { x25PLPConform 2 }

END

-- vim: ft=mib comments=\f\:\",\b\:\-\-,\:\-\-,\f\b\:- fo+=tcqlornw tw=72 nocin nosi sts=4 sw=4
