--@@ GDMOCHECK 2015-01-24T09:15+0000
--@@ Copyright (c), 2008-2015 Monavacon Limited <http://www.monavacon.com/>
--@@ Copyright (c), 2001-2008 OpenSS7 Corporation <http://www.openss7.com/>
--@@ Copyright (c), 1999-2000 Brian F. G. Bidulock <bidulock@openss7.org>
--@@ 
--@@ Input File: <(standard input)>
--@@ Special File: <(standard input).specials>
--@@ Date: Sat Jan 24 05:16:44 MST 2015
--@@ 
--< GDMO.Document "ITU-T Rec. X.751 (1995) | ISO/IEC 10164-17 : 1996"
--  { joint-iso-ccitt ms(9) function(2) part17(17) } >--
MODULE "ITU-T Rec. X.751 (1995) | ISO/IEC 10164-17 : 1996" { joint-iso-ccitt ms(9) function(2) part17(17) }
--< ASN1.Version 1994 ChangeOverASN1Productions
--  { joint-iso-ccitt ms(9) function(2) part17(17) asn1Module(2) 0 } >--
-- Annex B
-- Abstract syntax definitions
-- (This annex forms an integral part of this Recommendation | International Standard)
ChangeOverASN1Productions { joint-iso-ccitt ms(9) function(2) part17(17) asn1Module(2) 0 }
DEFINITIONS ::=
BEGIN
IMPORTS
CMIP-ATTRIBUTE, AttributeSet, ObjectInstance, Attribute, ModifyOperator
	FROM CMIP-1 { joint-iso-ccitt ms(9) cmip(1) modules(0) protocol(3) };-- Corrigendum 1
part17Action OBJECT IDENTIFIER ::= { joint-iso-ccitt ms(9) function(2) part17(17) action(9) }
part17Attribute OBJECT IDENTIFIER ::= { joint-iso-ccitt ms(9) function(2) part17(17) attribute(7) }
part17MObjectClass OBJECT IDENTIFIER ::= { joint-iso-ccitt ms(9) function(2) part17(17) managedObjectClass(3) }
part17Package OBJECT IDENTIFIER ::= { joint-iso-ccitt ms(9) function(2) part17(17) package(4) }
part17Parameter OBJECT IDENTIFIER ::= { joint-iso-ccitt ms(9) function(2) part17(17) parameter(5) }
part17MRelClass OBJECT IDENTIFIER ::= { joint-iso-ccitt ms(9) function(2) part17(17) relationshipClass(11) }
part17Role OBJECT IDENTIFIER ::= { joint-iso-ccitt ms(9) function(2) part17(17) relationshipRole(13) }
BackUpInfo ::= SEQUENCE {
	backedUpObjectSpecified [0] OptionalObject DEFAULT noObject : NULL,
	backUpObjectSpecified [1] OptionalObject DEFAULT noObject : NULL,
	backedUpObjectExisting [2] OptionalObject DEFAULT noObject : NULL,
	backUpObjectExisting [3] OptionalObject DEFAULT noObject : NULL }-- Corrigendum 1
BackUpObject ::= OptionalObject-- Corrigendum 1
ChangeBackInfo ::= SEQUENCE {
	backedUpObject [0] ObjectInstance,
	backUpObject [1] OptionalObject DEFAULT noObject : NULL,
	backedUpObjectChanges [2] IMPLICIT ExpectedAttributeList OPTIONAL,
	backUpObjectChanges [3] IMPLICIT ExpectedAttributeList OPTIONAL }-- Corrigendum 1
ChangeOverInfo ::= SEQUENCE {
	primary [0] ObjectInstance,
	secondary [1] OptionalObject DEFAULT noObject : NULL,
	primaryChanges [2] IMPLICIT ExpectedAttributeList OPTIONAL,
	secondaryChanges [3] IMPLICIT ExpectedAttributeList OPTIONAL }-- Corrigendum 1
Condition ::= SEQUENCE {
	object ObjectInstance,
	details SET OF Attribute }
-- At least one of the two components of Conditions must be present
Conditions ::= SEQUENCE {
	primary [0] IMPLICIT Condition OPTIONAL,
	secondary [1] IMPLICIT Condition OPTIONAL }
ExpectedAttributeList ::= SET OF SEQUENCE {
	modifyOperator [0] IMPLICIT ModifyOperator DEFAULT replace,
	attributeId CMIP-ATTRIBUTE.&id( {AttributeSet }),
	attributeValue CMIP-ATTRIBUTE.&Value( { AttributeSet } { @.attributeId }) OPTIONAL }
NoSuchParticipant ::= SEQUENCE {
	role [0] OBJECT IDENTIFIER,
	objectInstance [1] ObjectInstance }
NoSuchRelationship ::= SEQUENCE {
	relationshipClass OBJECT IDENTIFIER,
	relationshipBinding OBJECT IDENTIFIER OPTIONAL,
	relationshipInstance [0] RelationshipInstance OPTIONAL }-- Corrigendum 1
OneToOne ::= INTEGER(1..1)-- added for cardinality corrections
ZeroOrOne ::= INTEGER(0..1)-- added for cardinality corrections
OneToN ::= INTEGER(1..MAX)-- added for cardinality corrections
OptionalObject ::= CHOICE {
	noObject NULL,
	object ObjectInstance }
PrimaryObject ::= ObjectInstance
PrimaryObjectSpecified ::= OptionalObject
-- At least one of the two components of UnattainableAttributeList must be present
RelationshipInstance ::= SET OF ObjectInstance
UnattainableAttributeList ::= SEQUENCE {
	primaryChanges [0] IMPLICIT ExpectedAttributeList OPTIONAL,
	secondaryChanges [1] IMPLICIT ExpectedAttributeList OPTIONAL }
END

END
--< GDMO.EndDocument "ITU-T Rec. X.751 (1995) | ISO/IEC 10164-17 : 1996"
--  { joint-iso-ccitt ms(9) function(2) part17(17) } >--
--@@ 
--@@ end of gdmos
--@@ 
--@@ 
--@@ vim: comments=\b\:\-\-,\:\-\-,\f\b\:- fo+=tcqlornw tw=120 nocin nosi
