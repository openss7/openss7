--@@ GDMOCHECK 2015-01-24T09:15+0000
--@@ Copyright (c), 2008-2015 Monavacon Limited <http://www.monavacon.com/>
--@@ Copyright (c), 2001-2008 OpenSS7 Corporation <http://www.openss7.com/>
--@@ Copyright (c), 1999-2000 Brian F. G. Bidulock <bidulock@openss7.org>
--@@ 
--@@ Input File: <(standard input)>
--@@ Special File: <(standard input).specials>
--@@ Date: Sat Jan 24 05:16:36 MST 2015
--@@ 
--< GDMO.Document "ITU-T Rec. X.723 (1993) | ISO/IEC 10165-5 : 1993"
--  { joint-iso-ccitt ms(9) smi(3) part5(5) } >--
--< GDMO.Version 1.3 >--
--< GDMO.Copyright
--  =============================================================================
--  
--  @(#) src/gdmo/X.723.asn
--  
--  -----------------------------------------------------------------------------
--  
--  Copyright (c) 2008-2015  Monavacon Limited <http://www.monavacon.com/>
--  Copyright (c) 2001-2008  OpenSS7 Corporation <http://www.openss7.com/>
--  Copyright (c) 1997-2000  Brian F. G. Bidulock <bidulock@openss7.org>
--  
--  All Rights Reserved.
--  
--  This program is free software; you can redistribute it and/or modify it under
--  the terms of the GNU General Public License as published by the Free Software
--  Foundation; version 3 of the License.
--  
--  This program is distributed in the hope that it will be useful, but WITHOUT
--  ANY WARRANTY; without even the implied warranty of MERCHANTABILITY or FITNESS
--  FOR A PARTICULAR PURPOSE.  See the GNU General Public License for more
--  details.
--  
--  You should have received a copy of the GNU General Public License along with
--  this program.  If not, see <http://www.gnu.org/licenses/>, or write to the
--  Free Software Foundation, Inc., 675 Mass Ave, Cambridge, MA 02139, USA.
--  
--  -----------------------------------------------------------------------------
--  
--  U.S. GOVERNMENT RESTRICTED RIGHTS.  If you are licensing this Software on
--  behalf of the U.S. Government ("Government"), the following provisions apply
--  to you.  If the Software is supplied by the Department of Defense ("DoD"), it
--  is classified as "Commercial Computer Software" under paragraph 252.227-7014
--  of the DoD Supplement to the Federal Acquisition Regulations ("DFARS") (or any
--  successor regulations) and the Government is acquiring only the license rights
--  granted herein (the license rights customarily provided to non-Government
--  users).  If the Software is supplied to any unit or agency of the Government
--  other than DoD, it is classified as "Restricted Computer Software" and the
--  Government's rights in the Software are defined in paragraph 52.227-19 of the
--  Federal Acquisition Regulations ("FAR") (or any successor regulations) or, in
--  the cases of NASA, in paragraph 18.52.227-86 of the NASA Supplement to the FAR
--  (or any successor regulations).
--  
--  -----------------------------------------------------------------------------
--  
--  Commercial licensing and support of this software is available from OpenSS7
--  Corporation at a fee.  See http://www.openss7.com/
--  
--  =============================================================================
--  >--
MODULE "ITU-T Rec. X.723 (1993) | ISO/IEC 10165-5 : 1993" { joint-iso-ccitt ms(9) smi(3) part5(5) }
--< ASN1.Version 1994 GMI-AttributeModule
--  { joint-iso-ccitt ms(9) smi(3) part5(5) asn1Module(2) gmiAttributeModule(0) } >--
GMI-AttributeModule { joint-iso-ccitt ms(9) smi(3) part5(5) asn1Module(2) gmiAttributeModule(0) }
DEFINITIONS IMPLICIT TAGS ::=
BEGIN
IMPORTS
GroupObjects, ManagementExtension
	FROM Attribute-ASN1Module { joint-iso-ccitt ms(9) smi(3) part2(2) asn1Module(2) 1 }
RelativeDistinguishedName
	FROM InformationFramework { joint-iso-ccitt ds(5) modules(1) informationFramework(1) };-- End of IMPORTS
ActionInfo ::= SET OF ManagementExtension
ActionReply ::= SET OF ManagementExtension
ApplicationProcessId ::= GraphicString
ApplicationProcessTitle ::= CHOICE {
	directory [0] SEQUENCE OF RelativeDistinguishedName,
	oid [1] OBJECT IDENTIFIER,
	notKnown NULL }
CommunicationsEntityId ::= GraphicString
CommunicationsInformation ::= SEQUENCE {
	informationType InformationType,
	informationData InformationData OPTIONAL }
ConnectionId ::= GraphicString
GenericCounter ::= INTEGER
Generic64BitCounter ::= INTEGER(0..18446744073709551615)
InformationType ::= OBJECT IDENTIFIER
InformationData ::= SET OF ManagementExtension
ProtocolMachineId ::= GraphicString
Sap1Address ::= INTEGER
Sap2Address ::= SET OF OCTET STRING
SapId ::= GraphicString
SubsystemId ::= GraphicString
Timer ::= SEQUENCE {
	exponent [1] INTEGER(-62..63),
	mantissa [2] INTEGER(0..65535) }
END

END
--< GDMO.ChangeLog
--  =============================================================================
--  
--  $Log: X.723.asn,v $
--  Revision 1.1.2.1  2009-06-21 11:22:55  brian
--  - added files to new distro
--
--  Revision 0.9.2.2  2007/09/29 14:28:10  brian
--  - update gdmos and asns
--
--  Revision 0.9.2.1  2007/09/06 10:59:03  brian
--  - added new gdmo files
--  
--  =============================================================================
--  >--
--< GDMO.EndDocument "ITU-T Rec. X.723 (1993) | ISO/IEC 10165-5 : 1993"
--  { joint-iso-ccitt ms(9) smi(3) part5(5) } >--
--@@ 
--@@ end of gdmos
--@@ 
--@@ 
--@@ vim: comments=\b\:\-\-,\:\-\-,\f\b\:- fo+=tcqlornw tw=120 nocin nosi
