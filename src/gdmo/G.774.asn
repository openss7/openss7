--@@ GDMOCHECK 2015-01-24T09:15+0000
--@@ Copyright (c), 2008-2015 Monavacon Limited <http://www.monavacon.com/>
--@@ Copyright (c), 2001-2008 OpenSS7 Corporation <http://www.openss7.com/>
--@@ Copyright (c), 1999-2000 Brian F. G. Bidulock <bidulock@openss7.org>
--@@ 
--@@ Input File: <(standard input)>
--@@ Special File: <(standard input).specials>
--@@ Date: Sat Jan 24 05:16:17 MST 2015
--@@ 
--< GDMO.Document "ITU-T Rec. G.774 : 2001"
--  { itu-t(0) recommendation(0) g(7) sdhm(774) informationModel(0) } >--
MODULE "ITU-T Rec. G.774 : 2001" { itu-t(0) recommendation(0) g(7) sdhm(774) informationModel(0) }
--< ASN1.Version 1994 SDH
--  { itu-t(0) recommendation(0) g(7) sdhm(774) informationModel(0) asn1Module(2) sdh(0) } >--
--10  Supporting ASN.1 
SDH { itu-t(0) recommendation(0) g(7) sdhm(774) informationModel(0) asn1Module(2) sdh(0) }
DEFINITIONS IMPLICIT TAGS ::=
BEGIN
IMPORTS
NameType
	FROM ASN1DefinedTypesModule { itu-t(0) recommendation(0) m(13) gnm(3100) informationModel(0) asn1Modules(2) asn1DefinedTypeModule(0) };-- Recommendation M.3100
g774 OBJECT IDENTIFIER ::= { itu-t(0) recommendation(0) g(7) sdhm(774) informationModel(0) }
g774ObjectClass OBJECT IDENTIFIER ::= { g774 managedObjectClass(3) }
g774Attribute OBJECT IDENTIFIER ::= { g774 attribute(7) }
g774NameBinding OBJECT IDENTIFIER ::= { g774 nameBinding(6) }
Boolean ::= BOOLEAN
C2SignalLabel ::= INTEGER(0..255)
defaultNull Null ::= NULL
Null ::= NULL
Integer ::= INTEGER
OpticalReach ::= ENUMERATED {
	intraOffice(0),
	shortHaul(1),
	longHaul(2) }
OpticalWavelength ::= ENUMERATED {
	wl1310(0),
	wl1550(1) }
PathTrace ::= CHOICE {
	null NULL,
	pathtrace [1] GraphicString }
-- Reffering to PointerSinkType. The ENUMERATED value of invalidPointer(2)
-- should be used when a LOP condition exists or if the pointer value is unknown.
PointerSinkType ::= ENUMERATED {
	normalPointer(0),
	concatenationIndication(1),
	invalidPointer(2) }
PointerSourceType ::= ENUMERATED {
	normalPointer(0),
	concatenationIndication(1) }
TrailTraceReceiveSend ::= GraphicString
V5SignalLabel ::= INTEGER(0..7)
END

END
--< GDMO.EndDocument "ITU-T Rec. G.774 : 2001"
--  { itu-t(0) recommendation(0) g(7) sdhm(774) informationModel(0) } >--
--@@ 
--@@ end of gdmos
--@@ 
--@@ 
--@@ vim: comments=\b\:\-\-,\:\-\-,\f\b\:- fo+=tcqlornw tw=120 nocin nosi
