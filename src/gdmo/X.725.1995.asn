--@@ GDMOCHECK 2015-01-24T09:15+0000
--@@ Copyright (c), 2008-2015 Monavacon Limited <http://www.monavacon.com/>
--@@ Copyright (c), 2001-2008 OpenSS7 Corporation <http://www.openss7.com/>
--@@ Copyright (c), 1999-2000 Brian F. G. Bidulock <bidulock@openss7.org>
--@@ 
--@@ Input File: <(standard input)>
--@@ Special File: <(standard input).specials>
--@@ Date: Sat Jan 24 05:16:36 MST 2015
--@@ 
--< GDMO.Document "ITU-T Rec. X.725 (1995) | ISO/IEC 10165-7 : 1996"
--  { joint-iso-itu-t ms(9) smi(3) part7(7) } >--
MODULE "ITU-T Rec. X.725 (1995) | ISO/IEC 10165-7 : 1996" { joint-iso-itu-t ms(9) smi(3) part7(7) }
--< ASN1.Version 1994 GRMD
--  { joint-iso-itu-t ms(9) smi(3) part7(7) asn1Module(2) 1 } >--
-- B.1 Allocation of object identifiers
-- This Recommendation | International Standard allocates the following object identifiers:
GRMD { joint-iso-itu-t ms(9) smi(3) part7(7) asn1Module(2) 1 }
DEFINITIONS ::=
BEGIN
grm-Object OBJECT IDENTIFIER ::= { joint-iso-itu-t ms(9) smi(3) part7(7) managedObjectClass(3) }
grm-Package OBJECT IDENTIFIER ::= { joint-iso-itu-t ms(9) smi(3) part7(7) package(4) }
grm-Parameter OBJECT IDENTIFIER ::= { joint-iso-itu-t ms(9) smi(3) part7(7) parameter(5) }
grm-NameBinding OBJECT IDENTIFIER ::= { joint-iso-itu-t ms(9) smi(3) part7(7) nameBinding(6) }
grm-Attribute OBJECT IDENTIFIER ::= { joint-iso-itu-t ms(9) smi(3) part7(7) attribute(7) }
grm-RelationshipClass OBJECT IDENTIFIER ::= { joint-iso-itu-t ms(9) smi(3) part7(7) relationshipClass(11) }
grm-RelationshipMapping OBJECT IDENTIFIER ::= { joint-iso-itu-t ms(9) smi(3) part7(7) relationshipMapping(12) }
grm-RelationshipRole OBJECT IDENTIFIER ::= { joint-iso-itu-t ms(9) smi(3) part7(7) relationshipRole(13) }
END

--< ASN1.Version 1994 GRM-ASN1Module
--  { joint-iso-itu-t ms(9) smi(3) part7(7) asn1Module(2) 2 } >--
-- B.6 Abstract syntax definitions
GRM-ASN1Module { joint-iso-itu-t ms(9) smi(3) part7(7) asn1Module(2) 2 }
DEFINITIONS ::=
BEGIN
IMPORTS
ObjectInstance
	FROM CMIP-1 { joint-iso-itu-t ms(9) cmip(1) version(1) protocol(3) }
SimpleNameType, GroupObjects
	FROM Attribute-ASN1Module { joint-iso-itu-t ms(9) smi(3) part2(2) asn1Module(2) 1 };
RelationshipClass ::= OBJECT IDENTIFIER
RelationshipMapping ::= OBJECT IDENTIFIER
Null ::= NULL
END

END
--< GDMO.EndDocument "ITU-T Rec. X.725 (1995) | ISO/IEC 10165-7 : 1996"
--  { joint-iso-itu-t ms(9) smi(3) part7(7) } >--
--@@ 
--@@ end of gdmos
--@@ 
--@@ 
--@@ vim: comments=\b\:\-\-,\:\-\-,\f\b\:- fo+=tcqlornw tw=120 nocin nosi
