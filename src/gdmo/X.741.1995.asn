--< ASN1.Version 1994 AccessControlDefinitions{ joint-iso-ccitt(2) ms(9) function(2) part9(9) asn1Module(2) 1 } >--
-- A.1 Allocation of object identifiers
-- This Recommendation | International Standard allocates the following object identifiers
AccessControlDefinitions{ joint-iso-ccitt(2) ms(9) function(2) part9(9) asn1Module(2) 1 }
DEFINITIONS ::= BEGIN
accessControl-Object OBJECT IDENTIFIER ::=
{ joint-iso-ccitt(2) ms(9) function(2) part9(9) managedObjectClass(3) }
accessControl-Package OBJECT IDENTIFIER ::=
{ joint-iso-ccitt(2) ms(9) function(2) part9(9) package (4) }
accessControl-Parameter OBJECT IDENTIFIER ::=
{ joint-iso-ccitt(2) ms(9) function(2) part9(9) parameter(5) }
accessControl-NameBinding OBJECT IDENTIFIER ::=
{ joint-iso-ccitt(2) ms(9) function(2) part9(9) nameBinding(6) }
accessControl-Attribute OBJECT IDENTIFIER ::=
{ joint-iso-ccitt(2) ms(9) function(2) part9(9) attribute(7) }
END
--< ASN1.Version 1994 AccessControlDefinitions { joint-iso-ccitt ms(9) function(2) part9(9) asn1Module(2) 1 } >--
-- A.6 Abstract syntax definitions
AccessControlDefinitions { joint-iso-ccitt ms(9) function(2) part9(9) asn1Module(2) 1 }
DEFINITIONS IMPLICIT TAGS ::= BEGIN
IMPORTS
AttributeId, CMISFilter, CMISSync, ObjectClass, ObjectInstance, Scope, ActionTypeId
FROM CMIP-1 { joint-iso-ccitt ms(9) cmip(1) modules(0) protocol(3) }
DistinguishedName
FROM InformationFramework { joint-iso-ccitt ds(5) modules(1) informationFramework(1) }
FunctionalUnitPackage
FROM SMASE-A-ASSOCIATE-Information { joint-iso-ccitt ms(9) smo(0) negotiationAbstractSyntax(1) version1(1) }
AETitle
FROM ACSE-1 { joint-iso-ccitt association-Control(2) abstractSyntax(1) apdus(0) version(1) }
DiscriminatorConstruct
FROM Attribute-ASN1Module { joint-iso-ccitt ms(9) smi(3) part2(2) asn1Module(2) 1 };
AccessControlList ::= SET OF CHOICE { proxy [0] Proxy,
initiatorName [1] InitiatorName }
InitiatorName CHOICE { individualName [1] IMPLICIT DistinguishedName,
groupName [2] IMPLICIT DistinguishedName,
role [3] IMPLICIT DistinguishedName,
application [4] IMPLICIT AETitle }
Proxy ::= SEQUENCE { proxyId [0] IMPLICIT OBJECT IDENTIFIER,
proxyValue [1] ANY DEFINED BY proxyId }
AccessControlObjectName ::= GraphicString
ActionFilterList ::= SET OF SEQUENCE { actionTypeId ActionTypeId,
attributeFilterList FilterList OPTIONAL }
AuthenticationContext ::= SEQUENCE
{ authenticationPolicyId [0] IMPLICIT OBJECT IDENTIFIER,
requirements [1] ANY DEFINED BY authenticationPolicyId }
Boolean ::= BOOLEAN
false Boolean ::= FALSE
CapabilityIdentitiesList ::= SET OF CHOICE {
knownForm [0] SEQUENCE {
initiatorName InitiatorName,
sdaList SdaList OPTIONAL },
unknownForm [1] SEQUENCE {
identifier IMPLICIT OBJECT IDENTIFIER,
value ANY DEFINED BY identifier }}
SdaList ::= SET OF SEQUENCE {
securityDomainAuthorityName SecurityDomainAuthorityName,
operationType OperationType }
DefaultAccess ::= SEQUENCE {
action [0] IMPLICIT EnforcementAction DEFAULT deny,
create [1] IMPLICIT EnforcementAction DEFAULT deny,
delete [2] IMPLICIT EnforcementAction DEFAULT deny,
get [3] IMPLICIT EnforcementAction DEFAULT deny,
replace [4] IMPLICIT EnforcementAction DEFAULT deny,
addMember [5] IMPLICIT EnforcementAction DEFAULT deny,
removeMember [6] IMPLICIT EnforcementAction DEFAULT deny,
replaceWithDefault [7] IMPLICIT EnforcementAction DEFAULT deny,
multipleObjectSelection [8] IMPLICIT EnforcementAction DEFAULT deny,
filter [9] IMPLICIT EnforcementAction DEFAULT deny }
denyAll DefaultAccess ::= {}
DenialResponse ::= EnforcementAction ENUMERATED
{ denyWithResponse (0),
denyWithoutResponse (1),
abortAssociation (2),
denyWithFalseResponse (3) }
DenialGranularity ::= ENUMERATED { request(0),
object(1),
attribute(2) }
DomainIdentity ::= CHOICE { domainName DistinguishedName,
privateName OCTET STRING }
EnforcementAction ::= ENUMERATED { denyWithResponse (0),
denyWithoutResponse (1),
abortAssociation (2),
denyWithFalseResponse (3),
allow (4) }
Deny EnforcementAction ::= denyWithResponse
FilterList ::= SET OF CMISFilter
InvalidAccessControlFilter ::= SEQUENCE
{ errorId ENUMERATED
{ duplicateId(0),
heterogeneousId(1),
invalidId(2) },
{ filter CMISFilter OPTIONAL }
LabelName ::= INTEGER
ObjectClassList ::= SET OF SEQUENCE { objectClass [0] ObjectClass,
nameBinding [1] OBJECT IDENTIFIER OPTIONAL}
OperationsList ::= SET OF OperationType
OperationType ::= INTEGER { action (0),
create (1),
delete (2),
get (3),
replace (4),
addMember (5),
removeMember (6),
replaceWithDefault (7),
multipleObjectSelection (8),
filter (9) }
SecurityLabel ::= SET OF CHOICE {
initiatorLabel [1] IMPLICIT SEQUENCE {
clearance CHOICE {
localForm [0] IMPLICIT INTEGER,
globalForm [1] IMPLICIT OBJECT IDENTIFIER },
category [2] IMPLICIT BIT STRING OPTIONAL } }
SecurityDomainAuthorityName ::= CHOICE {
domainAuthorityName [1] IMPLICIT DistinguishedName,
alternativeAuthorityName [2] IMPLICIT Proxy }
StateConditions ::= SET OF SEQUENCE { conditionalObject ObjectInstance,
state CMISFilter }
END
