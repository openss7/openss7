--@@ GDMOCHECK 2015-01-24T09:15+0000
--@@ Copyright (c), 2008-2015 Monavacon Limited <http://www.monavacon.com/>
--@@ Copyright (c), 2001-2008 OpenSS7 Corporation <http://www.openss7.com/>
--@@ Copyright (c), 1999-2000 Brian F. G. Bidulock <bidulock@openss7.org>
--@@ 
--@@ Input File: <(standard input)>
--@@ Special File: <(standard input).specials>
--@@ Date: Sat Jan 24 05:16:38 MST 2015
--@@ 
--< GDMO.Document "ITU-T Rec. X.739 (1993) | ISO/IEC 10164-11 : 1994"
--  { joint-iso-ccitt ms(9) function(2) part11(11) } >--
MODULE "ITU-T Rec. X.739 (1993) | ISO/IEC 10164-11 : 1994" { joint-iso-ccitt ms(9) function(2) part11(11) }
--< ASN1.Version 1994 MetricModule
--  { joint-iso-ccitt ms(9) function(2) part11(11) asn1Module(2) 0 } >--
-- A.5 ASN.1 definitions
MetricModule { joint-iso-ccitt ms(9) function(2) part11(11) asn1Module(2) 0 }
DEFINITIONS IMPLICIT TAGS ::=
BEGIN
-- EXPORTS everything
IMPORTS
AttributeId, ObjectInstance
	FROM CMIP-1 { joint-iso-itu-t ms(9) cmip(1) modules(0) protocol(3) }
ObservedValue, PerceivedSeverity, SimpleNameType, SpecificIdentifier
	FROM Attribute-ASN1Module { joint-iso-ccitt ms(9) smi(3) part2(2) asn1Module(2) 1 };
-- Value assignments for the specific problems parameter
moaSpecificProblems OBJECT IDENTIFIER ::= { joint-iso-ccitt ms(9) function(2) part11(11) standardSpecificExtension(0) 0 }
resourceRequestRate SpecificIdentifier ::= oi : { moaSpecificProblems 1 }
resourceUtilization SpecificIdentifier ::= oi : { moaSpecificProblems 2 }
rejectionRate SpecificIdentifier ::= oi : { moaSpecificProblems 3 }
moaAlgorithmIdentifiers OBJECT IDENTIFIER ::= { joint-iso-ccitt ms(9) function(2) part11(11) standardSpecificExtension(0) algorithm(1) }
ewmaAlgorithm AlgorithmIdentifier ::= { moaAlgorithmIdentifiers 0 }
--This identifier is allocated to indicate that the EWMA algorithm is used for data smoothing.
--The EWMA algorithm is defined in B.2.
uwmaAlgorithm AlgorithmIdentifier ::= { moaAlgorithmIdentifiers 1 }
--This identifier is allocated to indicate that the UWMA algorithm is used for data smoothing.
--The UWMA algorithm is defined in C.2.
AlgorithmIdentifier ::= OBJECT IDENTIFIER
GlobalTime ::= GeneralizedTime
Integer ::= INTEGER
ObjectIdentifier ::= OBJECT IDENTIFIER
SeverityIndicatingGaugeThreshold ::= SET OF SEQUENCE {
	notifyLow SeverityIndicatingThreshold,
	notifyHigh SeverityIndicatingThreshold }
SeverityIndicatingThreshold ::= SEQUENCE {
	threshold ObservedValue,
	notifyOnOff BOOLEAN,
	severityIndication PerceivedSeverity OPTIONAL }
TimePeriod ::= CHOICE {
	days [0] INTEGER,
	hours [1] INTEGER,
	minutes [2] INTEGER,
	seconds [3] INTEGER,
	milliSeconds [4] INTEGER,
	microSeconds [5] INTEGER,
	nanoSeconds [6] INTEGER,
	picoSeconds [7] INTEGER }
END

END
--< GDMO.EndDocument "ITU-T Rec. X.739 (1993) | ISO/IEC 10164-11 : 1994"
--  { joint-iso-ccitt ms(9) function(2) part11(11) } >--
--@@ 
--@@ end of gdmos
--@@ 
--@@ 
--@@ vim: comments=\b\:\-\-,\:\-\-,\f\b\:- fo+=tcqlornw tw=120 nocin nosi
